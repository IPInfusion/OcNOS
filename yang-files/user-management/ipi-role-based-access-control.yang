/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-role-based-access-control.yang
*
*/

module ipi-role-based-access-control {

    yang-version 1.1;

    namespace   "http://www.ipinfusion.com/yang/ocnos/ipi-role-based-access-control";

    prefix "ipi-role-based-access-control";

    import cml-data-types {
        prefix cml-data-types;
        revision-date 2022-09-30;
    }

    import ipi-role-based-access-control-types {
        prefix ipi-role-based-access-control-types;
        revision-date 2022-06-01;
    }

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "Role-Based Access Control (RBAC)";


    revision "2022-06-01" {
        description "Updated the yang file with feature";
        reference " 0.3.0.";
    }

    revision "2022-01-28" {
        description "Restructured module as per open-config";
        reference " 0.2.0.";
    }

    revision "2018-06-21" {
        description "Intial datamodel for Role-Based Access Control";
        reference " 0.1.0.";
    }

    grouping rbac-roles-policies-config {
        description
            "Grouping for RBAC Roles configurations";
        leaf policy-name  {
            type  leafref {
                path  "/role-based-access-control/policies/policy/policy-name";
            }
            description "Use this attribute to add a policy to a TACACS+ role-based
                        authorization (RBAC) role";
        } // END of policy-name definition.

    } // END of rbac-roles-policies-config definition.
    grouping rbac-roles-policies-top {
        description
            "Grouping for RBAC Roles configurations";
        container policies {
            description
                "Configuration data for policies";

            list policy {
                key "policy-name";
                description
                    "policy list attached to a role";
                leaf policy-name  {
                    type  leafref {
                        path  "../config/policy-name";
                    }
                    description "Use this attribute to add a policy to a TACACS+ Role-based Access
                                Control (RBAC) role";
                } // END of policy-name definition.

                container config {
                    description
                        "Configuration data for policies";
                    uses rbac-roles-policies-config;
                } // END of config-container definition.
                container state {
                    config false;
                    description
                        "Operational state data for policies";
                    uses rbac-roles-policies-config;
                } // END of state-container definition.
            } // End of policy-list
        } // END of policies-container definition.
    } // END of rbac-roles-policies-top definition.
    grouping rbac-roles-config {
        description
            "Grouping for RBAC Roles configurations";
        leaf role-name  {
            type  string {
                length "2..16";
                pattern "[^?' =,>|]+";
            }
            description "Use this attribute to create a TACACS+ Role-Based Authorization (RBAC)
                        role and to switch to RBAC role mode. End-user cannot specify one of
                        these roles already defined in OcNOS:
                        network-admin
                        network-user
                        network-operator
                        network-engineer
                        For more about these built-in roles, see 'username' CLI configuration";
        } // END of role-name definition.

        leaf default-policy  {
            type  ipi-role-based-access-control-types:rbac_default_rule_type_t;
            default "deny-all";
            description "Use this atribute to set the default rule for a TACACS+ Role-Based
                        Access Control (RBAC) role.";
        } // END of default-policy definition.

    } // END of rbac-roles-config definition.
    grouping rbac-roles-top {
        description
            "Grouping for RBAC Roles top configurations";
        container roles {
            description
                "Configuration data for roles";

            list role {
            when " /ipi-role-based-access-control:role-based-access-control/ipi-role-based-access-control:config/ipi-role-based-access-control:enable ";
                key "role-name";
                description
                    "object list for RBAC user role";
                leaf role-name  {
                    type  leafref {
                        path  "../config/role-name";
                    }
                    description "Use this attribute to create a TACACS+ Role-Based Authorization (RBAC)
                                role and to switch to RBAC role mode. End-user cannot specify one of
                                these roles already defined in OcNOS:
                                network-admin
                                network-user
                                network-operator
                                network-engineer
                                For more about these built-in roles, see 'username' CLI configuration";
                } // END of role-name definition.

                container config {
                    description
                        "Configuration data for roles";
                    uses rbac-roles-config;
                } // END of config-container definition.
                container state {
                    config false;
                    description
                        "Operational state data for roles";
                    uses rbac-roles-config;
                } // END of state-container definition.
                uses rbac-roles-policies-top;
            } // End of role-list
        } // END of roles-container definition.
    } // END of rbac-roles-top definition.
    grouping rbac-policies-rules-config {
        description
            "Grouping for RBAC Rules configurations";
        leaf rule-name  {
            type  cml-data-types:cml_line_t {
                length "3..255";
            }
            description "This attribute specifies rule string configured as regex-expression
                        for cli authorization";
        } // END of rule-name definition.

        leaf rule-type  {
            type  ipi-role-based-access-control-types:rbac_rule_type_t;
            mandatory true;
            description "This attribute to add a deny/permit rule to a TACACS+ RBAC policy";
        } // END of rule-type definition.

        leaf-list command-mode  {
            type  string {
                length "1..1965";
                pattern "[^?' =,>|]+";
            }
            description "Attribute to specify the mode in which CLI should be allowed/denied.
                        Command prompt string such as 'config-router' or 'config-if',
                        deny/Permit access to the command only in this mode.";
        } // END of command-mode definition.

    } // END of rbac-policies-rules-config definition.
    grouping rbac-policies-rules-top {
        description
            "Grouping for RBAC Rules top configurations";
        container rules {
            description
                "Configuration data for rules in policies";

            list rule {
                key "rule-name";
                description
                    "List of RBAC Rules";
                leaf rule-name  {
                    type  leafref {
                        path  "../config/rule-name";
                    }
                    description "This attribute specifies rule string configured as regex-expression
                                for cli authorization";
                } // END of rule-name definition.

                container config {
                    description
                        "Configuration data for rules in policies";
                    uses rbac-policies-rules-config;
                } // END of config-container definition.
                container state {
                    config false;
                    description
                        "Operational state data for rules in policies";
                    uses rbac-policies-rules-config;
                } // END of state-container definition.
            } // End of rule-list
        } // END of rules-container definition.
    } // END of rbac-policies-rules-top definition.
    grouping rbac-policies-config {
        description
            "Grouping for RBAC Policies configurations";
        leaf policy-name  {
            type  string {
                length "2..16";
                pattern "[^?' =,>|]+";
            }
            description "Use this attribute to create a TACACS+ role-based authorization (RBAC)
                        policy and enter RBAC policy mode.";
        } // END of policy-name definition.

    } // END of rbac-policies-config definition.
    grouping rbac-policies-top {
        description
            "Grouping for RBAC Policies top configurations";
        container policies {
            description
                "Configuration data for policies";

            list policy {
            when " /ipi-role-based-access-control:role-based-access-control/ipi-role-based-access-control:config/ipi-role-based-access-control:enable ";
                key "policy-name";
                description
                    "List of RBAC Policies";
                leaf policy-name  {
                    type  leafref {
                        path  "../config/policy-name";
                    }
                    description "Use this attribute to create a TACACS+ Role-Based Authorization (RBAC)
                                policy and enter RBAC policy mode.";
                } // END of policy-name definition.

                container config {
                    description
                        "Configuration data for policies";
                    uses rbac-policies-config;
                } // END of config-container definition.
                container state {
                    config false;
                    description
                        "Operational state data for policies";
                    uses rbac-policies-config;
                } // END of state-container definition.
                uses rbac-policies-rules-top;
            } // End of policy-list
        } // END of policies-container definition.
    } // END of rbac-policies-top definition.
    grouping rbac-config {
        description
            "Grouping for RBAC configurations";
        leaf enable  {
            type  empty;
            description "Enable or disable the TACAS+ Role-Based Access Control of RBAC feature";
        } // END of enable definition.

    } // END of rbac-config definition.
    grouping rbac-top {
        description
            "Grouping for RBAC top configurations";
        container config {
            description
                "Configuration data for RBAC top configurations";
            uses rbac-config;
        } // END of config-container definition.
        container state {
            config false;
            description
                "Operational state data for RBAC top configurations";
            uses rbac-config;
        } // END of state-container definition.
        uses rbac-policies-top;
        uses rbac-roles-top;
    } // END of rbac-top definition.

    grouping  role-based-access-control-grouping {
    description
        "RBAC top container";
    container role-based-access-control {
        if-feature feature-list:HAVE_HOSTPD;
        if-feature feature-list:HAVE_RBAC;
        description
            "RBAC top container";
        uses rbac-top;
    } // END of role-based-access-control-container definition.
    } // END of role-based-access-control-grouping definition.

    uses role-based-access-control-grouping;

}
