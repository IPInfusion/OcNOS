/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-user-management.yang
*
*/

module ipi-user-management {

    yang-version 1.1;

    namespace   "http://www.ipinfusion.com/yang/ocnos/ipi-user-management";

    prefix "ipi-user-management";

    import cml-data-types {
        prefix cml-data-types;
        revision-date 2022-09-30;
    }

    import ipi-user-management-types {
        prefix ipi-user-management-types;
        revision-date 2022-06-25;
    }

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "Data model for User-Management Module";


    revision "2022-06-25" {
        description "Kept different attribute for rbac-role";
        reference " 0.3.0.";
    }

    revision "2022-06-01" {
        description "Updated the yang file with feature";
        reference " 0.6.0.";
    }

    revision "2022-01-14" {
        description "Updated utils_func flag for username attribute";
        reference " 0.5.0.";
    }

    revision "2021-10-18" {
        description "Updated 'role' as a non-mandatory node";
        reference " 0.4.0.";
    }

    revision "2021-09-22" {
        description "Changed default user handling";
        reference " 0.3.0.";
    }

    revision "2021-09-03" {
        description "Update descriptions of attribute";
        reference " 0.2.0.";
    }

    revision "2021-06-07" {
        description "Initial Version";
        reference " 0.1.0.";
    }

    grouping user-management-config {
        description
            "Configuration for Users";
        leaf username  {
            type  string {
                length "2..15";
                pattern "[^?' =,>|]+";
            }
            description "Use this attribute to set the login name of the user";
        } // END of username definition.

        leaf role  {
            type  ipi-user-management-types:user_mgmt_role_types_t;
            description "Use this attribute to set the user role.
                        Operations that an user is allowed to perform are determined based on
                        the role";
        } // END of role definition.

        leaf rbac-role  {
            if-feature feature-list:HAVE_RBAC;
            type  ipi-user-management-types:user_mgmt_rbac_role_t {
                length "1..1965";
            }
            description "Use this attribute to set the user role.
                        Operations that an user is allowed to perform are determined based on
                        the role";
        } // END of rbac-role definition.

        choice password-type {
            description
                "Select the password-type";
            case plain-text {

                description
                    "Username with plain-text password";

                leaf password  {
                    type  string {
                        length "5..32";
                        pattern "[^?' =,>|]+";
                    }
                    description "Use this attribute to add a user or to change a user password.";
                } // END of password definition.

            }
            case hashed {

                description
                    "Username with encrypted password";

                leaf password-hashed  {
                    type  string {
                        length "26..106";
                        pattern "[^?' =,>|]+";
                    }
                    description "Use this attribute to specify user password in encrypted form. This
                                option is provided for reconfiguring
                                a user password using an earlier encrypted password that was available
                                in running configuration display or get-config payload.
                                Users are advised not to use this option for entering passwords
                                generated in any other method";
                } // END of password-hashed definition.

            }
        } // END of password-type-choice definition.
    } // END of user-management-config definition.
    grouping user-management-top {
        description
            "Global User Managament Configurations";
        container users {
            description
                "Container for user configurations";

            list user {
                key "username";
                max-elements 1000;
                description
                    "Configuration for users";
                leaf username  {
                    type  leafref {
                        path  "../config/username";
                    }
                    description "Login name of the user";
                } // END of username definition.

                container config {
                    description
                        "Config container for user configurations";
                    uses user-management-config;
                } // END of config-container definition.
                container state {
                    config false;
                    description
                        "State container for user configurations";
                    uses user-management-config;
                } // END of state-container definition.
            } // End of user-list
        } // END of users-container definition.
    } // END of user-management-top definition.
    grouping user-management-debug-config {
        description
            "User Management Debug configurations";
        leaf enable  {
            type  empty;
            description "Use this attribute to enable user management debugging information.";
        } // END of enable definition.

    } // END of user-management-debug-config definition.
    grouping user-management-debug-state {
        description
            "User Management Debug State";
        leaf terminal-debug-status  {
            type  cml-data-types:cml_on_off_t;
            description "Use this attribute to display user management terminal debugging
                        state.";
        } // END of terminal-debug-status definition.

    } // END of user-management-debug-state definition.
    grouping user-management-global-top {
        description
            "Top level container for user management global configuration";
        container global {
            description
                "User Management global configuration";
            container config {
                description
                    "User Management global configuration";
                uses user-management-global-config;
            } // END of config-container definition.
            container state {
                config false;
                description
                    "Global User Management Operational state data";
                uses user-management-global-config;
            } // END of state-container definition.
        } // END of global-container definition.
    } // END of user-management-global-top definition.
    grouping user-management-global-config {
        description
            "User Management global configuration";
        leaf disable-default-user  {
            type  empty;
            description "Use this attribute to prevent default user from being enabled at start
                        up";
        } // END of disable-default-user definition.

    } // END of user-management-global-config definition.

    grouping  user-management-grouping {
    description
        "User Management configurations";
    container user-management {
        if-feature feature-list:HAVE_HOSTPD;
        if-feature feature-list:HAVE_USER_MGMT;
        description
            "User Management configurations";
        container debug {
            description
                "User Management Debugging configurations";
            container config {
                description
                    "config container for debug configurations";
                uses user-management-debug-config;
            } // END of config-container definition.
            container state {
                config false;
                description
                    "state container for debug configurations";
                uses user-management-debug-config;
                uses user-management-debug-state;
            } // END of state-container definition.
        } // END of debug-container definition.
        uses user-management-global-top;
        uses user-management-top;
    } // END of user-management-container definition.
    } // END of user-management-grouping definition.

    uses user-management-grouping;

    rpc user-management-terminal-debugging-on {
        if-feature feature-list:HAVE_HOSTPD;
        if-feature feature-list:HAVE_USER_MGMT;
        description "Use this RPC to enable debugging for user manegement";
    }

    rpc user-management-terminal-debugging-off {
        if-feature feature-list:HAVE_HOSTPD;
        if-feature feature-list:HAVE_USER_MGMT;
        description "Use this RPC to disable debugging for user manegement";
    }

}
