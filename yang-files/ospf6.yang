/*
* Copyright (C) 2016 IP Infusion, Inc. 
*  All Rights Reserved.
*
*** Auto generated by zebmdc

* Unless required by applicable law or agreed to in writing,
* software distributed under the License is distributed on an
* "AS IS" BASIS, WITHOUT WARRANTIES OR CONDITIONS OF ANY
* KIND, either express or implied.

* File name : ospf6.yang
*
*/

submodule ospf6 {

    belongs-to  ZebOS { prefix ZebOS; }
    include interface;
    include vrf;


    import cml_data_types {
        prefix cml_data_types;
    }

    description
        "Layer-3 ospf configurations";


    revision "2015-04-25" {
        description "Revisied on 2015-04-25.";    }



    grouping ospf6-grouping {
        list ospf6 {
             

            description
                "ospf6";

            config true;
            key "ospf6ProcessTag";

            
            leaf vrId  {
                mandatory false;                
                type  leafref {
                    path  "/vr/vrId";
                }
            } // END of vrId definition.

            leaf ospf6ProcessTag  {
                mandatory true;                
                type  cml_data_types:CML_STRING_T;  
                config true;
            } // END of ospf6ProcessTag definition.

            leaf ospf6logAdjacency  {
                mandatory false;                
                type  cml_data_types:CML_STRING_T;  
                config true;
            } // END of ospf6logAdjacency definition.

            leaf ospf6RouterId  {
                mandatory false;                
                type  cml_data_types:CML_IPV4_ADDR_T;  
                config true;
            } // END of ospf6RouterId definition.

            leaf ospf6ReferenceBandWidth  {
                mandatory false;                
                type  cml_data_types:CML_INT32_T {
                     range "1..4294967";
                }
                default "100000";
                config true;
            } // END of ospf6ReferenceBandWidth definition.

            leaf maxDBDescriptor  {
                mandatory false;                
                type  cml_data_types:CML_UINT16_T {
                     range "1..65535";
                }
                default "5";
                config true;
            } // END of maxDBDescriptor definition.

            leaf maxUnusePkt  {
                mandatory false;                
                type  cml_data_types:CML_UINT32_T {
                     range "0..65535";
                }
                default "200";
                config true;
            } // END of maxUnusePkt definition.

            leaf maxUnuseLsa  {
                mandatory false;                
                type  cml_data_types:CML_UINT32_T {
                     range "0..65535";
                }
                default "200";
                config true;
            } // END of maxUnuseLsa definition.

            leaf ospf6DefaultMetric  {
                mandatory false;                
                type  cml_data_types:CML_UINT32_T {
                     range "1..16777214";
                }
                default "20";
                config true;
            } // END of ospf6DefaultMetric definition.

            leaf abrType  {
                mandatory false;                
                type  cml_data_types:CML_OSPF6_ABR_TYPE_T;  
                default "cisco";
                config true;
            } // END of abrType definition.

            leaf ospf6AdminDistance  {
                mandatory false;                
                type  cml_data_types:CML_INT32_T {
                     range "1..254";
                }
                default "110";
                config true;
            } // END of ospf6AdminDistance definition.

            leaf minDelay  {
                mandatory false;                
                type  cml_data_types:CML_UINT32_T {
                     range "0..2147483647";
                }
                default "500";
                config true;
            } // END of minDelay definition.

            leaf maxDelay  {
                mandatory false;                
                type  cml_data_types:CML_UINT32_T {
                     range "0..2147483647";
                }
                default "50000";
                config true;
            } // END of maxDelay definition.

            leaf ospf6ShutdownStatus  {
                mandatory false;                
                type  cml_data_types:CML_BOOL_T;  
                config true;
            } // END of ospf6ShutdownStatus definition.

            leaf ospf6FRKeepAllPath  {
                mandatory false;                
                type  cml_data_types:CML_BOOL_T;  
                config true;
            } // END of ospf6FRKeepAllPath definition.

            leaf-list passiveIfName  {
                
                type  cml_data_types:CML_STRING_T;  
                config true;
            } // END of passiveIfName definition.

            leaf isPassiveIfDefault  {
                mandatory false;                
                type  cml_data_types:CML_BOOL_T;  
                config true;
            } // END of isPassiveIfDefault definition.

            leaf ospf6CapabilityTE  {
                mandatory false;                
                type  cml_data_types:CML_BOOL_T;  
                config true;
            } // END of ospf6CapabilityTE definition.

            leaf ospf6CspfCapability  {
                mandatory false;                
                type  cml_data_types:CML_BOOL_T;  
                config true;
            } // END of ospf6CspfCapability definition.

            leaf ospf6EnableCspf  {
                mandatory false;                
                type  cml_data_types:CML_BOOL_T;  
                config true;
            } // END of ospf6EnableCspf definition.

            leaf ospf6EnableDBSummary  {
                mandatory false;                
                type  cml_data_types:CML_BOOL_T;  
                config true;
            } // END of ospf6EnableDBSummary definition.

            leaf tieBreak  {
                mandatory false;                
                type  cml_data_types:CML_OSPF6_CSPF_TYPE_T;  
                default "random";
                config true;
            } // END of tieBreak definition.

            leaf cspfInterval  {
                mandatory false;                
                type  cml_data_types:CML_UINT16_T {
                     range "1..3600";
                }
                default "10";
                config true;
            } // END of cspfInterval definition.

            leaf ospf6CapabilityRestartMethod  {
                mandatory false;                
                type  cml_data_types:CML_BOOL_T;  
                default true;
                config true;
            } // END of ospf6CapabilityRestartMethod definition.

            leaf bfdAllInterface  {
                mandatory false;                
                type  cml_data_types:CML_BOOL_T;  
                config true;
            } // END of bfdAllInterface definition.

            leaf teDBRTAddrLsaAge  {
                mandatory false;                
                type  cml_data_types:CML_INT32_T;  
                config false;
            } // END of teDBRTAddrLsaAge definition.

            leaf teLsaHeaderMsgType  {
                mandatory false;                
                type  cml_data_types:CML_STRING_T;  
                config false;
            } // END of teLsaHeaderMsgType definition.

            leaf teLsaHeaderType  {
                mandatory false;                
                type  cml_data_types:CML_UINT8_T;  
                config false;
            } // END of teLsaHeaderType definition.

            leaf teInstance  {
                mandatory false;                
                type  cml_data_types:CML_INT32_T;  
                config false;
            } // END of teInstance definition.

            leaf teAdvrRouter  {
                mandatory false;                
                type  cml_data_types:CML_STRING_T;  
                config false;
            } // END of teAdvrRouter definition.

            leaf teLSSeqNum  {
                mandatory false;                
                type  cml_data_types:CML_INT32_T;  
                config false;
            } // END of teLSSeqNum definition.

            leaf teLSChecksum  {
                mandatory false;                
                type  cml_data_types:CML_UINT16_T;  
                config false;
            } // END of teLSChecksum definition.

            leaf teLength  {
                mandatory false;                
                type  cml_data_types:CML_UINT16_T;  
                config false;
            } // END of teLength definition.

            leaf teRouterState  {
                mandatory false;                
                type  cml_data_types:CML_BOOL_T;  
                config false;
            } // END of teRouterState definition.

            leaf teNeighborState  {
                mandatory false;                
                type  cml_data_types:CML_BOOL_T;  
                config false;
            } // END of teNeighborState definition.

            leaf teNeighborInterfaceId  {
                mandatory false;                
                type  cml_data_types:CML_STRING_T;  
                config false;
            } // END of teNeighborInterfaceId definition.

            leaf teNeighborRouterId  {
                mandatory false;                
                type  cml_data_types:CML_STRING_T;  
                config false;
            } // END of teNeighborRouterId definition.

            leaf teRouterAddr  {
                mandatory false;                
                type  cml_data_types:CML_STRING_T;  
                config false;
            } // END of teRouterAddr definition.

            leaf teLocalInterfaceState  {
                mandatory false;                
                type  cml_data_types:CML_BOOL_T;  
                config false;
            } // END of teLocalInterfaceState definition.

            leaf teLocalInterfaceAddr  {
                mandatory false;                
                type  cml_data_types:CML_STRING_T;  
                config false;
            } // END of teLocalInterfaceAddr definition.

            leaf teRemoteInterfaceState  {
                mandatory false;                
                type  cml_data_types:CML_BOOL_T;  
                config false;
            } // END of teRemoteInterfaceState definition.

            leaf teRemoteInterfaceAddr  {
                mandatory false;                
                type  cml_data_types:CML_STRING_T;  
                config false;
            } // END of teRemoteInterfaceAddr definition.

            leaf teLinkMetricState  {
                mandatory false;                
                type  cml_data_types:CML_BOOL_T;  
                config false;
            } // END of teLinkMetricState definition.

            leaf teLinkMetric  {
                mandatory false;                
                type  cml_data_types:CML_UINT32_T;  
                config false;
            } // END of teLinkMetric definition.

            leaf teMaxResBWState  {
                mandatory false;                
                type  cml_data_types:CML_BOOL_T;  
                config false;
            } // END of teMaxResBWState definition.

            leaf teMaxResBW  {
                mandatory false;                
                type  cml_data_types:CML_STRING_T;  
                config false;
            } // END of teMaxResBW definition.

            leaf teMaxBWState  {
                mandatory false;                
                type  cml_data_types:CML_BOOL_T;  
                config false;
            } // END of teMaxBWState definition.

            leaf teMaxBW  {
                mandatory false;                
                type  cml_data_types:CML_STRING_T;  
                config false;
            } // END of teMaxBW definition.

            leaf teLinkAttrBc  {
                mandatory false;                
                type  cml_data_types:CML_BOOL_T;  
                config false;
            } // END of teLinkAttrBc definition.

            leaf teBWConsModel  {
                mandatory false;                
                type  cml_data_types:CML_UINT8_T;  
                config false;
            } // END of teBWConsModel definition.

            leaf teUnResBWState  {
                mandatory false;                
                type  cml_data_types:CML_BOOL_T;  
                config false;
            } // END of teUnResBWState definition.

            leaf teUnResBWPrio  {
                mandatory false;                
                type  cml_data_types:CML_STRING_T;  
                config false;
            } // END of teUnResBWPrio definition.

            leaf teResourceColorState  {
                mandatory false;                
                type  cml_data_types:CML_BOOL_T;  
                config false;
            } // END of teResourceColorState definition.

            leaf teResourceColorVal  {
                mandatory false;                
                type  cml_data_types:CML_INT32_T;  
                config false;
            } // END of teResourceColorVal definition.

            leaf teBWCons  {
                mandatory false;                
                type  cml_data_types:CML_STRING_T;  
                config false;
            } // END of teBWCons definition.

            leaf teBWCtr  {
                mandatory false;                
                type  cml_data_types:CML_INT32_T;  
                config false;
            } // END of teBWCtr definition.

            leaf teLinkStateType  {
                mandatory false;                
                type  cml_data_types:CML_BOOL_T;  
                config false;
            } // END of teLinkStateType definition.

            leaf teLinkType  {
                mandatory false;                
                type  cml_data_types:CML_STRING_T;  
                config false;
            } // END of teLinkType definition.

            leaf teLinkStateID  {
                mandatory false;                
                type  cml_data_types:CML_BOOL_T;  
                config false;
            } // END of teLinkStateID definition.

            leaf teLinkId  {
                mandatory false;                
                type  cml_data_types:CML_STRING_T;  
                config false;
            } // END of teLinkId definition.

            leaf pathCode  {
                mandatory false;                
                type  cml_data_types:CML_STRING_T;  
                config false;
            } // END of pathCode definition.

            leaf pathCost  {
                mandatory false;                
                type  cml_data_types:CML_STRING_T;  
                config false;
            } // END of pathCost definition.

            leaf nextHop  {
                mandatory false;                
                type  cml_data_types:CML_STRING_T;  
                config false;
            } // END of nextHop definition.

            leaf ifPathCode  {
                mandatory false;                
                type  cml_data_types:CML_STRING_T;  
                config false;
            } // END of ifPathCode definition.

            leaf areaTransit  {
                mandatory false;                
                type  cml_data_types:CML_STRING_T;  
                config false;
            } // END of areaTransit definition.

            leaf nhAddr  {
                mandatory false;                
                type  cml_data_types:CML_STRING_T;  
                config false;
            } // END of nhAddr definition.

            leaf lspP2mpId  {
                mandatory false;                
                type  cml_data_types:CML_UINT32_T;  
                config false;
            } // END of lspP2mpId definition.

            leaf lspId  {
                mandatory false;                
                type  cml_data_types:CML_UINT32_T;  
                config false;
            } // END of lspId definition.

            leaf lspIngress  {
                mandatory false;                
                type  cml_data_types:CML_STRING_T;  
                config false;
            } // END of lspIngress definition.

            leaf lspEgress  {
                mandatory false;                
                type  cml_data_types:CML_STRING_T;  
                config false;
            } // END of lspEgress definition.

            leaf lspExTunnelId  {
                mandatory false;                
                type  cml_data_types:CML_STRING_T;  
                config false;
            } // END of lspExTunnelId definition.

            leaf lspType  {
                mandatory false;                
                type  cml_data_types:CML_UINT8_T;  
                config false;
            } // END of lspType definition.

            leaf lspClientId  {
                mandatory false;                
                type  cml_data_types:CML_UINT8_T;  
                config false;
            } // END of lspClientId definition.

            leaf lspState  {
                mandatory false;                
                type  cml_data_types:CML_UINT8_T;  
                config false;
            } // END of lspState definition.

            leaf lspSetupPri  {
                mandatory false;                
                type  cml_data_types:CML_UINT8_T;  
                config false;
            } // END of lspSetupPri definition.

            leaf lspHoldPri  {
                mandatory false;                
                type  cml_data_types:CML_UINT8_T;  
                config false;
            } // END of lspHoldPri definition.

            leaf lspBidirectionalStatus  {
                mandatory false;                
                type  cml_data_types:CML_BOOL_T;  
                config false;
            } // END of lspBidirectionalStatus definition.

            leaf lspBandwidth  {
                mandatory false;                
                type  cml_data_types:CML_STRING_T;  
                config false;
            } // END of lspBandwidth definition.

            leaf lspBWStat  {
                mandatory false;                
                type  cml_data_types:CML_BOOL_T;  
                config false;
            } // END of lspBWStat definition.

            leaf lspHopLimit  {
                mandatory false;                
                type  cml_data_types:CML_UINT8_T;  
                config false;
            } // END of lspHopLimit definition.

            leaf lspAdmControl  {
                mandatory false;                
                type  cml_data_types:CML_STRING_T;  
                config false;
            } // END of lspAdmControl definition.

            leaf lspIncludeMask  {
                mandatory false;                
                type  cml_data_types:CML_UINT32_T;  
                config false;
            } // END of lspIncludeMask definition.

            leaf lspExcludeMask  {
                mandatory false;                
                type  cml_data_types:CML_UINT32_T;  
                config false;
            } // END of lspExcludeMask definition.

            leaf lspAttrRetry  {
                mandatory false;                
                type  cml_data_types:CML_BOOL_T;  
                config false;
            } // END of lspAttrRetry definition.

            leaf lspRetryInt  {
                mandatory false;                
                type  cml_data_types:CML_UINT16_T;  
                config false;
            } // END of lspRetryInt definition.

            leaf lspRetryLimit  {
                mandatory false;                
                type  cml_data_types:CML_UINT16_T;  
                config false;
            } // END of lspRetryLimit definition.

            leaf lspTeMetric  {
                mandatory false;                
                type  cml_data_types:CML_UINT32_T;  
                config false;
            } // END of lspTeMetric definition.

            leaf lspPathStat  {
                mandatory false;                
                type  cml_data_types:CML_BOOL_T;  
                config false;
            } // END of lspPathStat definition.

            leaf lspPathDetail  {
                mandatory false;                
                type  cml_data_types:CML_STRING_T;  
                config false;
            } // END of lspPathDetail definition.

            leaf lspExcludePathStat  {
                mandatory false;                
                type  cml_data_types:CML_BOOL_T;  
                config false;
            } // END of lspExcludePathStat definition.

            leaf lspExcludePathDetail  {
                mandatory false;                
                type  cml_data_types:CML_STRING_T;  
                config false;
            } // END of lspExcludePathDetail definition.

            leaf lspRouteStat  {
                mandatory false;                
                type  cml_data_types:CML_BOOL_T;  
                config false;
            } // END of lspRouteStat definition.

            leaf lspRouteDetail  {
                mandatory false;                
                type  cml_data_types:CML_STRING_T;  
                config false;
            } // END of lspRouteDetail definition.

            leaf isAbrType  {
                mandatory false;                
                type  cml_data_types:CML_STRING_T;  
                config false;
            } // END of isAbrType definition.

            leaf isAbrStateType  {
                mandatory false;                
                type  cml_data_types:CML_UINT32_T;  
                config false;
            } // END of isAbrStateType definition.

            leaf vrfIfName  {
                mandatory false;                
                type  cml_data_types:CML_STRING_T;  
                config false;
            } // END of vrfIfName definition.

            leaf vrfIvName  {
                mandatory false;                
                type  cml_data_types:CML_STRING_T;  
                config false;
            } // END of vrfIvName definition.

            leaf asbrSet  {
                mandatory false;                
                type  cml_data_types:CML_UINT8_T;  
                config false;
            } // END of asbrSet definition.

            leaf spfMinDelay  {
                mandatory false;                
                type  cml_data_types:CML_STRING_T;  
                config false;
            } // END of spfMinDelay definition.

            leaf spfMaxDelay  {
                mandatory false;                
                type  cml_data_types:CML_STRING_T;  
                config false;
            } // END of spfMaxDelay definition.

            leaf ddCountIn  {
                mandatory false;                
                type  cml_data_types:CML_UINT16_T;  
                config false;
            } // END of ddCountIn definition.

            leaf ddCountOut  {
                mandatory false;                
                type  cml_data_types:CML_UINT16_T;  
                config false;
            } // END of ddCountOut definition.

            leaf externalLsa  {
                mandatory false;                
                type  cml_data_types:CML_UINT32_T;  
                config false;
            } // END of externalLsa definition.

            leaf checksum  {
                mandatory false;                
                type  cml_data_types:CML_UINT32_T;  
                config false;
            } // END of checksum definition.

            leaf unknownLsa  {
                mandatory false;                
                type  cml_data_types:CML_UINT32_T;  
                config false;
            } // END of unknownLsa definition.

            leaf selfLsa  {
                mandatory false;                
                type  cml_data_types:CML_UINT32_T;  
                config false;
            } // END of selfLsa definition.

            leaf recvLsa  {
                mandatory false;                
                type  cml_data_types:CML_UINT32_T;  
                config false;
            } // END of recvLsa definition.

            leaf processUpTime  {
                mandatory false;                
                type  cml_data_types:CML_STRING_T;  
                config false;
            } // END of processUpTime definition.

            leaf restartMethodType  {
                mandatory false;                
                type  cml_data_types:CML_UINT32_T;  
                config false;
            } // END of restartMethodType definition.

            leaf areaCount  {
                mandatory false;                
                type  cml_data_types:CML_UINT32_T;  
                config false;
            } // END of areaCount definition.

            leaf obufSize  {
                mandatory false;                
                type  cml_data_types:CML_UINT32_T;  
                config false;
            } // END of obufSize definition.

            leaf lbufSize  {
                mandatory false;                
                type  cml_data_types:CML_UINT32_T;  
                config false;
            } // END of lbufSize definition.

            leaf ibufSize  {
                mandatory false;                
                type  cml_data_types:CML_UINT32_T;  
                config false;
            } // END of ibufSize definition.

            leaf opunuseMax  {
                mandatory false;                
                type  cml_data_types:CML_UINT16_T;  
                config false;
            } // END of opunuseMax definition.

            leaf opunuseCount  {
                mandatory false;                
                type  cml_data_types:CML_UINT16_T;  
                config false;
            } // END of opunuseCount definition.

            leaf lsaunuseCount  {
                mandatory false;                
                type  cml_data_types:CML_UINT16_T;  
                config false;
            } // END of lsaunuseCount definition.

            leaf lsaunuseMax  {
                mandatory false;                
                type  cml_data_types:CML_UINT16_T;  
                config false;
            } // END of lsaunuseMax definition.

            leaf accessListName  {
                mandatory false;                
                type  cml_data_types:CML_STRING_T;  
                config true;
            } // END of accessListName definition.

            leaf ospf6DistIn  {
                mandatory false;                
                type  cml_data_types:CML_BOOL_T;  
                config true;
            } // END of ospf6DistIn definition.

            leaf-list ospf6RedistProtocolDist  {
                
                type  cml_data_types:CML_OSPF6_DIST_ROUTE_SOURCE_TYPE_T;  
                config true;
            } // END of ospf6RedistProtocolDist definition.

            leaf-list ospf6DistributeTag  {
                
                type  cml_data_types:CML_STRING_T;  
                config true;
            } // END of ospf6DistributeTag definition.


            list neighborRun {
                 

                description
                    "neighborRun";

                config false;
                key "neighborIf";

                
                leaf neighborIf  {
                    mandatory true;                    
                    type  cml_data_types:CML_STRING_T;  
                    config false;
                } // END of neighborIf definition.

                leaf neighborPriority  {
                    mandatory false;                    
                    type  cml_data_types:CML_UINT8_T;  
                    config false;
                } // END of neighborPriority definition.

                leaf neighborDownState  {
                    mandatory false;                    
                    type  cml_data_types:CML_BOOL_T;  
                    config false;
                } // END of neighborDownState definition.

                leaf neighborRetransmitCount  {
                    mandatory false;                    
                    type  cml_data_types:CML_INT32_T;  
                    config false;
                } // END of neighborRetransmitCount definition.

                leaf neighborRequestCount  {
                    mandatory false;                    
                    type  cml_data_types:CML_INT32_T;  
                    config false;
                } // END of neighborRequestCount definition.

                leaf neighborDbSummaryCount  {
                    mandatory false;                    
                    type  cml_data_types:CML_INT32_T;  
                    config false;
                } // END of neighborDbSummaryCount definition.

                leaf neighborChangeState  {
                    mandatory false;                    
                    type  cml_data_types:CML_UINT32_T;  
                    config false;
                } // END of neighborChangeState definition.

                leaf neighborArea  {
                    mandatory false;                    
                    type  cml_data_types:CML_STRING_T;  
                    config false;
                } // END of neighborArea definition.

                leaf neighborInterfaceAddress  {
                    mandatory false;                    
                    type  cml_data_types:CML_STRING_T;  
                    config false;
                } // END of neighborInterfaceAddress definition.

                leaf neighborDRouterId  {
                    mandatory false;                    
                    type  cml_data_types:CML_STRING_T;  
                    config false;
                } // END of neighborDRouterId definition.

                leaf neighborBDRouterId  {
                    mandatory false;                    
                    type  cml_data_types:CML_STRING_T;  
                    config false;
                } // END of neighborBDRouterId definition.

                leaf neighborOptions  {
                    mandatory false;                    
                    type  cml_data_types:CML_UINT32_T;  
                    config false;
                } // END of neighborOptions definition.

                leaf neighborOptionDump  {
                    mandatory false;                    
                    type  cml_data_types:CML_STRING_T;  
                    config false;
                } // END of neighborOptionDump definition.

                leaf neighborState  {
                    mandatory false;                    
                    type  cml_data_types:CML_STRING_T;  
                    config false;
                } // END of neighborState definition.

                leaf neighborDeadTime  {
                    mandatory false;                    
                    type  cml_data_types:CML_STRING_T;  
                    config false;
                } // END of neighborDeadTime definition.

                leaf neighborId  {
                    mandatory false;                    
                    type  cml_data_types:CML_IPV4_ADDR_T;  
                    config false;
                } // END of neighborId definition.

                leaf neighborInst  {
                    mandatory false;                    
                    type  cml_data_types:CML_STRING_T;  
                    config false;
                } // END of neighborInst definition.

            } // End of neighborRun-list

            list frrTieBreak {
                 

                description
                    "frrTieBreak";

                config true;
                key "frrTieBreakVal";

                
                leaf frrTieBreakVal  {
                    mandatory true;                    
                    type  cml_data_types:CML_OSPF_FRR_TIE_BREAK_VAL_T;  
                    config true;
                } // END of frrTieBreakVal definition.

                leaf frrTieBreakIndex  {
                    mandatory true;                    
                    type  cml_data_types:CML_UINT32_T {
                         range "1..4";
                    }
                    config true;
                } // END of frrTieBreakIndex definition.

                leaf isFrrPrioSet  {
                    mandatory true;                    
                    type  cml_data_types:CML_BOOL_T;  
                    config true;
                } // END of isFrrPrioSet definition.

            } // End of frrTieBreak-list

            list summaryAddress {
                 

                description
                    "summaryAddress";

                config true;
                key "summaryIpv6Addr";

                
                leaf summaryIpv6Addr  {
                    mandatory true;                    
                    type  cml_data_types:CML_IPV6_PREFIX_T;  
                    config true;
                } // END of summaryIpv6Addr definition.

                leaf addressNotMask6len  {
                    mandatory false;                    
                    type  cml_data_types:CML_BOOL_T;  
                    config true;
                } // END of addressNotMask6len definition.

                leaf summaryRoute6Tag  {
                    mandatory false;                    
                    type  cml_data_types:CML_UINT32_T {
                         range "0..4294967295";
                    }
                    config true;
                } // END of summaryRoute6Tag definition.

                leaf summaryRoute6TranslateTag  {
                    mandatory false;                    
                    type  cml_data_types:CML_UINT32_T {
                         range "0..4294967295";
                    }
                    config true;
                } // END of summaryRoute6TranslateTag definition.

            } // End of summaryAddress-list

            list ospf6Area {
                 

                description
                    "ospf6Area";

                config true;
                key "areaId";

                
                leaf areaId  {
                    mandatory true;                    
                    type  cml_data_types:CML_STRING_T;  
                    config true;
                } // END of areaId definition.

                leaf defaultCost  {
                    mandatory false;                    
                    type  cml_data_types:CML_INT32_T {
                         range "1..16777215";
                    }
                    default "1";
                    config true;
                } // END of defaultCost definition.

                leaf isAreaType  {
                    mandatory false;                    
                    type  cml_data_types:CML_STRING_T;  
                    config false;
                } // END of isAreaType definition.

                leaf isAreaActive  {
                    mandatory false;                    
                    type  cml_data_types:CML_UINT8_T;  
                    config false;
                } // END of isAreaActive definition.

                leaf activeIfCount  {
                    mandatory false;                    
                    type  cml_data_types:CML_UINT32_T;  
                    config false;
                } // END of activeIfCount definition.

                leaf areaIfCount  {
                    mandatory false;                    
                    type  cml_data_types:CML_UINT32_T;  
                    config false;
                } // END of areaIfCount definition.

                leaf spfCalcCount  {
                    mandatory false;                    
                    type  cml_data_types:CML_UINT32_T;  
                    config false;
                } // END of spfCalcCount definition.

                leaf areaLsdbCountAll  {
                    mandatory false;                    
                    type  cml_data_types:CML_UINT32_T;  
                    config false;
                } // END of areaLsdbCountAll definition.

                leaf areaChecksum  {
                    mandatory false;                    
                    type  cml_data_types:CML_UINT32_T;  
                    config false;
                } // END of areaChecksum definition.

                leaf areaStrId  {
                    mandatory false;                    
                    type  cml_data_types:CML_STRING_T;  
                    config false;
                } // END of areaStrId definition.

                leaf isAreaDefault  {
                    mandatory false;                    
                    type  cml_data_types:CML_UINT32_T;  
                    config false;
                } // END of isAreaDefault definition.

                leaf isAreaNssa  {
                    mandatory false;                    
                    type  cml_data_types:CML_UINT32_T;  
                    config false;
                } // END of isAreaNssa definition.

                leaf areaUnknownLsa  {
                    mandatory false;                    
                    type  cml_data_types:CML_UINT32_T;  
                    config false;
                } // END of areaUnknownLsa definition.

                leaf isNssaDisabled  {
                    mandatory false;                    
                    type  cml_data_types:CML_STRING_T;  
                    config false;
                } // END of isNssaDisabled definition.

                leaf vlinkName  {
                    mandatory false;                    
                    type  cml_data_types:CML_STRING_T;  
                    config false;
                } // END of vlinkName definition.

                leaf transitArea  {
                    mandatory false;                    
                    type  cml_data_types:CML_STRING_T;  
                    config false;
                } // END of transitArea definition.

                leaf authEnabled  {
                    mandatory false;                    
                    type  cml_data_types:CML_STRING_T;  
                    config false;
                } // END of authEnabled definition.

                leaf authStateEnabled  {
                    mandatory false;                    
                    type  cml_data_types:CML_STRING_T;  
                    config false;
                } // END of authStateEnabled definition.

                leaf localAddr  {
                    mandatory false;                    
                    type  cml_data_types:CML_STRING_T;  
                    config false;
                } // END of localAddr definition.

                leaf remoteAddr  {
                    mandatory false;                    
                    type  cml_data_types:CML_STRING_T;  
                    config false;
                } // END of remoteAddr definition.

                leaf ifFsmState  {
                    mandatory false;                    
                    type  cml_data_types:CML_STRING_T;  
                    config false;
                } // END of ifFsmState definition.

                leaf helloDueIn  {
                    mandatory false;                    
                    type  cml_data_types:CML_STRING_T;  
                    config false;
                } // END of helloDueIn definition.

                leaf ifPassiveState  {
                    mandatory false;                    
                    type  cml_data_types:CML_BOOL_T;  
                    config false;
                } // END of ifPassiveState definition.

                leaf vlinkAdjState  {
                    mandatory false;                    
                    type  cml_data_types:CML_STRING_T;  
                    config false;
                } // END of vlinkAdjState definition.

                leaf vlinkState  {
                    mandatory false;                    
                    type  cml_data_types:CML_STRING_T;  
                    config false;
                } // END of vlinkState definition.

                leaf vlinkInterface  {
                    mandatory false;                    
                    type  cml_data_types:CML_STRING_T;  
                    config false;
                } // END of vlinkInterface definition.


                list areaStub {
                     

                    description
                        "areaStub";

                    config true;
                    key "isAreaStub";

                    
                    leaf isAreaStub  {
                        mandatory true;                        
                        type  cml_data_types:CML_BOOL_T;  
                        config true;
                    } // END of isAreaStub definition.

                    leaf ospf6AreaSummary  {
                        mandatory false;                        
                        type  cml_data_types:CML_BOOL_T;  
                        config true;
                    } // END of ospf6AreaSummary definition.

                } // End of areaStub-list

                list areaVlink {
                     

                    description
                        "areaVlink";

                    config true;
                    key "peerId";

                    
                    leaf peerId  {
                        mandatory true;                        
                        type  cml_data_types:CML_IPV4_ADDR_T;  
                        config true;
                    } // END of peerId definition.

                    leaf virtualLinkRetransmitInterval  {
                        mandatory false;                        
                        type  cml_data_types:CML_INT32_T {
                             range "1..1800";
                        }
                        default "1";
                        config true;
                    } // END of virtualLinkRetransmitInterval definition.

                    leaf virtualLinkTransmitDelay  {
                        mandatory false;                        
                        type  cml_data_types:CML_INT32_T {
                             range "1..1800";
                        }
                        default "1";
                        config true;
                    } // END of virtualLinkTransmitDelay definition.

                    leaf virtualLinkHelloInterval  {
                        mandatory false;                        
                        type  cml_data_types:CML_INT32_T {
                             range "1..65535";
                        }
                        default "1";
                        config true;
                    } // END of virtualLinkHelloInterval definition.

                    leaf virtualLinkDeadInterval  {
                        mandatory false;                        
                        type  cml_data_types:CML_INT32_T {
                             range "1..65535";
                        }
                        default "1";
                        config true;
                    } // END of virtualLinkDeadInterval definition.

                    leaf areaVlinkTimer  {
                        mandatory false;                        
                        type  cml_data_types:CML_STRING_T;  
                        config true;
                    } // END of areaVlinkTimer definition.

                    leaf virtualLinkSeconds  {
                        mandatory false;                        
                        type  cml_data_types:CML_INT32_T {
                             range "1..65535";
                        }
                        config true;
                    } // END of virtualLinkSeconds definition.

                    leaf VirtualLinkInstanceId  {
                        mandatory false;                        
                        type  cml_data_types:CML_INT32_T {
                             range "0..255";
                        }
                        default "0";
                        config true;
                    } // END of VirtualLinkInstanceId definition.

                } // End of areaVlink-list

                list areaNssa {
                     

                    description
                        "areaNssa";

                    config true;
                    key "ospf6Nssa";

                    
                    leaf ospf6Nssa  {
                        mandatory true;                        
                        type  cml_data_types:CML_BOOL_T;  
                        config true;
                    } // END of ospf6Nssa definition.

                    leaf stabilityInterval  {
                        mandatory false;                        
                        type  cml_data_types:CML_INT32_T {
                             range "0..2147483647";
                        }
                        default "40";
                        config true;
                    } // END of stabilityInterval definition.

                    leaf nssaAreaSummary  {
                        mandatory false;                        
                        type  cml_data_types:CML_BOOL_T;  
                        config true;
                    } // END of nssaAreaSummary definition.

                    leaf ospf6AreaNssaTransRole  {
                        mandatory false;                        
                        type  cml_data_types:CML_OSPF6_TRANSLATOR_ROLE_T;  
                        default "candidate";
                        config true;
                    } // END of ospf6AreaNssaTransRole definition.

                    leaf ospf6DefaultOriginMetric  {
                        mandatory false;                        
                        type  cml_data_types:CML_INT32_T {
                             range "1..16777214";
                        }
                        default "1";
                        config true;
                    } // END of ospf6DefaultOriginMetric definition.

                    leaf ospf6DefaultOriginMetricType  {
                        mandatory false;                        
                        type  cml_data_types:CML_OSPF6_METRIC_TYPE_T;  
                        config true;
                    } // END of ospf6DefaultOriginMetricType definition.

                    leaf ospf6NssaRedist  {
                        mandatory false;                        
                        type  cml_data_types:CML_BOOL_T;  
                        default true;
                        config true;
                    } // END of ospf6NssaRedist definition.

                    leaf ospf6NssaDefaultInfo  {
                        mandatory false;                        
                        type  cml_data_types:CML_BOOL_T;  
                        config true;
                    } // END of ospf6NssaDefaultInfo definition.

                    leaf NssaRouteMapName  {
                        mandatory false;                        
                        type  cml_data_types:CML_STRING_T;  
                        config true;
                    } // END of NssaRouteMapName definition.

                    container nssaAreaTranslator {
                        
                        config true;

                        description
                            "nssaAreaTranslator";

                        leaf nssaAreaTranslatorRole  {
                            mandatory false;                            
                            type  cml_data_types:CML_OSPF6_NSSA_TRANSLATOR_ROLE_T;  
                            config true;
                        } // END of nssaAreaTranslatorRole definition.

                    } // END of nssaAreaTranslator-container definition.
                } // End of areaNssa-list

                list rangeipv6 {
                     

                    description
                        "rangeipv6";

                    config true;
                    key "areaRangeAddr";

                    
                    leaf areaRangeAddr  {
                        mandatory true;                        
                        type  cml_data_types:CML_IPV6_PREFIX_T;  
                        config true;
                    } // END of areaRangeAddr definition.

                    leaf ospf6AreaRangeStatus  {
                        mandatory true;                        
                        type  cml_data_types:CML_OSPF6_AREA_RANGE_T;  
                        config true;
                    } // END of ospf6AreaRangeStatus definition.

                } // End of rangeipv6-list
            } // End of ospf6Area-list

            list redistributeProc {
                 

                description
                    "redistributeProc";

                config true;
                key "sourceOspf6Tag";

                
                leaf sourceOspf6Tag  {
                    mandatory true;                    
                    type  cml_data_types:CML_STRING_T;  
                    config true;
                } // END of sourceOspf6Tag definition.

                leaf ospf6RedistMetricType  {
                    mandatory false;                    
                    type  cml_data_types:CML_OSPF6_METRIC_TYPE_T;  
                    default "2";
                    config true;
                } // END of ospf6RedistMetricType definition.

                leaf ospf6RedistMetricValue  {
                    mandatory false;                    
                    type  cml_data_types:CML_UINT32_T {
                         range "0..16777214";
                    }
                    config true;
                } // END of ospf6RedistMetricValue definition.

                leaf ospf6RedistTagVal  {
                    mandatory false;                    
                    type  cml_data_types:CML_UINT32_T {
                         range "0..4294967295";
                    }
                    default "0";
                    config true;
                } // END of ospf6RedistTagVal definition.

                leaf ospf6RouteMapName  {
                    mandatory false;                    
                    type  cml_data_types:CML_STRING_T;  
                    config true;
                } // END of ospf6RouteMapName definition.

            } // End of redistributeProc-list

            list redistribute {
                 

                description
                    "redistribute";

                config true;
                key "ospf6RedistProtocol";

                
                leaf ospf6RedistProtocol  {
                    mandatory true;                    
                    type  cml_data_types:CML_OSPF6_ROUTE_SOURCE_TYPE_T;  
                    config true;
                } // END of ospf6RedistProtocol definition.

                leaf ospf6RedistMetricType  {
                    mandatory false;                    
                    type  cml_data_types:CML_OSPF6_METRIC_TYPE_T;  
                    default "2";
                    config true;
                } // END of ospf6RedistMetricType definition.

                leaf ospf6RedistMetricValue  {
                    mandatory false;                    
                    type  cml_data_types:CML_UINT32_T {
                         range "0..16777214";
                    }
                    config true;
                } // END of ospf6RedistMetricValue definition.

                leaf ospf6RedistTagVal  {
                    mandatory false;                    
                    type  cml_data_types:CML_UINT32_T {
                         range "0..4294967295";
                    }
                    default "0";
                    config true;
                } // END of ospf6RedistTagVal definition.

                leaf ospf6RouteMapName  {
                    mandatory false;                    
                    type  cml_data_types:CML_STRING_T;  
                    config true;
                } // END of ospf6RouteMapName definition.

            } // End of redistribute-list

            list ospf6DefaultInformation {
                 

                description
                    "ospf6DefaultInformation";

                config true;
                key "ospf6RedistDefaultOrigin";

                
                leaf ospf6RedistDefaultOrigin  {
                    mandatory true;                    
                    type  cml_data_types:CML_BOOL_T;  
                    config true;
                } // END of ospf6RedistDefaultOrigin definition.

                leaf ospf6RedistDefaultOriginAlways  {
                    mandatory false;                    
                    type  cml_data_types:CML_BOOL_T;  
                    config true;
                } // END of ospf6RedistDefaultOriginAlways definition.

                leaf ospf6RedistDefaultMetric  {
                    mandatory false;                    
                    type  cml_data_types:CML_OSPF6_METRIC_TYPE_T;  
                    config true;
                } // END of ospf6RedistDefaultMetric definition.

                leaf ospf6RedistDefaultMetricValue  {
                    mandatory false;                    
                    type  cml_data_types:CML_UINT32_T {
                         range "0..16777214";
                    }
                    config true;
                } // END of ospf6RedistDefaultMetricValue definition.

                leaf routeMapName  {
                    mandatory false;                    
                    type  cml_data_types:CML_STRING_T;  
                    config true;
                } // END of routeMapName definition.

            } // End of ospf6DefaultInformation-list

            list addressFamily {
                 

                description
                    "addressFamily";

                config true;
                key "addFamily";

                
                leaf addFamily  {
                    mandatory true;                    
                    type  cml_data_types:CML_BOOL_T;  
                    config true;
                } // END of addFamily definition.


                list afRangeipv4 {
                     

                    description
                        "afRangeipv4";

                    config true;
                    key "areaId";

                    
                    leaf areaId  {
                        mandatory true;                        
                        type  cml_data_types:CML_STRING_T;  
                        config true;
                    } // END of areaId definition.


                    list rangeipv4 {
                         

                        description
                            "rangeipv4";

                        config true;
                        key "areaRangeIpv4Addr";

                        
                        leaf areaRangeIpv4Addr  {
                            mandatory true;                            
                            type  cml_data_types:CML_IPV4_PREFIX_T;  
                            config true;
                        } // END of areaRangeIpv4Addr definition.

                        leaf ospfAreaRangeStatus  {
                            mandatory true;                            
                            type  cml_data_types:CML_OSPF6_AREA_RANGE_T;  
                            config true;
                        } // END of ospfAreaRangeStatus definition.

                    } // End of rangeipv4-list
                } // End of afRangeipv4-list

                list addressRedistribute {
                     

                    description
                        "addressRedistribute";

                    config true;
                    key "ospfRedistProtocol";

                    
                    leaf ospfRedistProtocol  {
                        mandatory true;                        
                        type  cml_data_types:CML_OSPF6_AF_ROUTE_SOURCE_TYPE_T;  
                        config true;
                    } // END of ospfRedistProtocol definition.

                    leaf ospfRedistMetricType  {
                        mandatory false;                        
                        type  cml_data_types:CML_OSPF6_METRIC_TYPE_T;  
                        default "2";
                        config true;
                    } // END of ospfRedistMetricType definition.

                    leaf ospfRedistMetricValue  {
                        mandatory false;                        
                        type  cml_data_types:CML_UINT32_T {
                             range "0..16777214";
                        }
                        default "0";
                        config true;
                    } // END of ospfRedistMetricValue definition.

                    leaf ospfRedistTagVal  {
                        mandatory false;                        
                        type  cml_data_types:CML_UINT32_T {
                             range "0..4294967295";
                        }
                        default "0";
                        config true;
                    } // END of ospfRedistTagVal definition.

                    leaf ospfRouteMapName  {
                        mandatory false;                        
                        type  cml_data_types:CML_STRING_T;  
                        config true;
                    } // END of ospfRouteMapName definition.

                } // End of addressRedistribute-list

                list addressRedistributeProc {
                     

                    description
                        "addressRedistributeProc";

                    config true;
                    key "sourceOspfTag";

                    
                    leaf sourceOspfTag  {
                        mandatory true;                        
                        type  cml_data_types:CML_INT32_T {
                             range "1..65535";
                        }
                        config true;
                    } // END of sourceOspfTag definition.

                    leaf ospfRedistMetricType  {
                        mandatory false;                        
                        type  cml_data_types:CML_OSPF6_METRIC_TYPE_T;  
                        default "2";
                        config true;
                    } // END of ospfRedistMetricType definition.

                    leaf ospfRedistMetricValue  {
                        mandatory false;                        
                        type  cml_data_types:CML_UINT32_T {
                             range "0..16777214";
                        }
                        default "0";
                        config true;
                    } // END of ospfRedistMetricValue definition.

                    leaf ospfRedistTagVal  {
                        mandatory false;                        
                        type  cml_data_types:CML_UINT32_T {
                             range "0..4294967295";
                        }
                        default "0";
                        config true;
                    } // END of ospfRedistTagVal definition.

                    leaf ospfRouteMapName  {
                        mandatory false;                        
                        type  cml_data_types:CML_STRING_T;  
                        config true;
                    } // END of ospfRouteMapName definition.

                } // End of addressRedistributeProc-list

                list summaryAddressIpv4 {
                     

                    description
                        "summaryAddressIpv4";

                    config true;
                    key "summaryIpv4Addr";

                    
                    leaf summaryIpv4Addr  {
                        mandatory true;                        
                        type  cml_data_types:CML_IPV4_PREFIX_T;  
                        config true;
                    } // END of summaryIpv4Addr definition.

                    leaf summaryRouteTag  {
                        mandatory false;                        
                        type  cml_data_types:CML_UINT32_T {
                             range "0..4294967295";
                        }
                        config true;
                    } // END of summaryRouteTag definition.

                    leaf addressNotMask4len  {
                        mandatory false;                        
                        type  cml_data_types:CML_BOOL_T;  
                        config true;
                    } // END of addressNotMask4len definition.

                } // End of summaryAddressIpv4-list

                list ospf6FamilyDefaultInformation {
                     

                    description
                        "ospf6FamilyDefaultInformation";

                    config true;
                    key "ospf6FamRedistDefaultOrigin";

                    
                    leaf ospf6FamRedistDefaultOrigin  {
                        mandatory true;                        
                        type  cml_data_types:CML_BOOL_T;  
                        config true;
                    } // END of ospf6FamRedistDefaultOrigin definition.

                    leaf ospf6FamRedistDefaultOriginAlways  {
                        mandatory false;                        
                        type  cml_data_types:CML_BOOL_T;  
                        config true;
                    } // END of ospf6FamRedistDefaultOriginAlways definition.

                    leaf ospf6FamRedistDefaultMetric  {
                        mandatory false;                        
                        type  cml_data_types:CML_OSPF6_METRIC_TYPE_T;  
                        config true;
                    } // END of ospf6FamRedistDefaultMetric definition.

                    leaf ospf6FamRedistDefaultMetricValue  {
                        mandatory false;                        
                        type  cml_data_types:CML_UINT32_T {
                             range "0..16777214";
                        }
                        config true;
                    } // END of ospf6FamRedistDefaultMetricValue definition.

                    leaf ospf6FamRouteMapName  {
                        mandatory false;                        
                        type  cml_data_types:CML_STRING_T;  
                        config true;
                    } // END of ospf6FamRouteMapName definition.

                } // End of ospf6FamilyDefaultInformation-list
            } // End of addressFamily-list
            container distanceTypes {
                
                config true;

                description
                    "distanceTypes";

                leaf intraDistance  {
                    mandatory false;                    
                    type  cml_data_types:CML_INT32_T {
                         range "1..254";
                    }
                    default "110";
                    config true;
                } // END of intraDistance definition.

                leaf interDistance  {
                    mandatory false;                    
                    type  cml_data_types:CML_INT32_T {
                         range "1..254";
                    }
                    default "110";
                    config true;
                } // END of interDistance definition.

                leaf externalDistance  {
                    mandatory false;                    
                    type  cml_data_types:CML_INT32_T {
                         range "1..254";
                    }
                    default "110";
                    config true;
                } // END of externalDistance definition.

            } // END of distanceTypes-container definition.
        } // End of ospf6-list
    } // END of ospf6-grouping definition.


    grouping ospf6Interface-grouping {
        list ospf6Interface {
             

            description
                "OSPFv3 interface related operations";

            config true;
            key "ifName";

            
            leaf ifName  {
                mandatory true;                
                type  leafref {
                    path  "/vr/interface/ifName";
                }
            } // END of ifName definition.

            leaf isDisable  {
                mandatory false;                
                type  cml_data_types:CML_INT32_T;  
                config true;
            } // END of isDisable definition.

            leaf bfdDisable  {
                mandatory false;                
                type  cml_data_types:CML_BOOL_T;  
                default false;
                config true;
            } // END of bfdDisable definition.

            leaf isIfLoopBackType  {
                mandatory false;                
                type  cml_data_types:CML_BOOL_T;  
                config false;
            } // END of isIfLoopBackType definition.


            list ospf6IfinstanceId {
                 

                description
                    "OSPFv3 instanceId of interface related operations";

                config true;
                key "instanceId";

                
                leaf instanceId  {
                    mandatory true;                    
                    type  cml_data_types:CML_INT32_T {
                         range "0..31 | 64..95";
                    }
                    config true;
                } // END of instanceId definition.

                leaf ospf6IfType  {
                    mandatory false;                    
                    type  cml_data_types:CML_OSPF6_NETWORK_T;  
                    config true;
                } // END of ospf6IfType definition.

                leaf ospf6IfMultiType  {
                    mandatory false;                    
                    type  cml_data_types:CML_BOOL_T;  
                    config true;
                } // END of ospf6IfMultiType definition.

                leaf ospf6IfPriority  {
                    mandatory false;                    
                    type  cml_data_types:CML_INT32_T {
                         range "0..255";
                    }
                    default "1";
                    config true;
                } // END of ospf6IfPriority definition.

                leaf ifMtuIgnore  {
                    mandatory false;                    
                    type  cml_data_types:CML_BOOL_T;  
                    config true;
                } // END of ifMtuIgnore definition.

                leaf ospf6IfCost  {
                    mandatory false;                    
                    type  cml_data_types:CML_UINT32_T {
                         range "1..65535";
                    }
                    default "10";
                    config true;
                } // END of ospf6IfCost definition.

                leaf transmitDelay  {
                    mandatory false;                    
                    type  cml_data_types:CML_UINT32_T {
                         range "1..1800";
                    }
                    default "1";
                    config true;
                } // END of transmitDelay definition.

                leaf retransmitInterval  {
                    mandatory false;                    
                    type  cml_data_types:CML_UINT32_T {
                         range "1..1800";
                    }
                    default "5";
                    config true;
                } // END of retransmitInterval definition.

                leaf helloInterval  {
                    mandatory false;                    
                    type  cml_data_types:CML_UINT32_T {
                         range "1..65535";
                    }
                    default "10";
                    config true;
                } // END of helloInterval definition.

                leaf deadInterval  {
                    mandatory false;                    
                    type  cml_data_types:CML_UINT32_T {
                         range "1..65535";
                    }
                    default "40";
                    config true;
                } // END of deadInterval definition.

                leaf ospf6TeMetric  {
                    mandatory false;                    
                    type  cml_data_types:CML_UINT32_T {
                         range "1..65535";
                    }
                    default "10";
                    config true;
                } // END of ospf6TeMetric definition.

                leaf ospf6LsaSuppressionValue  {
                    mandatory false;                    
                    type  cml_data_types:CML_OSPF6_LSA_SUPRESSION_STATE_T;  
                    default "enable";
                    config true;
                } // END of ospf6LsaSuppressionValue definition.

                leaf ospf6NeighborAddr  {
                    mandatory false;                    
                    type  cml_data_types:CML_IPV6_ADDR_T;  
                    config true;
                } // END of ospf6NeighborAddr definition.

                leaf ospf6IfNbrCost  {
                    mandatory false;                    
                    type  cml_data_types:CML_UINT32_T {
                         range "1..65535";
                    }
                    default "10";
                    config true;
                } // END of ospf6IfNbrCost definition.

                leaf ospf6IfNbrPollInterval  {
                    mandatory false;                    
                    type  cml_data_types:CML_UINT32_T {
                         range "0..4294967295";
                    }
                    config true;
                } // END of ospf6IfNbrPollInterval definition.

                leaf ospf6IfNbrPriority  {
                    mandatory false;                    
                    type  cml_data_types:CML_INT32_T {
                         range "0..255";
                    }
                    config true;
                } // END of ospf6IfNbrPriority definition.

                leaf fastRerouteIfSet  {
                    mandatory false;                    
                    type  cml_data_types:CML_BOOL_T;  
                    config true;
                } // END of fastRerouteIfSet definition.

                leaf ifAreaId  {
                    mandatory false;                    
                    type  cml_data_types:CML_STRING_T;  
                    config true;
                } // END of ifAreaId definition.

                leaf ifProcessTag  {
                    mandatory false;                    
                    type  cml_data_types:CML_STRING_T;  
                    default "";
                    config true;
                } // END of ifProcessTag definition.

                leaf ifProcessTagPresent  {
                    mandatory false;                    
                    type  cml_data_types:CML_BOOL_T;  
                    config true;
                } // END of ifProcessTagPresent definition.

                leaf ifState  {
                    mandatory false;                    
                    type  cml_data_types:CML_STRING_T;  
                    config false;
                } // END of ifState definition.

                leaf ifIndex  {
                    mandatory false;                    
                    type  cml_data_types:CML_UINT32_T;  
                    config false;
                } // END of ifIndex definition.

                leaf ipAddr  {
                    mandatory false;                    
                    type  cml_data_types:CML_STRING_T;  
                    config false;
                } // END of ipAddr definition.

                leaf ipLinkLocalAddr  {
                    mandatory false;                    
                    type  cml_data_types:CML_STRING_T;  
                    config false;
                } // END of ipLinkLocalAddr definition.

                leaf ipLinkAddr  {
                    mandatory false;                    
                    type  cml_data_types:CML_STRING_T;  
                    config false;
                } // END of ipLinkAddr definition.

                leaf interfaceProcessTag  {
                    mandatory false;                    
                    type  cml_data_types:CML_STRING_T;  
                    config false;
                } // END of interfaceProcessTag definition.

                leaf interfaceAreaId  {
                    mandatory false;                    
                    type  cml_data_types:CML_STRING_T;  
                    config false;
                } // END of interfaceAreaId definition.

                leaf interfaceRouterId  {
                    mandatory false;                    
                    type  cml_data_types:CML_STRING_T;  
                    config false;
                } // END of interfaceRouterId definition.

                leaf interfaceInstanceId  {
                    mandatory false;                    
                    type  cml_data_types:CML_UINT32_T;  
                    config false;
                } // END of interfaceInstanceId definition.

                leaf stateChange  {
                    mandatory false;                    
                    type  cml_data_types:CML_STRING_T;  
                    config false;
                } // END of stateChange definition.

                leaf neighborCount  {
                    mandatory false;                    
                    type  cml_data_types:CML_INT32_T;  
                    config false;
                } // END of neighborCount definition.

                leaf adjNeighborCount  {
                    mandatory false;                    
                    type  cml_data_types:CML_INT32_T;  
                    config false;
                } // END of adjNeighborCount definition.

                leaf designatedRouterId  {
                    mandatory false;                    
                    type  cml_data_types:CML_STRING_T;  
                    config false;
                } // END of designatedRouterId definition.

                leaf backupDesignatedRouterId  {
                    mandatory false;                    
                    type  cml_data_types:CML_STRING_T;  
                    config false;
                } // END of backupDesignatedRouterId definition.

                leaf interfaceIfType  {
                    mandatory false;                    
                    type  cml_data_types:CML_STRING_T;  
                    config false;
                } // END of interfaceIfType definition.

                leaf interfaceIfCost  {
                    mandatory false;                    
                    type  cml_data_types:CML_UINT32_T;  
                    config false;
                } // END of interfaceIfCost definition.

                leaf interfaceTeMetric  {
                    mandatory false;                    
                    type  cml_data_types:CML_UINT32_T;  
                    config false;
                } // END of interfaceTeMetric definition.

                leaf interfaceTransmitDelay  {
                    mandatory false;                    
                    type  cml_data_types:CML_UINT32_T;  
                    config false;
                } // END of interfaceTransmitDelay definition.

                leaf interfaceFsmState  {
                    mandatory false;                    
                    type  cml_data_types:CML_STRING_T;  
                    config false;
                } // END of interfaceFsmState definition.

                leaf interfaceIfPriority  {
                    mandatory false;                    
                    type  cml_data_types:CML_INT32_T;  
                    config false;
                } // END of interfaceIfPriority definition.

                leaf interfaceHelloInterval  {
                    mandatory false;                    
                    type  cml_data_types:CML_UINT32_T;  
                    config false;
                } // END of interfaceHelloInterval definition.

                leaf interfaceIfPassiveState  {
                    mandatory false;                    
                    type  cml_data_types:CML_STRING_T;  
                    config false;
                } // END of interfaceIfPassiveState definition.

                leaf interfaceDeadInterval  {
                    mandatory false;                    
                    type  cml_data_types:CML_UINT32_T;  
                    config false;
                } // END of interfaceDeadInterval definition.

                leaf interfaceRetransmitInterval  {
                    mandatory false;                    
                    type  cml_data_types:CML_UINT32_T;  
                    config false;
                } // END of interfaceRetransmitInterval definition.

                leaf interfaceHelloDueIn  {
                    mandatory false;                    
                    type  cml_data_types:CML_STRING_T;  
                    config false;
                } // END of interfaceHelloDueIn definition.

                leaf interfaceStateChange  {
                    mandatory false;                    
                    type  cml_data_types:CML_UINT32_T;  
                    config false;
                } // END of interfaceStateChange definition.

                leaf interfaceNeighborCount  {
                    mandatory false;                    
                    type  cml_data_types:CML_INT32_T;  
                    config false;
                } // END of interfaceNeighborCount definition.

                leaf isInterfaceType  {
                    mandatory false;                    
                    type  cml_data_types:CML_BOOL_T;  
                    config false;
                } // END of isInterfaceType definition.

            } // End of ospf6IfinstanceId-list
        } // End of ospf6Interface-list
    } // END of ospf6Interface-grouping definition.


    grouping ospf6Global-grouping {
        list ospf6Global {
             

            description
                "ospf6Global";

            config true;
            key "vrId";

            
            leaf vrId  {
                mandatory true;                
                type  cml_data_types:CML_UINT32_T;  
                config true;
            } // END of vrId definition.

            leaf gracePeriod  {
                mandatory false;                
                type  cml_data_types:CML_INT32_T {
                     range "1..1800";
                }
                default "120";
                config true;
            } // END of gracePeriod definition.

            leaf gracefulRestartPlanned  {
                mandatory false;                
                type  cml_data_types:CML_BOOL_T;  
                config true;
            } // END of gracefulRestartPlanned definition.

            leaf ospf6RouterSingleline  {
                mandatory false;                
                type  cml_data_types:CML_BOOL_T;  
                config true;
            } // END of ospf6RouterSingleline definition.

            leaf ospf6Debug  {
                mandatory false;                
                type  cml_data_types:CML_OSPF6_DEBUG_T;  
                config true;
            } // END of ospf6Debug definition.

            leaf isDebug  {
                mandatory false;                
                type  cml_data_types:CML_BOOL_T;  
                config true;
            } // END of isDebug definition.

            leaf ospf6Packet  {
                mandatory false;                
                type  cml_data_types:CML_OSPF6_DEBUG_PACKET_TYPE_T;  
                config true;
            } // END of ospf6Packet definition.

            leaf ospf6PacketDebug  {
                mandatory false;                
                type  cml_data_types:CML_BOOL_T;  
                config true;
            } // END of ospf6PacketDebug definition.

            container restartConfig {
                
                config true;

                description
                    "restartConfig";

                leaf never  {
                    mandatory false;                    
                    type  cml_data_types:CML_BOOL_T;  
                    config true;
                } // END of never definition.

                leaf nbrRouterId  {
                    mandatory false;                    
                    type  cml_data_types:CML_STRING_T;  
                    config true;
                } // END of nbrRouterId definition.

                leaf restartAll  {
                    mandatory false;                    
                    type  cml_data_types:CML_BOOL_T;  
                    config true;
                } // END of restartAll definition.

            } // END of restartConfig-container definition.
            container restartAllConfig {
                
                config true;

                description
                    "restartAllConfig";

                leaf onlyReload  {
                    mandatory false;                    
                    type  cml_data_types:CML_BOOL_T;  
                    config true;
                } // END of onlyReload definition.

                leaf onlyUpgrade  {
                    mandatory false;                    
                    type  cml_data_types:CML_BOOL_T;  
                    config true;
                } // END of onlyUpgrade definition.

                leaf restartHelperPeriod  {
                    mandatory false;                    
                    type  cml_data_types:CML_INT32_T {
                         range "1..1800";
                    }
                    default "120";
                    config true;
                } // END of restartHelperPeriod definition.

            } // END of restartAllConfig-container definition.
        } // End of ospf6Global-list
    } // END of ospf6Global-grouping definition.


    grouping ospf6Vrf-grouping {
        list ospf6Vrf {
             

            description
                "Enable an IPv6 VRF routing process";

            config true;
            key "vrId";

            
            leaf vrId  {
                mandatory true;                
                type  leafref {
                    path  "/vr/vrId";
                }
            } // END of vrId definition.

            leaf vrfName  {
                mandatory false;                
                type  leafref {
                    path  "/vr/vrf/vrfName";
                }
            } // END of vrfName definition.

        } // End of ospf6Vrf-list
    } // END of ospf6Vrf-grouping definition.


}
