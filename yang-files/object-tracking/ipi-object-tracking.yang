/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-object-tracking.yang
*
*/

module ipi-object-tracking {

    yang-version 1.1;

    namespace   "http://www.ipinfusion.com/yang/ocnos/ipi-object-tracking";

    prefix "ipi-object-tracking";

    import ipi-object-tracking-types {
        prefix ipi-object-tracking-types;
        revision-date 2022-06-01;
    }

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for Object Tracking Configuration and operational data.";


    revision "2022-06-01" {
        description "Updated the yang file with feature";
        reference " 0.2.0.";
    }

    revision "2021-12-08" {
        description "Initial Version";
        reference " 0.1.0.";
    }

    grouping tracker-object-config {
        description
            "Grouping for Object tracking config objects.";
        leaf tracker-id  {
            type  uint16 {
                 range "1..500"  {
                    description "1..500: Supported range 1 - 500";
                 }
            }
            description "Use this attribute for Object Tracking id.";
        } // END of tracker-id definition.

        leaf ip-sla-id  {
            type  uint16 {
                 range "1..65535"  {
                    description "1..65535: Supported range 1 - 65535";
                 }
            }
            mandatory true;
            description "Use this attribute for ip-sla-id.";
        } // END of ip-sla-id definition.

        leaf delay-up  {
            type  uint16 {
                 range "1..9999"  {
                    description "1..9999: Supported range 1 - 9999";
                 }
            }
            description "Use this attribute to set notification delay up.";
        } // END of delay-up definition.

        leaf delay-down  {
            type  uint16 {
                 range "1..9999"  {
                    description "1..9999: Supported range 1 - 9999";
                 }
            }
            description "Use this attribute to set notification delay down.";
        } // END of delay-down definition.

    } // END of tracker-object-config definition.
    grouping tracker-object-state {
        description
            "Grouping for object tracking operation state objects..";
        leaf reachability-status  {
            if-feature feature-list:HAVE_OBJ_TRACKING;
            type  ipi-object-tracking-types:object_tracking_reachability_status_t;
            config false;
            description "To track Object tracking reachability status";
        } // END of reachability-status definition.

    } // END of tracker-object-state definition.

    grouping  object-tracking-grouping {
    description
        "Top level container for Object Tracking, including configuration and
                state data";
    container object-tracking {
        if-feature feature-list:HAVE_OBJ_TRACKING;
        description
            "Top level container for Object Tracking, including configuration and
                    state data";
        container trackers {
            description
                "Enclosing container for tracker config objects";

            list tracker {
                key "tracker-id";
                description
                    "List of tracked objects which will provide identifier for IP SLA";
                leaf tracker-id  {
                    type  leafref {
                        path  "../config/tracker-id";
                    }
                    description "Use this attribute for Object Tracking id.";
                } // END of tracker-id definition.

                container config {
                    description
                        "This container defines Tracked object configuration.";
                    uses tracker-object-config;
                } // END of config-container definition.
                container state {
                    config false;
                    description
                        "This container defines Tracked object Operational states.";
                    uses tracker-object-config;
                    uses tracker-object-state;
                } // END of state-container definition.
            } // End of tracker-list
        } // END of trackers-container definition.
    } // END of object-tracking-container definition.
    } // END of object-tracking-grouping definition.

    uses object-tracking-grouping;

}
