/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-bridge.yang
*
*/

module ipi-bridge {

    yang-version 1.1;

    namespace   "http://www.ipinfusion.com/yang/ocnos/ipi-bridge";

    prefix "ipi-bridge";

    import cml-data-types {
        prefix cml-data-types;
    }

    import ipi-bridge-types {
        prefix ipi-bridge-types;
    }

    import ipi-interface {
        prefix ipi-interface;
    }

    import ipi-network-instance {
        prefix ipi-network-instance;
    }

    import feature-list {
        prefix feature-list;
    }

    organization
        "IP Infusion Inc.";

    contact
        "Address: 3965 Freedom Circle, Suite 200, Santa Clara, CA 95054
         Phone: +1 408-400-1900
         E-mail: support@ipinfusion.com
         Web: http://www.ipinfusion.com/";

    description
        "Layer-2 bridge configurations";


    revision "2021-02-09" {
        description "JIRA-43764: dot1 encapsulation for switching and SVI routing";
        reference " 0.4.0.";
    }

    revision "2021-01-27" {
        description "Change to have descriptions for individual leafs";
        reference " 0.3.0.";
    }

    revision "2020-12-15" {
        description "Change to have data-types in lower case instead of camel case";
        reference " 0.2.0.";
    }

    revision "2018-06-21" {
        description "Initial Version";
        reference " 0.1.0.";
    }

    grouping bridge-config {
        description
            "Bridge configuration data";
        leaf protocol  {
            type  ipi-bridge-types:bridge_protocol_t;
            mandatory true;
            description "Bridge protocol type";
        } // END of protocol definition.

        leaf disable-dynamic-learning  {
            type  empty;
            description "Enable/Disable a bridge to learn station location information for an
                        instance.This helps in making forwarding decisions";
        } // END of disable-dynamic-learning definition.

        leaf l2-protocol-destination-mac  {
            type  cml-data-types:cml_mac_addr_t;
            default "0100.C2CD.CDD0";
            description "This attribute changes L2 protocol destination MAC";
        } // END of l2-protocol-destination-mac definition.

        leaf dot1q-encapsulation  {
            if-feature feature-list:HAVE_DUNE;
            type  empty;
            description "Configure to use encapsulated dot1q value for switching and routing by
                        bridge ports";
        } // END of dot1q-encapsulation definition.

    } // END of bridge-config definition.
    grouping bridge-interface-config {
        description
            "Configuration data for STP on each interface";
        leaf name  {
            type  leafref {
                path  "/ipi-interface:interfaces/ipi-interface:interface/ipi-interface:name";
            }
            description "The textual name of the interface";
        } // END of name definition.

        leaf spanning-tree-protocol-status  {
            type  ipi-bridge-types:bridge_spanningtree_enable_disable_t;
            description "Attribute specifies to enable/disable Spanning Tree Protocol on a
                        interface";
        } // END of spanning-tree-protocol-status definition.

    } // END of bridge-interface-config definition.
    grouping bridge-ports-top {
        description
            "Top level grouping for interface stp configuration and state data";
        container bridge-ports {
            description
                "Container for STP configuration and state data on each interface";

            list interface {
            when " /ipi-interface:interfaces/ipi-interface:interface/ipi-interface:name + /ipi-interface:interfaces/ipi-interface:interface/ipi-interface:config/ipi-interface:switchport-status = 'true' ";
                key "name";
                description
                    "List of interfaces on which spanning tree protocol is
                                enabled/available";
                leaf name  {
                    type  leafref {
                        path  "../config/name";
                    }
                    description "The textual name of the interface";
                } // END of name definition.

                container config {
                    description
                        "Configuration data for STP on each interface";
                    uses bridge-interface-config;
                } // END of config-container definition.
                container state {
                    config false;
                    description
                        "Operational state data";
                    uses bridge-interface-config;
                } // END of state-container definition.
            } // End of interface-list
        } // END of bridge-ports-container definition.
    } // END of bridge-ports-top definition.
    grouping fdb-entry-config {
        description
            "Configuration data for FDB MAC address";
        leaf mac-address  {
            type  cml-data-types:cml_mac_addr_t;
            description "Use this attribute to configure the static forwarding table MAC entry
                        for the bridge";
        } // END of mac-address definition.

        leaf action  {
            type  ipi-bridge-types:bridge_discardforward_t;
            mandatory true;
            description "Use this attribute to configure fame discard/forward action for given
                        MAC address";
        } // END of action definition.

    } // END of fdb-entry-config definition.
    grouping static-mac-table-entry-top {
        description
            "Top level grouping for FDB  configuration and state data";

        list entry {
            key "interface-name mac-address";
            description
                "List of FDB MAC entries";
            leaf interface-name  {
                type  leafref {
                    path  "/ipi-interface:interfaces/ipi-interface:interface/ipi-interface:name";
                }
                description "The textual name of the interface";
            } // END of interface-name definition.

            leaf mac-address  {
                type  leafref {
                    path  "../config/mac-address";
                }
                description "Use this attribute to configure the static forwarding table MAC entry
                            for the bridge";
            } // END of mac-address definition.

            container config {
                description
                    "Configuration data for FDB MAC entries";
                uses fdb-entry-config;
            } // END of config-container definition.
            container state {
                config false;
                description
                    "Operational state data";
                uses fdb-entry-config;
            } // END of state-container definition.
        } // End of entry-list
    } // END of static-mac-table-entry-top definition.
    grouping static-mac-table-top {
        description
            "Top level grouping for FDB  configuration and state data";
        container static-mac-table {
            description
                "MAC table information";
            uses static-mac-table-entry-top;
        } // END of static-mac-table-container definition.
    } // END of static-mac-table-top definition.
    grouping fdb-interface-config {
        description
            "Grouping for FDB MAC address entries";
        leaf disable-mac-learning  {
            type  cml-data-types:cml_enable_disable_t;
            mandatory true;
            description "Use this attribute to disable MAC learning on a interface";
        } // END of disable-mac-learning definition.

    } // END of fdb-interface-config definition.
    grouping fdb-interface-top {
        description
            "Top level grouping for interface FDB data";

        list interface {
            key "interface-name";
            description
                "List of FDB interface entries";
            leaf interface-name  {
                type  leafref {
                    path  "/ipi-interface:interfaces/ipi-interface:interface/ipi-interface:name";
                }
                description "The textual name of the interface";
            } // END of interface-name definition.

            container config {
                description
                    "Configuration data for FDB interface";
                uses fdb-interface-config;
            } // END of config-container definition.
            container state {
                config false;
                description
                    "Operational state data";
                uses fdb-interface-config;
            } // END of state-container definition.
        } // End of interface-list
    } // END of fdb-interface-top definition.
    grouping fdb-interfaces-top {
        description
            "Top level grouping for interface FDB data";
        container interfaces {
            description
                "MAC table information";
            uses fdb-interface-top;
        } // END of interfaces-container definition.
    } // END of fdb-interfaces-top definition.
    grouping dynamic-mac-table-state {
        description
            "Dynamic learned MAC information";
        leaf mac-address  {
            type  cml-data-types:cml_mac_addr_t;
            description "Dynamic learned MAC address";
        } // END of mac-address definition.

        leaf cvlan-id  {
            type  uint16;
            description "Customer vlan ID";
        } // END of cvlan-id definition.

        leaf interface-name  {
            type  string {
                length "1..max";
                pattern "[^?' =,>|]+";
            }
            description "MAC learned interface";
        } // END of interface-name definition.

        leaf action  {
            type  ipi-bridge-types:bridge_discardforward_t;
            description "Fame discard/forward information for given MAC address";
        } // END of action definition.

        leaf entry-time-out  {
            type  uint32;
            units "seconds";
            description "The remaining time to delete entry for given MAC address from dynamic
                        MAC learned table";
        } // END of entry-time-out definition.

    } // END of dynamic-mac-table-state definition.
    grouping dynamic-mac-table-top {
        description
            "Top level group for dynamic learned MAC address information";

        list dynamic-mac-table {
            if-feature feature-list:HAVE_HAL;
            key "mac-address cvlan-id";
            config false;
            description
                "List of dynamic learned MAC addresses";
            leaf mac-address  {
                type  leafref {
                    path  "../state/mac-address";
                }
                description "Dynamic learned MAC address";
            } // END of mac-address definition.

            leaf cvlan-id  {
                type  leafref {
                    path  "../state/cvlan-id";
                }
                description "Customer vlan ID";
            } // END of cvlan-id definition.

            container state {
                if-feature feature-list:HAVE_HAL;
                config false;
                description
                    "dynamic learned operational state data";
                uses dynamic-mac-table-state;
            } // END of state-container definition.
        } // End of dynamic-mac-table-list
    } // END of dynamic-mac-table-top definition.
    grouping fdb-top {
        description
            "Top level grouping FDB";
        container fdb {
            description
                "List of FDB MAC and interface entries";
            uses fdb-interfaces-top;
            uses static-mac-table-top;
            uses dynamic-mac-table-top;
        } // END of fdb-container definition.
    } // END of fdb-top definition.
    grouping evc-config {
        description
            "Grouping for ethernet virtual conneciton data";
        leaf id  {
            type  string {
                length "1..max";
                pattern "[^?' =,>|]+";
            }
            description "Ethernet virtual conneciton ID";
        } // END of id definition.

        leaf maximum-uni  {
            type  uint32 {
                 range "1..32"  {
                    description "Maximum UNI number for the EVC/SVLAN";
                 }
            }
            mandatory true;
            description "Use this attribute to configure maximum UNI number for the given
                        EVC/SVLAN";
        } // END of maximum-uni definition.

    } // END of evc-config definition.
    grouping evc-top {
        description
            "Top level grouping for ethernet virtual conneciton configuration and
                        state data";
    } // END of evc-top definition.

    grouping  bridge-grouping {
    description
        "Bridge configuration and state data";
    container bridge {
        description
            "Bridge configuration and state data";
        container config {
            presence "Configure bridge protocol";
            description
                "Configuration data for bridge group";
            uses bridge-config;
        } // END of config-container definition.
        container state {
            config false;
            description
                "Operational state data";
            uses bridge-config;
        } // END of state-container definition.
        uses bridge-ports-top;
        uses fdb-top;
        uses evc-top;
    } // END of bridge-container definition.
    } // END of bridge-grouping definition.

    augment /ipi-network-instance:network-instances/ipi-network-instance:network-instance {
    when " /ipi-network-instance:network-instances/ipi-network-instance:network-instance/ipi-network-instance:instance-type = 'l2ni' + /ipi-network-instance:network-instances/ipi-network-instance:network-instance/ipi-bridge:bridge/ipi-bridge:config/ipi-bridge:protocol ";
        description
            "Bridge configuration and state data";
        uses bridge-grouping;
    }


    rpc clear-mac-address-table {
        description "Use this rpc to clear fdb entry for given MAC/interface/vlan";
        input  {
            leaf mac-type  {
                type ipi-bridge-types:bridge_mac_type_t;
                mandatory true;
                description "MAC address type";
            }
            leaf bridge-id  {
                type string {
                    pattern "([1-9]|[12][0-9]|3[0-2])";
                }
                mandatory true;
                description "Bridge group number";
            }
            leaf interface-name  {
                type string {
                    length "1..33";
                }
                description "The textual name of the interface";
            }
            leaf mac-address  {
                type cml-data-types:cml_mac_addr_t;
                description "Interface MAC address";
            }
            leaf vlan-id  {
                type uint16;
                description "Vlan ID";
            }
        }
    }

    rpc clear-dynamic-mac-address-table {
        description "Use this rpc to clear dynamic fdb entries for given interface/MAC/vlan";
        input  {
            leaf bridge-id  {
                type string {
                    pattern "([1-9]|[12][0-9]|3[0-2])";
                }
                mandatory true;
                description "Bridge group number";
            }
            leaf mac-address  {
                type cml-data-types:cml_mac_addr_t;
                description "Interface MAC address";
            }
            leaf interface-name  {
                type string {
                    length "1..33";
                }
                description "The textual name of the interface";
            }
            leaf vlan-id  {
                type uint16;
                description "Vlan ID";
            }
        }
    }

    rpc clear-mstp-port-dynamic-mac-address-table {
        description "Use this attribute clear dynamic mac address table entries for given
                    MSTP instance";
        input  {
            leaf interface-name  {
                type string {
                    length "1..33";
                }
                mandatory true;
                description "The textual name of the interface";
            }
            leaf instance-id  {
                type uint32;
                mandatory true;
                description "MSTP instance ID";
            }
            leaf bridge-id  {
                type string {
                    pattern "([1-9]|[12][0-9]|3[0-2])";
                }
                mandatory true;
                description "Bridge group number";
            }
        }
    }

}
