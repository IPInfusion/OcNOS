/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-l2vpn-vpls.yang
*
*/

module ipi-l2vpn-vpls {

    yang-version 1.1;

    namespace   "http://www.ipinfusion.com/yang/ocnos/ipi-l2vpn-vpls";

    prefix "ipi-l2vpn-vpls";

    import cml-data-types {
        prefix cml-data-types;
    }

    import ipi-vpls-types {
        prefix ipi-vpls-types;
    }

    import ietf-inet-types {
        prefix inet;
    }

    import ipi-interface {
        prefix ipi-interface;
    }

    import ipi-network-instance {
        prefix ipi-network-instance;
    }

    import ipi-mpls {
        prefix ipi-mpls;
    }

    import ipi-qos {
        prefix ipi-qos;
    }

    import feature-list {
        prefix feature-list;
    }

    organization
        "IP Infusion Inc.";

    contact
        "Address: 3965 Freedom Circle, Suite 200, Santa Clara, CA 95054
         Phone: +1 408-400-1900
         E-mail: support@ipinfusion.com
         Web: http://www.ipinfusion.com/";

    description
        "YANG version of the ipi-l2vpn-vpls";


    revision "2020-11-30" {
        description "Initial Version";
        reference "Initial Version";
    }

    grouping vpls-service-template-mapping-top {
        description
            "Top level Grouping for service template mapping to VPLS on AC
                        interface";

        list service-template-mapping {
            key "interface-name vpls-name service-template-name";
            description
                "Configuration data for Service Template mapping to VPLS on an
                            interface";
            leaf interface-name  {
                type  leafref {
                    path  "../config/interface-name";
                }
                description "This attribute specifies the attachment circuit interface to which the
                            service template is applied";
            } // END of interface-name definition.

            leaf vpls-name  {
                type  leafref {
                    path  "../config/vpls-name";
                }
                description "Specify VPLS instance name";
            } // END of vpls-name definition.

            leaf service-template-name  {
                type  leafref {
                    path  "../config/service-template-name";
                }
                description "Specify Customer service template name to bind to this Attachment
                            circuit";
            } // END of service-template-name definition.

            container config {
                description
                    "Configuration data for Attachment-Circuit";
                uses vpls-service-template-mapping-config;
            } // END of config-container definition.
            container state {
                config false;
                description
                    "Operation state data for Attachment-Circuit";
                uses vpls-service-template-mapping-config;
            } // END of state-container definition.
            uses virtual-circuit-quality-of-service-top;
        } // End of service-template-mapping-list
    } // END of vpls-service-template-mapping-top definition.
    grouping vpls-service-template-mapping-config {
        description
            "Grouping for VPLS Attachment-Circuit configuration";
        leaf interface-name  {
            type  leafref {
                path  "/ipi-interface:interfaces/ipi-interface:interface/ipi-interface:name";
            }
            description "This attribute specifies the attachment circuit interface to which the
                        service template is applied";
        } // END of interface-name definition.

        leaf service-template-name  {
            type  leafref {
                path  "/ipi-mpls:mpls/ipi-mpls:l2vpn/ipi-mpls:customer-service-template/ipi-mpls:config/ipi-mpls:name";
            }
            description "Specify Customer service template name to bind to this Attachment
                        circuit";
        } // END of service-template-name definition.

        leaf vpls-name  {
            type  string {
                length "1..max";
                pattern "[^?' =,>|]+";
            }
            description "Specify VPLS instance name";
        } // END of vpls-name definition.

        leaf admin-status  {
            type  ipi-vpls-types:vpls_ac_admin_status_t;
            description "Specify admin status for VPLS AC";
        } // END of admin-status definition.

        leaf attachment-circuit-description  {
            type  cml-data-types:cml_line_t;
            description "Specify description of VPLS AC";
        } // END of attachment-circuit-description definition.

        leaf mac-learning  {
            type  ipi-vpls-types:vpls_mac_learning_t;
            description "Specify mac-learning for VPLS AC";
        } // END of mac-learning definition.

        leaf allow-layer2-bridge-pdu  {
            type  empty;
            description "Specify allowed L2 packts through VPLS network";
        } // END of allow-layer2-bridge-pdu definition.

    } // END of vpls-service-template-mapping-config definition.
    grouping virtual-circuit-quality-of-service-top {
        description
            "Top level grouping for VPLS QOS Profile on AC";

        list quality-of-service-profile {
        when " /ipi-qos:qos/ipi-qos:global/ipi-qos:map-profile/ipi-qos:cos-to-queue-profiles/ipi-qos:cos-to-queue-profile/ipi-qos:name  or /ipi-qos:qos/ipi-qos:global/ipi-qos:map-profile/ipi-qos:queue-color-to-cos-profiles/ipi-qos:queue-color-to-cos-profile/ipi-qos:name ";
            if-feature feature-list:HAVE_QOS;
            key "profile-type profile-name";
            description
                "Configuration VPLS QOS profile on AC";
            leaf profile-type  {
                type  leafref {
                    path  "../config/profile-type";
                }
                description "Specify map profile type for VPLS";
            } // END of profile-type definition.

            leaf profile-name  {
                type  leafref {
                    path  "../config/profile-name";
                }
                description "Specify profile name for map profile";
            } // END of profile-name definition.

            container config {
                description
                    "Configuration data for Attachment-Circuit";
                uses vpls-quality-of-service-config;
            } // END of config-container definition.
            container state {
                config false;
                description
                    "Operation state data for Attachment-Circuit";
                uses vpls-quality-of-service-config;
            } // END of state-container definition.
        } // End of quality-of-service-profile-list
    } // END of virtual-circuit-quality-of-service-top definition.
    grouping vpls-quality-of-service-config {
        description
            "Grouping for       VPLS QOS Profile Configuration attributes";
        leaf profile-type  {
            type  ipi-vpls-types:vpls_qos_map_profile_type_t;
            description "Specify map profile type for VPLS";
        } // END of profile-type definition.

        leaf profile-name  {
            type  string {
                length "1..max";
                pattern "[^?' =,>|]+";
            }
            description "Specify profile name for map profile";
        } // END of profile-name definition.

    } // END of vpls-quality-of-service-config definition.
    grouping vpls-quality-of-service-top {
        description
            "Top level grouping for VPLS QOS Profile on AC";

        list quality-of-service-profile {
        when " /ipi-qos:qos/ipi-qos:global/ipi-qos:map-profile/ipi-qos:cos-to-queue-profiles/ipi-qos:cos-to-queue-profile/ipi-qos:name  or /ipi-qos:qos/ipi-qos:global/ipi-qos:map-profile/ipi-qos:queue-color-to-cos-profiles/ipi-qos:queue-color-to-cos-profile/ipi-qos:name ";
            if-feature feature-list:HAVE_QOS;
            key "profile-type profile-name";
            description
                "Configuration VPLS QOS profile on AC";
            leaf profile-type  {
                type  leafref {
                    path  "../config/profile-type";
                }
                description "Specify map profile type for VPLS";
            } // END of profile-type definition.

            leaf profile-name  {
                type  leafref {
                    path  "../config/profile-name";
                }
                description "Specify profile name";
            } // END of profile-name definition.

            container config {
                description
                    "Configuration data for Attachment-Circuit";
                uses vpls-quality-of-service-config;
            } // END of config-container definition.
            container state {
                config false;
                description
                    "Operation state data for Attachment-Circuit";
                uses vpls-quality-of-service-config;
            } // END of state-container definition.
        } // End of quality-of-service-profile-list
    } // END of vpls-quality-of-service-top definition.
    grouping vpls-static-vpls-top {
        description
            "Top level Grouping for Static Forwarding for VPLS";

        list static-vpls {
        when " /ipi-network-instance:network-instances/ipi-network-instance:network-instance/ipi-l2vpn-vpls:vpls-instance/ipi-l2vpn-vpls:vpls-peers/ipi-l2vpn-vpls:vpls-peer/ipi-l2vpn-vpls:config/ipi-l2vpn-vpls:peer-type = '1' ";
            key "vpls-identifier peer-address";
            description
                "List for Static VPLS Forwarding Information Base";
            leaf vpls-identifier  {
                type  leafref {
                    path  "/ipi-network-instance:network-instances/ipi-network-instance:network-instance/vpls-instance/config/vpls-identifier";
                }
                description "VPLS Instance Identifier for static VPLS signaling";
            } // END of vpls-identifier definition.

            leaf peer-address  {
                type  leafref {
                    path  "/ipi-network-instance:network-instances/ipi-network-instance:network-instance/vpls-instance/vpls-peers/vpls-peer/config/peer-address";
                }
                description "Specify VPLS peer IPv4 address";
            } // END of peer-address definition.

            container config {
                description
                    "Configuration data for Static VPLS";
                uses vpls-static-forwarding-config;
            } // END of config-container definition.
            container state {
                config false;
                description
                    "Operation state data for Static VPLS";
                uses vpls-static-forwarding-config;
            } // END of state-container definition.
        } // End of static-vpls-list
    } // END of vpls-static-vpls-top definition.
    grouping vpls-static-hvpls-top {
        description
            "Top level Grouping for Static Forwarding for HVPLS";

        list static-hierarchical-vpls {
        when " /ipi-network-instance:network-instances/ipi-network-instance:network-instance/ipi-l2vpn-vpls:vpls-instance/ipi-l2vpn-vpls:vpls-peers/ipi-l2vpn-vpls:vpls-peer/ipi-l2vpn-vpls:config/ipi-l2vpn-vpls:peer-type = '1' ";
            key "vpls-identifier spoke-pseudowire-name";
            description
                "List for Configuration data of Static Forwarding for HVPLS";
            leaf vpls-identifier  {
                type  leafref {
                    path  "/ipi-network-instance:network-instances/ipi-network-instance:network-instance/vpls-instance/config/vpls-identifier";
                }
                description "Specify VPLS identifier";
            } // END of vpls-identifier definition.

            leaf spoke-pseudowire-name  {
                type  leafref {
                    path  "/ipi-network-instance:network-instances/ipi-network-instance:network-instance/vpls-instance/spoke-pseudowire/config/pseudowire-name";
                }
                description "Specify spoke virtual circuit name";
            } // END of spoke-pseudowire-name definition.

            container config {
                description
                    "Configuration data for Static HVPLS";
                uses vpls-static-forwarding-config;
            } // END of config-container definition.
            container state {
                config false;
                description
                    "Operation state data for Static HVPLS";
                uses vpls-static-forwarding-config;
            } // END of state-container definition.
        } // End of static-hierarchical-vpls-list
    } // END of vpls-static-hvpls-top definition.
    grouping vpls-static-forwarding-config {
        description
            "Grouping for VPLS static forwarding configuration attributes";
        leaf in-label  {
            type  uint32 {
                 range "16..15999"  {
                    description "In-coming Label";
                 }
            }
            mandatory true;
            description "Specify in-coming label for VPLS static forwarding";
        } // END of in-label definition.

        leaf out-label  {
            type  uint32 {
                 range "16..15999"  {
                    description "Out-going Label <16-15999>";
                 }
            }
            mandatory true;
            description "Specify out going label for VPLS static forwarding";
        } // END of out-label definition.

        leaf out-interface-name  {
            type  string {
                length "1..max";
                pattern "[^?' =,>|]+";
            }
            mandatory true;
            description "Specify provider facing interface name";
        } // END of out-interface-name definition.

    } // END of vpls-static-forwarding-config definition.
    grouping vpls-instance-global-config {
        description
            "Grouping for VPLS Instance global configuration  attributes";
        leaf vpls-identifier  {
            type  uint32 {
                 range "1..4294967295"  {
                    description "Identifying value for VPLS";
                 }
            }
            mandatory true;
            description "Specify VPLS identifier";
        } // END of vpls-identifier definition.

        leaf service-transport-identifier  {
            type  ipi-vpls-types:vpls_svc_tpid_t;
            description "Specify service transport identifier";
        } // END of service-transport-identifier definition.

        leaf maximum-transmission-unit  {
            type  uint16 {
                 range "576..65535"  {
                    description "Identifying value for VPLS";
                 }
            }
            default "1500";
            description "Set the Maximum Transmission Unit (MTU) size for a given VPLS
                        instance. This size is signaled to peer VPLS routers";
        } // END of maximum-transmission-unit definition.

        leaf vpls-description  {
            type  cml-data-types:cml_line_t;
            default "NULL";
            description "Specify a description for this VPLS instance";
        } // END of vpls-description definition.

        leaf control-word  {
            type  empty;
            description "Control Word for VPLS instance";
        } // END of control-word definition.

        leaf mac-learning-disable  {
            type  empty;
            description "Specify mac learning disable for VPLS instance";
        } // END of mac-learning-disable definition.

        leaf mac-learning-limit  {
            if-feature feature-list:NOT_HAVE_TRIDENT2;
            if-feature feature-list:NOT_HAVE_TRIDENT2PLUS;
            type  uint32 {
                 range "5..32767"  {
                    description "Mac learning limit value";
                 }
            }
            default "32767";
            description "Specify mac learning limit";
        } // END of mac-learning-limit definition.

        leaf attachment-circuit-group-name  {
            type  leafref {
                path  "/ipi-mpls:mpls/ipi-mpls:l2vpn/ipi-mpls:access-circuit-group/ipi-mpls:config/ipi-mpls:group-name";
            }
            description "Specify ac-group name";
        } // END of attachment-circuit-group-name definition.

    } // END of vpls-instance-global-config definition.
    grouping vpls-spoke-pseudowire-top {
        description
            "Top level grouping for H-VPLS spoke-pseudowire";

        list spoke-pseudowire {
            key "pseudowire-name";
            description
                "Spoke Pseudowire list for H-VPLS";
            leaf pseudowire-name  {
                type  leafref {
                    path  "../config/pseudowire-name";
                }
                description "Specify pseudowire name to be added";
            } // END of pseudowire-name definition.

            container config {
                description
                    "Configuration data for spoke-pseudowire";
                uses vpls-spoke-pseudowire-config;
            } // END of config-container definition.
            container state {
                config false;
                description
                    "Operation state data for spoke-pseudowire";
                uses vpls-spoke-pseudowire-config;
            } // END of state-container definition.
        } // End of spoke-pseudowire-list
    } // END of vpls-spoke-pseudowire-top definition.
    grouping vpls-spoke-pseudowire-config {
        description
            "Grouping for H-VPLS spoke-pseudowire configuration attributes";
        leaf pseudowire-name  {
            type  string {
                length "1..max";
                pattern "[^?' =,>|]+";
            }
            description "Specify pseudowire name to be added";
        } // END of pseudowire-name definition.

        leaf pseudowire-type  {
            type  ipi-vpls-types:vpls_vc_spoke_type_t;
            default "ethernet";
            description "Specify pseudowire type";
        } // END of pseudowire-type definition.

    } // END of vpls-spoke-pseudowire-config definition.
    grouping vpls-static-mac-address-top {
        description
            "Top level grouping for H-VPLS spoke-pseudowire";

        list static-mac-address {
            key "mac-address interface-name";
            description
                "Static Mac Address list for VPLS";
            leaf mac-address  {
                type  leafref {
                    path  "../config/mac-address";
                }
                description "Specify mac address";
            } // END of mac-address definition.

            leaf interface-name  {
                type  leafref {
                    path  "/ipi-interface:interfaces/ipi-interface:interface/ipi-interface:name";
                }
                description "Specify customer edge egress interface name for static MAC entry";
            } // END of interface-name definition.

            container config {
                description
                    "Configuration data for static mac-address";
                uses vpls-static-mac-address-config;
            } // END of config-container definition.
            container state {
                config false;
                description
                    "Operation state data for static mac-address";
                uses vpls-static-mac-address-config;
            } // END of state-container definition.
        } // End of static-mac-address-list
    } // END of vpls-static-mac-address-top definition.
    grouping vpls-static-mac-address-config {
        description
            "Grouping for static mac-address configuration attributes";
        leaf mac-address  {
            type  string {
                length "1..max";
                pattern "[0-9a-fA-F]{4}\\.[0-9a-f]{4}\\.[0-9a-f]{4}";
            }
            description "Specify mac address";
        } // END of mac-address definition.

        leaf vlan-identifier  {
            type  uint16 {
                 range "1..4094"  {
                    description "Vlan ID";
                 }
            }
            description "Specify customer facing egress VLAN identifier for static MAC entry";
        } // END of vlan-identifier definition.

    } // END of vpls-static-mac-address-config definition.
    grouping vpls-peer-top {
        description
            "Top level grouping for VPLS Peer";
        container vpls-peers {
            description
                "Top level container for vpls peer";

            list vpls-peer {
            when " /ipi-network-instance:network-instances/ipi-network-instance:network-instance/ipi-l2vpn-vpls:vpls-instance/ipi-l2vpn-vpls:vpls-peers/ipi-l2vpn-vpls:vpls-peer/ipi-l2vpn-vpls:config/ipi-l2vpn-vpls:peer-type = '1'  or /ipi-network-instance:network-instances/ipi-network-instance:network-instance/ipi-l2vpn-vpls:vpls-instance/ipi-l2vpn-vpls:vpls-peers/ipi-l2vpn-vpls:config/ipi-l2vpn-vpls:signaling-protocol-ldp ";
                key "peer-address";
                description
                    "Configuration data for VPLS peer";
                leaf peer-address  {
                    type  leafref {
                        path  "../config/peer-address";
                    }
                    description "Specify VPLS peer address";
                } // END of peer-address definition.

                container config {
                    description
                        "Configuration data for vpls peer";
                    uses vpls-peer-config;
                } // END of config-container definition.
                container state {
                    config false;
                    description
                        "Operation state data for vpls peer";
                    uses vpls-peer-config;
                } // END of state-container definition.
                uses vpls-peer-fec129-top;
            } // End of vpls-peer-list
            container config {
                presence "Enable Ldp signaling for VPLS";
                description
                    "Global Configuration data for vpls peers";
                uses vpls-global-peer-config;
            } // END of config-container definition.
            container state {
                config false;
                description
                    "Global Operation state data for vpls peers";
                uses vpls-global-peer-config;
            } // END of state-container definition.
        } // END of vpls-peers-container definition.
    } // END of vpls-peer-top definition.
    grouping vpls-global-peer-config {
        description
            "Grouping for global vpls peer configuration attributes";
        leaf signaling-protocol-ldp  {
            when " /ipi-network-instance:network-instances/ipi-network-instance:network-instance/ipi-l2vpn-vpls:vpls-instance/ipi-l2vpn-vpls:vpls-peers/ipi-l2vpn-vpls:vpls-peer/ipi-l2vpn-vpls:config/ipi-l2vpn-vpls:peer-type != '1'  + not(/ipi-network-instance:network-instances/ipi-network-instance:network-instance/ipi-l2vpn-vpls:vpls-instance/ipi-l2vpn-vpls:bgp-signaling/ipi-l2vpn-vpls:config/ipi-l2vpn-vpls:signaling-protocol-bgp) ";
            type  empty;
            mandatory true;
            description "Specify protocol used for signaling is ldp";
        } // END of signaling-protocol-ldp definition.

        leaf disable-mac-withdrawal  {
            when " /ipi-network-instance:network-instances/ipi-network-instance:network-instance/ipi-l2vpn-vpls:vpls-instance/ipi-l2vpn-vpls:vpls-peers/ipi-l2vpn-vpls:config/ipi-l2vpn-vpls:signaling-protocol-ldp ";
            type  empty;
            description "Specify mac address withdrawal disable";
        } // END of disable-mac-withdrawal definition.

        leaf vpls-encapsulation-type  {
            type  ipi-vpls-types:vpls_vc_type_t;
            description "Specify encapsulation type";
        } // END of vpls-encapsulation-type definition.

    } // END of vpls-global-peer-config definition.
    grouping vpls-peer-config {
        description
            "Grouping for vpls peer configuration attributes";
        leaf peer-address  {
            type  inet:ipv4-address;
            description "Specify VPLS peer address";
        } // END of peer-address definition.

        leaf tunnel-identifier  {
            type  string {
                length "1..max";
                pattern "[^?' =,>|]+";
            }
            description "Specify tunnel identifier value";
        } // END of tunnel-identifier definition.

        leaf peer-type  {
            when " not(/ipi-network-instance:network-instances/ipi-network-instance:network-instance/ipi-l2vpn-vpls:vpls-instance/ipi-l2vpn-vpls:vpls-peers/ipi-l2vpn-vpls:config/ipi-l2vpn-vpls:signaling-protocol-ldp ) + not(/ipi-network-instance:network-instances/ipi-network-instance:network-instance/ipi-l2vpn-vpls:vpls-instance/ipi-l2vpn-vpls:bgp-signaling/ipi-l2vpn-vpls:config/ipi-l2vpn-vpls:signaling-protocol-bgp) ";
            type  ipi-vpls-types:vpls_peer_type_t;
            default "manual";
            description "Specify that peer type is manual and  no signaling is used to set-up
                        the Virtual Circuit";
        } // END of peer-type definition.

    } // END of vpls-peer-config definition.
    grouping vpls-peer-fec129-top {
        description
            "Top level grouping for Fec129 (Genfec) VPLS Peer";

        list fec129 {
        when " /ipi-network-instance:network-instances/ipi-network-instance:network-instance/ipi-l2vpn-vpls:vpls-instance/ipi-l2vpn-vpls:vpls-peers/ipi-l2vpn-vpls:config/ipi-l2vpn-vpls:signaling-protocol-ldp ";
            key "attachment-group-identifier source-attachment-individual-identifier target-attachment-individual-identifier";
            max-elements 1;
            description
                "Configuration data for VPLS genfec peer";
            leaf attachment-group-identifier  {
                type  leafref {
                    path  "../config/attachment-group-identifier";
                }
                description "Specify the Address Group Identifier";
            } // END of attachment-group-identifier definition.

            leaf source-attachment-individual-identifier  {
                type  leafref {
                    path  "../config/source-attachment-individual-identifier";
                }
                description "Specify the Source Attachment Individual Identifier";
            } // END of source-attachment-individual-identifier definition.

            leaf target-attachment-individual-identifier  {
                type  leafref {
                    path  "../config/target-attachment-individual-identifier";
                }
                description "Specify the Target Attachment Individual Identifier";
            } // END of target-attachment-individual-identifier definition.

            container config {
                description
                    "Configuration data for vpls peer";
                uses vpls-peer-fec129-config;
            } // END of config-container definition.
            container state {
                config false;
                description
                    "Operation state data for vpls peer";
                uses vpls-peer-fec129-config;
            } // END of state-container definition.
        } // End of fec129-list
    } // END of vpls-peer-fec129-top definition.
    grouping vpls-peer-fec129-config {
        description
            "Configuration attributes for genfec based VPLS peer";
        leaf attachment-group-identifier  {
            when " not(/ipi-network-instance:network-instances/ipi-network-instance:network-instance/ipi-l2vpn-vpls:vpls-instance/ipi-l2vpn-vpls:vpls-peers/ipi-l2vpn-vpls:config/ipi-l2vpn-vpls:signaling-protocol-ldp) ";
            type  string {
                length "1..max";
                pattern "[^?' =,>|]+";
            }
            description "Specify the Address Group Identifier";
        } // END of attachment-group-identifier definition.

        leaf source-attachment-individual-identifier  {
            when " not(/ipi-network-instance:network-instances/ipi-network-instance:network-instance/ipi-l2vpn-vpls:vpls-instance/ipi-l2vpn-vpls:vpls-peers/ipi-l2vpn-vpls:config/ipi-l2vpn-vpls:signaling-protocol-ldp) ";
            type  string {
                length "1..max";
                pattern "[^?' =,>|]+";
            }
            description "Specify the Source Attachment Individual Identifier";
        } // END of source-attachment-individual-identifier definition.

        leaf target-attachment-individual-identifier  {
            when " not(/ipi-network-instance:network-instances/ipi-network-instance:network-instance/ipi-l2vpn-vpls:vpls-instance/ipi-l2vpn-vpls:vpls-peers/ipi-l2vpn-vpls:config/ipi-l2vpn-vpls:signaling-protocol-ldp) ";
            type  string {
                length "1..max";
                pattern "[^?' =,>|]+";
            }
            description "Specify the Target Attachment Individual Identifier";
        } // END of target-attachment-individual-identifier definition.

        leaf tunnel-identifier  {
            when " not(/ipi-network-instance:network-instances/ipi-network-instance:network-instance/ipi-l2vpn-vpls:vpls-instance/ipi-l2vpn-vpls:vpls-peers/ipi-l2vpn-vpls:config/ipi-l2vpn-vpls:signaling-protocol-ldp) ";
            type  string {
                length "1..max";
                pattern "[^?' =,>|]+";
            }
            description "Specify tunnel id value";
        } // END of tunnel-identifier definition.

    } // END of vpls-peer-fec129-config definition.
    grouping vpls-bgp-top {
        description
            "Top level grouping for BGP VPLS";
        container bgp-signaling {
            description
                "Top level container for BGP vpls";
            container config {
                when " /ipi-network-instance:network-instances/ipi-network-instance:network-instance/ipi-l2vpn-vpls:vpls-instance/ipi-l2vpn-vpls:vpls-peers/ipi-l2vpn-vpls:vpls-peer/ipi-l2vpn-vpls:config/ipi-l2vpn-vpls:peer-type != '1'  + not(/ipi-network-instance:network-instances/ipi-network-instance:network-instance/ipi-l2vpn-vpls:vpls-instance/ipi-l2vpn-vpls:vpls-peers/ipi-l2vpn-vpls:config/ipi-l2vpn-vpls:signaling-protocol-ldp) ";
                presence "Enable BGP VPLS";
                description
                    "Configuration data for bgp vpls";
                uses vpls-bgp-config;
            } // END of config-container definition.
            container state {
                config false;
                description
                    "Operation state data for bgp vpls";
                uses vpls-bgp-config;
            } // END of state-container definition.
        } // END of bgp-signaling-container definition.
    } // END of vpls-bgp-top definition.
    grouping vpls-bgp-config {
        description
            "Grouping for BGP VPLS Configuration attributes";
        leaf signaling-protocol-bgp  {
            type  empty;
            mandatory true;
            description "Specify protocol used for signaling is bgp";
        } // END of signaling-protocol-bgp definition.

        leaf vpls-edge-identifier  {
            type  int32 {
                 range "1..1000"  {
                    description "VE ID Range";
                 }
            }
            description "Specify VPLS edge identifier value";
        } // END of vpls-edge-identifier definition.

    } // END of vpls-bgp-config definition.

    grouping  vpls-grouping {
    description
        "VPLS global level container";
    container vpls {
        description
            "VPLS global level container";
        container attachment-circuit {
            description
                "VPLS-Attachment Circuit container";
            uses vpls-service-template-mapping-top;
        } // END of attachment-circuit-container definition.
        container static-forwarding {
            description
                "Static VPLS Forwarding Information Base container";
            uses vpls-static-vpls-top;
            uses vpls-static-hvpls-top;
        } // END of static-forwarding-container definition.
    } // END of vpls-container definition.
    } // END of vpls-grouping definition.

    grouping  vpls-instance-grouping {
    description
        "Top level list for VPLS-Instance";
    container vpls-instance {
        description
            "Top level list for VPLS-Instance";
        container config {
            presence "Create VPLS Instance";
            description
                "Configuration data for VPLS-Instance";
            uses vpls-instance-global-config;
        } // END of config-container definition.
        container state {
            config false;
            description
                "Operation state data for VPLS-Instance";
            uses vpls-instance-global-config;
        } // END of state-container definition.
        uses vpls-spoke-pseudowire-top;
        uses vpls-static-mac-address-top;
        uses vpls-peer-top;
        uses vpls-bgp-top;
        uses vpls-quality-of-service-top;
    } // END of vpls-instance-container definition.
    } // END of vpls-instance-grouping definition.

    uses vpls-grouping;
    augment /ipi-network-instance:network-instances/ipi-network-instance:network-instance {
    when " /ipi-network-instance:network-instances/ipi-network-instance:network-instance/ipi-l2vpn-vpls:vpls-instance/ipi-l2vpn-vpls:config/ipi-l2vpn-vpls:vpls-identifier + /ipi-network-instance:network-instances/ipi-network-instance:network-instance/ipi-network-instance:instance-type = 'vpls' ";
        description
            "Top level list for VPLS-Instance";
        uses vpls-instance-grouping;
    }


    rpc clear-mpls-vpls-name-statistics-port-type {
        description "Use this attribute to clear mpls vpls statistics by portType";
        input  {
            leaf port-type  {
                type ipi-vpls-types:vpls_port_type_t;
                mandatory true;
                description "Specify port type";
            }
            leaf port-circuit-name  {
                type string;
                mandatory true;
                description "Specify port circuit name";
            }
        }
    }

    rpc clear-mpls-vpls-name-statistics-network-port-peer {
        description "Use this attribute to clear mpls vpls statistics by network portType";
        input  {
            leaf port-circuit-name  {
                type string;
                mandatory true;
                description "Specify port circuit name";
            }
            leaf vc-circuit-type  {
                type ipi-vpls-types:vpls_peer_address_type_t;
                mandatory true;
                description "Specify peer VC circuit name";
            }
        }
    }

    rpc clear-mpls-vpls-name-statistics-network-port-spoke {
        description "Use this attribute to clear mpls vpls statistics by network portType";
        input  {
            leaf port-circuit-name  {
                type string;
                mandatory true;
                description "Specify port circuit name";
            }
            leaf vc-circuit-type  {
                type ipi-vpls-types:vpls_spoke_vc_type_t;
                mandatory true;
                description "Specify VC circuit name";
            }
        }
    }

    rpc clear-mpls-vpls-name-statistics-access-port {
        description "Use this attribute to clear mpls l2-circuit statistics by access
                    portType";
        input  {
            leaf port-circuit-name  {
                type string;
                mandatory true;
                description "Specify port circuit name";
            }
            leaf vc-interface-name  {
                type string;
                mandatory true;
                description "Specify ingress VC interface name";
            }
            leaf vc-access-type  {
                type ipi-vpls-types:vpls_mpls_access_type_t;
                mandatory true;
                description "Specify VC access type";
            }
        }
    }

    rpc clear-mpls-vpls-name-statistics {
        description "Use this attribute to clear vpls statistics";
        input  {
            leaf vpls-circuit-name  {
                type string;
                mandatory true;
                description "Specify VC circuit name";
            }
        }
    }

    rpc clear-mpls-vpls-mac-addresses-for-instance {
        description "Use this attribute to clear mpls vpls by NAME and mac_addresses";
        input  {
            leaf name  {
                type string;
                mandatory true;
                description "Specify VPLS instance name";
            }
        }
    }

    rpc clear-mpls-vpls-mac-addresses-all {
        description "Use this attribute to clear mpls vpls mac_addresses";
    }

}
