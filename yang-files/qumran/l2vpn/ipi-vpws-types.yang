/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-vpws-types.yang
*
*/

module ipi-vpws-types {

    yang-version 1.1;

    namespace   "http://www.ipinfusion.com/yang/ocnos/ipi-vpws-types";

    prefix "ipi-vpws-types";

    import ietf-inet-types {
        prefix inet;
        revision-date 2013-07-15;
    }

    organization
        "IP Infusion Inc.";

    contact
        "Address: 3965 Freedom Circle,        Suite 200, Santa Clara, CA 95054
         Phone: +1 408-400-1900
         E-mail: support@ipinfusion.com
         Web: http://www.ipinfusion.com/";

    description
        "Datatypes for VPWS Datamodel";


    revision "2020-11-25" {
        description "Initial Version";
        reference "Initial Version";
    }



    typedef  vpws_ip_addr_t {
        type union {
            type inet:ipv4-address {

            }
            type inet:ipv6-address {

            }
        }
        description "type definition for VPWS_IP_ADDR_T";
    }

    typedef  vpws_tunnel_direction_type_t {
        type enumeration {
            enum forward {
                value 0;
                description "Tunnel Direction - Forward tunnel identifier - Default Value";
            }
            enum reverse {
                value 1;
                description "Tunnel Direction - Reverse tunnel identifier";
            }
        }
        description "type definition for VPWS_TUNNEL_DIRECTION_TYPE_T";
    }

    typedef  vpws_svc_tpid_t {
        type enumeration {
            enum dot1.q {
                value 33024;
                description "Set tpid value as 0x8100";
            }
            enum dot1.ad {
                value 34984;
                description "Set tpid value as 0x88a8";
            }
            enum 0x9100 {
                value 37120;
                description "Set tpid value as 0x9100";
            }
        }
        description "type definition for VPWS_SVC_TPID_T";
    }

    typedef  vpws_mpls_tpid_t {
        type enumeration {
            enum 88a8 {
                value 34984;
                description "Set tpid value as 88a8";
            }
            enum 9100 {
                value 37120;
                description "Set tpid value as 9100";
            }
        }
        description "type definition for VPWS_MPLS_TPID_T";
    }

    typedef  vpws_mpls_vcmode_t {
        type enumeration {
            enum standby {
                value 2;
                description "VC runtime Standby mode";
            }
            enum revertive {
                value 4;
                description "VC redundancy revertive mode";
            }
        }
        description "type definition for VPWS_MPLS_VCMODE_T";
    }

    typedef  vpws_mpls_if_vctype_t {
        type enumeration {
            enum hdlc {
                value 6;
                description "Hdlc";
            }
            enum ppp {
                value 7;
                description "Point-to-Point";
            }
            enum tdm-E1 {
                value 17;
                description "TDM - E1 line";
            }
            enum tdm-T1 {
                value 18;
                description "TDM - T1 line";
            }
            enum tdm-E3 {
                value 19;
                description "TDM - E3 line";
            }
            enum tdm-T3 {
                value 20;
                description "TDM - T3 line";
            }
        }
        description "type definition for VPWS_MPLS_IF_VCTYPE_T";
    }

    typedef  vpws_mpls_vclinkmode_t {
        type enumeration {
            enum primary {
                value 0;
                description "Primary Link";
            }
            enum secondary {
                value 16;
                description "Secondary Link - Will not be activated unless primary fails";
            }
        }
        description "type definition for VPWS_MPLS_VCLINKMODE_T";
    }

    typedef  vpws_mpls_vc_admin_status_t {
        type enumeration {
            enum down {
                value 0;
                description "VPWS_ADMIN_DOWN";
            }
            enum up {
                value 1;
                description "VPWS_ADMIN_UP";
            }
        }
        description "type definition for VPWS_MPLS_VC_ADMIN_STATUS_T";
    }

    typedef  vpws_mpls_vc_owner_t {
        type enumeration {
            enum unknown {
                value 1;
                description "MPLS_UNKNOWN";
            }
            enum other {
                value 2;
                description "MPLS_OTHER";
            }
            enum snmp {
                value 3;
                description "MPLS_SNMP";
            }
            enum ldp {
                value 4;
                description "MPLS_LDP";
            }
            enum rsvp {
                value 6;
                description "MPLS_RSVP";
            }
            enum bgp {
                value 8;
                description "MPLS_OTHER_BGP";
            }
            enum cli {
                value 9;
                description "MPLS_OTHER_CLI";
            }
            enum ldp-vc {
                value 10;
                description "MPLS_OTHER_LDP_VC";
            }
        }
        description "type definition for VPWS_MPLS_VC_OWNER_T";
    }

    typedef  vpws_mpls_mapping_dir_t {
        type enumeration {
            enum psn-bound {
                value 1;
                description "PSNBOUND";
            }
            enum from-psn {
                value 2;
                description "FROMPSN";
            }
        }
        description "type definition for VPWS_MPLS_MAPPING_DIR_T";
    }

    typedef  vpws_mpls_pw_status_t {
        type enumeration {
            enum forwarding {
                value 0;
                description "Pseudowire Forwarding";
            }
            enum not-forwarding {
                value 1;
                description "Pseudowire not Forwarding";
            }
            enum ac-ingress-rx-fault {
                value 2;
                description "Pseudowire Ingress AC Fault";
            }
            enum ac-egress-tx-fault {
                value 4;
                description "Pseudowire Egress AC Fault";
            }
            enum psn-ingress-rx-fault {
                value 8;
                description "Pseudowire Ingress PSN Fault";
            }
            enum psn-egress-tx-fault {
                value 16;
                description "Pseudowire Engress PSN Fault";
            }
            enum standby {
                value 32;
                description "Pseudowire Standby";
            }
            enum request-switchover {
                value 64;
                description "Pseudowire switchover requested";
            }
        }
        description "type definition for VPWS_MPLS_PW_STATUS_T";
    }

    typedef  vpws_mpls_pw_state_t {
        type enumeration {
            enum unknown {
                value 0;
                description "State Unknown";
            }
            enum down {
                value 1;
                description "PW Down";
            }
            enum active {
                value 2;
                description "PW Active";
            }
            enum complete {
                value 3;
                description "PW Complete";
            }
            enum up {
                value 4;
                description "PW Up";
            }
        }
        description "type definition for VPWS_MPLS_PW_STATE_T";
    }

    typedef  vpws_mpls_pw_type_t {
        type enumeration {
            enum eth-vlan {
                value 4;
                description "Eth-Vlan";
            }
            enum ethernet {
                value 5;
                description "Ethernet";
            }
            enum hdlc {
                value 6;
                description "Hdlc";
            }
            enum ppp {
                value 7;
                description "Point-to-Point";
            }
            enum tdm-E1 {
                value 17;
                description "TDM - E1 line";
            }
            enum tdm-T1 {
                value 18;
                description "TDM - T1 line";
            }
            enum tdm-E3 {
                value 19;
                description "TDM - E3 line";
            }
            enum tdm-T3 {
                value 20;
                description "TDM - T3 line";
            }
        }
        description "type definition for VPWS_MPLS_PW_TYPE_T";
    }

    typedef  vpws_mpls_pw_mode_t {
        type enumeration {
            enum standby {
                value 0;
                description "PW-STANDBY";
            }
            enum active {
                value 1;
                description "PW-ACTIVE";
            }
        }
        description "type definition for VPWS_MPLS_PW_MODE_T";
    }

    typedef  vpws_mpls_port_type_t {
        type enumeration {
            enum access-port {
                value 1;
                description "Access interface statistics counters";
            }
            enum network-port {
                value 2;
                description "Network interface statistics counters";
            }
        }
        description "type definition for VPWS_MPLS_PORT_TYPE_T";
    }

}
