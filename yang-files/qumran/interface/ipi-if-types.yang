/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-if-types.yang
*
*/

module ipi-if-types {

    yang-version 1.1;

    namespace   "http://www.ipinfusion.com/yang/ocnos/ipi-if-types";

    prefix "ipi-if-types";

    import ietf-inet-types {
        prefix inet;
        revision-date 2013-07-15;
    }

    organization
        "IP Infusion Inc.";

    contact
        "Address: 3965 Freedom Circle, Suite 200, Santa Clara, CA 95054
         Phone: +1 408-400-1900
         E-mail: support@ipinfusion.com
         Web: http://www.ipinfusion.com/";

    description
        "YANG version of the ipi-if-types";


    revision "2021-03-16" {
        description "Modified IF_SUBIF_ENCAP_T, IF_HW_TYPE_T, IF_SUBIF_L2_VLAN_ACTIONTYPE_T and IF_SUBIF_REWRITE_POP_TYPE_T for subinterface remodelling";
        reference " 0.5.0.";
    }

    revision "2021-01-27" {
        description "Removed datatype IF_MONITOR_TYPE_T";
        reference " 0.4.0.";
    }

    revision "2020-12-15" {
        description "Change to have data-types in lower case instead of camel case";
        reference " 0.3.0.";
    }

    revision "2020-11-13" {
        description "Updated datatype as part of extended interface module, removed speed values for auto-neg, moved datatype IF_LACP_PSC_T to LACP data model";
        reference " 0.2.0.";
    }

    revision "2020-07-15" {
        description "Initial Version";
        reference " 0.1.0.";
    }



    typedef  if_interface_oper_status_t {
        type enumeration {
            enum up {
                value 1;
                description "ready to pass packets";
            }
            enum down {
                value 2;
                description "down state";
            }
            enum testing {
                value 3;
                description "in some test mode";
            }
            enum unknown {
                value 4;
                description "status can not be determined for some reason";
            }
            enum dormant {
                value 5;
                description "not in a condition to pass packets but is instead in a pending state waiting for some external event. ";
            }
            enum notPresent {
                value 6;
                description "some component is missing";
            }
            enum lowerLayerDown {
                value 7;
                description "down due to state of lower-layer interface(s)";
            }
        }
        description "datatype for operational state of the interface";
    }

    typedef  if_iface_prop_t {
        type bits {
            bit interface_active {
                position 0;
                description "active interface";
            }
            bit dhcp_addr {
                position 15;
                description "IPV4 DHCP client is enabled";
            }
            bit dhcp6_addr {
                position 16;
                description "IPV6 DHCP IA-NA client is enabled";
            }
            bit Breakout_control_port {
                position 20;
                description "Breakout Control Port (Active)";
            }
            bit Bundle_control_port {
                position 21;
                description "Bundle Control Port (Active)";
            }
            bit Breakout_enable {
                position 22;
                description "port breakout enable";
            }
            bit Bundle_enable {
                position 23;
                description "port bundle enable";
            }
            bit Sbuport_inactive {
                position 24;
                description "Non Control Port (InActive)";
            }
        }
        description "datatype for interface mapping properties";
    }

    typedef  if_duplex_t {
        type enumeration {
            enum half {
                value 0;
                description "set half duplex";
            }
            enum full {
                value 1;
                description "set full duplex";
            }
        }
        description "datatype for interface duplex-mode";
    }

    typedef  if_interface_admin_status_t {
        type enumeration {
            enum up {
                value 1;
                description "ready to pass packets";
            }
            enum down {
                value 2;
                description "down state";
            }
            enum testing {
                value 3;
                description "in some test mode";
            }
        }
        description "datatype for interface admin status";
    }

    typedef  if_iana_if_type_t {
        type enumeration {
            enum other {
                value 1;
                description "other";
            }
            enum regular1822 {
                value 2;
                description "regular1822";
            }
            enum hdh1822 {
                value 3;
                description "hdh1822";
            }
            enum ddnX25 {
                value 4;
                description "ddnX25";
            }
            enum rfc877x25 {
                value 5;
                description "rfc877x25 ";
            }
            enum ethernetCsmacd {
                value 6;
                description "ethernetCsmacd";
            }
        }
        description "datatype for interface type";
    }

    typedef  if_hw_type_t {
        type enumeration {
            enum UNK {
                value 0;
                description "UNK-Interface type unknown";
            }
            enum LB {
                value 1;
                description "LB-loopback";
            }
            enum ETH {
                value 2;
                description "ETH-Ethernet";
            }
            enum HDLC {
                value 3;
                description "HDLC";
            }
            enum PPP {
                value 4;
                description "PPP";
            }
            enum ATM {
                value 5;
                description "ATM";
            }
            enum FR {
                value 6;
                description "FR-Frame Relay";
            }
            enum SVI {
                value 7;
                description "VLAN";
            }
            enum AGG {
                value 9;
                description "AGG-aggregate";
            }
            enum PBB {
                value 11;
                description "PBB- PBB logical Port";
            }
            enum VP {
                value 12;
                description "VPORT- Virtual port";
            }
            enum CVP {
                value 13;
                description "CVP-Channelised Virtual port";
            }
            enum METH {
                value 14;
                description "Management Ethernet";
            }
            enum MLAG {
                value 16;
                description "MLAG-Mlag Aggregate";
            }
            enum TUN {
                value 101;
                description "TUN-Tunnel";
            }
            enum SUBINTERFACE {
                value 111;
                description "Subinterface";
            }
        }
        description "datatype to describes HardWare Type";
    }

    typedef  if_interface_speed_t {
        type enumeration {
            enum 10m {
                value 0;
                description "10 mega bits";
            }
            enum 100m {
                value 1;
                description "100 mega bits";
            }
            enum 1g {
                value 2;
                description "1 giga bits";
            }
            enum 2.5g {
                value 3;
                description "2.5 giga bits";
            }
            enum 10g {
                value 4;
                description "10 giga bits";
            }
            enum 20g {
                value 5;
                description "20 giga bits";
            }
            enum 25g {
                value 6;
                description "25 giga bits";
            }
            enum 40g {
                value 7;
                description "40 giga bits";
            }
            enum 50g {
                value 8;
                description "50 giga bits";
            }
            enum 100g {
                value 9;
                description "100 giga bits";
            }
            enum auto {
                value 10;
                description "Auto Negotiation";
            }
        }
        description "datatype for port-speed of interface";
    }

    typedef  if_intf_fec_t {
        type enumeration {
            enum off {
                value 0;
                description "disable fec";
            }
            enum on {
                value 1;
                description "enable fec";
            }
            enum auto {
                value 2;
                description "enable fec auto";
            }
        }
        description "datatype for interface fec";
    }

    typedef  if_mautype_t {
        type enumeration {
            enum dot3MauType10BaseTHD {
                value 10;
                description "UTP MAU half duplex mode";
            }
            enum dot3MauType10BaseTFD {
                value 11;
                description "UTP MAU full duplex mode";
            }
            enum dot3MauType100BaseTXHD {
                value 15;
                description "2 pair category 5 UTP half duplex mode";
            }
            enum dot3MauType100BaseTXFD {
                value 16;
                description "2 pair category 5 UTP full duplex mode";
            }
            enum dot3MauType1000BaseXHD {
                value 21;
                description "PCS/PMA unknown PMD half duplex mode";
            }
            enum dot3MauType1000BaseXFD {
                value 22;
                description "PCS/PMA unknown PMD full duplex mode";
            }
            enum dot3MauType10GigBaseCX4 {
                value 41;
                description "X copper over 8 pair 100-Ohm balanced cable";
            }
            enum dot3MauType10GbaseKX4 {
                value 57;
                description "4 lane X backplane full duplex mode only";
            }
            enum dot3MauType10GbaseKR {
                value 58;
                description "R backplane full duplex mode only";
            }
            enum dot3MauType40GbaseCR4 {
                value 71;
                description "40GBASE-R PCS/PMA over 4 lane shielded copper balanced cable";
            }
        }
        description "datatype for mau type of interface";
    }

    typedef  if_bind_info_t {
        type bits {
            bit vrf {
                position 0;
                description "Bind Information vrf";
            }
            bit mpls_vc {
                position 1;
                description "Bind Information mpls_vc";
            }
            bit mpls_vc_vlan {
                position 2;
                description "Bind Information mpls_vc_vlan";
            }
            bit vpls {
                position 3;
                description "Bind Information vpls";
            }
            bit vpls_vlan {
                position 4;
                description "Bind Information vpls_vlan";
            }
            bit vxlan {
                position 5;
                description "Bind Information vxlan";
            }
            bit nvgre {
                position 6;
                description "Bind Information nvgre";
            }
        }
        description "datatype for Bind information of interface";
    }

    typedef  if_vrx_flag_t {
        type enumeration {
            enum normal {
                value 0;
                description "Normal Interface";
            }
            enum EVR-wrpj {
                value 1;
                description "EVR wrpj Interface";
            }
            enum VS-wrp {
                value 2;
                description "VS wrp Interface";
            }
        }
        description "datatype for vrx status";
    }

    typedef  if_local_flag_t {
        type enumeration {
            enum localsrc {
                value 1;
                description "localsrc of VS";
            }
        }
        description "datatype for local source of VS";
    }

    typedef  if_interface_type_t {
        type enumeration {
            enum Router {
                value 0;
                description "L3 interface";
            }
            enum Switch {
                value 1;
                description "L2 interface";
            }
            enum TDM {
                value 2;
                description "TDM interface";
            }
        }
        description "datatype for interface type";
    }

    typedef  if_trust_state_t {
        type enumeration {
            enum none {
                value 0;
                description "mls qos trust none";
            }
            enum cos {
                value 1;
                description "mls qos trust cos";
            }
            enum dscp {
                value 2;
                description "mls qos trust dscp";
            }
            enum ip-precedence {
                value 3;
                description "mls qos trust ip-precedence";
            }
            enum dscp-cos {
                value 6;
                description "mls qos trust cos and dscp both";
            }
        }
        description "datatype for trust interface state";
    }

    typedef  if_tfo_link_type_t {
        type enumeration {
            enum default {
                value 0;
                description "default link type";
            }
            enum uplink {
                value 1;
                description "link-type uplink";
            }
            enum downlink {
                value 2;
                description "link-type downlink";
            }
        }
        description "datatype for interface link type";
    }

    typedef  if_breakout_type_t {
        type enumeration {
            enum 4X10g {
                value 1;
                description "split to 4X10g";
            }
            enum 4X25g {
                value 2;
                description "split to 4X25g";
            }
            enum 2X50g {
                value 3;
                description "split to 2X50g";
            }
        }
        description "datatype for interface port breakout";
    }

    typedef  if_l2cp_t {
        type enumeration {
            enum stp {
                value 0;
                description "Spanning Tree Protocols";
            }
            enum lacp {
                value 7;
                description "Link Aggregation (LACP)";
            }
            enum dot1x {
                value 8;
                description "Port Authentication (802.1 X)";
            }
            enum lldp {
                value 9;
                description "Link layer discovery protocol";
            }
            enum efm {
                value 11;
                description "Ethernet first mile (Link OAM)";
            }
            enum elmi {
                value 12;
                description "Ethernet local management interface";
            }
            enum synce {
                value 14;
                description "Synchronous Ethernet";
            }
        }
        description "datatype for L2 Control Protocol";
    }

    typedef  if_l2cp_stats_process_t {
        type enumeration {
            enum peer {
                value 0;
                description "peer counters";
            }
            enum tunnel {
                value 1;
                description "tunnel counters";
            }
            enum discard {
                value 2;
                description "discard counters";
            }
            enum tunnel-discard {
                value 3;
                description "tunnel-discard counters";
            }
        }
        description "datatype for l2cp stats";
    }

    typedef  if_l2cp_process_t {
        type enumeration {
            enum peer {
                value 1;
                description "peer the protocol data unit";
            }
            enum tunnel {
                value 2;
                description "tunnel the protocol data unit";
            }
            enum discard {
                value 3;
                description "tunnel the protocol data unit";
            }
        }
        description "datatype for l2cp process";
    }

    typedef  if_error_set_type_t {
        type enumeration {
            enum packet-loss {
                value 0;
                description "Error-Type - Packet-loss";
            }
            enum stray-packets {
                value 1;
                description "Error-Type - Stray-packets";
            }
            enum malformed-packets {
                value 2;
                description "Error-Type - Malformed-packets";
            }
            enum excessive-packet-loss-rate {
                value 3;
                description "Error-Type - Excessive packet loss rate";
            }
            enum buffer-overrun {
                value 4;
                description "Error-Type - Buffer-overrun";
            }
            enum remote-packet-loss {
                value 5;
                description "Error-Type - Remote packet loss";
            }
        }
        description "datatype for interface error-set";
    }

    typedef  if_error_clear_type_t {
        type enumeration {
            enum packet-loss {
                value 6;
                description "Error-Type - Packet-loss";
            }
            enum stray-packets {
                value 7;
                description "Error-Type - Stray-packets";
            }
            enum malformed-packets {
                value 8;
                description "Error-Type - Malformed-packets";
            }
            enum excessive-packet-loss-rate {
                value 9;
                description "Error-Type - Excessive packet loss rate";
            }
            enum buffer-overrun {
                value 10;
                description "Error-Type - Buffer-overrun";
            }
            enum remote-packet-loss {
                value 11;
                description "Error-Type - Remote packet loss";
            }
        }
        description "datatype for interface error-clear";
    }

    typedef  if_rate_limit_level_t {
        type string;
        description "datatype for interface rate-limit-level";
    }

    typedef  if_rate_limit_t {
        type union {
            type uint32 {
                range "0..100000000";

            }
            type if_rate_limit_level_t {

            }
        }
        description "datatype for interface rate-limit";
    }

    typedef  if_rate_limit_type {
        type enumeration {
            enum level {
                value 0;
                description "Threshold level as a percentage";
            }
            enum kbps {
                value 1;
                description "Specifies the units of kilobits per second";
            }
            enum mbps {
                value 2;
                description "Specifies the units of megabits per second";
            }
            enum gbps {
                value 3;
                description "Specifies the units of gigabits per second";
            }
        }
        description "datatype for interface rate-limit-type";
    }

    typedef  if_subif_encap_type_t {
        type enumeration {
            enum dot1q {
                value 33024;
                description "IEEE 802.1Q VLAN-tagged packets";
            }
            enum dot1ad {
                value 34984;
                description "IEEE 802.1ad VLAN-tagged packets";
            }
        }
        description "datatype for sub-interface encap type";
    }

    typedef  if_subif_l2_encap_type_t {
        type enumeration {
            enum default {
                value 1;
                description "IEEE default packets";
            }
            enum untagged {
                value 2;
                description "IEEE untagged packets";
            }
        }
        description "datatype for sub-interface l2 encap type";
    }

    typedef  if_subif_l2_vlan_actiontype_t {
        type enumeration {
            enum pop {
                value 1;
                description "Pop the outer vid";
            }
            enum push {
                value 2;
                description "Push the outer vid";
            }
            enum translate {
                value 3;
                description "Translate the outer vid";
            }
        }
        description "datatype for sub-interface l2 vlan action type";
    }

    typedef  if_subif_rewrite_pop_type_t {
        type enumeration {
            enum 1tag {
                value 1;
                description "Pop 1 tag";
            }
            enum 2tag {
                value 2;
                description "Pop 2 tags";
            }
        }
        description "datatype for sub-interface l2 rewrite pop options";
    }

    typedef  if_switchport_ethertype_t {
        type enumeration {
            enum dropped {
                value 0;
                description "dropped (0x0000)";
            }
            enum ipv4 {
                value 2048;
                description "IP (0x0800)";
            }
            enum arp {
                value 2054;
                description "Address Resolution Protocol (0x0806)";
            }
            enum ipv6 {
                value 34525;
                description "IPv6 (0x86DD)";
            }
            enum mpls {
                value 34887;
                description "mpls (0x8847)";
            }
        }
        description "datatype for packet ethertype";
    }

    typedef  if_flowctrl_t {
        type enumeration {
            enum off {
                value 0;
                description "Turn off flowcontrol";
            }
            enum on {
                value 1;
                description "Turn on flowcontrol";
            }
        }
        description "datatype for flowcontrol";
    }

    typedef  if_raw_string_t {
        type string;
        description "datatype for string";
    }

    typedef  if_hardware_portmode_t {
        type enumeration {
            enum 4X10g {
                value 1;
                description "split to 4X10g";
            }
            enum 4X25g {
                value 2;
                description "split to 4X25g";
            }
            enum 2X50g {
                value 3;
                description "split to 2X50g";
            }
            enum 40g {
                value 4;
                description "split to 40g";
            }
            enum 100g {
                value 5;
                description "100g port - No breakout";
            }
        }
        description "datatype for hardware port-mode";
    }

    typedef  if_err_reason_t {
        type bits {
            bit lag-mismatch {
                position 0;
                description "Enable or Disable Lag-Mismatch";
            }
            bit link-flap {
                position 2;
                description "Enable or Disable  Link-Flap";
            }
            bit mac-move-limit {
                position 3;
                description "Enable or Disable Mac-Move-Limit";
            }
        }
        description "datatype for nsm error reason";
    }

    typedef  if_tunnel_mode_t {
        type enumeration {
            enum vxlan {
                value 6;
                description "Vxlan encapsulation";
            }
        }
        description "datatype for tunnel mode";
    }

    typedef  if_tunnel_key_t {
        type union {
            type uint32 {
                range "0..4294967295";

            }
            type inet:ipv4-address {

            }
        }
        description "datatype for tunnel key";
    }

    typedef  if_tunnel_ipv6_mode_t {
        type enumeration {
            enum ipv6ip {
                value 3;
                description "IPv6 over IP encapsulation";
            }
            enum 6to4 {
                value 4;
                description "IPv6 automatic tunnelling using 6to4";
            }
            enum isatap {
                value 5;
                description "IPv6 automatic tunnelling using ISATAP";
            }
        }
        description "datatype for tunnel ipv6 mode";
    }

    typedef  if_port_group_speed_t {
        type enumeration {
            enum 1g {
                value 1;
                description "port group speed 1g";
            }
            enum 10g {
                value 2;
                description "port group speed 10g";
            }
        }
        description "datatype for interface port group speed";
    }

    typedef  if_errdisable_state_t {
        type bits {
            bit lag-mismatch {
                position 0;
                description "Lag-Mismatch";
            }
            bit stp-bpdu-guard {
                position 1;
                description "Stp-Bpdu-Guard";
            }
            bit link-flap {
                position 2;
                description "Link-Flap";
            }
            bit mac-move-limit {
                position 3;
                description "Mac-Move-Limit";
            }
            bit not-applicable {
                position 4;
                description "Not Applicable";
            }
        }
        description "datatype for error-disable state";
    }

    typedef  if_sr_absolute_t {
        type uint32 {
             range 16000..23999;
        }
        description "datatype for segment routing sid as absolute value";
    }

    typedef  if_sr_index_t {
        type uint32 {
             range 1..7999;
        }
        description "datatype for segment routing sid as index value";
    }

    typedef  if_sr_sid_t {
        type union {
            type if_sr_absolute_t {

            }
            type if_sr_index_t {

            }
        }
        description "datatype for segment routing sid type";
    }

    typedef  if_last_clear_time_t {
        type string;
        description "datatype for interface last clear time";
    }

    typedef  if_debounce_running_state {
        type enumeration {
            enum idle {
                value 0;
                description "Debounce timer is idle";
            }
            enum running {
                value 1;
                description "Debounce timer is running";
            }
            enum enable {
                value 2;
                description "Debounce time is configured";
            }
            enum disable {
                value 3;
                description "Debounce time is not configured";
            }
        }
        description "datatype for debounce running and configuration state";
    }

}
