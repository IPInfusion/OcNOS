/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-if-extended.yang
*
*/

module ipi-if-extended {

    yang-version 1.1;

    namespace   "http://www.ipinfusion.com/yang/ocnos/ipi-if-extended";

    prefix "ipi-if-extended";

    import cml-data-types {
        prefix cml-data-types;
        revision-date 2021-05-03;
    }

    import ipi-if-types {
        prefix ipi-if-types;
        revision-date 2021-03-16;
    }

    import ipi-interface {
        prefix ipi-interface;
        revision-date 2021-06-14;
    }

    import ipi-if-ethernet {
        prefix ipi-if-ethernet;
        revision-date 2021-03-16;
    }

    import ietf-inet-types {
        prefix inet;
        revision-date 2013-07-15;
    }

    import ietf-yang-types {
        prefix yang;
        revision-date 2013-07-15;
    }

    import feature-list {
        prefix feature-list;
        revision-date 2021-05-03;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for IPI Interface extended module";


    revision "2021-06-10" {
        description "Added new attribute hardware-applied-bcast-value, hardware-applied-mcast-value and hardware-applied-dlf-bcast-value to show hardware applied storm control value in netconf";
        reference " 0.8.2.";
    }

    revision "2021-06-09" {
        description "Added yang support for attribute storm-total-discards";
        reference " 0.8.1.";
    }

    revision "2021-04-08" {
        description "Added notification to remove interfaces from cross connects";
        reference " 0.8.0.";
    }

    revision "2021-03-29" {
        description "Changed container name of hardware-profile to hardware-profile-flexport";
        reference " 0.7.0.";
    }

    revision "2021-03-16" {
        description "Remodelled encapsulation, rewrite and cross-connects for sub-interface remodelling.";
        reference " 0.6.0.";
    }

    revision "2021-03-05" {
        description "Added dot1q-ether-type from mo_ipi-port.xml to make it independent of bridge";
        reference " 0.5.0.";
    }

    revision "2021-03-01" {
        description "Added new atrribute in-bpdu-pkts, in-oamp-pkts, in-bfd-pkts, in-vrrp-rip-dhcp-pkts, in-rsvd-mc-pkts,
                       in-link-local-pkts, in-icmp-pkts, in-icmp-redirect-pkts, in-misc-pkts.
                       Removed attribute last-flap.
                       Added support for changing process type for L2 protocols for an interface.
        ";
        reference " 0.4.0.";
    }

    revision "2021-01-27" {
        description "Changed attribute multicast to disable-multicast and datatype from boolean to empty,
                       Removed attribute enable and added two attribute enable-speed and enable-queue-drops
                       and changed datatype to empty,
                       Removed attribute mac-learn-limit, mdi-crossover, autonegotiation-fault-advertised, autonegotiation-bits-advertised,
                       default-auto-negotiation and auto-negotiation,
                       Added new atrribute last-flapped and auto-ipv6-link-local-address,
                       Changed attribute snmp-trap-link-status to disable-snmp-trap-link-status and datatype from boolean to empty,
                       Added vxlan dependency on tunnel mode attribute.
        ";
        reference " 0.3.0.";
    }

    revision "2020-12-15" {
        description "Change to have data-types in lower case instead of camel case";
        reference " 0.2.0.";
    }

    revision "2020-11-13" {
        description "Initial Version";
        reference " 0.1.0.";
    }



    grouping port-group-speed-map-grouping {
    description
        "Global configuration for Port-group";
        list port-group-speed-map {
            if-feature feature-list:HAVE_DUNE;
            if-feature feature-list:HAVE_HAL;
            if-feature feature-list:NOT_HAVE_SWFWDR;
            key "group-index";
            description
                "Global configuration for Port-group";
            leaf group-index  {
                type  leafref {
                    path  "../config/group-index";
                }
                description "This attribute specifies the port group number";
            } // END of group-index definition.

            container config {
                description
                    "Port-group global configuration data";
                uses port-group-config;
            } // END of config-container definition.
            container state {
                config false;
                description
                    "State data for Port-group";
                uses port-group-config;
            } // END of state-container definition.
        } // End of port-group-speed-map-list
    } // END of port-group-speed-map-grouping definition.
    grouping ipi-interface-extended-config {
        description
            "Grouping for interface-extended module config objects.";
        leaf disable-multicast  {
            type  empty;
            description "This attribute is used to set multicast flag for the interface. For a
                        MAC layer protocol, this includes both Group and Functional addresses.
                        Multicast is enabled by default for L3 interfaces. Setting multicast
                        flag for loopback and L2 subinterface is not allowed";
        } // END of disable-multicast definition.

        leaf link-flap-error-disable  {
            type  empty;
            description "This object specifies whether the interface is enabled for link-flap
                        error-disable or not. If this is '0', then interface is not enabled.
                        Otherwise it is enabled.";
        } // END of link-flap-error-disable definition.

        leaf mac-move-limit-error-disable  {
            type  empty;
            description "This object specifies whether the interface is enabled for
                        mac-move-limit error-disable or not. If this is '0', then interface is
                        not enabled. Otherwise it is enabled.";
        } // END of mac-move-limit-error-disable definition.

        leaf disable-snmp-trap-link-status  {
            type  empty;
            description "This Object is used to set the snmp trap link status in an interface";
        } // END of disable-snmp-trap-link-status definition.

        leaf mau-default-type  {
            if-feature feature-list:HAVE_L2;
            type  ipi-if-types:if_mautype_t;
            description "This attribute is used to set the mau type in an interface";
        } // END of mau-default-type definition.

        leaf debounce-time  {
            type  uint16 {
                 range "250..5000"  {
                    description "250..5000:Timer value in milliseconds.";
                 }
            }
            description "Use this attribute to set the interface debounce timer value";
        } // END of debounce-time definition.

    } // END of ipi-interface-extended-config definition.
    grouping ipi-interface-extended-state {
        description
            "Grouping for interface-extended module counters/state parameters.";
        leaf properties  {
            type  ipi-if-types:if_iface_prop_t;
            description "This attribute is used to display interface mapping properties";
        } // END of properties definition.

        leaf original-name  {
            if-feature feature-list:HAVE_INTERFACE_NAME_MAPPING;
            type  string {
                length "1..33";
                pattern "[^?' =,>|]+";
            }
            description "This Object is used to map the interface name";
        } // END of original-name definition.

        leaf mapped-name  {
            type  string {
                length "1..33";
                pattern "[^?' =,>|]+";
            }
            description "This Object is used to set interface mapped name";
        } // END of mapped-name definition.

        leaf if-counter-discontinuity-time  {
            type  yang:timestamp;
            description "The value of sysUpTime on the most recent occasion at which
                        any one or more of this interface's counters suffered a
                        discontinuity.  The relevant counters are the specific
                        instances associated with this interface of any Counter32 or
                        Counter64 object contained in the ifTable or ifXTable.  If
                        no such discontinuities have occurred since the last re-
                        initialization of the local management subsystem, then this
                        object contains a zero value.";
        } // END of if-counter-discontinuity-time definition.

        leaf slot-id  {
            type  uint32;
            description "This object describes slot-id";
        } // END of slot-id definition.

        leaf hardware-type  {
            type  ipi-if-types:if_hw_type_t;
            description "This Object describes hardware type";
        } // END of hardware-type definition.

        leaf storm-total-discards  {
            if-feature feature-list:HAVE_BROADCOM;
            if-feature feature-list:HAVE_RATE_LIMIT;
            if-feature feature-list:NOT_HAVE_DUNE;
            type  yang:counter64;
            description "This object describes total storm-discards";
        } // END of storm-total-discards definition.

        leaf metric  {
            type  int32;
            description "This Object is used to check interface Metric";
        } // END of metric definition.

        leaf if-type  {
            type  ipi-if-types:if_interface_type_t;
            description "This Object describes the interface type L2, L3, TDM";
        } // END of if-type definition.

        leaf trust-state  {
            if-feature feature-list:HAVE_QOS;
            type  ipi-if-types:if_trust_state_t;
            description "This Object describes the trust interface state";
        } // END of trust-state definition.

        leaf monitor-port-grp  {
            if-feature feature-list:HAVE_TFO;
            type  boolean;
            config false;
            description "This attribute describes Monitor Port Groups (MPG) interface";
        } // END of monitor-port-grp definition.

        leaf failover-link-type  {
            if-feature feature-list:HAVE_TFO;
            type  ipi-if-types:if_tfo_link_type_t;
            description "This attribute describes trigger failover(TFO) link type";
        } // END of failover-link-type definition.

        leaf udld-flush-transmitted  {
            if-feature feature-list:HAVE_UDLD;
            type  uint16;
            description "This attribute describes interface udld Flush transmitted";
        } // END of udld-flush-transmitted definition.

        leaf debounce-flap-count  {
            type  uint16;
            config false;
            description "This attribute describes number of flap within debounce time interval";
        } // END of debounce-flap-count definition.

        leaf debounce-last-flap-time  {
            type  yang:date-and-time {
                pattern "\\d{4}-\\d{2}-\\d{2}T\\d{2}:\\d{2}:\\d{2}(\\.\\d+)?(Z|[\\+\\-]\\d{2}:\\d{2})";
                }
                config false;
                description "This attribute describes the last debounce flap time";
            } // END of debounce-last-flap-time definition.

            leaf debounce-remain-time  {
                type  yang:counter32;
                config false;
                description "This attribute describes the remaining  debounce time interval";
            } // END of debounce-remain-time definition.

            leaf debounce-running-status  {
                type  ipi-if-types:if_debounce_running_state;
                config false;
                description "This attribute describes debounce time Running Status";
            } // END of debounce-running-status definition.

            leaf debounce-config-status  {
                type  ipi-if-types:if_debounce_running_state;
                config false;
                description "This attribute describes whether debounce is configured or not";
            } // END of debounce-config-status definition.

            leaf last-flapped  {
                type  ipi-if-types:if_last_clear_time_t {
                    length "1..1965";
                }
                description "This Object describes time when the interface last
                            flapped.";
            } // END of last-flapped definition.

            leaf auto-ipv6-link-local-address  {
                if-feature feature-list:HAVE_IPV6;
                type  inet:ipv6-prefix;
                description "This Object describes the default link local IPv6 address
                            assigned to the interface.";
            } // END of auto-ipv6-link-local-address definition.

    } // END of ipi-interface-extended-state definition.
    grouping port-monitor-config {
        description
            "Grouping for Port-monitoring config";
        leaf enable-speed  {
            type  empty;
            description "This object is used to enable port-monitoring for the specified
                        parameters, average speed of the interface";
        } // END of enable-speed definition.

        leaf enable-queue-drops  {
            type  empty;
            description "This object is used to enable queue-drops of the interface";
        } // END of enable-queue-drops definition.

    } // END of port-monitor-config definition.
    grouping port-monitor-threshold-config {
        description
            "Grouping for Port-monitoring config";
        leaf warning-threshold  {
            type  uint8 {
                 range "1..100"  {
                    description "1..100:warning level threshold value in percentage";
                 }
            }
            units "%";
            mandatory true;
            description "This object is used to specify warning threshold for port speed
                        monitor. Warning threshold must be greater than recovery threshold";
        } // END of warning-threshold definition.

        leaf recovery-threshold  {
            when " ../warning-threshold ";
            type  uint8 {
                 range "1..100"  {
                    description "1..100:recovery level threshold value in percentage";
                 }
            }
            units "%";
            mandatory true;
            description "This object is used to specify recovery threshold for port speed
                        monitor.";
        } // END of recovery-threshold definition.

    } // END of port-monitor-threshold-config definition.
    grouping capabilities-state {
        description
            "Grouping for physical interface capabilities";
        leaf speed-half-duplex  {
            type  string {
                length "1..1965";
                pattern "[^ ]*";
            }
            description "This Object describes the Interface Speed half duplex capability";
        } // END of speed-half-duplex definition.

        leaf speed-full-duplex  {
            type  string {
                length "1..1965";
                pattern "[^ ]*";
            }
            description "This Object describes the Interface Speed full duplex capability";
        } // END of speed-full-duplex definition.

        leaf pause  {
            type  ipi-if-types:if_raw_string_t {
                length "1..1965";
                pattern "[^ ]*";
            }
            description "This Object describes the Interface pause Capability";
        } // END of pause definition.

        leaf interface-type  {
            type  ipi-if-types:if_raw_string_t {
                length "1..1965";
                pattern "[^ ]*";
            }
            description "This Object describes the Interface Capability";
        } // END of interface-type definition.

        leaf medium  {
            type  ipi-if-types:if_raw_string_t {
                length "1..1965";
                pattern "[^ ]*";
            }
            description "This Object describes the Interface medium Capability";
        } // END of medium definition.

        leaf loopback  {
            type  ipi-if-types:if_raw_string_t {
                length "1..1965";
                pattern "[^ ]*";
            }
            description "This Object describes the Interface loopback Capability";
        } // END of loopback definition.

        leaf flags  {
            type  string {
                length "1..1965";
                pattern "[^?' =,>|]+";
            }
            description "This Object describes the Interface flags Capability";
        } // END of flags definition.

        leaf eee  {
            type  string {
                length "1..1965";
                pattern "[^?' =,>|]+";
            }
            description "This Object describes the Interface eee Capability";
        } // END of eee definition.

        leaf fcmap  {
            type  string {
                length "1..1965";
                pattern "[^?' =,>|]+";
            }
            description "This Object describes the Interface fcmap Capability";
        } // END of fcmap definition.

        leaf encapsulation  {
            type  ipi-if-types:if_raw_string_t {
                length "1..1965";
                pattern "[^ ]*";
            }
            description "This Object describes the Interface encapsulation Capability";
        } // END of encapsulation definition.

        leaf fec  {
            type  ipi-if-types:if_raw_string_t {
                length "1..1965";
                pattern "[^?' =>|]+";
            }
            description "This Object describes the Interface fec Capability";
        } // END of fec definition.

    } // END of capabilities-state definition.
    grouping extended-counters-state {
        description
            "Operational state representing extended interface statistics.";
        leaf in-compressed  {
            type  yang:counter64;
            config false;
            description "This Object describes Received compressed.This counter is only
                        applicable to loopback (lo) and management interfaces like eth0";
        } // END of in-compressed definition.

        leaf out-compressed  {
            type  yang:counter64;
            config false;
            description "This Object describes Transmitted compressed.This counter is only
                        applicable to loopback (lo) and management interfaces like eth0";
        } // END of out-compressed definition.

        leaf collisions  {
            type  yang:counter64;
            config false;
            description "This Object describes collisions.This counter is only applicable to
                        loopback (lo) and management interfaces like eth0";
        } // END of collisions definition.

        leaf unicast-rpf-discard  {
            type  yang:counter64;
            config false;
            description "This Object describes unicast RPF discards.This counter is only
                        applicable to loopback (lo) and management interfaces like eth0";
        } // END of unicast-rpf-discard definition.

        leaf in-length-errors  {
            type  yang:counter64;
            config false;
            description "This Object describes Received Length Errors.This counter is only
                        applicable to loopback (lo) and management interfaces like eth0";
        } // END of in-length-errors definition.

        leaf in-oversize-errors  {
            type  yang:counter64;
            config false;
            description "This Object describes Received over Errors.This counter is only
                        applicable to loopback (lo) and management interfaces like eth0";
        } // END of in-oversize-errors definition.

        leaf in-crc-errors  {
            type  yang:counter64;
            config false;
            description "This Object describes Received CRC Errors.This counter is only
                        applicable to loopback (lo) and management interfaces like eth0";
        } // END of in-crc-errors definition.

        leaf in-frame-errors  {
            type  yang:counter64;
            config false;
            description "This Object describes Received Frame Errors.This counter is only
                        applicable to loopback (lo) and management interfaces like eth0";
        } // END of in-frame-errors definition.

        leaf in-fifo-errors  {
            type  yang:counter64;
            config false;
            description "This Object describes Received Fifo Errors.This counter is only
                        applicable to loopback (lo) and management interfaces like eth0";
        } // END of in-fifo-errors definition.

        leaf in-missed-errors  {
            type  yang:counter64;
            config false;
            description "This Object describes Received Missed Errors.This counter is only
                        applicable to loopback (lo) and management interfaces like eth0";
        } // END of in-missed-errors definition.

        leaf out-aborted-errors  {
            type  yang:counter64;
            config false;
            description "This Object describes Transmitted Aborted Errors.This counter is only
                        applicable to loopback (lo) and management interfaces like eth0";
        } // END of out-aborted-errors definition.

        leaf out-carrier-errors  {
            type  yang:counter64;
            config false;
            description "This Object describes Transmitted Carrier Errors.This counter is only
                        applicable to loopback (lo) and management interfaces like eth0";
        } // END of out-carrier-errors definition.

        leaf out-fifo-errors  {
            type  yang:counter64;
            config false;
            description "This Object describes Transmitted Fifo Errors.This counter is only
                        applicable to loopback (lo) and management interfaces like eth0";
        } // END of out-fifo-errors definition.

        leaf out-heartbeat-errors  {
            type  yang:counter64;
            config false;
            description "This Object describes Transmitted Heart beat Errors.This counter is
                        only applicable to loopback (lo) and management interfaces like eth0";
        } // END of out-heartbeat-errors definition.

        leaf out-window-errors  {
            type  yang:counter64;
            config false;
            description "This Object describes Transmitted Window Errors.This counter is only
                        applicable to loopback (lo) and management interfaces like eth0";
        } // END of out-window-errors definition.


        list l2-protocol-pkt-stat {
            if-feature feature-list:HAVE_HAL;
            if-feature feature-list:HAVE_BROADCOM;
            key "l2cp-counter-type";
            config false;
            description
                "This list is used to display statistics for L2 protocol control
                            packets";
            leaf lacp-counters  {
                type  yang:counter64;
                description "This attribute specifies LACP Protocol Packets received on the
                            interface";
            } // END of lacp-counters definition.

            leaf stp-counters  {
                type  yang:counter64;
                description "This attribute specifies stp protocol packets";
            } // END of stp-counters definition.

            leaf lldp-counters  {
                type  yang:counter64;
                description "This attribute specifies lldp protocol Packets received on the
                            interface";
            } // END of lldp-counters definition.

            leaf efmCounters  {
                type  yang:counter64;
                description "This attribute specifies efm protocol Packets received on the
                            interface";
            } // END of efmCounters definition.

            leaf elmi-counters  {
                type  yang:counter64;
                description "This attribute specifies elmi protocol Packets received on the
                            interface";
            } // END of elmi-counters definition.

            leaf dot1x-counters  {
                type  yang:counter64;
                description "This attribute specifies dot1x protocol Packets received on the
                            interface";
            } // END of dot1x-counters definition.

            leaf synce-counters  {
                type  yang:counter64;
                description "This attribute specifies synce protocol Packets received on the
                            interface";
            } // END of synce-counters definition.

            leaf l2cp-counter-type  {
                type  ipi-if-types:if_l2cp_stats_process_t;
                description "This attribute specifies the Protocol Packets received on the
                            interface";
            } // END of l2cp-counter-type definition.

        } // End of l2-protocol-pkt-stat-list
    } // END of extended-counters-state definition.
    grouping extended-ethernet-config {
        description
            "Grouping for extended ethernet module config objects.";
        leaf forward-err-correction  {
            type  ipi-if-types:if_intf_fec_t;
            default "auto";
            description "This Object is used to set forward-error-correction to interface";
        } // END of forward-err-correction definition.

        leaf load-interval  {
            if-feature feature-list:HAVE_BROADCOM;
            type  uint16 {
                 range "30..300"  {
                    description "30..300:Load period in multiples of 30 seconds (default is 300
                            seconds).";
                 }
            }
            default "300";
            description "This attribute is used to configure load interval period in multiples
                        of 30 seconds";
        } // END of load-interval definition.

    } // END of extended-ethernet-config definition.
    grouping extended-ethernet-state {
        description
            "Grouping for extended ethernet module counters/state parameters.";
        leaf default-duplex-mode  {
            type  uint8;
            description "This object specifies interface default Duplex";
        } // END of default-duplex-mode definition.

        leaf default-speed  {
            type  string {
                length "1..1965";
                pattern "[^?' =,>|]+";
            }
            description "This Object describes interface default link speed, bytes/s";
        } // END of default-speed definition.

    } // END of extended-ethernet-state definition.
    grouping extended-ethernet-counters-state {
        description
            "Operational data representing extended interface ethernet counters";
        leaf in-good-octets  {
            type  yang:counter64;
            config false;
            description "This Object describes Good Octets Received";
        } // END of in-good-octets definition.

        leaf in-bad-octets  {
            type  yang:counter64;
            config false;
            description "This Object describes Bad Octets Received.This counter is currently
                        not supported for Broadcom hardware";
        } // END of in-bad-octets definition.

        leaf mac-transmit-error  {
            type  yang:counter64;
            config false;
            description "This Object describes MAC Transmit Error";
        } // END of mac-transmit-error definition.

        leaf in-good-pkts  {
            type  yang:counter64;
            config false;
            description "This Object describes Good packets Received";
        } // END of in-good-pkts definition.

        leaf in-bad-pkts  {
            type  yang:counter64;
            config false;
            description "This Object describes Bad packets Received";
        } // END of in-bad-pkts definition.

        leaf out-good-octets  {
            type  yang:counter64;
            config false;
            description "This Object describes Good Octets Send";
        } // END of out-good-octets definition.

        leaf out-good-pkts  {
            type  yang:counter64;
            config false;
            description "This Object describes Good Packets Send";
        } // END of out-good-pkts definition.

        leaf excessive-collisions  {
            type  yang:counter64;
            config false;
            description "This Object describes Excessive Collisions";
        } // END of excessive-collisions definition.

        leaf in-unrecognized-mac-control  {
            type  yang:counter64;
            config false;
            description "This Object describes unrecognized mac control received";
        } // END of in-unrecognized-mac-control definition.

        leaf drop-events  {
            type  yang:counter64;
            config false;
            description "This Object describes Drop Events";
        } // END of drop-events definition.

        leaf in-mac-errors  {
            type  yang:counter64;
            config false;
            description "This Object describes MAC Reacived Error";
        } // END of in-mac-errors definition.

        leaf in-dribble-errors  {
            type  yang:counter64;
            config false;
            description "This Object describes Dribble";
        } // END of in-dribble-errors definition.

        leaf collisions-state  {
            type  yang:counter64;
            config false;
            description "collisions State";
        } // END of collisions-state definition.

        leaf late-collisions  {
            type  yang:counter64;
            config false;
            description "This Object describes late Collisions";
        } // END of late-collisions definition.

        leaf deferred-tx  {
            type  yang:counter64;
            config false;
            description "This Object describes Deferred Transmitted";
        } // END of deferred-tx definition.

        leaf mtu-exceed-discards  {
            type  yang:counter64;
            config false;
            description "This Object describes mtu Exceed count";
        } // END of mtu-exceed-discards definition.

        leaf in-jumbo-frames  {
            type  yang:counter64;
            config false;
            description "This Object describes inJumbo count";
        } // END of in-jumbo-frames definition.

        leaf out-jumbo-frames  {
            type  yang:counter64;
            config false;
            description "This Object describes outJumbo count";
        } // END of out-jumbo-frames definition.

        leaf receive-pkt-rate  {
            type  yang:counter64;
            config false;
            description "This Object describes Recived Packet Rate";
        } // END of receive-pkt-rate definition.

        leaf receive-bit-rate  {
            type  yang:counter64;
            config false;
            description "This Object describes Recived BitRate";
        } // END of receive-bit-rate definition.

        leaf send-pkt-rate  {
            type  yang:counter64;
            config false;
            description "This Object describes Transmitted packet Rate";
        } // END of send-pkt-rate definition.

        leaf send-bit-rate  {
            type  yang:counter64;
            config false;
            description "This Object describes Transmitted BitRate";
        } // END of send-bit-rate definition.

    } // END of extended-ethernet-counters-state definition.
    grouping subif-crossconnect-config {
        description
            "Grouping for Sub-interface cross-connect configurations";
        leaf xc-name  {
            type  string {
                length "1..30";
                pattern "[^?' =,>|]+";
            }
            description "This attribute specifies the cross-connect name. Use this attribute to
                        cross-connect between subinterfaces.";
        } // END of xc-name definition.

        leaf-list endpoint-if  {
            type  string {
                length "1..1965";
                pattern "[^?' =,>|]+";
            }
            description "This attribute specifies the endpoint for cross-connect";
        } // END of endpoint-if definition.

        leaf xc-description  {
            type  cml-data-types:cml_line_t {
                length "1..1965";
            }
            description "This attribute secifies the description for cross-connect";
        } // END of xc-description definition.

        leaf admin-disable  {
            type  empty;
            description "This attribute is used to temporarily shutdown the cross-connect";
        } // END of admin-disable definition.

    } // END of subif-crossconnect-config definition.
    grouping port-group-config {
        description
            "Grouping for port-group speed configurations";
        leaf group-index  {
            type  uint8 {
                 range "1..64"  {
                    description "1..64:port group number";
                 }
            }
            description "This attribute specifies the port group number";
        } // END of group-index definition.

        leaf group-speed  {
            if-feature feature-list:HAVE_HAL;
            if-feature feature-list:NOT_HAVE_SWFWDR;
            type  ipi-if-types:if_port_group_speed_t;
            mandatory true;
            description "This attribute specifies the speed mode of the port.";
        } // END of group-speed definition.

    } // END of port-group-config definition.
    grouping interface-counters-extended {
        description
            "Grouping for Interface-index state details";
        leaf error-disable-reason  {
            type  ipi-if-types:if_errdisable_state_t;
            description "This object specifies the event that caused the interface to be
                        error-disabled. If interface is error-disabled because of
                        lag-mismatch, value of this object is 1. If interface is
                        error-disabled because of stp-bpdu-guard, value of this object is 2.
                        If interface is error-disabled because of link-flap, value of this
                        object is 4.";
        } // END of error-disable-reason definition.

    } // END of interface-counters-extended definition.
    grouping hardware-profile-flexport-config {
        description
            "Grouping for Hardware Profile Flexport config";
        leaf port-mode  {
            type  ipi-if-types:if_hardware_portmode_t;
            description "This Object is to set port mode";
        } // END of port-mode definition.

    } // END of hardware-profile-flexport-config definition.
    grouping error-disable-config {
        description
            "Grouping for error-disable config";
        leaf reason  {
            type  ipi-if-types:if_err_reason_t;
            description "This object is to enable various error-disable reasons like
                        lag-mismatch, stp-bpdu-guard and link-flap. As the datatype is BITS,
                        0th bit corresponds to lag-mismatch, 1st bit corresponds to
                        stp-bpdu-guard, 2nd bit corresponds to link-flap";
        } // END of reason definition.

        leaf error-disable-stp-bpdu-guard  {
            type  boolean;
            description "This object is used to configure error disable STP BPDU Guard";
        } // END of error-disable-stp-bpdu-guard definition.

        leaf timeout-interval  {
            type  uint32 {
                 range "0..1000000"  {
                    description "0..1000000:timeout interval in seconds. Set 0 to disable automatic
                            recovery.";
                 }
            }
            default "0";
            description "This object is to configure timeout for error-disable automatic
                        recovery timer";
        } // END of timeout-interval definition.

        leaf link-flap-max-count  {
            when " ../link-flap-timer-interval ";
            // when " ../reason >= '4' ";
            type  uint32 {
                 range "1..100"  {
                    description "1..100:Allowed Flap count range";
                 }
            }
            default "5";
            description "This object is to configure allowed flap count to detect link-flap
                        error-disable";
        } // END of link-flap-max-count definition.

        leaf link-flap-timer-interval  {
            when " ../link-flap-max-count ";
            // when " ../reason >= '4' ";
            type  uint32 {
                 range "1..1800"  {
                    description "1..1800:timeout interval in seconds";
                 }
            }
            units "seconds";
            default "10";
            description "This object is configure timer interval for link-flap timer";
        } // END of link-flap-timer-interval definition.

        leaf mac-move-limit  {
            // when " ../reason >= '8' ";
            type  uint32 {
                 range "1..1000"  {
                    description "1..1000:Allowed Mac movement in 5 seconds";
                 }
            }
            units "seconds";
            default "100";
            description "This object configures threshold for mac movement";
        } // END of mac-move-limit definition.

    } // END of error-disable-config definition.
    grouping switchport-allowed-ether-types-config {
        description
            "Grouping for switchport-allowed-ether-types config data";
        leaf arp  {
            type  boolean;
            description "This attribute is used to allow ARP traffic";
        } // END of arp definition.

        leaf ipv4  {
            type  boolean;
            description "This attribute is used to allow IPv4 traffic";
        } // END of ipv4 definition.

        leaf ipv6  {
            type  boolean;
            description "This attribute is used to allow IPv6 traffic";
        } // END of ipv6 definition.

        leaf mpls  {
            type  boolean;
            description "This attribute is used to allow MPLS traffic";
        } // END of mpls definition.

        leaf-list ether-type-value  {
            type  string {
                length "1..1965";
                pattern "[^?' =,>|]+";
            }
            description "This attribute is used to allow traffic of any Ethertype value (0x600
                        - 0xFFFF)";
        } // END of ether-type-value definition.

        leaf log  {
            type  boolean;
            description "This attribute is used to log unwanted ethertype packets";
        } // END of log definition.

    } // END of switchport-allowed-ether-types-config definition.
    grouping switchport-allowed-ether-types-stats {
        description
            "Grouping for switchport-allowed-ether-types statistics";
        leaf ether-type  {
            type  ipi-if-types:if_switchport_ethertype_t;
            description "This attribute is used to specify the ethertype of packet";
        } // END of ether-type definition.

        leaf packets  {
            type  yang:counter64;
            description "This attribute is used to specify Packets count";
        } // END of packets definition.

        leaf bytes  {
            type  yang:counter64;
            description "This attribute is used to specify Bytes count";
        } // END of bytes definition.

    } // END of switchport-allowed-ether-types-stats definition.
    grouping subif-encapsulation-config {
        description
            "Grouping for dot1q and dot1ad encapsulation data";
        leaf encapsulation-type  {
            when " ../outer-vlan-id ";
            type  ipi-if-types:if_subif_encap_type_t;
            mandatory true;
            description "This attribute is used to configure the dot1q encapsulation type.
                        To change the encapsulation config, delete and recreate the entire
                        encapsulation config.";
        } // END of encapsulation-type definition.

        leaf outer-vlan-id  {
            when " ../encapsulation-type ";
            type  cml-data-types:cml_range_t;
            mandatory true;
            description "This attribute is used to configure the outer vlan tag.
                        To change the encapsulation config, delete and recreate the entire
                        encapsulation config.";
        } // END of outer-vlan-id definition.

        leaf inner-vlan-id  {
            when " ../encapsulation-type and ../outer-vlan-id ";
            type  cml-data-types:cml_range_t;
            description "This Object is used to configure the inner vlan ID.
                        To change the encapsulation config, delete and recreate the entire
                        encapsulation config.";
        } // END of inner-vlan-id definition.

    } // END of subif-encapsulation-config definition.
    grouping native-layer2-encapsulation-config {
        description
            "Grouping for dot1q and dot1ad encapsulation data";
        leaf l2-encapsulation-type  {
            type  ipi-if-types:if_subif_l2_encap_type_t;
            mandatory true;
            description "This attribute is used to configure the l2 subinterface encapsulation
                        type.
                        To change the encapsulation config, delete and recreate the entire
                        encapsulation config.";
        } // END of l2-encapsulation-type definition.

    } // END of native-layer2-encapsulation-config definition.
    grouping subif-rewrite-config {
        description
            "Grouping for dot1q and dot1ad encapsulation data";
        leaf vlan-action  {
            when " ../enable-pop or ../push-tpid or ../translate-tpid ";
            type  ipi-if-types:if_subif_l2_vlan_actiontype_t;
            mandatory true;
            description "This object is used to configure the rewrite action to push, pop or
                        translate the outer VLAN-id.
                        To change the rewrite config, delete and recreate the entire rewrite
                        config.";
        } // END of vlan-action definition.

        choice vlan-action-type {
            description
                "Vlan Action Types";
            case pop {

                description
                    "Pop the outer and inner vid";

                leaf enable-pop  {
                    when " ../vlan-action='1' ";
                    type  ipi-if-types:if_subif_rewrite_pop_type_t;
                    mandatory true;
                    description "This attribute is used to configure pop outer and inner tag.
                                To change the rewrite config, delete and recreate the entire rewrite
                                config.";
                } // END of enable-pop definition.

            }
            case push {

                description
                    "Push the outer and inner vid for a tpid";

                leaf push-tpid  {
                    when " ../vlan-action='2' and ../push-outer-vlan-id ";
                    type  string {
                        length "1..1965";
                        pattern "[^?' =,>|]+";
                    }
                    mandatory true;
                    description "This attribute is used to configure tpid.
                                To change the rewrite config, delete and recreate the entire rewrite
                                config.";
                } // END of push-tpid definition.

                leaf push-outer-vlan-id  {
                    when " ../vlan-action='2' and ../push-tpid ";
                    type  uint16 {
                         range "1..4094"  {
                            description "1..4094:Vid range";
                         }
                    }
                    mandatory true;
                    description "This Object is used to configure outer vlan ID range for rewrite.
                                To change the rewrite config, delete and recreate the entire rewrite
                                config.";
                } // END of push-outer-vlan-id definition.

                leaf push-inner-vlan-id  {
                    type  uint16 {
                         range "1..4094"  {
                            description "1..4094:inner-vlan";
                         }
                    }
                    description "This Object is used to configure the inner vlan ID for rewrite.
                                To change the rewrite config, delete and recreate the entire rewrite
                                config.";
                } // END of push-inner-vlan-id definition.

            }
            case translate {

                description
                    "Translate the outer vid for a tpid";

                leaf translate-tpid  {
                    when " ../vlan-action='3' and ../translate-vlan-id ";
                    type  string {
                        length "1..1965";
                        pattern "[^?' =,>|]+";
                    }
                    mandatory true;
                    description "This attribute is used to configure tpid.
                                To change the rewrite config, delete and recreate the entire rewrite
                                config.";
                } // END of translate-tpid definition.

                leaf translate-vlan-id  {
                    when " ../vlan-action='3' and ../translate-tpid ";
                    type  uint16 {
                         range "1..4094"  {
                            description "1..4094:Vid range";
                         }
                    }
                    mandatory true;
                    description "This Object is used to configure VLAN ID range for rewrite.
                                To change the rewrite config, delete and recreate the entire rewrite
                                config.";
                } // END of translate-vlan-id definition.

            }
        } // END of vlan-action-type-choice definition.
    } // END of subif-rewrite-config definition.
    grouping l2cp-config {
        description
            "Grouping for Layer2 Control Protocol configurations";
        leaf l2cp-type  {
            type  ipi-if-types:if_l2cp_t;
            description "This attribute is used to configure the layer2 control-protocol type";
        } // END of l2cp-type definition.

        leaf tunnel-vlan  {
            if-feature feature-list:HAVE_SWFWDR;
            type  int32;
            description "This attribute is used to configure the layer2 control-protocol type
                        tunnel VLAN";
        } // END of tunnel-vlan definition.

        leaf protocol-process  {
            type  ipi-if-types:if_l2cp_process_t;
            mandatory true;
            description "This attribute is used to change the process of protocol to
                        peer/discard/tunnel";
        } // END of protocol-process definition.

    } // END of l2cp-config definition.
    grouping tdm-config {
        description
            "Grouping for TDM interface configurations";
        leaf jitter-buffer  {
            if-feature feature-list:HAVE_TDM_VC;
            type  uint16 {
                 range "1..500"  {
                    description "1..500:Range for jitter buffer size in millisec";
                 }
            }
            default "500";
            description "This attribute is used to configure jitter-buffer-size";
        } // END of jitter-buffer definition.

        leaf payload-bytes  {
            if-feature feature-list:HAVE_TDM_VC;
            type  uint32 {
                 range "0..32768"  {
                    description "0..32768:Range for setting payload bytes";
                 }
            }
            default "0";
            description "This attribute is used to configure tdm payload-bytes";
        } // END of payload-bytes definition.

        leaf rtp-header  {
            if-feature feature-list:HAVE_TDM_VC;
            type  boolean;
            default false;
            description "This attribute is used to configure rtp-header";
        } // END of rtp-header definition.

    } // END of tdm-config definition.
    grouping tdm-error-set-config {
        description
            "Grouping for TDM interface error-set configurations";
        leaf error-type  {
            type  ipi-if-types:if_error_set_type_t;
            description "This attribute is used to configure the error-set type";
        } // END of error-type definition.

        leaf error-period  {
            type  uint32 {
                 range "2000..10000"  {
                    description "2000..10000:Range for setting the error-set period in millisec";
                 }
            }
            mandatory true;
            description "This attribute describes the range for setting the error-set period in
                        millisec";
        } // END of error-period definition.

    } // END of tdm-error-set-config definition.
    grouping tdm-error-clear-config {
        description
            "Grouping for TDM interface error-clear configurations";
        leaf error-clear-type  {
            type  ipi-if-types:if_error_clear_type_t;
            description "This attribute is used to configure the error-clear";
        } // END of error-clear-type definition.

        leaf error-clear-period  {
            type  uint32 {
                 range "2000..10000"  {
                    description "2000..10000:Range for setting the error-clear period in millisec";
                 }
            }
            mandatory true;
            description "This attribute describes the range for setting the error-clear period
                        in millisec";
        } // END of error-clear-period definition.

    } // END of tdm-error-clear-config definition.
    grouping tunnel-config {
        description
            "Grouping for tunnel interface configurations";
        leaf mode  {
            type  ipi-if-types:if_tunnel_mode_t;
            default "vxlan";
            description "This attribute is used to unset the tunnel mode";
        } // END of mode definition.

        leaf src  {
            type  inet:ipv4-address;
            description "This attribute is used to set tunnel source";
        } // END of src definition.

        leaf multicast-interface  {
            if-feature feature-list:HAVE_VXLAN;
            type  string {
                length "1..1965";
                pattern "[^?' =,>|]+";
            }
            description "This attribute is used to configure egress multicast interface for
                        tunnel";
        } // END of multicast-interface definition.

        leaf dst  {
            type  inet:ipv4-address;
            description "This attribute is used to set destination of tunnel packets";
        } // END of dst definition.

        leaf checksum-enable  {
            type  empty;
            description "This attribute is used to enable end to end checksumming of packets";
        } // END of checksum-enable definition.

        leaf tos-byte  {
            type  uint16 {
                 range "0..255"  {
                    description "0..255:type of service byte";
                 }
            }
            description "This attribute is used to set type of service byte";
        } // END of tos-byte definition.

        leaf ttl  {
            type  uint16 {
                 range "1..255"  {
                    description "1..255:tunnel time to live";
                 }
            }
            description "This attribute is used to set time to live";
        } // END of ttl definition.

        leaf path-mtu-enable  {
            type  empty;
            description "This attribute is used to enable Path MTU Discovery on tunnel";
        } // END of path-mtu-enable definition.

        leaf dst-mac-address  {
            if-feature feature-list:HAVE_USER_HSL;
            type  string {
                length "1..1965";
                pattern "[^?' =,>|]+";
            }
            description "This attribute is used to set next Hop Destination MAC Address of
                        Tunnel Packets";
        } // END of dst-mac-address definition.

        leaf gre-key  {
            if-feature feature-list:HAVE_GRE_KEY;
            type  ipi-if-types:if_tunnel_key_t;
            description "This attribute is used to set the gre-key for tunnel";
        } // END of gre-key definition.

    } // END of tunnel-config definition.
    grouping protocol-pkt-statistics {
        description
            "Grouping for interface protocol packets statistics";
        leaf in-bgp-pkts  {
            type  yang:counter32;
            description "bgp protocol packets received on the interface";
        } // END of in-bgp-pkts definition.

        leaf in-ospf-pkts  {
            type  yang:counter32;
            description "ospf protocol packets received on the interface";
        } // END of in-ospf-pkts definition.

        leaf in-isis-pkts  {
            type  yang:counter32;
            description "isis protocol packets received on the interface";
        } // END of in-isis-pkts definition.

        leaf in-ldp-rsvp-pkts  {
            type  yang:counter32;
            description "ldp_rsvp protocol packets received on the interface";
        } // END of in-ldp-rsvp-pkts definition.

        leaf in-arp-pkts  {
            type  yang:counter32;
            description "arp protocol packets received on the interface";
        } // END of in-arp-pkts definition.

        leaf in-evpn-pkts  {
            type  yang:counter32;
            description "evpn protocol packets received on the interface";
        } // END of in-evpn-pkts definition.

        leaf in-igmp-pkts  {
            type  yang:counter32;
            description "igmp protocol packets received on the interface";
        } // END of in-igmp-pkts definition.

        leaf in-pim-pkts  {
            type  yang:counter32;
            description "pim protocol packets received on the interface";
        } // END of in-pim-pkts definition.

        leaf in-bpdu-pkts  {
            if-feature feature-list:HAVE_DUNE;
            type  yang:counter32;
            description "bpdu protocol packets received on the interface";
        } // END of in-bpdu-pkts definition.

        leaf in-oamp-pkts  {
            if-feature feature-list:HAVE_DUNE;
            type  yang:counter32;
            description "oamp protocol packets received on the interface";
        } // END of in-oamp-pkts definition.

        leaf in-bfd-pkts  {
            if-feature feature-list:HAVE_DUNE;
            type  yang:counter32;
            description "bfd protocol packets received on the interface";
        } // END of in-bfd-pkts definition.

        leaf in-vrrp-rip-dhcp-pkts  {
            if-feature feature-list:HAVE_DUNE;
            type  yang:counter32;
            description "vrrp-rip-dhcp protocol packets received on the interface";
        } // END of in-vrrp-rip-dhcp-pkts definition.

        leaf in-rsvd-mc-pkts  {
            if-feature feature-list:HAVE_DUNE;
            type  yang:counter32;
            description "rsvd-mc protocol packets received on the interface";
        } // END of in-rsvd-mc-pkts definition.

        leaf in-link-local-pkts  {
            if-feature feature-list:HAVE_DUNE;
            type  yang:counter32;
            description "link-local protocol packets received on the interface";
        } // END of in-link-local-pkts definition.

        leaf in-icmp-pkts  {
            if-feature feature-list:HAVE_DUNE;
            type  yang:counter32;
            description "icmp protocol packets received on the interface";
        } // END of in-icmp-pkts definition.

        leaf in-icmp-redirect-pkts  {
            if-feature feature-list:HAVE_DUNE;
            type  yang:counter32;
            description "icmp-redirect protocol packets received on the interface";
        } // END of in-icmp-redirect-pkts definition.

        leaf in-misc-pkts  {
            if-feature feature-list:HAVE_DUNE;
            type  yang:counter32;
            description "misc protocol packets received on the interface";
        } // END of in-misc-pkts definition.

        leaf in-total-pkts  {
            type  yang:counter32;
            description "total protocol packets received on the interface";
        } // END of in-total-pkts definition.

    } // END of protocol-pkt-statistics definition.
    grouping obm-total-count-stats {
        description
            "Grouping for HAL interface OBM drop reason total statistics";
        leaf high-priority-drops  {
            type  yang:counter64;
            description "Packets dropped because of high priority over subscription";
        } // END of high-priority-drops definition.

        leaf low-priority-drops  {
            type  yang:counter64;
            description "Packets dropped because of low priority over subscription";
        } // END of low-priority-drops definition.

        leaf lossless0-drops  {
            type  yang:counter64;
            description "Packets dropped because of Lossless0 over subscription";
        } // END of lossless0-drops definition.

        leaf lossless1-drops  {
            type  yang:counter64;
            description "Packets dropped because of Lossless1 over subscription";
        } // END of lossless1-drops definition.

        leaf total-obm-drops  {
            type  yang:counter64;
            description "Total packets dropped because of over subscription";
        } // END of total-obm-drops definition.

    } // END of obm-total-count-stats definition.
    grouping obm-last-increment-count-stats {
        description
            "Grouping for HAL interface OBM Drop last-incremented statistics";
        leaf high-priority-drops  {
            type  yang:counter64;
            description "Last number of Packets dropped because of high priority over
                        subscription
                        This is Updated at every 5sec interval.";
        } // END of high-priority-drops definition.

        leaf low-priority-drops  {
            type  yang:counter64;
            description "Last number of Packets dropped because of low priority over
                        subscription
                        This is Updated at every 5sec interval.";
        } // END of low-priority-drops definition.

        leaf lossless0-drops  {
            type  yang:counter64;
            description "Last number of Packets dropped because of lossless0 over subscription
                        This is Updated at every 5sec interval.";
        } // END of lossless0-drops definition.

        leaf lossless1-drops  {
            type  yang:counter64;
            description "Last number of Packets dropped because of lossless1 over subscription
                        This is Updated at every 5sec interval.";
        } // END of lossless1-drops definition.

        leaf total-obm-drops  {
            type  yang:counter64;
            description "Total last number of packets dropped because of over subscription
                        This is Updated at every 5sec interval.";
        } // END of total-obm-drops definition.

    } // END of obm-last-increment-count-stats definition.
    grouping obm-last-increment-time-stats {
        description
            "Grouping for obm-OBM Drop statistics last-incremented timestamp";
        leaf high-priority-drops  {
            type  yang:date-and-time {
                pattern "\\d{4}-\\d{2}-\\d{2}T\\d{2}:\\d{2}:\\d{2}(\\.\\d+)?(Z|[\\+\\-]\\d{2}:\\d{2})";
                }
                description "Last increment time of OBM high priority dropped packets.
                            This is Updated at every 5sec interval.";
            } // END of high-priority-drops definition.

            leaf low-priority-drops  {
                type  yang:date-and-time {
                    pattern "\\d{4}-\\d{2}-\\d{2}T\\d{2}:\\d{2}:\\d{2}(\\.\\d+)?(Z|[\\+\\-]\\d{2}:\\d{2})";
                    }
                    description "Last increment time of OBM low priority dropped packets.
                                This is Updated at every 5sec interval.";
                } // END of low-priority-drops definition.

                leaf lossless0-drops  {
                    type  yang:date-and-time {
                        pattern "\\d{4}-\\d{2}-\\d{2}T\\d{2}:\\d{2}:\\d{2}(\\.\\d+)?(Z|[\\+\\-]\\d{2}:\\d{2})";
                        }
                        description "Last increment time of OBM lossless0 dropped packets.
                                    This is Updated at every 5sec interval.";
                    } // END of lossless0-drops definition.

                    leaf lossless1-drops  {
                        type  yang:date-and-time {
                            pattern "\\d{4}-\\d{2}-\\d{2}T\\d{2}:\\d{2}:\\d{2}(\\.\\d+)?(Z|[\\+\\-]\\d{2}:\\d{2})";
                            }
                            description "Last increment time of OBM lossless1 dropped packets.
                                        This is Updated at every 5sec interval.";
                        } // END of lossless1-drops definition.

                        leaf total-obm-drops  {
                            type  yang:date-and-time {
                                pattern "\\d{4}-\\d{2}-\\d{2}T\\d{2}:\\d{2}:\\d{2}(\\.\\d+)?(Z|[\\+\\-]\\d{2}:\\d{2})";
                                }
                                description "Total last increment time of OBM dropped packets.
                                            This is Updated at every 5sec interval.";
                            } // END of total-obm-drops definition.

    } // END of obm-last-increment-time-stats definition.
    grouping error-discard-statistics {
        description
            "Grouping for error_counters and discard_counters";
    } // END of error-discard-statistics definition.
    grouping queue-statistics {
        description
            "Grouping for CPU queue statistics";

        list queue-stats {
            if-feature feature-list:HAVE_HAL;
            if-feature feature-list:HAVE_BROADCOM;
            if-feature feature-list:NOT_HAVE_DUNE;
            key "queue-id";
            config false;
            description
                "CPU cos queue statistics";
            leaf queue-id  {
                type  uint8;
                description "This is a unique number representing each queue in CPU";
            } // END of queue-id definition.

            leaf queue-name  {
                type  string {
                    length "1..1965";
                    pattern "[^?' =,>|]+";
                }
                description "Queue Name corresponding to the Queue Id.";
            } // END of queue-name definition.

            leaf out-pkts  {
                type  yang:counter64;
                description "The number of outbound packets that are transmitted through the queue";
            } // END of out-pkts definition.

            leaf out-octets  {
                type  yang:counter64;
                description "The number of outbound bytes that are transmitted through the queue";
            } // END of out-octets definition.

            leaf out-dropped-pkts  {
                type  yang:counter64;
                description "The number of outbound packets that are dropped in the queue.";
            } // END of out-dropped-pkts definition.

            leaf out-dropped-octets  {
                type  yang:counter64;
                description "The number of outbound bytes that are dropped in the queue";
            } // END of out-dropped-octets definition.

            leaf queue-size-in-octets  {
                type  yang:counter64;
                description "The size of the queue, referred by the  queue Id";
            } // END of queue-size-in-octets definition.

            container cos-rate-stats {
                if-feature feature-list:HAVE_HAL;
                if-feature feature-list:HAVE_BROADCOM;
                if-feature feature-list:NOT_HAVE_DUNE;
                config false;
                description
                    "cpu cosq rate stats";
                leaf tx-pkt-rate  {
                    type  yang:counter32;
                    description "The number of outbound packets transmitted from the corresponding CPU
                                queue.";
                } // END of tx-pkt-rate definition.

                leaf tx-bit-rate  {
                    type  yang:counter32;
                    description "The number of outbound bytes transmitted from the corresponding CPU
                                queue.";
                } // END of tx-bit-rate definition.

                leaf rate-percent  {
                    type  int8;
                    description "Percentage of control packets transmitted in the CPU queue.
                                Value of -1 indicates rate percentage is not applicable.";
                } // END of rate-percent definition.

                leaf last-increment-count  {
                    type  yang:counter64;
                    description "The number of Last Dropped Pkts in the corresponding CPU queue.
                                This is Updated at every 5sec interval.";
                } // END of last-increment-count definition.

                leaf last-increment-time  {
                    type  yang:date-and-time {
                        pattern "\\d{4}-\\d{2}-\\d{2}T\\d{2}:\\d{2}:\\d{2}(\\.\\d+)?(Z|[\\+\\-]\\d{2}:\\d{2})";
                        }
                        description "Last increment time of Tx Dropped Packets in CPU Queue.
                                    This is Updated at every 5sec interval.";
                    } // END of last-increment-time definition.

            } // END of cos-rate-stats-container definition.
        } // End of queue-stats-list
    } // END of queue-statistics definition.
    grouping broadcast-config {
        description
            "Grouping for configurations";
        leaf bcast-value  {
            when " /ipi-interface:interfaces/ipi-interface:interface/ipi-interface:config/ipi-interface:switchport-status = 'true' ";
            type  ipi-if-types:if_rate_limit_t;
            mandatory true;
            description "This attribute is used to set the storm control configuration, Set
                        Broadcast Rate Limiting of layer2 Interface";
        } // END of bcast-value definition.

        leaf bcast-rate-limit-format  {
            type  ipi-if-types:if_rate_limit_type;
            mandatory true;
            description "This attribute is used to set the storm control configuration, Set the
                        format for units in kbps|mbps|gbps or level for threshold percentage";
        } // END of bcast-rate-limit-format definition.

    } // END of broadcast-config definition.
    grouping broadcast-state {
        description
            "Grouping for  state attributes";
        leaf bcast-discards  {
            if-feature feature-list:HAVE_HAL;
            if-feature feature-list:NOT_HAVE_BROADCOM;
            type  int32;
            config false;
            description "This attribute is used to denote the broadcast Storm Discards";
        } // END of bcast-discards definition.

        leaf hardware-applied-bcast-value  {
            if-feature feature-list:HAVE_BROADCOM;
            if-feature feature-list:HAVE_RATE_LIMIT;
            type  decimal64 {
                 fraction-digits 3;            }
            config false;
            description "This attribute is used to denote the hardware applied storm control
                        broadcast value when rate format is not set as level";
        } // END of hardware-applied-bcast-value definition.

    } // END of broadcast-state definition.
    grouping multicast-config {
        description
            "Grouping for configurations";
        leaf mcast-value  {
            when " /ipi-interface:interfaces/ipi-interface:interface/ipi-interface:config/ipi-interface:switchport-status = 'true' ";
            type  ipi-if-types:if_rate_limit_t;
            mandatory true;
            description "This attribute is used to set the storm control configuration,Set
                        Multicast Rate Limiting of layer2 Interface";
        } // END of mcast-value definition.

        leaf mcast-rate-limit-format  {
            type  ipi-if-types:if_rate_limit_type;
            mandatory true;
            description "This attribute is used to set the storm control configuration, Set the
                        format for units in kbps|mbps|gbps or level for threshold percentage";
        } // END of mcast-rate-limit-format definition.

    } // END of multicast-config definition.
    grouping multicast-state {
        description
            "Grouping for  state attributes";
        leaf mcast-discards  {
            if-feature feature-list:HAVE_HAL;
            if-feature feature-list:NOT_HAVE_BROADCOM;
            type  int32;
            config false;
            description "This attribute is used to denote Multicast Storm Discards";
        } // END of mcast-discards definition.

        leaf hardware-applied-mcast-value  {
            if-feature feature-list:HAVE_BROADCOM;
            if-feature feature-list:HAVE_RATE_LIMIT;
            type  decimal64 {
                 fraction-digits 3;            }
            config false;
            description "This attribute is used to denote the hardware applied storm control
                        multicast value when rate format is not set as level";
        } // END of hardware-applied-mcast-value definition.

    } // END of multicast-state definition.
    grouping dlf-broadcast-config {
        description
            "Grouping for configurations";
        leaf dlf-bcast-value  {
            when " /ipi-interface:interfaces/ipi-interface:interface/ipi-interface:config/ipi-interface:switchport-status = 'true' ";
            type  ipi-if-types:if_rate_limit_t;
            mandatory true;
            description "This attribute is used to set the storm control configuration,Set DLF
                        Broadcast Rate Limiting of layer2 Interface";
        } // END of dlf-bcast-value definition.

        leaf dlf-bcast-rate-limit-format  {
            type  ipi-if-types:if_rate_limit_type;
            mandatory true;
            description "This attribute is used to set the storm control configuration, Set the
                        format for units in kbps|mbps|gbps or level for threshold percentage";
        } // END of dlf-bcast-rate-limit-format definition.

    } // END of dlf-broadcast-config definition.
    grouping dlf-broadcast-state {
        description
            "Grouping for  state attributes";
        leaf dlf-bcast-discards  {
            if-feature feature-list:HAVE_HAL;
            if-feature feature-list:NOT_HAVE_BROADCOM;
            type  uint32;
            config false;
            description "This attribute is used to denote the DLF Bcast Storm Discards";
        } // END of dlf-bcast-discards definition.

        leaf hardware-applied-dlf-bcast-value  {
            if-feature feature-list:HAVE_BROADCOM;
            if-feature feature-list:HAVE_RATE_LIMIT;
            type  decimal64 {
                 fraction-digits 3;            }
            config false;
            description "This attribute is used to denote the hardware applied storm control
                        dlf broadcast value when rate format is not set as level";
        } // END of hardware-applied-dlf-bcast-value definition.

    } // END of dlf-broadcast-state definition.
    grouping if-arbiter-config {
        description
            "Grouping for interface Arbiter global configuration";
        leaf if-arbiter  {
            type  uint32 {
                 range "1..65535"  {
                    description "1..65535:Seconds";
                 }
            }
            default "20";
            description "Use this attribute to discover new interfaces recently added to the
                        kernel and add them to the OcNOS database.";
        } // END of if-arbiter definition.

    } // END of if-arbiter-config definition.

    grouping  extended-grouping {
    description
        "Top-level container for extended interface module";
    container extended {
        description
            "Top-level container for extended interface module";

        list l2-control-protocol {
            key "l2cp-type";
            description
                "Layer2 Control Protocol";
            leaf l2cp-type  {
                type  leafref {
                    path  "../config/l2cp-type";
                }
                description "This attribute is used to configure the layer2 control-protocol type";
            } // END of l2cp-type definition.

            container config {
                description
                    "Configuration data for Layer2 Control Protocol";
                uses l2cp-config;
            } // END of config-container definition.
            container state {
                config false;
                description
                    "Operational data for Layer2 Control Protocol";
                uses l2cp-config;
            } // END of state-container definition.
        } // End of l2-control-protocol-list
        container config {
            description
                "Configuration data for extended interface module";
            uses ipi-interface-extended-config;
        } // END of config-container definition.
        container state {
            config false;
            description
                "Counters/State data for extended interface module";
            uses ipi-interface-extended-config;
            uses ipi-interface-extended-state;
        } // END of state-container definition.
        container port-monitor {
            description
                "Container for Port-monitoring";
            container config {
                description
                    "Container for Port-monitor config";
                uses port-monitor-config;
            } // END of config-container definition.
            container state {
                config false;
                description
                    "State data for Port-monitoring";
                uses port-monitor-config;
            } // END of state-container definition.
            container port-monitor-threshold {
                description
                    "Container for Port-monitoring-threshold";
                container config {
                    presence "Port-monitor threshold config";
                    description
                        "Container for Port-monitor threshold config";
                    uses port-monitor-threshold-config;
                } // END of config-container definition.
                container state {
                    config false;
                    description
                        "State data for Port-monitoring";
                    uses port-monitor-threshold-config;
                } // END of state-container definition.
            } // END of port-monitor-threshold-container definition.
        } // END of port-monitor-container definition.
        container capabilities {
            if-feature feature-list:HAVE_HAL;
            config false;
            description
                "Container for physical interface capabilities";
            container state {
                config false;
                description
                    "Container for physical interface capabilities state";
                uses capabilities-state;
            } // END of state-container definition.
        } // END of capabilities-container definition.
        container subinterface-encapsulation {
            if-feature feature-list:HAVE_SUBINTERFACE;
            description
                "Container for dot1q and dot1ad encapsulation data";
            container vlan-service {
                description
                    "Container for vlan service";
                container config {
                    presence "Enable dot1q and dot1ad encapsulation";
                    description
                        "Configuration data for dot1q and dot1ad encapsulation";
                    uses subif-encapsulation-config;
                } // END of config-container definition.
                container state {
                    config false;
                    description
                        "Operational state data for dot1q and dot1ad encapsulation";
                    uses subif-encapsulation-config;
                } // END of state-container definition.
            } // END of vlan-service-container definition.
            container native-layer2 {
                description
                    "Container for native L2 subinterface";
                container config {
                    presence "Enable native L2 encapsulation";
                    description
                        "Configuration data for native L2 encapsulation";
                    uses native-layer2-encapsulation-config;
                } // END of config-container definition.
                container state {
                    config false;
                    description
                        "Operational state data for native L2 subinterface";
                    uses native-layer2-encapsulation-config;
                } // END of state-container definition.
            } // END of native-layer2-container definition.
            container rewrite {
                when " /ipi-interface:interfaces/ipi-interface:interface/ipi-if-extended:extended/ipi-if-extended:subinterface-encapsulation/ipi-if-extended:vlan-service/ipi-if-extended:config/ipi-if-extended:encapsulation-type  or /ipi-interface:interfaces/ipi-interface:interface/ipi-if-extended:extended/ipi-if-extended:subinterface-encapsulation/ipi-if-extended:native-layer2/ipi-if-extended:config/ipi-if-extended:l2-encapsulation-type ";
                description
                    "Container for rewrite action to push or translate the outer VLAN-id";
                container config {
                    presence "Enable rewrite action to push or translate the outer VLAN-id";
                    description
                        "Configuration data for rewrite action to push or translate the outer
                                VLAN-id";
                    uses subif-rewrite-config;
                } // END of config-container definition.
                container state {
                    config false;
                    description
                        "Operational state data for rewrite action to push or translate the
                                outer VLAN-id";
                    uses subif-rewrite-config;
                } // END of state-container definition.
            } // END of rewrite-container definition.
        } // END of subinterface-encapsulation-container definition.
    } // END of extended-container definition.
    } // END of extended-grouping definition.

    grouping  extended-ethernet-grouping {
    description
        "Top-level container for ethernet extensions";
    container extended-ethernet {
        description
            "Top-level container for ethernet extensions";
        container config {
            description
                "Configuration data for ethernet extensions";
            uses extended-ethernet-config;
        } // END of config-container definition.
        container state {
            config false;
            description
                "Counters/State data for ethernet extensions";
            uses extended-ethernet-config;
            uses extended-ethernet-state;
        } // END of state-container definition.
    } // END of extended-ethernet-container definition.
    } // END of extended-ethernet-grouping definition.

    grouping  storm-control-grouping {
    description
        "Container for storm-control module";
    container storm-control {
        if-feature feature-list:HAVE_RATE_LIMIT;
        description
            "Container for storm-control module";
        container broadcast {
            when " /ipi-interface:interfaces/ipi-interface:interface/ipi-if-ethernet:ethernet/ipi-if-extended:storm-control/ipi-if-extended:broadcast/ipi-if-extended:config/ipi-if-extended:bcast-value ";
            if-feature feature-list:HAVE_RATE_LIMIT;
            description
                "Storm-control Broadcast related commands";
            container config {
                if-feature feature-list:HAVE_RATE_LIMIT;
                presence "Enable Storm-control Broadcast";
                description
                    "Configuration data for Storm-control Broadcast module";
                uses broadcast-config;
            } // END of config-container definition.
            container state {
                if-feature feature-list:HAVE_RATE_LIMIT;
                config false;
                description
                    "Operational state data for Storm-control Broadcast module";
                uses broadcast-config;
                uses broadcast-state;
            } // END of state-container definition.
        } // END of broadcast-container definition.
        container multicast {
            when " /ipi-interface:interfaces/ipi-interface:interface/ipi-if-ethernet:ethernet/ipi-if-extended:storm-control/ipi-if-extended:multicast/ipi-if-extended:config/ipi-if-extended:mcast-value ";
            if-feature feature-list:HAVE_RATE_LIMIT;
            description
                "Storm-control Multicast related commands";
            container config {
                if-feature feature-list:HAVE_RATE_LIMIT;
                presence "Enable Storm-control Multicast";
                description
                    "Configuration data for Storm-control Multicast module";
                uses multicast-config;
            } // END of config-container definition.
            container state {
                if-feature feature-list:HAVE_RATE_LIMIT;
                config false;
                description
                    "Operational state data for Storm-control Multicast module";
                uses multicast-config;
                uses multicast-state;
            } // END of state-container definition.
        } // END of multicast-container definition.
        container dlf-broadcast {
            when " /ipi-interface:interfaces/ipi-interface:interface/ipi-if-ethernet:ethernet/ipi-if-extended:storm-control/ipi-if-extended:dlf-broadcast/ipi-if-extended:config/ipi-if-extended:dlf-bcast-value ";
            if-feature feature-list:HAVE_RATE_LIMIT;
            description
                "Storm-control DLF-Broadcast related commands";
            container config {
                if-feature feature-list:HAVE_RATE_LIMIT;
                presence "Enable Storm-control DLF-Broadcast";
                description
                    "Configuration data for Storm-control DLF-Broadcast module";
                uses dlf-broadcast-config;
            } // END of config-container definition.
            container state {
                if-feature feature-list:HAVE_RATE_LIMIT;
                config false;
                description
                    "Operational state data for Storm-control DLF-Broadcast module";
                uses dlf-broadcast-config;
                uses dlf-broadcast-state;
            } // END of state-container definition.
        } // END of dlf-broadcast-container definition.
    } // END of storm-control-container definition.
    } // END of storm-control-grouping definition.

    grouping  extended-counters-grouping {
    description
        "A collection of extended interface-related statistics counters";
    container extended-counters {
        config false;
        description
            "A collection of extended interface-related statistics counters";
        uses extended-counters-state;
        uses interface-counters-extended;
        uses error-discard-statistics;
    } // END of extended-counters-container definition.
    } // END of extended-counters-grouping definition.

    grouping  extended-ethernet-counters-grouping {
    description
        "A collection of extended interface-related ethernet counters";
    container extended-ethernet-counters {
        if-feature feature-list:HAVE_BROADCOM;
        if-feature feature-list:HAVE_HAL;
        if-feature feature-list:NOT_HAVE_SWFWDR;
        if-feature feature-list:NOT_HAVE_POND;
        config false;
        description
            "A collection of extended interface-related ethernet counters";
        container protocol-pkt-stats {
            if-feature feature-list:HAVE_HAL;
            if-feature feature-list:HAVE_BROADCOM;
            config false;
            description
                "Statistics for interface protocol packets";
            uses protocol-pkt-statistics;
        } // END of protocol-pkt-stats-container definition.
        uses extended-ethernet-counters-state;
    } // END of extended-ethernet-counters-container definition.
    } // END of extended-ethernet-counters-grouping definition.

    grouping  global-grouping {
    description
        "Top-level container for global interface-related module";
    container global {
        description
            "Top-level container for global interface-related module";
        container hardware-profile-flexport {
            if-feature feature-list:HAVE_FLEXPORT;
            description
                "Global Hardware Profile Flexport configuration container for router";
            container config {
                description
                    "Global hardware-profile configuration parameters for the router";
                uses hardware-profile-flexport-config;
            } // END of config-container definition.
            container state {
                config false;
                description
                    "State data for global hardware-profile";
                uses hardware-profile-flexport-config;
            } // END of state-container definition.
        } // END of hardware-profile-flexport-container definition.
        container error-disable {
            description
                "Global Error-Disable objects";
            container config {
                description
                    "Global error-disable configuration parameters for the router";
                uses error-disable-config;
            } // END of config-container definition.
            container state {
                config false;
                description
                    "State data for global error-disable";
                uses error-disable-config;
            } // END of state-container definition.
        } // END of error-disable-container definition.
    } // END of global-container definition.
    } // END of global-grouping definition.

    grouping  cross-connects-grouping {
    description
        "Global container for cross connect between subinterfaces";
    container cross-connects {
        description
            "Global container for cross connect between subinterfaces";

        list subinterface-cross-connect {
            if-feature feature-list:HAVE_SUBINTERFACE;
            key "xc-name";
            description
                "Global configuration for cross-connect between subinterfaces";
            leaf xc-name  {
                type  leafref {
                    path  "../config/xc-name";
                }
                description "This attribute specifies the cross-connect name. Use this attribute to
                            cross-connect between subinterfaces.";
            } // END of xc-name definition.

            container config {
                description
                    "Global configuration for cross-connect between subinterfaces";
                uses subif-crossconnect-config;
            } // END of config-container definition.
            container state {
                config false;
                description
                    "State data for cross-connect between subinterfaces";
                uses subif-crossconnect-config;
            } // END of state-container definition.
        } // End of subinterface-cross-connect-list
    } // END of cross-connects-container definition.
    } // END of cross-connects-grouping definition.

    grouping  tunnel-grouping {
    description
        "Interface tunnel related data";
    container tunnel {
        if-feature feature-list:HAVE_TUNNEL;
        description
            "Interface tunnel related data";
        container config {
            description
                "Configuration data for tunnel interface";
            uses tunnel-config;
        } // END of config-container definition.
        container state {
            config false;
            description
                "Operational state data for tunnel interface";
            uses tunnel-config;
        } // END of state-container definition.
    } // END of tunnel-container definition.
    } // END of tunnel-grouping definition.

    augment /ipi-interface:interfaces/ipi-interface:interface {
    when " /ipi-interface:interfaces/ipi-interface:interface/ipi-if-extended:extended ";
        description
            "Top-level container for extended interface module";
        uses extended-grouping;
    }

    augment /ipi-interface:interfaces/ipi-interface:interface/ipi-if-ethernet:ethernet {
        description
            "Top-level container for ethernet extensions";
        uses extended-ethernet-grouping;
    }

    augment /ipi-interface:interfaces/ipi-interface:interface/ipi-if-ethernet:ethernet {
    when " /ipi-interface:interfaces/ipi-interface:interface/ipi-interface:config/ipi-interface:switchport-status = 'true' ";
        description
            "Container for storm-control module";
        uses storm-control-grouping;
    }

    augment /ipi-interface:interfaces/ipi-interface:interface/ipi-interface:state/ipi-interface:counters {
        description
            "A collection of extended interface-related statistics counters";
        uses extended-counters-grouping;
    }

    augment /ipi-interface:interfaces/ipi-interface:interface/ipi-if-ethernet:ethernet/ipi-if-ethernet:state/ipi-if-ethernet:counters {
        description
            "A collection of extended interface-related ethernet counters";
        uses extended-ethernet-counters-grouping;
    }

    augment /ipi-interface:interfaces {
        description
            "Top-level container for global interface-related module";
        uses global-grouping;
    }

    augment /ipi-interface:interfaces {
        description
            "Global container for cross connect between subinterfaces";
        uses cross-connects-grouping;
    }

    augment /ipi-interface:interfaces/ipi-interface:interface {
        description
            "Interface tunnel related data";
        uses tunnel-grouping;
    }

    augment /ipi-interface:interfaces {
        description
            "Global configuration for Port-group";
        uses port-group-speed-map-grouping;
    }


    rpc clear-interface-forward-error-correction-counters {
        description "Use this RPC to clear interface forward error correction counters.";
        input  {
            leaf if-name  {
                type string;
                mandatory true;
                description "Name of the interface to clear counters for. Specify NULL to clear
                            counters for all interfaces";
            }
        }
    }

    rpc clear-interface-error-disable {
        description "Use this RPC to clear interface error disable counters.";
        input  {
            leaf if-name  {
                type string;
                mandatory true;
                description "Name of the interface to clear counters for. Specify NULL to clear
                            counters for all interfaces";
            }
        }
    }

    notification interface-error-disable-notification {

        description "The interface-Errdis-Notif/interfaceErrdisNotif is generated when an interface is error-disabled(error-disable-reason will have non-zero value) and when it recovers from errdisabled state (error-disable-reason will have '0'). Severity level is CRITICAL for interface going down and MINOR for interface moving to UP state when it recovers from errdisabled state..";

        // eventClass "STATE";
        leaf name {
            type  string;
        description
            "The textual name of the interface. The value of this
                    object should
                    be the name of the interface as assigned by the local device and
                    should be suitable for use in commands entered at the device's
                    `console'. This might be a text name, such as `le0' or a simple
                    port number, such as `1', depending on the interface naming syntax
                    of the device. If several entries in the ifTable together represent
                    a single interface as named by the device, then each will have the
                    same value of name. Note that for an agent which responds to SNMP
                    queries concerning an interface on some other (proxied) device,
                    then the value of name for such an interface is the proxied
                    device's local name for it. If there is no local name, or this
                    object is otherwise not applicable, then this object contains a
                    zero-length string.";
        }

        leaf error-disable-reason {
            type ipi-if-types:if_errdisable_state_t;
        description
            "This object specifies the event that caused the interface to be
                    error-disabled. If interface is error-disabled because of
                    lag-mismatch, value of this object is 1. If interface is
                    error-disabled because of stp-bpdu-guard, value of this object is 2.
                    If interface is error-disabled because of link-flap, value of this
                    object is 4.";
        }
    }

}
