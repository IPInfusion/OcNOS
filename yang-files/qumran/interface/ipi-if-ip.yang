/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-if-ip.yang
*
*/

module ipi-if-ip {

    yang-version 1.1;

    namespace   "http://www.ipinfusion.com/yang/ocnos/ipi-if-ip";

    prefix "ipi-if-ip";

    import cml-data-types {
        prefix cml-data-types;
        revision-date 2021-05-03;
    }

    import ipi-network-instance {
        prefix ipi-network-instance;
        revision-date 2020-12-15;
    }

    import ipi-vrf {
        prefix ipi-vrf;
        revision-date 2021-01-27;
    }

    import ipi-interface {
        prefix ipi-interface;
        revision-date 2021-06-14;
    }

    import ietf-inet-types {
        prefix inet;
        revision-date 2013-07-15;
    }

    import feature-list {
        prefix feature-list;
        revision-date 2021-05-03;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for IP interface module";


    revision "2021-01-27" {
        description "Removed interface mode on ipv6 address attribute";
        reference " 0.5.0.";
    }

    revision "2021-01-14" {
        description "Changed datatype for IPv6 address anycast attr from boolean to empty";
        reference " 0.4.0.";
    }

    revision "2020-12-15" {
        description "Change to have data-types in lower case instead of camel case";
        reference " 0.3.0.";
    }

    revision "2020-11-13" {
        description "Updated IP/IPv6/ICMP forwarding attribute from bool to empty, Added new attribute enable-dhcp-ip-address and enable-dhcp-ipv6-address";
        reference " 0.2.0.";
    }

    revision "2020-07-15" {
        description "Initial Version Openconfig Yang model : https://github.com/openconfig/public/blob/master/release/models/interfaces/openconfig-if-ip.yang";
        reference " 0.1.0.";
    }

    grouping ipv4-interface-config {
        description
            "Configuration data for IPv4 per interface";
        leaf primary-ip-addr  {
            // when " ipi-interface:interfaces/interface/config/switchport-status != '1' ";
            type  inet:ipv4-prefix;
            description "Use this attribute to specify that an IP address and prefix length
                        will be used by this interface. If the secondary parameter is not
                        specified, this attribute overwrites the primary IP address. If the
                        secondary parameter is specified, this attribute adds a new IP address
                        to the interface. The secondary address cannot be configured in the
                        absence of a primary IP address. The primary address cannot be removed
                        when a secondary address is present.";
        } // END of primary-ip-addr definition.

        leaf enable-dhcp-ip-address  {
            if-feature feature-list:HAVE_DHCP_CLIENT;
            type  empty;
            description "Use this attribute to  specify that a DHCP client will be used to
                        obtain an IP address for an interface.";
        } // END of enable-dhcp-ip-address definition.

        leaf prefix-length  {
            type  uint8;
            description "The subnet mask associated with the IPv4 address of this entry. The
                        value of the mask is an IPv4 address with all the network bits set to
                        1 and all the hosts bits set to 0.";
        } // END of prefix-length definition.

        leaf ip-addr-label  {
            // when " ipi-if-ip:ipv4/config/primary-ip-addr ";
            type  cml-data-types:cml_line_t {
                length "1..1965";
            }
            default "NULL";
            description "Label of this address.";
        } // END of ip-addr-label definition.

        leaf ipv4-unnumbered-if-name  {
            if-feature feature-list:HAVE_NSM_IF_UNNUMBERED;
            type  string {
                length "1..1965";
                pattern "[^?' =,>|]+";
            }
            description "This attribute is used to Enable IP processing without an explicit
                        address";
        } // END of ipv4-unnumbered-if-name definition.

        leaf remote-address  {
            if-feature feature-list:HAVE_NSM_IF_UNNUMBERED;
            type  string {
                length "1..1965";
                pattern "[^?' =,>|]+";
            }
            description "This attribute is used to set the remote address of the PPP link";
        } // END of remote-address definition.

    } // END of ipv4-interface-config definition.
    grouping ipv4-sec-addr-config {
        description
            "Per IPv4 secondary adresss configuration data for the interface";
        leaf ip-address  {
            type  inet:ipv4-prefix;
            description "Use this attribute to specify a secondary IP address that will be
                        used by this interface. The secondary address cannot be configured in
                        the absence of a primary IP address. The primary address cannot be
                        removed when a secondary address is present.";
        } // END of ip-address definition.

        leaf ip-label  {
            type  cml-data-types:cml_line_t {
                length "1..1965";
            }
            default "NULL";
            description "Use this attribute to specify a descriptive label for this IPv4
                        address.";
        } // END of ip-label definition.

    } // END of ipv4-sec-addr-config definition.
    grouping ipv4-interface-state {
        description
            "IPv4 operational state for the interface";
        leaf dhcp-ip-adddress  {
            if-feature feature-list:HAVE_DHCP_CLIENT;
            type  inet:ipv4-prefix;
            config false;
            description "This attribute displays the IPv4 address allocated by DHCP";
        } // END of dhcp-ip-adddress definition.

        leaf ipv4-enabled-status  {
            type  boolean;
            config false;
            description "This attribute displays IPv4 enable status";
        } // END of ipv4-enabled-status definition.

    } // END of ipv4-interface-state definition.
    grouping ipv6-interface-config {
        description
            "Configuration data for IPv6 per interface";
        leaf ipv6-unnumbered-if-name  {
            if-feature feature-list:HAVE_NSM_IF_UNNUMBERED;
            if-feature feature-list:HAVE_IPV6;
            type  string {
                length "1..1965";
                pattern "[^?' =,>|]+";
            }
            description "Use this attribute to enable IP processing without an explicit address";
        } // END of ipv6-unnumbered-if-name definition.

        leaf enable-dhcp-ipv6-address  {
            if-feature feature-list:HAVE_DHCP_CLIENT;
            type  empty;
            description "Use this attribute to  specify that a DHCP client will be used to
                        obtain an IP address for an interface.";
        } // END of enable-dhcp-ipv6-address definition.

        leaf dhcp-address-prefix-length  {
            if-feature feature-list:HAVE_DHCP_CLIENT;
            type  uint8 {
                 range "1..128"  {
                    description "1..128:IPv6 Prefix length range. Default is 128";
                 }
            }
            description "Use this attribute to configure the prefix length for the dynamically
                        learnt ipv6 address";
        } // END of dhcp-address-prefix-length definition.

        leaf enable-auto-config  {
            if-feature feature-list:HAVE_IPV6;
            type  boolean;
            description "";
        } // END of enable-auto-config definition.

    } // END of ipv6-interface-config definition.
    grouping ipv6-addr-config {
        description
            "Per IPV6 address configuration data for the interface";
        leaf ipv6-address  {
            type  inet:ipv6-prefix;
            description "Use this attribute to set the IPv6 address of an interface";
        } // END of ipv6-address definition.

        leaf anycast  {
            type  empty;
            description "Use this attribute to set the anycast flag for the IPv6
                        address of an interface.
                        Anycast flag cannot be deleted for an IPv6 address once set. Please
                        delete IPv6 address and reconfigure to remove anycast property.";
        } // END of anycast definition.

    } // END of ipv6-addr-config definition.
    grouping ipv6-interface-state {
        description
            "IPv6 operational state for the interface";
        leaf dhcp-ipv6-adddress  {
            if-feature feature-list:HAVE_DHCP_CLIENT;
            type  inet:ipv6-prefix;
            config false;
            description "This attribute is used to describes DHCP IPv6 Address";
        } // END of dhcp-ipv6-adddress definition.

        leaf ipv6-enabled-status  {
            if-feature feature-list:HAVE_IPV6;
            type  boolean;
            config false;
            description "This attribute describes the IPv6 capability status";
        } // END of ipv6-enabled-status definition.

        leaf forwarding-status  {
            if-feature feature-list:HAVE_IPV6;
            type  boolean;
            config false;
            description "This attribute describes the IPv6 Forwarding status";
        } // END of forwarding-status definition.

    } // END of ipv6-interface-state definition.
    grouping ip-global-config {
        description
            "Global IP related configuration data for the router";
        leaf router-id  {
            type  string {
                length "1..1965";
                pattern "[^?' =,>|]+";
            }
            description "Router id of the router - an unsigned 32-bit integer expressed in
                        dotted quad notation";
        } // END of router-id definition.

        leaf enable-auto-router-id-selection  {
            type  boolean;
            description "Turn on Automatic Selection of Router ID";
        } // END of enable-auto-router-id-selection definition.

        leaf disable-ip-forwarding  {
            type  empty;
            description "Enable IP forwarding for the router";
        } // END of disable-ip-forwarding definition.

        leaf disable-ipv6-forwarding  {
            if-feature feature-list:HAVE_IPV6;
            type  empty;
            description "Enable IPv6 forwarding for the router";
        } // END of disable-ipv6-forwarding definition.

        leaf default-vrf-enable-icmp-broadcast  {
            type  empty;
            description "This attribute is used to control ICMP echo broadcast reply. It
                        ignores ICMP echo broacast when set to true";
        } // END of default-vrf-enable-icmp-broadcast definition.

    } // END of ip-global-config definition.
    grouping ip-vrf-config {
        description
            "Per VRF configuration data for the router";
        leaf disable-ip-vrf-forwarding  {
            type  empty;
            description "Turn on IP forwarding for the VRF instance";
        } // END of disable-ip-vrf-forwarding definition.

        leaf disable-ipv6-vrf-forwarding  {
            if-feature feature-list:HAVE_IPV6;
            type  empty;
            description "Turn on IPv6 forwarding for the VRF instance";
        } // END of disable-ipv6-vrf-forwarding definition.

        leaf enable-icmp-broadcast  {
            type  empty;
            description "This attribute is used to control ICMP echo broadcast reply for VRF
                        instance. It ignores ICMP echo broacast when set to true";
        } // END of enable-icmp-broadcast definition.

    } // END of ip-vrf-config definition.

    grouping  ipv4-grouping {
    description
        "Parameters for the IPv4 address family";
    container ipv4 {
        description
            "Parameters for the IPv4 address family";

        list secondary-addresses {
        // when " ipi-if-ip:ipv4/config/primary-ip-addr ";
            key "ip-address";
            description
                "List of secondary IPv4 Addresses for the interface";
            leaf ip-address  {
                type  leafref {
                    path  "../config/ip-address";
                }
                description "Use this attribute to specify a secondary IP address that will be
                            used by this interface. The secondary address cannot be configured in
                            the absence of a primary IP address. The primary address cannot be
                            removed when a secondary address is present.";
            } // END of ip-address definition.

            container config {
                description
                    "IPv4 secondary address configuration data for the interface";
                uses ipv4-sec-addr-config;
            } // END of config-container definition.
            container state {
                config false;
                description
                    "IPv4 secondary address list operational information";
                uses ipv4-sec-addr-config;
            } // END of state-container definition.
        } // End of secondary-addresses-list
        container config {
            description
                "Top-level IPv4 configuration data for the interface";
            uses ipv4-interface-config;
        } // END of config-container definition.
        container state {
            config false;
            description
                "Top-level IPv4 operational state data for the interface";
            uses ipv4-interface-config;
            uses ipv4-interface-state;
        } // END of state-container definition.
    } // END of ipv4-container definition.
    } // END of ipv4-grouping definition.

    grouping  ipv6-grouping {
    description
        "Parameters for the IPv6 address family";
    container ipv6 {
        description
            "Parameters for the IPv6 address family";

        list addresses {
        when " /ipi-interface:interfaces/ipi-interface:interface/ipi-interface:config/ipi-interface:switchport-status != 'true' ";
            if-feature feature-list:HAVE_IPV6;
            key "ipv6-address";
            description
                "List of IPv6 Addresses for the interface";
            leaf ipv6-address  {
                type  leafref {
                    path  "../config/ipv6-address";
                }
                description "Use this attribute to set the IPv6 address of an interface";
            } // END of ipv6-address definition.

            container config {
                description
                    "IPv6 address configuration data for the interface";
                uses ipv6-addr-config;
            } // END of config-container definition.
            container state {
                config false;
                description
                    "IPv6 address list operational data for the interface";
                uses ipv6-addr-config;
            } // END of state-container definition.
        } // End of addresses-list
        container config {
            description
                "Top-level IPv6 configuration data for the interface";
            uses ipv6-interface-config;
        } // END of config-container definition.
        container state {
            config false;
            description
                "Top-level IPv6 operational state data for the interface";
            uses ipv6-interface-config;
            uses ipv6-interface-state;
        } // END of state-container definition.
    } // END of ipv6-container definition.
    } // END of ipv6-grouping definition.

    grouping  ip-global-grouping {
    description
        "Global configuration container for the router";
    container ip-global {
        description
            "Global configuration container for the router";

        list vrf {
            if-feature feature-list:HAVE_VRF;
            key "vrfName";
            description
                "List of Virtual Routing and Forwarding instances on the router";
            leaf vrfName  {
                type  leafref {
                    path  "/ipi-network-instance:network-instances/ipi-network-instance:network-instance/ipi-vrf:vrf/ipi-vrf:config/ipi-vrf:vrf-name";
                }
                description "VPN routing/forwarding Instance name";
            } // END of vrfName definition.

            container config {
                description
                    "Configuration parameters relating to a VRF instance";
                uses ip-vrf-config;
            } // END of config-container definition.
            container state {
                config false;
                description
                    "Configuration parameters relating to a VRF instance";
                uses ip-vrf-config;
            } // END of state-container definition.
        } // End of vrf-list
        container config {
            description
                "Global configuration parameters for the router";
            uses ip-global-config;
        } // END of config-container definition.
        container state {
            config false;
            description
                "Global operational parameters for the router";
            uses ip-global-config;
        } // END of state-container definition.
    } // END of ip-global-container definition.
    } // END of ip-global-grouping definition.

    augment /ipi-interface:interfaces/ipi-interface:interface {
        description
            "Parameters for the IPv4 address family";
        uses ipv4-grouping;
    }

    augment /ipi-interface:interfaces/ipi-interface:interface {
        description
            "Parameters for the IPv6 address family";
        uses ipv6-grouping;
    }

    uses ip-global-grouping;

}
