/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-if-types.yang
*
*/

module ipi-if-types {

    namespace   "http://www.ipinfusion.com/yang/ocnos/ipi-if-types";

    prefix "ipi-if-types";

    import ietf-inet-types {
        prefix inet;
    }

    organization
        "IP Infusion Inc.";

    contact
        "Address: 3965 Freedom Circle, Suite 200, Santa Clara, CA 95054
         Phone: +1 408-400-1900
         E-mail: support@ipinfusion.com
         Web: http://www.ipinfusion.com/";

    description
        "YANG version of the ipi-if-types";


    revision "2018-06-21" {
        description " Initial Version.";
        reference "Initial Version";
    }



typedef  IF_INTERFACE_OPER_STATUS_T {
    type enumeration {
        enum up {
            value 1;
            description "ready to pass packets";
        }
        enum down {
            value 2;
            description "down state";
        }
        enum testing {
            value 3;
            description "in some test mode";
        }
        enum unknown {
            value 4;
            description "status can not be determined for some reason";
        }
        enum dormant {
            value 5;
            description "not in a condition to pass packets but is instead in a pending state waiting for some external event. ";
        }
        enum notPresent {
            value 6;
            description "some component is missing";
        }
        enum lowerLayerDown {
            value 7;
            description "down due to state of lower-layer interface(s)";
        }
    }
    description "datatype for operational state of the interface";
}

typedef  IF_SUBIF_ENCAP_T {
    type enumeration {
        enum encapsulation {
            value 1;
            description "Configure encapsulation";
        }
    }
    description "datatype for configure the dot1q encapsulation";
}

typedef  IF_IFACE_PROP_T {
    type bits {
        bit interface_active {
            position 0;
            description "active interface";
        }
        bit dhcp_addr {
            position 15;
            description "IPV4 DHCP client is enabled";
        }
        bit dhcp6_addr {
            position 16;
            description "IPV6 DHCP IA-NA client is enabled";
        }
        bit Breakout_control_port {
            position 20;
            description "Breakout Control Port (Active)";
        }
        bit Bundle_control_port {
            position 21;
            description "Bundle Control Port (Active)";
        }
        bit Breakout_enable {
            position 22;
            description "port breakout enable";
        }
        bit Bundle_enable {
            position 23;
            description "port bundle enable";
        }
        bit Sbuport_inactive {
            position 24;
            description "Non Control Port (InActive)";
        }
    }
    description "datatype for interface mapping properties";
}

typedef  IF_LACP_PSC_T {
    type enumeration {
        enum dst-mac {
            value 1;
            description "Destination Mac address based load balancing";
        }
        enum src-mac {
            value 2;
            description "Source Mac address based load balancing";
        }
        enum src-dst-mac {
            value 3;
            description "Source and Destination Mac address based load balancing";
        }
        enum src-ip {
            value 4;
            description "Source IP address based load balancing";
        }
        enum dst-ip {
            value 5;
            description "Destination IP address based load balancing";
        }
        enum src-dst-ip {
            value 6;
            description "Source and Destination IP address based load balancing";
        }
        enum src-port {
            value 7;
            description "Source TCP/UDP port based load balancing";
        }
        enum dst-port {
            value 8;
            description "Destination TCP/UDP port based load balancing";
        }
        enum src-dst-port {
            value 9;
            description "Source and Destination TCP/UDP port based load balancing";
        }
    }
    description "datatype for LACP port-channel";
}

typedef  IF_DUPLEX_T {
    type enumeration {
        enum half {
            value 0;
            description "set half duplex";
        }
        enum full {
            value 1;
            description "set full duplex";
        }
    }
    description "datatype for interface duplex-mode";
}

typedef  IF_INTERFACE_ADMIN_STATUS_T {
    type enumeration {
        enum up {
            value 1;
            description "ready to pass packets";
        }
        enum down {
            value 2;
            description "down state";
        }
        enum testing {
            value 3;
            description "in some test mode";
        }
    }
    description "datatype for interface admin status";
}

typedef  IF_IANA_IF_TYPE_T {
    type enumeration {
        enum other {
            value 1;
            description "other";
        }
        enum regular1822 {
            value 2;
            description "regular1822";
        }
        enum hdh1822 {
            value 3;
            description "hdh1822";
        }
        enum ddnX25 {
            value 4;
            description "ddnX25";
        }
        enum rfc877x25 {
            value 5;
            description "rfc877x25 ";
        }
        enum ethernetCsmacd {
            value 6;
            description "ethernetCsmacd";
        }
    }
    description "datatype for interface type";
}

typedef  IF_HW_TYPE_T {
    type enumeration {
        enum UNK {
            value 0;
            description "UNK-Interface type unknown";
        }
        enum LB {
            value 1;
            description "LB-loopback";
        }
        enum ETH {
            value 2;
            description "ETH-Ethernet";
        }
        enum HDLC {
            value 3;
            description "HDLC";
        }
        enum PPP {
            value 4;
            description "PPP";
        }
        enum ATM {
            value 5;
            description "ATM";
        }
        enum FR {
            value 6;
            description "FR-Frame Relay";
        }
        enum SVI {
            value 7;
            description "VLAN";
        }
        enum AGG {
            value 9;
            description "AGG-aggregate";
        }
        enum PBB {
            value 11;
            description "PBB- PBB logical Port";
        }
        enum VP {
            value 12;
            description "VPORT- Virtual port";
        }
        enum CVP {
            value 13;
            description "CVP-Channelised Virtual port";
        }
        enum METH {
            value 14;
            description "Management Ethernet";
        }
        enum MLAG {
            value 16;
            description "MLAG-Mlag Aggregate";
        }
        enum TUN {
            value 101;
            description "TUN-Tunnel";
        }
    }
    description "datatype to describes HardWare Type";
}

typedef  IF_INTERFACE_SPEED_T {
    type enumeration {
        enum 10m {
            value 0;
            description "10 mega bits";
        }
        enum 100m {
            value 1;
            description "100 mega bits";
        }
        enum 1g {
            value 2;
            description "1 giga bits";
        }
        enum 2.5g {
            value 3;
            description "2.5 giga bits";
        }
        enum 10g {
            value 4;
            description "10 giga bits";
        }
        enum 20g {
            value 5;
            description "20 giga bits";
        }
        enum 25g {
            value 6;
            description "25 giga bits";
        }
        enum 40g {
            value 7;
            description "40 giga bits";
        }
        enum 50g {
            value 8;
            description "50 giga bits";
        }
        enum 100g {
            value 9;
            description "100 giga bits";
        }
        enum auto {
            value 10;
            description "Auto Negotiation";
        }
        enum auto-10m {
            value 11;
            description "Auto Negotiation, 10 mega bits";
        }
        enum auto-100m {
            value 12;
            description "Auto Negotiation, 100 mega bits";
        }
        enum auto-1g {
            value 13;
            description "Auto Negotiation, 1 giga bits";
        }
        enum auto-2.5g {
            value 14;
            description "Auto Negotiation, 2.5 giga bits";
        }
        enum auto-10g {
            value 15;
            description "Auto Negotiation, 10 giga bits";
        }
        enum auto-20g {
            value 16;
            description "Auto Negotiation, 20 giga bits";
        }
        enum auto-25g {
            value 17;
            description "Auto Negotiation, 25 giga bits";
        }
        enum auto-40g {
            value 18;
            description "Auto Negotiation, 40 giga bits";
        }
        enum auto-50g {
            value 19;
            description "Auto Negotiation, 50 giga bits";
        }
        enum auto-100g {
            value 20;
            description "Auto Negotiation, 100 giga bits";
        }
    }
    description "datatype for port-speed of interface";
}

typedef  IF_INTF_FEC_T {
    type enumeration {
        enum off {
            value 0;
            description "disable fec";
        }
        enum on {
            value 1;
            description "enable fec";
        }
        enum auto {
            value 2;
            description "enable fec auto";
        }
    }
    description "datatype for interface fec";
}

typedef  IF_MAUTYPE_T {
    type enumeration {
        enum dot3MauType10BaseTHD {
            value 10;
            description "UTP MAU half duplex mode";
        }
        enum dot3MauType10BaseTFD {
            value 11;
            description "UTP MAU full duplex mode";
        }
        enum dot3MauType100BaseTXHD {
            value 15;
            description "2 pair category 5 UTP half duplex mode";
        }
        enum dot3MauType100BaseTXFD {
            value 16;
            description "2 pair category 5 UTP full duplex mode";
        }
        enum dot3MauType1000BaseXHD {
            value 21;
            description "PCS/PMA unknown PMD half duplex mode";
        }
        enum dot3MauType1000BaseXFD {
            value 22;
            description "PCS/PMA unknown PMD full duplex mode";
        }
        enum dot3MauType10GigBaseCX4 {
            value 41;
            description "X copper over 8 pair 100-Ohm balanced cable";
        }
        enum dot3MauType10GbaseKX4 {
            value 57;
            description "4 lane X backplane full duplex mode only";
        }
        enum dot3MauType10GbaseKR {
            value 58;
            description "R backplane full duplex mode only";
        }
        enum dot3MauType40GbaseCR4 {
            value 71;
            description "40GBASE-R PCS/PMA over 4 lane shielded copper balanced cable";
        }
    }
    description "datatype for mau type of interface";
}

typedef  IF_BIND_INFO_T {
    type bits {
        bit vrf {
            position 0;
            description "Bind Information vrf";
        }
        bit mpls_vc {
            position 1;
            description "Bind Information mpls_vc";
        }
        bit mpls_vc_vlan {
            position 2;
            description "Bind Information mpls_vc_vlan";
        }
        bit vpls {
            position 3;
            description "Bind Information vpls";
        }
        bit vpls_vlan {
            position 4;
            description "Bind Information vpls_vlan";
        }
        bit vxlan {
            position 5;
            description "Bind Information vxlan";
        }
        bit nvgre {
            position 6;
            description "Bind Information nvgre";
        }
    }
    description "datatype for Bind information of interface";
}

typedef  IF_VRX_FLAG_T {
    type enumeration {
        enum normal {
            value 0;
            description "Normal Interface";
        }
        enum EVR-wrpj {
            value 1;
            description "EVR wrpj Interface";
        }
        enum VS-wrp {
            value 2;
            description "VS wrp Interface";
        }
    }
    description "datatype for vrx status";
}

typedef  IF_LOCAL_FLAG_T {
    type enumeration {
        enum localsrc {
            value 1;
            description "localsrc of VS";
        }
    }
    description "datatype for local source of VS";
}

typedef  IF_INTERFACE_TYPE_T {
    type enumeration {
        enum Router {
            value 0;
            description "L3 interface";
        }
        enum Switch {
            value 1;
            description "L2 interface";
        }
        enum TDM {
            value 2;
            description "TDM interface";
        }
    }
    description "datatype for interface type";
}

typedef  IF_TRUST_STATE_T {
    type enumeration {
        enum none {
            value 0;
            description "mls qos trust none";
        }
        enum cos {
            value 1;
            description "mls qos trust cos";
        }
        enum dscp {
            value 2;
            description "mls qos trust dscp";
        }
        enum ip-precedence {
            value 3;
            description "mls qos trust ip-precedence";
        }
        enum dscp-cos {
            value 6;
            description "mls qos trust cos and dscp both";
        }
    }
    description "datatype for trust interface state";
}

typedef  IF_TFO_LINK_TYPE_T {
    type enumeration {
        enum default {
            value 0;
            description "default link type";
        }
        enum uplink {
            value 1;
            description "link-type uplink";
        }
        enum downlink {
            value 2;
            description "link-type downlink";
        }
    }
    description "datatype for interface link type";
}

typedef  IF_NSM_BREAKOUT_TYPE_T {
    type enumeration {
        enum 4X10g {
            value 1;
            description "split to 4X10g";
        }
        enum 4X25g {
            value 2;
            description "split to 4X25g";
        }
        enum 2X50g {
            value 3;
            description "split to 2X50g";
        }
    }
    description "datatype for interface port breakout";
}

typedef  IF_MONITOR_TYPE_T {
    type enumeration {
        enum speed {
            value 1;
            description "Current average speed on the interface";
        }
        enum queue-drops {
            value 2;
            description "Queue-drops";
        }
    }
    description "datatype to monitor specified parameters for interface";
}

typedef  IF_L2CP_T {
    type enumeration {
        enum stp {
            value 0;
            description "Spanning Tree Protocols";
        }
        enum lacp {
            value 7;
            description "Link Aggregation (LACP)";
        }
        enum dot1x {
            value 8;
            description "Port Authentication (802.1 X)";
        }
        enum lldp {
            value 9;
            description "Link layer discovery protocol";
        }
        enum efm {
            value 11;
            description "Ethernet first mile (Link OAM)";
        }
        enum elmi {
            value 12;
            description "Ethernet local management interface";
        }
    }
    description "datatype for L2 Control Protocol";
}

typedef  IF_L2CP_PROCESS_T {
    type enumeration {
        enum peer {
            value 1;
            description "peer the protocol data unit";
        }
        enum tunnel {
            value 2;
            description "tunnel the protocol data unit";
        }
        enum discard {
            value 3;
            description "tunnel the protocol data unit";
        }
    }
    description "datatype for l2cp stats";
}

typedef  IF_ERROR_SET_TYPE_T {
    type enumeration {
        enum packet-loss {
            value 0;
            description "Error-Type - Packet-loss";
        }
        enum stray-packets {
            value 1;
            description "Error-Type - Stray-packets";
        }
        enum malformed-packets {
            value 2;
            description "Error-Type - Malformed-packets";
        }
        enum excessive-packet-loss-rate {
            value 3;
            description "Error-Type - Excessive packet loss rate";
        }
        enum buffer-overrun {
            value 4;
            description "Error-Type - Buffer-overrun";
        }
        enum remote-packet-loss {
            value 5;
            description "Error-Type - Remote packet loss";
        }
    }
    description "datatype for interface error-set";
}

typedef  IF_ERROR_CLEAR_TYPE_T {
    type enumeration {
        enum packet-loss {
            value 6;
            description "Error-Type - Packet-loss";
        }
        enum stray-packets {
            value 7;
            description "Error-Type - Stray-packets";
        }
        enum malformed-packets {
            value 8;
            description "Error-Type - Malformed-packets";
        }
        enum excessive-packet-loss-rate {
            value 9;
            description "Error-Type - Excessive packet loss rate";
        }
        enum buffer-overrun {
            value 10;
            description "Error-Type - Buffer-overrun";
        }
        enum remote-packet-loss {
            value 11;
            description "Error-Type - Remote packet loss";
        }
    }
    description "datatype for interface error-clear";
}

typedef  IF_RATE_LIMIT_LEVEL_T {

    type string;
    description "datatype for interface rate-limit-level";
}

typedef  IF_RATE_LIMIT_T {
    type union {
        type uint32 {
            range "0..100000000";

        }
        type IF_RATE_LIMIT_LEVEL_T {

        }
    }
    description "datatype for interface rate-limit";
}

typedef  IF_RATE_LIMIT_TYPE {
    type enumeration {
        enum kbps {
            value 1;
            description "Specifies the units of kilobits per second";
        }
        enum mbps {
            value 2;
            description "Specifies the units of megabits per second";
        }
        enum gbps {
            value 3;
            description "Specifies the units of gigabits per second";
        }
    }
    description "datatype for interface rate-limit-type";
}

typedef  IF_SUBIF_ENCAP_TYPE_T {
    type enumeration {
        enum dot1q {
            value 33024;
            description "IEEE 802.1Q VLAN-tagged packets";
        }
        enum dot1ad {
            value 34984;
            description "IEEE 802.1ad VLAN-tagged packets";
        }
    }
    description "datatype for sub-interface encap type";
}

typedef  IF_SUBIF_L2_ENCAP_TYPE_T {
    type enumeration {
        enum default {
            value 1;
            description "IEEE default packets";
        }
        enum untagged {
            value 2;
            description "IEEE untagged packets";
        }
    }
    description "datatype for sub-interface l2 encap type";
}

typedef  IF_SUBIF_L2_VLAN_ACTIONTYPE_T {
    type enumeration {
        enum push {
            value 2;
            description "Push the outer vid";
        }
        enum translate {
            value 3;
            description "Translate the outer vid";
        }
    }
    description "datatype for sub-interface l2 vlan action type";
}

typedef  IF_SUBIF_L2_VLAN_ACTIONPOP_T {
    type enumeration {
        enum pop {
            value 1;
            description "Pop the outer vid";
        }
    }
    description "datatype for sub-interface l2 vlan action-pop";
}

typedef  IF_SWITCHPORT_ETHERTYPE_T {
    type enumeration {
        enum dropped {
            value 0;
            description "dropped (0x0000)";
        }
        enum ipv4 {
            value 2048;
            description "IP (0x0800)";
        }
        enum arp {
            value 2054;
            description "Address Resolution Protocol (0x0806)";
        }
        enum ipv6 {
            value 34525;
            description "IPv6 (0x86DD)";
        }
        enum mpls {
            value 34887;
            description "mpls (0x8847)";
        }
    }
    description "datatype for packet ethertype";
}

typedef  IF_FLOWCTRL_T {
    type enumeration {
        enum off {
            value 0;
            description "Turn off flowcontrol";
        }
        enum on {
            value 1;
            description "Turn on flowcontrol";
        }
    }
    description "datatype for flowcontrol";
}

typedef  IF_RAW_STRING_T {

    type string;
    description "datatype for string";
}

typedef  IF_NSM_HARDWARE_PORTMODE_T {
    type enumeration {
        enum 4X10g {
            value 1;
            description "split to 4X10g";
        }
    }
    description "datatype for hardware port-mode";
}

typedef  IF_NSM_HARDWARE_PROFILE_PORTMODE_BUNDLE_T {
    type enumeration {
        enum 4X10g {
            value 6;
            description "unbundle 40g port";
        }
        enum 40g {
            value 7;
            description "bundle four 10g ports into 40g por";
        }
    }
    description "datatype for hardware profile port-mode bundle";
}

typedef  IF_NSM_ERR_REASON_T {
    type bits {
        bit lag-mismatch {
            position 0;
            description "Enable or Disable Lag-Mismatch";
        }
        bit stp-bpdu-guard {
            position 1;
            description "Enable or Disable Stp-Bpdu-Guard";
        }
        bit link-flap {
            position 2;
            description "Enable or Disable  Link-Flap";
        }
        bit mac-move-limit {
            position 3;
            description "Enable or Disable Mac-Move-Limit";
        }
    }
    description "datatype for nsm error reason";
}

typedef  IF_TUNNEL_MODE_T {
    type enumeration {
        enum vxlan {
            value 6;
            description "Vxlan encapsulation";
        }
    }
    description "datatype for tunnel mode";
}

typedef  IF_TUNNEL_KEY_T {
    type union {
        type uint32 {
            range "0..4294967295";

        }
        type inet:ipv4-address {

        }
    }
    description "datatype for tunnel key";
}

typedef  IF_TUNNEL_IPV6_MODE_T {
    type enumeration {
        enum ipv6ip {
            value 3;
            description "IPv6 over IP encapsulation";
        }
        enum 6to4 {
            value 4;
            description "IPv6 automatic tunnelling using 6to4";
        }
        enum isatap {
            value 5;
            description "IPv6 automatic tunnelling using ISATAP";
        }
    }
    description "datatype for tunnel ipv6 mode";
}

typedef  IF_NSM_PORT_GROUP_SPEED_T {
    type enumeration {
        enum 1g {
            value 1;
            description "port group speed 1g";
        }
        enum 10g {
            value 2;
            description "port group speed 10g";
        }
    }
    description "datatype for interface port group speed";
}

typedef  IF_NSM_ERRDISABLE_STATE_T {
    type bits {
        bit lag-mismatch {
            position 0;
            description "Lag-Mismatch";
        }
        bit stp-bpdu-guard {
            position 1;
            description "Stp-Bpdu-Guard";
        }
        bit link-flap {
            position 2;
            description "Link-Flap";
        }
        bit mac-move-limit {
            position 3;
            description "Mac-Move-Limit";
        }
        bit not-applicable {
            position 4;
            description "Not Applicable";
        }
    }
    description "datatype for error-disable state";
}

typedef  IF_SR_ABSOLUTE_T {

    type uint32{
     range 16000..23999;
    }
    description "datatype for segment routing sid as absolute value";
}

typedef  IF_SR_INDEX_T {

    type uint32{
     range 1..7999;
    }
    description "datatype for segment routing sid as index value";
}

typedef  IF_SR_PREFIX_FLAG_T {
    type enumeration {
        enum php {
            value 0;
            description "Default is PHP";
        }
        enum explicit-null {
            value 1;
            description "Set explicit-null";
        }
        enum no-php {
            value 2;
            description "Set no-PHP";
        }
    }
    description "datatype for segment routing prefix flag";
}

typedef  IF_SR_N_FLAG_CLEAR_T {
    type enumeration {
        enum n-flag {
            value 0;
            description "Default set n-flag";
        }
        enum n-flag-clear {
            value 1;
            description "Clear n-flag";
        }
    }
    description "datatype for segment routing N flag";
}

typedef  IF_SR_SID_T {
    type union {
        type IF_SR_ABSOLUTE_T {

        }
        type IF_SR_INDEX_T {

        }
    }
    description "datatype for segment routing sid type";
}

typedef  IF_LAST_CLEAR_TIME_T {

    type string;
    description "datatype for interface last clear time";
}

}
