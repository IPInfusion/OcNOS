/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-system.yang
*
*/

module ipi-system {

    yang-version 1.1;

    namespace   "http://www.ipinfusion.com/yang/ocnos/ipi-system";

    prefix "ipi-system";

    import cml-data-types {
        prefix cml-data-types;
    }

    import ietf-yang-types {
        prefix yang;
    }

    import feature-list {
        prefix feature-list;
    }

    organization
        "IP Infusion Inc.";

    contact
        "Address: 3965 Freedom Circle, Suite 200, Santa Clara, CA 95054
         Phone: +1 408-400-1900
         E-mail: support@ipinfusion.com
         Web: http://www.ipinfusion.com/";

    description
        "system global configs";


    revision "2020-12-15" {
        description "Change to have data-types in lower case instead of camel case";
        reference " 0.2.0.";
    }

    revision "2019-08-22" {
        description "Initial Version";
        reference " 0.1.0.";
    }



    typedef  system_time_duration {
        type string;
        description "Define how long the system up and running time";
    }    grouping system-clock-top {
        description
            "Top-level grouping for system-wide clock configuration";
        container clock {
            description
                "Top-level container for clock configuration data";
            container state {
                config false;
                description
                    "Operational state data for system clock";
                uses system-clock-state;
            } // END of state-container definition.
        } // END of clock-container definition.
    } // END of system-clock-top definition.
    grouping system-clock-state {
        description
            "Operational state data for system-wide clock configuration";
        leaf timezone-name  {
            type  string {
                length "1..max";
                pattern "[^?' =,>|]+";
            }
            description "The attribute display timezone name used for the system";
        } // END of timezone-name definition.

    } // END of system-clock-state definition.
    grouping system-global-state {
        description
            "system global state parameters";
        leaf software-version  {
            type  cml-data-types:cml_raw_string_t;
            description "This attribute display software version";
        } // END of software-version definition.

        leaf software-build-number  {
            if-feature feature-list:BUILD_PRODUCT_VERSION;
            if-feature feature-list:BUILD_NUMBER;
            type  cml-data-types:cml_raw_string_t;
            description "This attribute display software Build Number";
        } // END of software-build-number definition.

        leaf system-uptime  {
            type  system_time_duration;
            description "This attribute display how long the system has been up and running";
        } // END of system-uptime definition.

        leaf boot-time  {
            type  uint64;
            units "seconds";
            description "This timestamp indicates the time that the system was last restarted.
                        The value is the timestamp in seconds relative to the Unix Epoch (Jan
                        1, 1970 00:00:00 UTC)";
        } // END of boot-time definition.

        leaf current-datetime  {
            type  yang:date-and-time {
                pattern "\\d{4}-\\d{2}-\\d{2}T\\d{2}:\\d{2}:\\d{2}(\\.\\d+)?(Z|[\\+\\-]\\d{2}:\\d{2})";
                }
                description "This attribute display the current system date and time.";
            } // END of current-datetime definition.

    } // END of system-global-state definition.
    grouping system-global-config {
        description
            "system global config parameters";
        leaf hostname  {
            type  string {
                length "1..63";
                pattern "[^?' =,>|]+";
            }
            description "Use this command to set the network name for the device. OcNOS uses
                        this name in system prompts and default configuration filenames.
                        Setting a host name using this command also sets the host name in the
                        kernel.After giving the hostname command, you must write to memory
                        using the write command. If you do not write to memory, the change
                        made by this command (the new host name) is not set after the device
                        reboots.";
        } // END of hostname definition.

    } // END of system-global-config definition.

    grouping  system-info-grouping {
    description
        "Enclosing container for system-related configuration and operational
                state data";
    container system-info {
        description
            "Enclosing container for system-related configuration and operational
                    state data";
        container config {
            description
                "Global configuration data for the system";
            uses system-global-config;
        } // END of config-container definition.
        container state {
            config false;
            description
                "Global operational state data for the system";
            uses system-global-config;
            uses system-global-state;
        } // END of state-container definition.
        uses system-clock-top;
    } // END of system-info-container definition.
    } // END of system-info-grouping definition.

    uses system-info-grouping;

}
