/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-logging-remote.yang
*
*/

submodule ipi-logging-remote {

    yang-version 1.1;

    belongs-to  ipi-logging { prefix ipi-logging; }

    import ipi-network-instance {
        prefix ipi-network-instance;
    }

    import cml-data-types {
        prefix cml-data-types;
    }

    import ipi-logging-types {
        prefix ipi-logging-types;
    }

    import ipi-vrf {
        prefix ipi-vrf;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for logging configurations";


    revision "2021-01-05" {
        description "Adding this module as submodule of libsyslog after restructuring it";
        reference " 0.3.0.";
    }

    revision "2020-12-15" {
        description "Change to have data-types in lower case instead of camel case";
        reference " 0.2.0.";
    }

    revision "2020-09-03" {
        description "Initial Version: Restructuring according to OpenConfig style";
        reference " 0.1.0.";
    }



    grouping rsyslog-grouping {
    description
        "Remote Logging feature";
        list rsyslog {
            key "vrf";
            max-elements 1;
            description
                "Remote Logging feature";
            leaf vrf  {
                type  leafref {
                    path  "../config/vrf";
                }
                description "VRF name for which the feature is being enabled";
            } // END of vrf definition.

            container config {
                description
                    "Configuration data";
                uses logging-feature-rsyslog-config;
            } // END of config-container definition.
            container state {
                config false;
                description
                    "Operational state data";
                uses logging-feature-rsyslog-config;
            } // END of state-container definition.
            uses logging-remote-server-top;
        } // End of rsyslog-list
    } // END of rsyslog-grouping definition.
    grouping logging-debug-host-config {
        description
            "Grouping for logging debug configuration";
        leaf host  {
            type  empty;
            description "This attribute enables/disables the logging host debug.";
        } // END of host definition.

    } // END of logging-debug-host-config definition.
    grouping logging-debug-terminal-state {
        description
            "Grouping for terminal debug operational state";
        leaf debug-host  {
            type  empty;
            description "This attribute indicates the terminal logging host debug operational
                        state.";
        } // END of debug-host definition.

    } // END of logging-debug-terminal-state definition.
    grouping logging-remote-server-config {
        description
            "Grouping for remote server configuration";
        leaf address  {
            type  cml-data-types:cml_hostname_t;
            description "Use this attribute to set a syslog server. Each syslog server can be
                        configured by address or hostname. You can configure the maximum 5
                        servers.";
        } // END of address definition.

        leaf severity  {
            type  ipi-logging-types:log_severity_t;
            mandatory true;
            description "This atribute is used to specify the kind of messages by severity
                        level. The default value is debug-detail. The possible values for
                        levels are as follows:
                        [Operator] 0-emerg; 1-alert; 2-critical; 3-error; 4-notify; 5-info
                        [Debug] 3-error; 4-warning; 5-notif; 6-debug-info; 7-debug-detail";
        } // END of severity definition.

    } // END of logging-remote-server-config definition.
    grouping logging-remote-server-top {
        description
            "Grouping for remote server configuration";
        container remote-servers {
            description
                "Remote servers configuration";

            list remote-server {
                key "address";
                max-elements 5;
                description
                    "list of servers";
                leaf address  {
                    type  leafref {
                        path  "../config/address";
                    }
                    description "Use this attribute to set a syslog server. Each sys log server can be
                                configured by address or hostname. You can configure the maximum 5
                                servers.";
                } // END of address definition.

                container config {
                    description
                        "Configuration data";
                    uses logging-remote-server-config;
                } // END of config-container definition.
                container state {
                    config false;
                    description
                        "Operational state data";
                    uses logging-remote-server-config;
                } // END of state-container definition.
            } // End of remote-server-list
        } // END of remote-servers-container definition.
    } // END of logging-remote-server-top definition.
    grouping logging-feature-rsyslog-config {
        description
            "Grouping for feature rsyslog configuration";
        leaf vrf  {
            type  leafref {
                path  "/ipi-network-instance:network-instances/ipi-network-instance:network-instance/ipi-vrf:vrf/ipi-vrf:config/ipi-vrf:vrf-name";
            }
            description "VRF name for which the feature is being enabled";
        } // END of vrf definition.

        leaf enable-rsyslog  {
            type  ipi-logging-types:log_rsyslog_feature_t;
            mandatory true;
            description "Enable/disable the rsyslog feature";
        } // END of enable-rsyslog definition.

    } // END of logging-feature-rsyslog-config definition.
    grouping logging-global-rsyslog-config {
        description
            "Grouping for global rsyslog configuration";
        leaf remote-server-facility  {
            type  ipi-logging-types:log_facility_t;
            default "local7";
            description "This attribute is used to specify the facility level used by syslog
                        messages. The default value is local7. The possible values are local0,
                        local1, local2, local3, local4, local5, local6, local7 and user.";
        } // END of remote-server-facility definition.

    } // END of logging-global-rsyslog-config definition.

    grouping  debug-grouping {
    description
        "Debugging functions";
    container debug {
        when " /logging/rsyslog/config/enable-rsyslog ";
        description
            "Debugging functions";
        container config {
            description
                "Configuration data";
            uses logging-debug-host-config;
        } // END of config-container definition.
        container state {
            config false;
            description
                "Operational state data";
            container terminal {
                config false;
                description
                    "Terminal debug operational state";
                uses logging-debug-terminal-state;
            } // END of terminal-container definition.
            uses logging-debug-host-config;
        } // END of state-container definition.
    } // END of debug-container definition.
    } // END of debug-grouping definition.

    grouping  global-grouping {
    description
        "Global rsyslog configuration";
    container global {
        when " /logging/rsyslog/config/enable-rsyslog ";
        description
            "Global rsyslog configuration";
        container config {
            description
                "Configuration data";
            uses logging-global-rsyslog-config;
        } // END of config-container definition.
        container state {
            config false;
            description
                "Operational state data";
            uses logging-global-rsyslog-config;
        } // END of state-container definition.
    } // END of global-container definition.
    } // END of global-grouping definition.


}
