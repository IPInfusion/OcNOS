/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-logging.yang
*
*/

module ipi-logging {

    yang-version 1.1;

    namespace   "http://www.ipinfusion.com/yang/ocnos/ipi-logging";

    prefix "ipi-logging";

    import ipi-logging-types {
        prefix ipi-logging-types;
    }

    include ipi-logging-remote;
    include ipi-logging-cli;
    organization
        "IP Infusion Inc.";

    contact
        "Address: 3965 Freedom Circle, Suite 200, Santa Clara, CA 95054
         Phone: +1 408-400-1900
         E-mail: support@ipinfusion.com
         Web: http://www.ipinfusion.com/";

    description
        "Syslog Configurations";


    revision "2021-01-05" {
        description "Restructured module as per open-config";
        reference " 0.2.0.";
    }

    revision "2018-06-21" {
        description "Initial Version";
        reference " 0.1.0.";
    }

    grouping logging-syslog-config {
        description
            "Grouping for syslog configuration";
        leaf enable-syslog  {
            type  empty;
            description "Use this attribute to begin logging of information to the system log
                        and set the level to debug.";
        } // END of enable-syslog definition.

        leaf timestamp-granularity  {
            type  ipi-logging-types:timestamp_units_t;
            default "milliseconds";
            description "Use this attribute to set the logging timestamp granularity.";
        } // END of timestamp-granularity definition.

    } // END of logging-syslog-config definition.
    grouping logging-syslog-top {
        description
            "Grouping for syslog configuration";
        container syslog {
            description
                "Syslog configuration parameters";
            container config {
                description
                    "Configuration data";
                uses logging-syslog-config;
            } // END of config-container definition.
            container state {
                config false;
                description
                    "Operational state data";
                uses logging-syslog-config;
            } // END of state-container definition.
        } // END of syslog-container definition.
    } // END of logging-syslog-top definition.
    grouping logging-debug-logfile-config {
        description
            "Grouping for debug logging log file configuration";
        leaf file-name  {
            type  string {
                length "1..max";
                pattern "[^?' =,>|]+";
            }
            mandatory true;
            description "Set name of the debug log file.";
        } // END of file-name definition.

        leaf max-file-size  {
            type  uint32 {
                 range "4096..4194304"  {
                    description "Enter the logfile size in bytes";
                 }
            }
            units "bytes";
            mandatory true;
            description "Set size of the debug log file in bytes. The default value is 4194304
                        bytes.";
        } // END of max-file-size definition.

    } // END of logging-debug-logfile-config definition.
    grouping logging-debug-logfile-top {
        description
            "Grouping for debug logging log file configuration";
        container debug-logfile {
            description
                "Log file logging debug configuration parameters";
            container config {
                presence "yes";
                description
                    "Configuration data";
                uses logging-debug-logfile-config;
            } // END of config-container definition.
            container state {
                config false;
                description
                    "Operational state data";
                uses logging-debug-logfile-config;
            } // END of state-container definition.
        } // END of debug-logfile-container definition.
    } // END of logging-debug-logfile-top definition.
    grouping logging-logfile-config {
        description
            "Grouping for logging log file configuration";
        leaf file-name  {
            type  string {
                length "1..max";
                pattern "[a-zA-Z0-9_]*";
            }
            mandatory true;
            description "Use this attribute to set name of the logging file.";
        } // END of file-name definition.

        leaf severity-level  {
            type  ipi-logging-types:log_severity_t;
            mandatory true;
            description "Use this attribute to set severity level of logging file. Default
                        value is 6-debug-info.";
        } // END of severity-level definition.

        leaf max-file-size  {
            type  uint32 {
                 range "4096..419430400"  {
                    description "Enter the logfile size in bytes (Default size: 419430400)";
                 }
            }
            units "bytes";
            mandatory true;
            description "Set size of the log file in bytes. Default value is 419430400 bytes.";
        } // END of max-file-size definition.

    } // END of logging-logfile-config definition.
    grouping logging-logfile-top {
        description
            "Grouping for logging log file configuration";
        container logfile {
            description
                "Log file logging configuration parameters";
            container config {
                presence "yes";
                description
                    "Configuration data";
                uses logging-logfile-config;
            } // END of config-container definition.
            container state {
                config false;
                description
                    "Operational state data";
                uses logging-logfile-config;
            } // END of state-container definition.
        } // END of logfile-container definition.
    } // END of logging-logfile-top definition.
    grouping logging-console-config {
        description
            "Grouping for logging console configuration";
        leaf enable-logging  {
            type  empty;
            mandatory true;
            description "Use this attribute to enable the logging console.";
        } // END of enable-logging definition.

        leaf severity-level  {
            type  ipi-logging-types:log_severity_t;
            mandatory true;
            description "Use this attribute to set severity level of logging console. Default
                        value is 2-critical.";
        } // END of severity-level definition.

    } // END of logging-console-config definition.
    grouping logging-console-top {
        description
            "Grouping for logging console configuration";
        container console-logging {
            description
                "Console logging configuration parameters";
            container config {
                presence "yes";
                description
                    "Configuration data";
                uses logging-console-config;
            } // END of config-container definition.
            container state {
                config false;
                description
                    "Operational state data";
                uses logging-console-config;
            } // END of state-container definition.
        } // END of console-logging-container definition.
    } // END of logging-console-top definition.
    grouping logging-monitor-config {
        description
            "Grouping for logging monitor configuration";
        leaf enable-logging  {
            type  empty;
            mandatory true;
            description "Use this attribute to enable logging monitor.";
        } // END of enable-logging definition.

        leaf severity-level  {
            type  ipi-logging-types:log_severity_t;
            mandatory true;
            description "Use this attribute to set severity level of logging monitor. Default
                        value is 7-debug-details.";
        } // END of severity-level definition.

    } // END of logging-monitor-config definition.
    grouping logging-monitor-top {
        description
            "Grouping for logging monitor configuration";
        container monitor-logging {
            description
                "Monitor logging configuration parameters";
            container config {
                presence "yes";
                description
                    "Configuration data";
                uses logging-monitor-config;
            } // END of config-container definition.
            container state {
                config false;
                description
                    "Operational state data";
                uses logging-monitor-config;
            } // END of state-container definition.
        } // END of monitor-logging-container definition.
    } // END of logging-monitor-top definition.
    grouping logging-module-config {
        description
            "Grouping for syslog modules level configuration";
        leaf module-name  {
            type  ipi-logging-types:module_names_t;
            description "Use this attribute to set the module name of proccess to be logged.";
        } // END of module-name definition.

        leaf severity-level  {
            type  ipi-logging-types:log_severity_t;
            mandatory true;
            description "Use this attribute to set the severity level that a message for a
                        specific module must reach before the messages is logged. Default
                        value is 2-critical.";
        } // END of severity-level definition.

    } // END of logging-module-config definition.
    grouping logging-module-top {
        description
            "Grouping for syslog modules level configuration";

        list module-logging {
            key "module-name";
            description
                "Modules";
            leaf module-name  {
                type  leafref {
                    path  "../config/module-name";
                }
                description "Use this attribute to set the module name of proccess to be logged.";
            } // END of module-name definition.

            container config {
                description
                    "Configuration data";
                uses logging-module-config;
            } // END of config-container definition.
            container state {
                config false;
                description
                    "Operational state data";
                uses logging-module-config;
            } // END of state-container definition.
        } // End of module-logging-list
    } // END of logging-module-top definition.

    grouping  logging-grouping {
    description
        "Logging control";
    container logging {
        description
            "Logging control";
        uses logging-module-top;
        uses logging-monitor-top;
        uses logging-console-top;
        uses logging-logfile-top;
        uses logging-debug-logfile-top;
        uses logging-syslog-top;
        uses rsyslog-grouping;
        uses debug-grouping;
        uses global-grouping;
        uses cli-logging-grouping;
    } // END of logging-container definition.
    } // END of logging-grouping definition.

    uses logging-grouping;

    rpc logging-terminal-debug-on {
        description "Enables the logging host debug";
    }

    rpc logging-terminal-debug-off {
        description "Disables the logging host debug";
    }

    rpc logging-clear-debug-logfile {
        description "Use logging-clear-debug-logfile to clear the debug logfile content.";
    }

    rpc logging-clear-logging-logfile {
        description "Use logging-clear-logging-logfile to clear the logging logfile
                    content.";
    }

}
