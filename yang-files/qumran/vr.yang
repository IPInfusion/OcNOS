/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : vr.yang
*
*/

module vr {

    namespace   "http://www.ipinfusion.com/yang/ocnos/vr";

    prefix "vr";

    import cml-data-types {
        prefix cml-data-types;
    }

    import feature-list {
        prefix feature-list;
    }

    organization
        "IP Infusion Inc.";

    contact
        "Address: 3965 Freedom Circle, Suite 200, Santa Clara, CA 95054
         Phone: +1 408-400-1900
         E-mail: support@ipinfusion.com
         Web: http://www.ipinfusion.com/";

    description
        "Virtual router";


    revision "2018-06-21" {
        description " Initial Version.";
        reference "Initial Version";
    }



    grouping vr-grouping {
    description
        "Virtual router object";
        list vr {
            key "vrId";
            description
                "Virtual router object";
            leaf vrId  {
                type  uint32 {
                     range "0..255"  {
                        description "vrId";
                     }
                }
                description "Virtual router id";
            } // END of vrId definition.

            leaf name  {
                type  string {
                    pattern "[^?' =,>|]*";
                    }
                    description "";
                } // END of name definition.


            list vrInstances {
                if-feature feature-list:HAVE_VR;
                key "vrName";
                description
                    "object for virtual router configurations";
                leaf vrName  {
                    type  string {
                        length "1..12";

                        pattern "[^?' =,>|]*";
                    }
                    description "Virtual router name";
                } // END of vrName definition.

                leaf description  {
                    type  cml-data-types:CML_LINE_T;
                    description "Virtual router description";
                } // END of description definition.

                leaf protocol  {
                    type  cml-data-types:CML_VR_PROTOCOL_T;
                    description "protocol load";
                } // END of protocol definition.

                leaf configurationFile  {
                    type  string {
                        pattern "[^?' =,>|]*";
                        }
                        description "Virtual router configuration file";
                    } // END of configurationFile definition.

                    leaf configReadWrite  {
                        type  cml-data-types:CML_VR_CONFIG_T;
                        description "Virtual router configuration file";
                    } // END of configReadWrite definition.

            } // End of vrInstances-list
        } // End of vr-list
    } // END of vr-grouping definition.

        uses vr-grouping;

}
