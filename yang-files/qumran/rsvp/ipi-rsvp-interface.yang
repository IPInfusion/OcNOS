/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-rsvp-interface.yang
*
*/

submodule ipi-rsvp-interface {

    yang-version 1.1;

    belongs-to  ipi-rsvp { prefix ipi-rsvp; }

    import ipi-interface {
        prefix ipi-interface;
    }

    import ipi-rsvp-types {
        prefix ipi-rsvp-types;
    }

    import ietf-inet-types {
        prefix inet;
    }

    organization
        "IP Infusion Inc.";

    contact
        "Address: 3965 Freedom Circle, Suite 200, Santa Clara, CA 95054
         Phone: +1 408-400-1900
         E-mail: support@ipinfusion.com
         Web: http://www.ipinfusion.com/";

    description
        "Resource Reservation Protocol";


    revision "2021-01-27" {
        description "Updated XPATH to API mappings. Fixed known bugs";
        reference " 0.3.0.";
    }

    revision "2020-12-15" {
        description "Change to have data-types in lower case instead of camel case";
        reference " 0.2.0.";
    }

    revision "2018-06-21" {
        description "Initial Version";
        reference " 0.1.0.";
    }

    grouping rsvp-data-link-state {
        description
            "Operational parameters for rsvp data link";
        leaf data-link-name  {
            type  string {
                length "1..max";
                pattern "[^?' =,>|]+";
            }
            description "Name of the RSVP data link";
        } // END of data-link-name definition.

        leaf gmpls-interface-index  {
            type  int32;
            description "RSVP data link interface index";
        } // END of gmpls-interface-index definition.

        leaf local-link-id  {
            type  string {
                length "1..max";
                pattern "[^?' =,>|]+";
            }
            description "local link identifier";
        } // END of local-link-id definition.

        leaf remote-link-id  {
            type  string {
                length "1..max";
                pattern "[^?' =,>|]+";
            }
            description "Remote link identifier";
        } // END of remote-link-id definition.

        leaf interface-name  {
            type  string {
                length "1..max";
                pattern "[^?' =,>|]+";
            }
            description "Name of the interface";
        } // END of interface-name definition.

        leaf te-link-name  {
            type  string {
                length "1..max";
                pattern "[^?' =,>|]+";
            }
            description "Name of the te link";
        } // END of te-link-name definition.

    } // END of rsvp-data-link-state definition.
    grouping rsvp-data-link-interfaces-state {
        description
            "Operational parameters for rsvp data link interface";
        leaf rsvp-status  {
            type  ipi-rsvp-types:rsvp_interface_status_t;
            description "RSVP GMPLS data link interface status";
        } // END of rsvp-status definition.

        leaf label-space-status  {
            type  ipi-rsvp-types:rsvp_label_space_status_t;
            description "RSVP data link interface label space value";
        } // END of label-space-status definition.

        leaf local-interface-index  {
            type  uint32;
            description "Index of the local interface";
        } // END of local-interface-index definition.

        leaf local-interface-label-space  {
            type  uint16;
            description "local interface label space value";
        } // END of local-interface-label-space definition.

        leaf local-interface-minimum-label-value  {
            type  uint32;
            description "local interface Minimum label value";
        } // END of local-interface-minimum-label-value definition.

        leaf local-interface-maximum-label-value  {
            type  uint32;
            description "local interface Maximum label value";
        } // END of local-interface-maximum-label-value definition.

    } // END of rsvp-data-link-interfaces-state definition.
    grouping rsvp-rr-state {
        description
            "Operational parameters for rsvp interface refresh reduction";
        leaf refresh-reduction  {
            type  empty;
            description "Status of refresh reduction";
        } // END of refresh-reduction definition.

        leaf message-ack  {
            type  empty;
            description "Status of Message Acknowledgement for this interface";
        } // END of message-ack definition.

        leaf ack-wait-interval  {
            type  uint16;
            description "Status of acknowledgement wait timeout for this interface";
        } // END of ack-wait-interval definition.

    } // END of rsvp-rr-state definition.
    grouping rsvp-non-iana-hello-config {
        description
            "Configuration parameters for rsvp interface IANA hello";
        leaf enable-iana-hello-config  {
            type  empty;
            description "Enable the exchange of non IANA specific Hello messages";
        } // END of enable-iana-hello-config definition.

    } // END of rsvp-non-iana-hello-config definition.
    grouping rsvp-interface-attributes-config {
        description
            "Configuration parameters for rsvp interface";
        leaf enable-rsvp  {
            type  empty;
            description "Use this attribute to enable control adjacency to send and receive
                        RSVP-TE control messages for MPLS and GMPLS";
        } // END of enable-rsvp definition.

    } // END of rsvp-interface-attributes-config definition.
    grouping rsvp-interface-attributes-state {
        description
            "Operational parameters for rsvp interface";
        leaf selected-ipv4-address  {
            type  inet:ipv4-address;
            description "configured IPV4 addresss on RSVP enabled interface";
        } // END of selected-ipv4-address definition.

        leaf selected-ipv6-address  {
            type  inet:ipv6-address;
            description "configured IPV6 addresss on RSVP enabled interface";
        } // END of selected-ipv6-address definition.

        leaf interface-type  {
            type  ipi-rsvp-types:rsvp_interface_type_t;
            description "Type of the interface like Ethernet, ATM or Frame Relay";
        } // END of interface-type definition.

        leaf interface-index  {
            type  uint32;
            description "value of the interface index";
        } // END of interface-index definition.

        leaf rsvp-status  {
            type  ipi-rsvp-types:rsvp_status_t;
            description "status of the RSVP interface (enable/disable)";
        } // END of rsvp-status definition.

        leaf-list administrative-group-name  {
            type  string {
                length "1..max";
                pattern "[^?' =,>|]+";
            }
            description "Name of the Administrative Group. Administrative Group name should be
                        configured before";
        } // END of administrative-group-name definition.

        leaf bundle-buffer-size  {
            type  uint16;
            description "Size of the bundle message consists of several standard RSVP messages
                        that are grouped into a single RSVP message.";
        } // END of bundle-buffer-size definition.

        leaf epoch  {
            type  uint32;
            description "Current Epoch Value";
        } // END of epoch definition.

    } // END of rsvp-interface-attributes-state definition.
    grouping rsvp-global-hellos-config {
        description
            "configuration parameters for hello messages";
        leaf enable-hello-receipt  {
            type  empty;
            description "Use this attribute to enable the receipt of Hello messages from peers.";
        } // END of enable-hello-receipt definition.

        leaf hello-interval  {
            type  int32 {
                 range "1..65535"  {
                    description "Interval value in seconds";
                 }
            }
            default "2";
            description "Use this attribute to set an interval between Hello packets.Used as a
                        global command, this value is over-ridden by the hello-interval set on
                        the interface (see rsvp hello-interval).For optimum performance, set
                        this value no more than one-third of the hello-timeout value.";
        } // END of hello-interval definition.

        leaf hello-timeout  {
            type  int32 {
                 range "1..65535"  {
                    description "Timeout value in seconds";
                 }
            }
            default "7";
            description "Timeout for clearing up all sessions shared with a neighbor.If an LSR
                        has not received a Hello message from a peer within the number of
                        seconds set with this command, all sessions shared with this peer are
                        reset. The hello-timeout determines how long an RSVP node waits for a
                        hello message before declaring a neighbor to be down.";
        } // END of hello-timeout definition.

    } // END of rsvp-global-hellos-config definition.
    grouping rsvp-global-hellos {
        description
            "Top level groupings for hello messages";
        container hellos {
            description
                "container for hello";
            container config {
                description
                    "configuration container for hello messages";
                uses rsvp-global-hellos-config;
            } // END of config-container definition.
            container state {
                config false;
                description
                    "Operational container for hello messages";
                uses rsvp-global-hellos-config;
            } // END of state-container definition.
        } // END of hellos-container definition.
    } // END of rsvp-global-hellos definition.
    grouping rsvp-rr-config {
        description
            "configuration parameters for route-refresh";
        leaf enable-message-ack  {
            type  empty;
            description "Use this attribute to enable message acknowledgement for all messages
                        being sent to neighbors that are known to support refresh reduction.";
        } // END of enable-message-ack definition.

        leaf enable-refresh-reduction  {
            type  empty;
            description "Use this attribute to enable refresh reduction capability
                        advertisement for all interfaces";
        } // END of enable-refresh-reduction definition.

        leaf ack-wait-timeout  {
            type  uint32 {
                 range "1..65535"  {
                    description "Specify a value for the acknowledgement wait timeout";
                 }
            }
            default "10";
            description "Use this attribute to configure the acknowledgement wait timeout for
                        all RSVP-TE neighbors";
        } // END of ack-wait-timeout definition.

        leaf refresh-time  {
            type  uint16 {
                 range "1..65535"  {
                    description "Specify a value for RSVP refresh interval timer";
                 }
            }
            default "30";
            description "Use this attribute to configure RSVP refresh interval timer. The timer
                        specifies the interval after which Path and/ or Reservation Request
                        (Resv) messages will be sent out.The refresh time and keep multiplier
                        are two interrelated timing parameters used to calculate the valid
                        Reservation Lifetime for an LSP. Refresh time regulates the interval
                        between Refresh messages which include Path and Reservation Request
                        (Resv) messages. Refresh messages are sent periodically so that
                        reservation does not timeout in the neighboring nodes. Each sender and
                        receiver host sends Path and Resv messages, downstream and upstream
                        respectively, along the paths.";
        } // END of refresh-time definition.

        leaf keep-multiplier  {
            type  int32 {
                 range "1..255"  {
                    description "Specify a value for the keep multiplier";
                 }
            }
            default "3";
            description "Use this attribute to configure the constant to be used to calculate a
                        valid reservation lifetime for a Labeled Switched Path (LSP).The
                        refresh time and keep multiplier are two interrelated timing
                        parameters used to calculate the valid reservation lifetime for an
                        LSP. The router sends refresh messages periodically so that the
                        neighbors do not timeout";
        } // END of keep-multiplier definition.

    } // END of rsvp-rr-config definition.
    grouping rsvp-interfaces-control-adjacency-state {
        description
            "Operational parameters for rsvp control adjacency";
        leaf control-channel-name  {
            type  string {
                length "1..max";
                pattern "[^?' =,>|]+";
            }
            description "Name of the Control Channel";
        } // END of control-channel-name definition.

        leaf control-channel-gmpls-interface-index  {
            type  uint32;
            description "Indec of the interface of Control Channel";
        } // END of control-channel-gmpls-interface-index definition.

        leaf control-channel-id  {
            type  uint32;
            description "Identifier of the control channel";
        } // END of control-channel-id definition.

        leaf binding-interface-index  {
            type  uint32;
            description "Index of the binding interface";
        } // END of binding-interface-index definition.

        leaf local-address  {
            type  inet:ip-address;
            description "Control-Channel Local-address";
        } // END of local-address definition.

        leaf remote-address  {
            type  inet:ip-address;
            description "Control-Channel Peer-address";
        } // END of remote-address definition.

    } // END of rsvp-interfaces-control-adjacency-state definition.

    grouping  interfaces-grouping {
    description
        "Container for RSVP interface";
    container interfaces {
        when " /rsvp-te/rsvp-instance/config ";
        description
            "Container for RSVP interface";

        list interface {
            key "name";
            description
                "Top level list for RSVP interface";
            leaf name  {
                type  leafref {
                    path  "/ipi-interface:interfaces/ipi-interface:interface/ipi-interface:name";
                }
                description "Reference to interface name";
            } // END of name definition.

            container config {
                description
                    "configuration container for rsvp interface";
                uses rsvp-interface-attributes-config;
                uses rsvp-non-iana-hello-config;
            } // END of config-container definition.
            container state {
                config false;
                description
                    "state parameters for RSVP interface";
                uses rsvp-interface-attributes-config;
                uses rsvp-non-iana-hello-config;
                uses rsvp-interface-attributes-state;
            } // END of state-container definition.
            container refresh-reduction {
                description
                    "configuration container for rsvp interface refresh reduction";
                container config {
                    description
                        "configuration container for rsvp interface refresh reduction";
                    uses rsvp-rr-config;
                } // END of config-container definition.
                container state {
                    config false;
                    description
                        "state parameters for rsvp interface refresh-reduction";
                    uses rsvp-rr-config;
                } // END of state-container definition.
            } // END of refresh-reduction-container definition.
            container hellos {
                description
                    "container for hello";
                container config {
                    description
                        "configuration container for hello messages";
                    uses rsvp-global-hellos-config;
                } // END of config-container definition.
                container state {
                    config false;
                    description
                        "Operational container for hello messages";
                    uses rsvp-global-hellos-config;
                } // END of state-container definition.
            } // END of hellos-container definition.
        } // End of interface-list
    } // END of interfaces-container definition.
    } // END of interfaces-grouping definition.


}
