/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-pcep-stats.yang
*
*/

submodule ipi-pcep-stats {

    yang-version 1.1;

    belongs-to  ipi-pcep { prefix ipi-pcep; }

    import ietf-yang-types {
        prefix yang;
        revision-date 2013-07-15;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for PCEP Entity Statictics";


    revision "2021-03-02" {
        description "Addtion of new attributes for peer counters";
        reference " 0.3.0.";
    }

    revision "2020-12-15" {
        description "Change to have data-types in lower case instead of camel case";
        reference " 0.2.0.";
    }

    revision "2018-06-21" {
        description "Initial version of PCEP Statistics datamodel";
        reference " 0.1.0.";
    }

    grouping peer-counters-common-state {
        description
            "Operation data related to sent and received PCEP messages";
        leaf tx-open-message  {
            type  yang:counter32;
            description "Number of PCReq or PCRep messages sent.";
        } // END of tx-open-message definition.

        leaf tx-keep-alive  {
            type  yang:counter32;
            description "Number of keepalive messages sent.";
        } // END of tx-keep-alive definition.

        leaf tx-pc-notifications  {
            type  yang:counter32;
            description "Number of PCNtf messages sent.";
        } // END of tx-pc-notifications definition.

        leaf tx-path-request-errors  {
            type  yang:counter32;
            description "Number of PCErr messages sent.";
        } // END of tx-path-request-errors definition.

        leaf tx-path-request  {
            type  yang:counter32;
            description "Number of path request messages sent.";
        } // END of tx-path-request definition.

        leaf tx-request  {
            type  yang:counter32;
            description "Number of path request objects sent.";
        } // END of tx-request definition.

        leaf tx-request-for-pending-reply  {
            type  yang:counter32;
            description "Number of requests that have been sent for which a response
                        is still pending.";
        } // END of tx-request-for-pending-reply definition.

        leaf tx-request-for-error-received  {
            type  yang:counter32;
            description "Number of requests that were rejected with a PCErr message.";
        } // END of tx-request-for-error-received definition.

        leaf tx-request-for-nopath-receive  {
            type  yang:counter32;
            description "Number of requests that have been sent for which a response
                        with a NO-PATH object was received.";
        } // END of tx-request-for-nopath-receive definition.

        leaf tx-request-for-cancel-receive  {
            type  yang:counter32;
            description "Number of requests that were cancelled with a PCNtf message
                        and number of requests that were received from the peer and explicitly
                        cancelled by the peer sending a PCNtf.";
        } // END of tx-request-for-cancel-receive definition.

        leaf tx-request-for-ero-received  {
            type  yang:counter32;
            description "Number of requests that were cancelled with a PCNtf
                        message.";
        } // END of tx-request-for-ero-received definition.

        leaf tx-request-timed-out  {
            type  yang:counter32;
            description "Number of requests that have been sent to a peer and have
                        been abandoned because the peer has taken too long to respond to them.";
        } // END of tx-request-timed-out definition.

        leaf tx-request-sent-cancel-sent  {
            type  yang:counter32;
            description "Number of requests that were sent to the peer and explicitly cancelled
                        by the local PCEP entity sending
                        a PCNotification.";
        } // END of tx-request-sent-cancel-sent definition.

        leaf tx-request-sent-closed  {
            type  yang:counter32;
            description "The number of requests that were sent to the peer and
                        implicitly cancelled when the session they were sent
                        over was closed.";
        } // END of tx-request-sent-closed definition.

        leaf rx-open-message  {
            type  yang:counter32;
            description "Number of PCReq or PCRep messages received.";
        } // END of rx-open-message definition.

        leaf rx-keep-alive  {
            type  yang:counter32;
            description "Number of keepalive messages received.";
        } // END of rx-keep-alive definition.

        leaf rx-pc-notifications  {
            type  yang:counter32;
            description "Number of PCNtf messages received.";
        } // END of rx-pc-notifications definition.

        leaf rx-path-request-errors  {
            type  yang:counter32;
            description "Number of PCErr messages received.";
        } // END of rx-path-request-errors definition.

        leaf rx-path-reply  {
            type  yang:counter32;
            description "Number of PCRep messages received.";
        } // END of rx-path-reply definition.

        leaf rx-unknown  {
            type  yang:counter32;
            description "Number of unknown messages received.";
        } // END of rx-unknown definition.

        leaf rx-corrupt  {
            type  yang:counter32;
            description "Number of corrupted PCEP message received.";
        } // END of rx-corrupt definition.

    } // END of peer-counters-common-state definition.
    grouping peer-counters-stateful-state {
        description
            "Operation data related to stateful report messages";
        leaf tx-path-reports  {
            type  yang:counter32;
            description "Number of PCRpt messages sent.";
        } // END of tx-path-reports definition.

        leaf tx-reports  {
            type  yang:counter32;
            description "Number of LSP Reports sent.A LSP report
                        corresponds 1:1 with an LSP object in a PCRpt
                        message. This might be greater than
                        num-pcrpt-sent because multiple reports can
                        be batched into a single PCRpt message.";
        } // END of tx-reports definition.

        leaf rx-path-updates  {
            type  yang:counter32;
            description "Number of PCUpd messages received.";
        } // END of rx-path-updates definition.

        leaf rx-updates  {
            type  yang:counter32;
            description "Number of LSP updates received.";
        } // END of rx-updates definition.

        leaf rx-pc-initiate  {
            type  yang:counter32;
            description "Number of PCInitiate messages received.";
        } // END of rx-pc-initiate definition.

        leaf rx-lsp-initiate  {
            type  yang:counter32;
            description "The number of LSP Initiation received from
                        PCE.  A LSP initiation corresponds 1:1 with
                        an LSP object in a PCInitiate message. This
                        might be greater than num-pcinitiate-rcvd
                        because multiple initiations can be batched
                        into a single PCInitiate message.";
        } // END of rx-lsp-initiate definition.

    } // END of peer-counters-stateful-state definition.
    grouping peer-counters-state {
        description
            "Operation data related to the request and response timers";
        leaf session-setup-fail  {
            type  yang:counter32;
            description "The number of PCEP sessions with the peer that have been
                        attempted but failed  before being fully established.";
        } // END of session-setup-fail definition.

    } // END of peer-counters-state definition.
    grouping pcep-peer-counters {
        description
            "PCEP Session statistics data";
        container counters {
            config false;
            description
                "Gather the statistics for sent and received PCEP messages";
            container stateful {
                config false;
                description
                    "The configured stateful PCE parameters";
                uses peer-counters-stateful-state;
            } // END of stateful-container definition.
            uses peer-counters-state;
            uses peer-counters-common-state;
        } // END of counters-container definition.
    } // END of pcep-peer-counters definition.


}
