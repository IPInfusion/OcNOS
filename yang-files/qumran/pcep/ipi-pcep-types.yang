/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-pcep-types.yang
*
*/

module ipi-pcep-types {

    yang-version 1.1;

    namespace   "http://www.ipinfusion.com/yang/ocnos/ipi-pcep-types";

    prefix "ipi-pcep-types";

    organization
        "IP Infusion Inc.";

    contact
        "Address: 3965 Freedom Circle, Suite 200, Santa Clara, CA 95054
         Phone: +1 408-400-1900
         E-mail: support@ipinfusion.com
         Web: http://www.ipinfusion.com/";

    description
        "YANG version of the ipi-pcep-types";


    revision "2021-03-15" {
        description "Addition of new datatypes related to PCEP tunnel Operational attributes";
        reference " 0.3.0.";
    }

    revision "2020-12-15" {
        description "Change to have data-types in lower case instead of camel case";
        reference " 0.2.0.";
    }

    revision "2018-06-21" {
        description "Initial Version";
        reference " 0.1.0.";
    }



    typedef  pcep_dlg_recovery_type_t {
        type enumeration {
            enum local-control {
                value 1;
                description "Signaling the LSP using local CSPF";
            }
            enum removal {
                value 2;
                description "Cleanup of the LSP";
            }
        }
        description "type definition for PCEP_DLG_RECOVERY_TYPE_T";
    }

    typedef  pcep_role_t {
        type enumeration {
            enum unknown {
                value 0;
                description "An unknown role";
            }
            enum pcc {
                value 1;
                description "The role of a Path Computation Client";
            }
            enum pce {
                value 2;
                description "The role of Path Computation Element";
            }
            enum pcc-and-pce {
                value 3;
                description "The role of both Path Computation Client and Path Computation Element";
            }
        }
        description "type definition for PCEP_ROLE_T";
    }

    typedef  pcep_initiator_t {
        type enumeration {
            enum local {
                value 1;
                description "The local PCEP entity initiated the session";
            }
            enum remote {
                value 2;
                description "The remote PCEP peer initiated the session";
            }
        }
        description "type definition for PCEP_INITIATOR_T";
    }

    typedef  pcep_session_state_t {
        type enumeration {
            enum idle {
                value 0;
                description "The down state of PCEP session";
            }
            enum tcp-pending {
                value 1;
                description "The tcp-pending state of PCEP session";
            }
            enum open-wait {
                value 2;
                description "The open-wait state of PCEP session";
            }
            enum keep-wait {
                value 3;
                description "The keep-wait state of PCEP session";
            }
            enum session-up {
                value 4;
                description "The session-up state of PCEP sessio";
            }
        }
        description "type definition for PCEP_SESSION_STATE_T";
    }

    typedef  pcep_lsp_oper_status_t {
        type enumeration {
            enum down {
                value 0;
                description "not active";
            }
            enum up {
                value 1;
                description "signalled";
            }
            enum active {
                value 2;
                description "up and carrying traffic";
            }
            enum going-up {
                value 3;
                description "LSP is being torn down, resources are being released";
            }
            enum going-down {
                value 4;
                description "LSP is being signalled";
            }
        }
        description "type definition for PCEP_LSP_OPER_STATUS_T";
    }

    typedef  pcep_lsp_setup_type_t {
        type enumeration {
            enum TE {
                value 1;
                description "PCEP Tunnels";
            }
            enum TE-P2P {
                value 2;
                description "PCEP Tunnels";
            }
            enum TP {
                value 3;
                description "PCEP Tunnels";
            }
            enum SR {
                value 4;
                description "SR Label Switched Paths";
            }
            enum GMPLS {
                value 5;
                description "PCEP GMPLS Paths";
            }
            enum STATIC {
                value 6;
                description "PCEP Static Paths";
            }
            enum TE-BYPASS {
                value 7;
                description "PCEP Bypass Paths";
            }
            enum UNKNOWN {
                value 8;
                description "PCEP Unknown Tunnels";
            }
        }
        description "type definition for PCEP_LSP_SETUP_TYPE_T";
    }

    typedef  pcep_lsp_error_t {
        type enumeration {
            enum no-error {
                value 1;
                description "No error, LSP is fine";
            }
            enum unknown {
                value 2;
                description "Unknown reason";
            }
            enum limit {
                value 3;
                description "Limit reached for PCE-controlled LSPs";
            }
            enum pending {
                value 4;
                description "Too many pending LSP update requests";
            }
            enum unacceptable {
                value 5;
                description "Unacceptable parameters";
            }
            enum internal {
                value 6;
                description "Internal error";
            }
            enum admin {
                value 7;
                description "LSP administratively brought down";
            }
            enum preempted {
                value 8;
                description "LSP preempted";
            }
            enum rsvp-signaling {
                value 9;
                description "RSVP signaling error";
            }
        }
        description "type definition for PCEP_LSP_ERROR_T";
    }

    typedef  pcep_debug_t {
        type bits {
            bit events {
                position 0;
                description "Path Computation Client FSM events";
            }
            bit error {
                position 1;
                description "Path Computation Client error";
            }
            bit packet {
                position 2;
                description "Path Computation Client packets";
            }
            bit timer {
                position 3;
                description "Path Computation Client timers";
            }
            bit update {
                position 4;
                description "Path Computation Update message";
            }
            bit report {
                position 5;
                description "Path Computation Report message";
            }
            bit instantiation {
                position 6;
                description "Path Computation instantiation message";
            }
            bit delegation {
                position 7;
                description "Path Computation delegation message";
            }
            bit request {
                position 8;
                description "Path Computation Request messages";
            }
        }
        description "type definition for PCEP_DEBUG_T";
    }

    typedef  pcep_infinity_t {
        type enumeration {
            enum infinity {
                value 0;
                description "Maintain the LSP state infinitely";
            }
        }
        description "type definition for PCEP_INFINITY_T";
    }

    typedef  pcep_lsp_state_timeout_t {
        type union {
            type uint32 {
                range "1..600";

            }
            type pcep_infinity_t {

            }
        }
        description "type definition for PCEP_LSP_STATE_TIMEOUT_T";
    }

    typedef  pcep_tunnel_err_flags_t {
        type bits {
            bit hop-limit {
                position 0;
                description "Error Flag Tunnel Hop Limit";
            }
            bit priority-setup {
                position 1;
                description "Error Flag Tunnel Priority Setup";
            }
            bit priority-hold {
                position 2;
                description "Error Flag Tunnel Priority Hold";
            }
            bit metric {
                position 3;
                description "Error Flag Tunnel Metric";
            }
            bit old-bandwidth {
                position 4;
                description "Error Flag Tunnel Old Bandwidth";
            }
            bit bandwidth {
                position 5;
                description "Error Flag Tunnel Bandwidth";
            }
            bit affinity-include-any {
                position 6;
                description "Error Flag Tunnel Include Any ";
            }
            bit affinity-include-all {
                position 7;
                description "Error Flag Tunnel Include All";
            }
            bit affinity-exclude-any {
                position 8;
                description "Error Flag Tunnel Exclude Any";
            }
            bit path-option {
                position 9;
                description "Error Flag Tunnel Path Option";
            }
            bit path-rro {
                position 10;
                description "Error Flag Tunnel RRO";
            }
            bit path-ero {
                position 11;
                description "Error Flag Tunnel ERO";
            }
            bit metric-bound {
                position 12;
                description " Error Flag Metric bound";
            }
            bit unknown-request {
                position 13;
                description "Error Flag Tunnel Unknown Obj";
            }
        }
        description "type definition for PCEP_TUNNEL_ERR_FLAGS_T";
    }

    typedef  pcep_tunnel_request_flags_t {
        type bits {
            bit hop-limit {
                position 0;
                description "Request Flag Tunnel Hop Limit";
            }
            bit priority-setup {
                position 1;
                description "Request Flag Tunnel Priority Setup";
            }
            bit priority-hold {
                position 2;
                description "Request Flag Tunnel Priority Hold";
            }
            bit metric {
                position 3;
                description "Request Flag Tunnel Metric";
            }
            bit old-bandwidth {
                position 4;
                description "Request Flag Tunnel Old Bandwidth";
            }
            bit bandwidth {
                position 5;
                description "Request Flag Tunnel Bandwidth";
            }
            bit affinity-include-any {
                position 6;
                description "Request Flag Tunnel Include Any ";
            }
            bit affinity-include-all {
                position 7;
                description "Request Flag Tunnel Include All";
            }
            bit affinity-exclude-any {
                position 8;
                description "Request Flag Tunnel Exclude Any";
            }
            bit path-option {
                position 9;
                description "Request Flag Tunnel Path Option";
            }
            bit path-rro {
                position 10;
                description "Request Flag Tunnel RRO";
            }
            bit path-ero {
                position 11;
                description "Request Flag Tunnel ERO";
            }
            bit metric-bound {
                position 12;
                description "Request Flag Metric bound";
            }
            bit unknown-request {
                position 13;
                description "Request Flag Tunnel Unknown Obj";
            }
        }
        description "type definition for PCEP_TUNNEL_REQUEST_FLAGS_T";
    }

    typedef  pcep_tunnel_request_state_t {
        type enumeration {
            enum nopath {
                value 1;
                description "No Path found";
            }
            enum pce-cancel {
                value 2;
                description "PCE Cancelled";
            }
            enum pce-error {
                value 3;
                description "PCE Error";
            }
            enum incorrect-reply {
                value 4;
                description "PCE Incorrect Reply";
            }
        }
        description "type definition for PCEP_TUNNEL_REQUEST_STATE_T";
    }

    typedef  pcep_binding_alloc_mode_t {
        type enumeration {
            enum explicit-label {
                value 1;
                description "Binding Label is explicit configured by the local policy entity";
            }
            enum specified-label {
                value 2;
                description "Binding Label is specified by the PCE controller";
            }
            enum dynamic-label {
                value 3;
                description "Binding Label is dynamically configured by the local policy entity";
            }
        }
        description "type definition for PCEP_BINDING_ALLOC_MODE_T";
    }

    typedef  pcep_tunnel_recent_event_t {
        type enumeration {
            enum new-session-up {
                value 0;
                description "New session up";
            }
            enum pce-session-down {
                value 1;
                description "PCE session down";
            }
            enum pcreq-msg-sent {
                value 2;
                description "PCReq msg sent";
            }
            enum pcrep-msg-received {
                value 3;
                description "PCRep msg recvd";
            }
            enum pcupdate-msg-received {
                value 4;
                description "PCUpd msg recvd";
            }
            enum nsm-response-received {
                value 5;
                description "NSM response recvd";
            }
            enum pcreq-max-reached {
                value 6;
                description "PCReq Max reaached";
            }
            enum redelegation-timeout {
                value 7;
                description "Redelegation timeout";
            }
            enum state-timeout-expiry {
                value 8;
                description "State timeout expiry";
            }
        }
        description "type definition for PCEP_TUNNEL_RECENT_EVENT_T";
    }

}
