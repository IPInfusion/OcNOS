/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-ldp.yang
*
*/

module ipi-ldp {

    yang-version 1.1;

    namespace   "http://www.ipinfusion.com/yang/ocnos/ipi-ldp";

    prefix "ipi-ldp";

    import cml-data-types {
        prefix cml-data-types;
        revision-date 2021-05-03;
    }

    import ipi-ldp-types {
        prefix ipi-ldp-types;
        revision-date 2020-12-15;
    }

    import ietf-inet-types {
        prefix inet;
        revision-date 2013-07-15;
    }

    import feature-list {
        prefix feature-list;
        revision-date 2021-05-03;
    }

    include ipi-ldp-l2vpn { revision-date 2020-12-15;}
    include ipi-ldp-interface { revision-date 2020-12-15;}
    include ipi-ldp-peer { revision-date 2020-12-15;}
    organization
        "IP Infusion Inc.";

    contact
        "Address: 3965 Freedom Circle, Suite 200, Santa Clara, CA 95054
         Phone: +1 408-400-1900
         E-mail: support@ipinfusion.com
         Web: http://www.ipinfusion.com/";

    description
        "Datamodel for LDP protocol";


    revision "2021-06-01" {
        description "Added dependency constraint between peer authentication password and password-type attrs";
        reference " 0.2.1.";
    }

    revision "2020-12-15" {
        description "Change to have data-types in lower case instead of camel case";
        reference " 0.2.0.";
    }

    revision "2018-06-21" {
        description "Initial Version";
        reference " 0.1.0.";
    }

    grouping ldp-capability-config {
        description
            "Grouping for LDP capabilities configuration";
        leaf ldp-instance  {
            type  ipi-ldp-types:ldp_instance_t;
            mandatory true;
            description "This command is used to enter the LDP specific command-line mode in
                        which global attributes for the LDP process can
                        be set. Without this command, the LSR does not perform any LDP
                        operations, such as sending hello packets.";
        } // END of ldp-instance definition.

        leaf router-identifier  {
            type  inet:ipv4-address;
            description "This attribute sets the router-id to the supplied IP address; the
                        router uses this address to generate the LDP-ID";
        } // END of router-identifier definition.

        leaf pseudowire-status-tlv  {
            if-feature feature-list:HAVE_MPLS_VC;
            type  boolean;
            default false;
            description "This attribute enables the use of the PW Status TLV to signal the
                        pseudowire status";
        } // END of pseudowire-status-tlv definition.

        leaf entropy-label-capability-enable  {
            type  boolean;
            default false;
            description "This attribute enables ELC for the router. An ELC TLV will be inserted
                        in the label mapping message if the router is capable of processing
                        Entropy Label.";
        } // END of entropy-label-capability-enable definition.

        leaf multicast-hello-disable  {
            type  empty;
            description "This attribute enable multicast hello exchange on all interfaces
                        enabled for LDP. This is used for autodiscovery of LDP peers on
                        directly connected networks. This option is enabled by default.";
        } // END of multicast-hello-disable definition.

        leaf advertise-label-for-default-route  {
            type  empty;
            description "Advertise the label for default route.";
        } // END of advertise-label-for-default-route definition.

        leaf import-bgp-routes  {
            type  boolean;
            default false;
            description "This attribute is used to import BGP routes into LDP. BGP routes are
                        not imported into LDP by default. Use the no parameter to flush out
                        all BGP routes currently being used by LDP, and to reject any further
                        BGP specific routing updates from ZebOS-XP.";
        } // END of import-bgp-routes definition.

        leaf ldp-optimization  {
            type  boolean;
            default false;
            description "This command helps optimize the resetting of an LDP session by
                        enabling the two scalability features for LDP. It Resets the session
                        keepalive timer on receipt of a hello message and Resets the hold
                        timer on receipt of any LDP control message.";
        } // END of ldp-optimization definition.

        leaf explicit-null  {
            type  boolean;
            default false;
            description "This attribute is used to configure the router to send explicit-null
                        labels for directly connected FECs instead of implicit-null labels.
                        Implicit-nulls are the default labels.";
        } // END of explicit-null definition.

        leaf global-merge  {
            type  ipi-ldp-types:ldp_merge_capable_t;
            default "merge-capable";
            description "This attribute is used to override the default merge capability
                        setting of all the interfaces for the current LSR. The merge
                        capability aggregates multiple incoming flows with the same
                        destination address into a single outgoing flow.";
        } // END of global-merge definition.

        leaf propagate-release  {
            type  boolean;
            default false;
            description "This attribute is used to propagate the release of labels to
                        downstream routers";
        } // END of propagate-release definition.

    } // END of ldp-capability-config definition.
    grouping ldp-label-management-config {
        description
            "Grouping for LDP capabilities for label management configuration";
        leaf control-mode  {
            type  ipi-ldp-types:ldp_controlmode_t;
            description "Use this attribute to override the default merge capability setting of
                        all the interfaces for the current LSR.The merge capability aggregates
                        multiple incoming flows with the same destination address into a
                        single outgoing flow. This reduces the label-space shortage by sharing
                        labels for different flows with the same destination, or the same FEC
                        (Forwarding Equivalence Class).an LSR replies to a request packet from
                        an LSR higher in the chain only after it receives a label from an LSR
                        lower in the chain. Independent processing setthe mode to instant
                        replies.In independent control mode, each LSR might advertise label
                        mappings to its neighbors at any time. In independent
                        downstream-on-demand mode, an LSR might answer requests for label
                        mappings immediately, without waiting for a label mapping from the
                        next hop. In independent downstream unsolicited mode, an LSR might
                        advertise a label mapping for an Forwarding Equivalence Class (FEC) to
                        its neighbors when ever it is prepared to label-switch that FEC.In
                        independent mode, an upstream label can be advertised before a
                        downstream label is received.In ordered control mode, an LSR may
                        initiate the transmission of label mapping only for an FEC for which
                        it has a label mapping for the FEC next hop, or for which the LSR is
                        the egress. For each FEC for which the LSR is not the egress and no
                        mapping exists, the LSR must wait until a label from a downstream LSR
                        is received. An LSR may be an egress for some FECs and a non-egress
                        for others. Changes in control mode only affect labels that were sent
                        or received after the change was made.";
        } // END of control-mode definition.

        leaf retention-mode  {
            type  ipi-ldp-types:ldp_retention_mode_t;
            description "This attribute is used to set the retention mode to be used for all
                        labels exchanged. When an LSR receives a label binding for a
                        particular FEC (Forwarding Equivalence Class) from another LSR that is
                        not its next hop for that FEC, it might keep track of such bindings or
                        discard them. Use the liberal parameter to retain all labels binding
                        to FEC received from label distribution peers, even if the LSR is not
                        the current next-hop. Use the conservative parameter to maintain only
                        the label bindings for valid next-hops in a LSP.";
        } // END of retention-mode definition.

        leaf advertisement-mode  {
            type  ipi-ldp-types:ldp_advertise_mode_t;
            default "downstream-unsolicited";
            description "This attribute is used to set the label advertisement mode for all the
                        interfaces for the current LSR. Specifying downstream-on-demand and
                        downstream-unsolicited mode affects which LSR initiates mapping
                        requests and mapping advertisements. This command is a global command
                        used to set the label advertisement mode for all interfaces for the
                        current LSR.";
        } // END of advertisement-mode definition.

    } // END of ldp-label-management-config definition.
    grouping ldp-debug-config {
        description
            "Grouping for LDP debugging configuration";
        leaf ldp  {
            type  ipi-ldp-types:ldp_debug_t;
            description "Use this attribute to enable the debugging of all LDP events.";
        } // END of ldp definition.

        leaf ldp-packet  {
            type  ipi-ldp-types:ldp_debug_packet_t;
            description "Use this attribute to enable the debugging of LDP packet events";
        } // END of ldp-packet definition.

        leaf iccp  {
            if-feature feature-list:HAVE_ICCP;
            type  ipi-ldp-types:ldp_iccp_debug_t;
            description "This attribute is used to enable the iccp debug logs";
        } // END of iccp definition.

    } // END of ldp-debug-config definition.
    grouping ldp-label-request-policy-config {
        description
            "Grouping for LDP policy for label-request message configuration";
        leaf request-retry-timeout  {
            type  uint16 {
                 range "1..65535"  {
                    description "1..65535:Loop detection hop count";
                 }
            }
            default "5";
            description "Use this attribute to set the interval between retries. Before this
                        time is over, a request is re-sent to a peer. This command changes the
                        interval between request messages that are resent to a peer to account
                        for routing changes.";
        } // END of request-retry-timeout definition.

        leaf request-retry  {
            type  boolean;
            default false;
            description "Use this attribute to enable the retry of requests once a request for
                        a label has been rejected for a valid reason. This command enables the
                        LSR to send a maximum of five label requests if a label request is
                        rejected by an LDP peer.";
        } // END of request-retry definition.

        leaf label-request-policy-ipv4  {
            type  string {
                length "1..1965";
                pattern "[^?' =,>|]+";
            }
            description "Use this attribute to send LDP Label Request Message for certain IPv4
                        FEC prefixes.";
        } // END of label-request-policy-ipv4 definition.

        leaf label-request-policy-ipv6  {
            type  string {
                length "1..1965";
                pattern "[^?' =,>|]+";
            }
            description "Use this attribute to send LDP Label Request Message for certain IPv6
                        FEC prefixes.";
        } // END of label-request-policy-ipv6 definition.

    } // END of ldp-label-request-policy-config definition.
    grouping ldp-loop-detection-config {
        description
            "Grouping for LDP loop-detection configuration";
        leaf loop-detection-enable  {
            type  empty;
            mandatory true;
            description "Use this attribute to enable loop detection on the current LSR. This
                        command detects looping LSPs, and prevent Label Request messages from
                        looping because of non-merge capable LSRs. This loop detection
                        mechanism is useful for networks of non time-to-live (non TTL)
                        decrementing devices that can not allocate resources among traffic
                        flows.";
        } // END of loop-detection-enable definition.

        leaf path-vector-limit  {
            type  uint32 {
                 range "1..255"  {
                    description "1..255:Loop detection hop count";
                 }
            }
            default "255";
            description "Use this attribute to set the loop detection vec (vector) count, which
                        determines the maximum supported path vectors. This command sets the
                        maximum supported path vectors for loop detection, which specifies the
                        permitted path vector length. An LSR that detects a path vector has
                        reached the maximum length behaves as if the containing message has
                        traversed a loop. This command ensures that a loop is detected while
                        establishing a label switched path before any data is passed over that
                        LSP.";
        } // END of path-vector-limit definition.

        leaf hop-count-limit  {
            type  uint32 {
                 range "1..255"  {
                    description "1..255:Loop detection hop count";
                 }
            }
            default "255";
            description "Use this attribute to set the loop detection hop count, which
                        determines the maximum hop-count value.
                        This command sets the maximum hop count value, which specifies the
                        permitted maximum permitted hop-count. An LSR that detects a maximum
                        hop count behaves as if the containing message has traversed a loop.
                        The use of this command ensures that a loop is detected while
                        establishing a label switched path before any data is passed via LSP";
        } // END of hop-count-limit definition.

    } // END of ldp-loop-detection-config definition.
    grouping ldp-transport-address-top {
        description
            "Top-Level Grouping for LDP transport address per label space";

        list transport-address {
        when " /ipi-ldp:ldp/ipi-ldp:global/ipi-ldp:config ";
            key "label-space-identifier";
            description
                "Object list for transport addresses per label-space";
            leaf label-space-identifier  {
                type  leafref {
                    path  "../config/label-space-identifier";
                }
                description "This attribute is used to configure Label space for which a transport
                            address is being configured";
            } // END of label-space-identifier definition.

            container config {
                description
                    "Configuration data";
                uses ldp-transport-address-config;
            } // END of config-container definition.
            container state {
                config false;
                description
                    "Operational state data";
                uses ldp-transport-address-config;
            } // END of state-container definition.
        } // End of transport-address-list
    } // END of ldp-transport-address-top definition.
    grouping ldp-transport-address-config {
        description
            "Grouping for LDP Transport-Address configuration";
        leaf label-space-identifier  {
            type  ipi-ldp-types:ldp_label_space_identifier_t;
            description "This attribute is used to configure Label space for which a transport
                        address is being configured";
        } // END of label-space-identifier definition.

        leaf transport-address-ipv4  {
            type  inet:ipv4-address;
            description "Use this attribute to configure the IPv4 transport address for a label
                        space.The transport address is the address used for the TCP session
                        over which LDP is running. Use this attribute to manually configure
                        the transport address. Transport addresses may either be bound to a
                        loopback interface, or to a physical interface that is bound to the
                        label space in question. A transport address can also be manually
                        configured using the CLI with the loopback address as the transport
                        address.";
        } // END of transport-address-ipv4 definition.

        leaf transport-address-ipv6  {
            if-feature feature-list:HAVE_IPV6;
            type  inet:ipv6-address;
            description "Use this attribute to configure an IPv6 transport address for a label
                        space.
                        The transport address is the address used for the TCP session over
                        which LDP is running. Use this attribute to
                        manually configure the transport address. Transport addresses may
                        either be bound to a loopback interface, or to a
                        physical interface that is bound to the label space in question. A
                        transport address can also be manually configured
                        using the CLI with the loopback address as the transport address. The
                        CLI accepts only the loopback address to be configured as
                        the transport address";
        } // END of transport-address-ipv6 definition.

    } // END of ldp-transport-address-config definition.
    grouping ldp-authentication-top {
        description
            "Top-Level Grouping for LDP authetication";

        list peer-authentication-list {
        when " /ipi-ldp:ldp/ipi-ldp:global/ipi-ldp:config ";
            if-feature feature-list:HAVE_TCP_MD5SIG;
            key "peer-address";
            description
                "list for ldp peer authentication information";
            leaf peer-address  {
                type  leafref {
                    path  "../config/peer-address";
                }
                description "Use this attribute to configure neighbors of LDP for authentication.";
            } // END of peer-address definition.

            container config {
                description
                    "Configuration data";
                uses ldp-authentication-config;
            } // END of config-container definition.
            container state {
                config false;
                description
                    "Operational state data";
                uses ldp-authentication-config;
            } // END of state-container definition.
        } // End of peer-authentication-list-list
    } // END of ldp-authentication-top definition.
    grouping ldp-authentication-config {
        description
            "Grouping for LDP authetication configuration data";
        leaf peer-address  {
            type  inet:ip-address;
            description "Use this attribute to configure neighbors of LDP for authentication.";
        } // END of peer-address definition.

        leaf password-type  {
            when " /ipi-ldp:ldp/ipi-ldp:peer-authentication-list/ipi-ldp:config/ipi-ldp:password ";
            type  cml-data-types:cml_md5_encrypt_password_t;
            mandatory true;
            description "Use this attribute to configure password type for LDP peer
                        authentication.";
        } // END of password-type definition.

        leaf password  {
            when " /ipi-ldp:ldp/ipi-ldp:peer-authentication-list/ipi-ldp:config/ipi-ldp:password-type ";
            type  cml-data-types:cml_md5_password_t {
                length "1..1965";
            }
            mandatory true;
            description "Use this attribute to configure password of LDP peer for
                        authentication.";
        } // END of password definition.

        leaf encrypt  {
            when " ../password-type='7' ";
            type  empty;
            description "Use this attribute to configure password of LDP peer for
                        authentication.";
        } // END of encrypt definition.

    } // END of ldp-authentication-config definition.
    grouping ldp-label-mapping-access-control-top {
        description
            "Top-Level Grouping for LDP label-advertisement-ACL";

        list label-mapping-access-list {
        when " /ipi-ldp:ldp/ipi-ldp:global/ipi-ldp:config ";
            key "peer-access-control-list-name prefix-access-control-list-name";
            description
                "Object list for ldp ACL information";
            leaf peer-access-control-list-name  {
                type  leafref {
                    path  "../config/peer-access-control-list-name";
                }
                description "Use this command to prevent the distribution of any locally assigned
                            labels";
            } // END of peer-access-control-list-name definition.

            leaf prefix-access-control-list-name  {
                type  leafref {
                    path  "../config/prefix-access-control-list-name";
                }
                description "Use this attribute to prevent the distribution of any locally assigned
                            labels";
            } // END of prefix-access-control-list-name definition.

            container config {
                description
                    "Configuration data";
                uses ldp-prefix-list-name-config;
                uses ldp-peer-list-name-config;
            } // END of config-container definition.
            container state {
                config false;
                description
                    "Operational state data";
                uses ldp-prefix-list-name-config;
                uses ldp-peer-list-name-config;
                uses ldp-peer-list-advertise-labels-state;
            } // END of state-container definition.
            container statistics {
                description
                    "state container for the statistics advertisement labels";
                container state {
                    config false;
                    description
                        "Operational state data";
                    uses ldp-peer-list-statistics-advertise-labels-state;
                } // END of state-container definition.
            } // END of statistics-container definition.
        } // End of label-mapping-access-list-list
    } // END of ldp-label-mapping-access-control-top definition.
    grouping ldp-prefix-list-name-config {
        description
            "Grouping for LDP prefix-ACL name configuration";
        leaf prefix-access-control-list-name  {
            type  string {
                length "1..1965";
                pattern "[^?' =,>|]+";
            }
            description "Use this attribute to prevent the distribution of any locally assigned
                        labels";
        } // END of prefix-access-control-list-name definition.

    } // END of ldp-prefix-list-name-config definition.
    grouping ldp-peer-list-name-config {
        description
            "Grouping for LDP label-advertisement-peer list name configuration";
        leaf peer-access-control-list-name  {
            type  string {
                length "1..1965";
                pattern "[^?' =,>|]+";
            }
            description "Use this command to prevent the distribution of any locally assigned
                        labels";
        } // END of peer-access-control-list-name definition.

    } // END of ldp-peer-list-name-config definition.
    grouping ldp-peer-list-advertise-labels-state {
        description
            "Grouping for LDP label-advertisement-peer list state parameters";
        leaf advertisement-type  {
            type  ipi-ldp-types:ldp_advertisement_type_t;
            config false;
            description "This object stores the advertisement-type for Prefix List.";
        } // END of advertisement-type definition.

    } // END of ldp-peer-list-advertise-labels-state definition.
    grouping ldp-peer-list-statistics-advertise-labels-state {
        description
            "Grouping for LDP label-advertisement-peer list static state parameters";
        leaf label-deny-mapping  {
            type  uint32;
            config false;
            description "Use this attribute to store the number of label mappings denied";
        } // END of label-deny-mapping definition.

        leaf label-deny-request  {
            type  uint32;
            config false;
            description "Use this attribute to store the number of label requests denied";
        } // END of label-deny-request definition.

    } // END of ldp-peer-list-statistics-advertise-labels-state definition.
    grouping ldp-inter-area-config {
        description
            "Grouping for LDP Inter-Area configuration";
        leaf inter-area-acl-name  {
            if-feature feature-list:HAVE_LDP_INTER_AREA;
            type  string {
                length "1..1965";
                pattern "[^?' =,>|]+";
            }
            description "Use this attribute to enable creation of inter-area LSPs.";
        } // END of inter-area-acl-name definition.

        leaf inter-area-enable  {
            if-feature feature-list:HAVE_LDP_INTER_AREA;
            type  string {
                length "1..1965";
                pattern "[^?' =,>|]+";
            }
            description "Use this attribute to enable creation of inter-area LSPs.";
        } // END of inter-area-enable definition.

    } // END of ldp-inter-area-config definition.
    grouping ldp-graceful-restart-config {
        description
            "Grouping for LDP Inter-Area configuration";
        leaf graceful-restart-enable  {
            type  ipi-ldp-types:ldp_helper_mode_t;
            description "Use this attribute with the enable option to enable Graceful Restart
                        capability on a router. This is a global command. LDP decides whether
                        or not to encode FT Session TLV in its initialization message for each
                        session depending on this capability, but the restart capability of
                        each session also depends on support for graceful restart at the peer
                        router";
        } // END of graceful-restart-enable definition.

        leaf helper-mode-enable  {
            type  boolean;
            default false;
            description "Use this attribute to enable helper mode";
        } // END of helper-mode-enable definition.

        leaf neighbor-liveness-timer  {
            type  int32 {
                 range "5..300"  {
                    description "5..300:Set the hold time for a targeted LDP peer";
                 }
            }
            default "120";
            description "Use this attribute to set the Neighbor-Liveness timer. The amount of
                        time the LSR keeps its stale label-FEC (Forwarding Equivalence Class)
                        bindings is set to the lesser of the Fault Tolerant (FT) Reconnect
                        timeout and Neighbor-Liveness timer. This command sets the
                        Neighbor-Liveness timer";
        } // END of neighbor-liveness-timer definition.

        leaf recovery-timer  {
            type  int32 {
                 range "15..600"  {
                    description "15..600:Interval until which LDP preserves routes after Peer Restart";
                 }
            }
            default "120";
            description "Use this attribute to set the maximum recovery time.If the LSR
                        determines that the neighbor was able to preserve its MPLS forwarding
                        state, the LSR should keep the stale label-FEC (Forwarding Equivalence
                        Class) bindings for as long as the lesser of: the recovery time
                        advertised by the neighbor and a local maximum recovery time. This
                        command sets the maximum recovery time";
        } // END of recovery-timer definition.

    } // END of ldp-graceful-restart-config definition.
    grouping ldp-graceful-restart-state {
        description
            "Grouping for LDP Inter-Area configuration";
        leaf restart-reason  {
            if-feature feature-list:HAVE_RESTART;
            type  uint8;
            config false;
            description "This attribute holds the descriptive reason for restart";
        } // END of restart-reason definition.

        leaf restart-count  {
            type  int32;
            config false;
            description "This attribute holds the count for restart";
        } // END of restart-count definition.

    } // END of ldp-graceful-restart-state definition.
    grouping ldp-inter-chassis-communication-protocol-config {
        description
            "Grouping for ICCP configuration";
        leaf redundancy-group-identifier  {
            type  uint32 {
                 range "0..65535"  {
                    description "0..65535:Group ID value";
                 }
            }
            mandatory true;
            description "This attribute is used to configure redundancy group id";
        } // END of redundancy-group-identifier definition.

        leaf ldp-peer-member-ip-address  {
            type  inet:ipv4-address;
            description "This attribute is used to configure peer Ip address of group member";
        } // END of ldp-peer-member-ip-address definition.

        leaf iccp-startup-delay-timer  {
            type  uint32 {
                 range "0..180"  {
                    description "0..180:timer value";
                 }
            }
            description "This attribute is used to configure startup delay timer";
        } // END of iccp-startup-delay-timer definition.

        leaf bfd-source-ip-address  {
            if-feature feature-list:HAVE_BFD;
            type  inet:ipv4-address;
            description "This attribute is used to configure Source IP address for BFD";
        } // END of bfd-source-ip-address definition.

    } // END of ldp-inter-chassis-communication-protocol-config definition.

    grouping  ldp-grouping {
    description
        "LDP global level container";
    container ldp {
        when " /ipi-ldp:ldp/ipi-ldp:global/ipi-ldp:config + /ipi-ldp:ldp/ipi-ldp:global/ipi-ldp:config/ipi-ldp:ldp-instance + /ipi-ldp:ldp/ipi-ldp:global ";
        description
            "LDP global level container";
        container global {
            description
                "Configuration data for LDP global capability configuration";
            container config {
                presence "Enable LDP";
                description
                    "LDP global structure for Configuration parameters";
                uses ldp-capability-config;
            } // END of config-container definition.
            container state {
                config false;
                description
                    "Operational state data";
                uses ldp-capability-config;
            } // END of state-container definition.
            container label-management {
                when " /ipi-ldp:ldp/ipi-ldp:global/ipi-ldp:config ";
                description
                    "Configuration data for LDP global label management configuration";
                container config {
                    description
                        "Configuration data";
                    uses ldp-label-management-config;
                } // END of config-container definition.
                container state {
                    config false;
                    description
                        "Operational state data";
                    uses ldp-label-management-config;
                } // END of state-container definition.
            } // END of label-management-container definition.
            container timers {
                when " /ipi-ldp:ldp/ipi-ldp:global/ipi-ldp:config ";
                description
                    "";
                container config {
                    description
                        "";
                    uses ldp-hello-timers-config;
                    uses ldp-session-timers-config;
                } // END of config-container definition.
                container state {
                    config false;
                    description
                        "Operational state data";
                    uses ldp-hello-timers-config;
                    uses ldp-session-timers-config;
                } // END of state-container definition.
            } // END of timers-container definition.
            container label-request-policy {
                when " /ipi-ldp:ldp/ipi-ldp:global/ipi-ldp:config ";
                description
                    "Configuration data for LDP policies for label-request";
                container config {
                    description
                        "Configuration data";
                    uses ldp-label-request-policy-config;
                } // END of config-container definition.
                container state {
                    config false;
                    description
                        "Operational state data";
                    uses ldp-label-request-policy-config;
                } // END of state-container definition.
            } // END of label-request-policy-container definition.
            container loop-detection-policy {
                when " /ipi-ldp:ldp/ipi-ldp:global/ipi-ldp:config ";
                description
                    "Configuration data for LDP policies for loop detection";
                container config {
                    presence "Enable Loop-Detection";
                    description
                        "Ldp structure for loop-detection configurationdata";
                    uses ldp-loop-detection-config;
                } // END of config-container definition.
                container state {
                    config false;
                    description
                        "Operational state data";
                    uses ldp-loop-detection-config;
                } // END of state-container definition.
            } // END of loop-detection-policy-container definition.
        } // END of global-container definition.
        container debug {
            description
                "Configuration data for LDP debugging configuration";
            container config {
                description
                    "Configuration data";
                uses ldp-debug-config;
            } // END of config-container definition.
            container state {
                config false;
                description
                    "Operational state data";
                uses ldp-debug-config;
            } // END of state-container definition.
        } // END of debug-container definition.
        container iccp {
            if-feature feature-list:HAVE_ICCP;
            description
                "Configuration data for ICCP feature";
            container config {
                presence "Enable ICCP";
                description
                    "Structure for ICCP configuration";
                uses ldp-inter-chassis-communication-protocol-config;
            } // END of config-container definition.
            container state {
                config false;
                description
                    "Operational state data";
                uses ldp-inter-chassis-communication-protocol-config;
            } // END of state-container definition.
        } // END of iccp-container definition.
        uses ldp-transport-address-top;
        uses ldp-authentication-top;
        uses ldp-label-mapping-access-control-top;
        uses interfaces-grouping;
        uses l2vpn-grouping;
        uses targeted-peers-grouping;
        uses peers-grouping;
    } // END of ldp-container definition.
    } // END of ldp-grouping definition.

    uses ldp-grouping;

    rpc clear-ldp-statistics {
        description "Use this RPC to clear LDP statistics";
    }

    rpc clear-ldp-statistics-advertise-labels {
        description "Use this RPC to clear ts LDP advertise-labels statistics";
    }

    rpc clear-ldp-statistics-advertise-labels-prefix {
        description "Use this RPC to clear LDP advertise-labels prefix statistics";
        input  {
            leaf prefix  {
                type string;
                mandatory true;
                description "prefix-list that have their labels advertised";
            }
        }
    }

    rpc clear-ldp-statistics-advertise-labels-prefix-peer {
        description "Use this RPC to clear LDP advertise-labels prefix-peer statistics";
        input  {
            leaf prefix  {
                type string;
                mandatory true;
                description "prefix-list that have their labels advertised";
            }
            leaf peer  {
                type string;
                mandatory true;
                description "peer address for the prefix list name";
            }
        }
    }

    rpc clear-ldp-session-all {
        description "Use this RPC to clear all LDP sessions";
    }

    rpc clear-ldp-session-ipv4 {
        description "Use this RPC to clear the particular LDP IPV4 session";
        input  {
            leaf addr  {
                type inet:ipv4-address;
                mandatory true;
                description "LDP session IPV4 address";
            }
        }
    }

    rpc clear-ldp-session-ipv6 {
        description "Use this RPC to clear all LDP IPV6 sessions";
        input  {
            leaf addr  {
                type inet:ipv6-address;
                mandatory true;
                description "LDP session IPV6 address";
            }
        }
    }

    rpc clear-ldp-adjacency-all {
        description "Use this RPC to clear an adjacency with a specified peer, or to clear
                    all adjacencies for the current LSR";
    }

    rpc clear-ldp-adjacency-ipv4 {
        description "Use this RPC to clear an adjacency with a specified IPV4 peer LSR";
        input  {
            leaf addr  {
                type inet:ipv4-address;
                mandatory true;
                description "LDP adjacency IPV4 address";
            }
        }
    }

    rpc clear-ldp-adjacency-ipv6 {
        description "Use this RPC to clear an adjacency with a specified IPV6 peer LSR";
        input  {
            leaf addr  {
                type inet:ipv6-address;
                mandatory true;
                description "LDP adjacency IPV6 address";
            }
        }
    }

    rpc snmp-restart-ldp {
        description "Use this RPC to restart SNMP in LDP";
    }

    rpc ldp-terminal-debug-on {
        description "Use this RPC to enable terminal LDP debugs";
        input  {
            leaf ldp-debug-options  {
                type ipi-ldp-types:ldp_debug_t;
                mandatory true;
                description "debug options for the ICCP";
            }
        }
    }

    rpc ldp-terminal-debug-off {
        description "Use this RPC to disable terminal LDP debugs";
        input  {
            leaf ldp-debug-options  {
                type ipi-ldp-types:ldp_debug_t;
                mandatory true;
                description "debug options for the LDP";
            }
        }
    }

    rpc ldp-packet-terminal-debug-on {
        description "Use this RPC to enable terminal LDP packet debugs";
        input  {
            leaf ldp-packet-debug-options  {
                type ipi-ldp-types:ldp_debug_packet_t;
                mandatory true;
                description "debug options for the LDP packet";
            }
        }
    }

    rpc ldp-packet-terminal-debug-off {
        description "Use this RPC to disable terminal LDP packet debugs";
        input  {
            leaf ldp-packet-debug-options  {
                type ipi-ldp-types:ldp_debug_packet_t;
                mandatory true;
                description "debug options for the LDP packet";
            }
        }
    }

    rpc restart-ldp-graceful {
        description "Use this RPC to LDP gracceful restart";
    }

    notification mpls-ldp-session-up {

        description "If this notification is sent when the value of MPLS LDP 'session-state' enters the operational(5) state..";

        // severity "MINOR";
        // eventClass "STATE";
        leaf peer-address {
            type  inet:ipv4-address;
        description
            "This attribute acquires LDP peer address";
        }

        leaf session-state {
            type ipi-ldp-types:ldp_session_state_t;
        description
            "This attribute acquires state of LDP Session";
        }

        leaf discontinuity-time {
            type  uint32;
        description
            "The value on the most recent occasion at which any one or more of this
                    session's
                    counters suffered a discontinuity.";
        }

        leaf unknown-message-type-errors {
            type  uint32;
        description
            "This object counts the number of Unknown Message Type Errors detected
                    by this LSR/LER during this session";
        }

        leaf unknown-tlv-type-errors {
            type  uint32;
        description
            "This object counts the number of Unknown TLV Errors detected by this
                    LSR/LER during this session";
        }
    }

    notification mpls-ldp-session-down {

        description "If this notification is sent when the value of MPLS LDP 'session-state' leaves the operational(5) state..";

        // severity "CRITICAL";
        // eventClass "STATE";
        leaf peer-address {
            type  inet:ipv4-address;
        description
            "This attribute acquires LDP peer address";
        }

        leaf session-state {
            type ipi-ldp-types:ldp_session_state_t;
        description
            "This attribute acquires state of LDP Session";
        }

        leaf discontinuity-time {
            type  uint32;
        description
            "The value on the most recent occasion at which any one or more of this
                    session's
                    counters suffered a discontinuity.";
        }

        leaf unknown-message-type-errors {
            type  uint32;
        description
            "This object counts the number of Unknown Message Type Errors detected
                    by this LSR/LER during this session";
        }

        leaf unknown-tlv-type-errors {
            type  uint32;
        description
            "This object counts the number of Unknown TLV Errors detected by this
                    LSR/LER during this session";
        }
    }

    notification mpls-ldp-init-session-threshold-exceeded {

        description "This notification is generated when the value of the 'initialization-session-threshold-limit' object is not zero, and the number of Session Initialization messages exceeds the value of the 'initialization-session-threshold-limit' object..";

        // severity "MINOR";
        // eventClass "STATE";
        leaf peer-address {
            type  inet:ipv4-address;
        description
            "This attribute acquires LDP peer address";
        }

        leaf initialization-session-threshold-limit {
            type  uint32;
        description
            "This attribute acquires the threshold value of number of Session
                    Initialization
                    messages can be sent.";
        }
    }

    notification mpls-ldp-path-vector-limit-mismatch {

        description "This notification is sent when the 'entity-path-vector-limit' does NOT match the value of the 'peer-path-vector-limit' for a specific Entity..";

        // severity "MINOR";
        // eventClass "STATE";
        leaf peer-address {
            type  inet:ipv4-address;
        description
            "This attribute acquires LDP peer address";
        }

        leaf entity-path-vector-limit {
            type  uint32;
        description
            "If this object has a value greater than zero, then Loop Dection for
                    Path Vectors is enabled,
                    and the Path Vector Limit is this value.";
        }

        leaf peer-path-vector-limit {
            type  uint32;
        description
            "This object acquires the peer's Path Vector Limit value.";
        }
    }

}
