/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-ldp-types.yang
*
*/

module ipi-ldp-types {

    yang-version 1.1;

    namespace   "http://www.ipinfusion.com/yang/ocnos/ipi-ldp-types";

    prefix "ipi-ldp-types";

    import ietf-inet-types {
        prefix inet;
        revision-date 2013-07-15;
    }

    organization
        "IP Infusion Inc.";

    contact
        "Address: 3965 Freedom Circle, Suite 200, Santa Clara, CA 95054
         Phone: +1 408-400-1900
         E-mail: support@ipinfusion.com
         Web: http://www.ipinfusion.com/";

    description
        "YANG version of the ipi-ldp-types";


    revision "2020-12-15" {
        description "Change to have data-types in lower case instead of camel case";
        reference " 0.2.0.";
    }

    revision "2018-06-21" {
        description "Initial Version";
        reference " 0.1.0.";
    }



    typedef  ldp_helper_mode_t {
        type enumeration {
            enum disable {
                value 0;
                description "Disable graceful restart";
            }
            enum enable {
                value 1;
                description "Enable graceful restart";
            }
        }
        description "type definition for LDP_HELPER_MODE_T";
    }

    typedef  ldp_advertise_mode_t {
        type enumeration {
            enum downstream-unsolicited {
                value 0;
                description "DU advertisement mode";
            }
            enum downstream-on-demand {
                value 1;
                description "DOD advertisement mode";
            }
        }
        description "type definition for LDP_ADVERTISE_MODE_T";
    }

    typedef  ldp_controlmode_t {
        type enumeration {
            enum independent {
                value 0;
                description "DU advertisement mode";
            }
            enum ordered {
                value 1;
                description "DOD advertisement mode";
            }
        }
        description "type definition for LDP_CONTROLMODE_T";
    }

    typedef  ldp_retention_mode_t {
        type enumeration {
            enum liberal {
                value 0;
                description "Set liberal label retention mode";
            }
            enum conservative {
                value 1;
                description "Set conservative label retention mode";
            }
        }
        description "type definition for LDP_RETENTION_MODE_T";
    }

    typedef  ldp_merge_capable_t {
        type enumeration {
            enum merge-capable {
                value 0;
                description "Set merge capable";
            }
            enum non-merge-capable {
                value 1;
                description "Set non merge capable";
            }
        }
        description "type definition for LDP_MERGE_CAPABLE_T";
    }

    typedef  ldp_enable_type_t {
        type enumeration {
            enum disable-ldp {
                value 0;
                description "Disable LDP on interface";
            }
            enum enable-ldp {
                value 1;
                description "Enable LDP on Interface";
            }
        }
        description "type definition for LDP_ENABLE_TYPE_T";
    }

    typedef  ldp_igp_sync_t {
        type enumeration {
            enum igp-sync {
                value 0;
                description "Enable/Disable LDP for IPV4";
            }
            enum no-igp-sync {
                value 1;
                description "Enable/Disable LDP for IPV6";
            }
        }
        description "type definition for LDP_IGP_SYNC_T";
    }

    typedef  ldp_instance_t {
        type enumeration {
            enum ldp {
                value 1;
                description "Label Distribution Protocol (LDP)";
            }
        }
        description "type definition for LDP_INSTANCE_T";
    }

    typedef  ldp_debug_t {
        type bits {
            bit events {
                position 0;
                description "LDP events";
            }
            bit fsm {
                position 1;
                description "Enable FSM debugging";
            }
            bit hexdump {
                position 2;
                description "Enable HEXDUMP";
            }
            bit dsm {
                position 3;
                description "Enable Downstream SM";
            }
            bit usm {
                position 4;
                description "LDP Upstream SM";
            }
            bit tsm {
                position 5;
                description "LDP Trunk SM";
            }
            bit qos {
                position 6;
                description "LDP QoS";
            }
            bit nsm {
                position 7;
                description "NSM messages";
            }
            bit advertise-labels {
                position 8;
                description "List IP prefix lists of advertise-labels";
            }
            bit cspf {
                position 9;
                description "CSPF messages";
            }
            bit vc-usm {
                position 10;
                description "LDP VC Info,LDP VC USM";
            }
            bit vc-dsm {
                position 11;
                description "LDP VC Info,LDP VC DSM";
            }
            bit graceful-restart {
                position 12;
                description "LDP Graceful Restart Debugging";
            }
            bit rib {
                position 13;
                description "RIB messages";
            }
            bit inter-area {
                position 15;
                description "LDP Inter-Area Information";
            }
        }
        description "type definition for LDP_DEBUG_T";
    }

    typedef  ldp_debug_packet_t {
        type bits {
            bit notification {
                position 0;
                description "LDP notification packet";
            }
            bit hello {
                position 1;
                description "LDP hello packet";
            }
            bit initialization {
                position 2;
                description "LDP initialization packet";
            }
            bit keepalive {
                position 3;
                description "LDP keepalive packet";
            }
            bit address {
                position 4;
                description "LDP address (withdraw) packet";
            }
            bit label {
                position 5;
                description "LDP label mapping/request(abort)/withdraw/release packet";
            }
        }
        description "type definition for LDP_DEBUG_PACKET_T";
    }

    typedef  ldp_failure_t {
        type enumeration {
            enum restart {
                value 0;
                description "Restart LSP";
            }
        }
        description "type definition for LDP_FAILURE_T";
    }

    typedef  ldp_ip_addr_t {
        type union {
            type inet:ipv4-address {

            }
            type inet:ipv6-address {

            }
        }
        description "type definition for LDP_IP_ADDR_T";
    }

    typedef  ldp_iccp_debug_t {
        type bits {
            bit events {
                position 0;
                description "Events";
            }
            bit fsm {
                position 1;
                description "FSM";
            }
            bit hexdump {
                position 2;
                description "hexdump of messages";
            }
            bit packet {
                position 3;
                description "Packets";
            }
            bit bfd {
                position 4;
                description "BFD";
            }
        }
        description "type definition for LDP_ICCP_DEBUG_T";
    }

    typedef  ldp_label_space_identifier_t {
        type enumeration {
            enum 0 {
                value 0;
                description "Platform-wide Label space for which a transport address is being configured (Platform-wide labels are used for all interfaces that can share the same labels)";
            }
        }
        description "type definition for LDP_LABEL_SPACE_IDENTIFIER_T";
    }

    typedef  ldp_tcp_status_t {
        type enumeration {
            enum not-established {
                value 0;
                description "TCP Connection not established";
            }
            enum established {
                value 1;
                description "TCP Connection established";
            }
        }
        description "type definition for LDP_TCP_STATUS_T";
    }

    typedef  ldp_vc_state_t {
        type enumeration {
            enum down {
                value 0;
                description "VC State down (Idle, Active)";
            }
            enum up {
                value 1;
                description "VC State up (Complete)";
            }
        }
        description "type definition for LDP_VC_STATE_T";
    }

    typedef  ldp_label_merge_capability_t {
        type enumeration {
            enum non-merge-capable {
                value 0;
                description "Label-Merge capibility, non-merge capable";
            }
            enum merge-capable {
                value 1;
                description "Label-Merge capibility, merge capable";
            }
        }
        description "type definition for LDP_LABEL_MERGE_CAPABILITY_T";
    }

    typedef  ldp_session_state_t {
        type enumeration {
            enum non-existant {
                value 0;
                description "Non-Existent State";
            }
            enum initialized {
                value 1;
                description " Initialized State";
            }
            enum open-sent {
                value 2;
                description " open-sent State";
            }
            enum open-recieved {
                value 3;
                description " open-recieved State";
            }
            enum operational {
                value 4;
                description "operational State";
            }
        }
        description "type definition for LDP_SESSION_STATE_T";
    }

    typedef  ldp_session_role_t {
        type enumeration {
            enum passive {
                value 0;
                description "Passive Mode";
            }
            enum active {
                value 1;
                description "Active Mode";
            }
        }
        description "type definition for LDP_SESSION_ROLE_T";
    }

    typedef  ldp_advertisement_type_t {
        type enumeration {
            enum enable-distribution {
                value 0;
                description "Enable the distribution of all assigned labels";
            }
            enum Prevent-distribution {
                value 1;
                description "Prevent the distribution of any assigned labels";
            }
        }
        description "type definition for LDP_ADVERTISEMENT_TYPE_T";
    }

}
