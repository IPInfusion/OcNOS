/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-twamp.yang
*
*/

submodule zebos-twamp {

    belongs-to  zebos { prefix zebos; }

    import cml_data_types {
        prefix cml_data_types;
    }

    import ietf-inet-types {
        prefix inet;
    }

    organization
        "IP Infusion Inc.";

    contact
        "Address: 3965 Freedom Circle, Suite 200, Santa Clara, CA 95054
         Phone: +1 408-400-1900
         E-mail: support@ipinfusion.com
         Web: http://www.ipinfusion.com/";

    description
        "";


    revision "2018-12-28" {
        description "Revised on 2018-12-28.";        reference "";    }

    revision "2018-06-21" {
        description "Revised on 2018-06-21.";        reference "";    }



    typedef  CML_TWAMP_SERVER_T {
        type enumeration {
            enum server {
                value 1;
                description "no mip can be created for this vid";
            }
        }
        description "";
        reference "";
    }

    typedef  CML_TWAMP_CLIENT_T {
        type enumeration {
            enum client {
                value 2;
                description "no mip can be created for this vid";
            }
        }
        description "";
        reference "";
    }

    typedef  CML_TWAMP_SESS_SENDER_T {
        type enumeration {
            enum session-sender {
                value 3;
                description "no mip can be created for this vid";
            }
        }
        description "";
        reference "";
    }

    typedef  CML_TWAMP_SESS_REFLECTOR_T {
        type enumeration {
            enum session-reflector {
                value 4;
                description "no mip can be created for this vid";
            }
        }
        description "";
        reference "";
    }

    typedef  CML_TWAMP_LIGHT_REFLECTOR_T {
        type enumeration {
            enum reflector {
                value 1;
                description "configure as reflector";
            }
        }
        description "";
        reference "";
    }

    typedef  CML_TWAMP_LIGHT_CONTROL_T {
        type enumeration {
            enum control {
                value 1;
                description "configure as control";
            }
        }
        description "";
        reference "";
    }

    typedef  CML_TWAMP_LIGHT_SENDER_T {
        type enumeration {
            enum sender {
                value 1;
                description "configure as sender";
            }
        }
        description "";
        reference "";
    }

    typedef  TWAMP_TIMESTAMP_FORMAT {
        type enumeration {
            enum ntp {
                value 0;
                description "Use ntp timestamp format";
            }
            enum ptp {
                value 1;
                description "Use ptp timestamp format";
            }
        }
        description "";
        reference "";
    }
    grouping  twampLightReflector-grouping {
    description
        "twampLightReflector";
    container twampLightReflector {
        presence "yes";
        description
            "twampLightReflector";
        leaf twampLightReflector  {
            type  CML_TWAMP_LIGHT_REFLECTOR_T;
            mandatory true;
            description "This feature relates to the device functions as the TWAMP Light Session-Reflector";
        } // END of twampLightReflector definition.


        leaf reflectorLightAdminState  {
            type  cml_data_types:CML_ENABLE_DISABLE_T;
            description "";
        } // END of reflectorLightAdminState definition.


        leaf reflectorIp  {
            type  cml_data_types:CML_HOSTPNAME_T {
                length "0..255";
            }
            description "";
        } // END of reflectorIp definition.


        leaf reflectorPort  {
            type  cml_data_types:CML_UINT16_T {
                 range "1025..65535";
            }
            description "";
        } // END of reflectorPort definition.


    } // END of twampLightReflector-container definition.
    } // END of twampLightReflector-container definition.

    grouping  twampLightControl-grouping {
    description
        "twampLightControl";
    container twampLightControl {
        presence "yes";
        description
            "twampLightControl";
        leaf twampLightControl  {
            type  CML_TWAMP_LIGHT_CONTROL_T;
            mandatory true;
            description "This feature relates to the device functions as the TWAMP Light Control";
        } // END of twampLightControl definition.


        leaf controlLightAdminState  {
            type  cml_data_types:CML_ENABLE_DISABLE_T;
            description "";
        } // END of controlLightAdminState definition.


        leaf timestampFormat  {
            type  TWAMP_TIMESTAMP_FORMAT;
            description "";
        } // END of timestampFormat definition.



        list controlLightTestSessions {
            key "controlLightTestSessionName";
            description
                "controlLightTestSessions";
            leaf controlLightTestSessionName  {
                type  cml_data_types:CML_STRING_T {
                    length "0..255";
                }
                description "";
            } // END of controlLightTestSessionName definition.


            leaf senderIp  {
                type  cml_data_types:CML_HOSTPNAME_T {
                    length "0..255";
                }
                mandatory true;
                description "";
            } // END of senderIp definition.


            leaf senderPort  {
                type  cml_data_types:CML_UINT16_T {
                     range "1025..65535";
                }
                mandatory true;
                description "";
            } // END of senderPort definition.


            leaf reflectorIpTst  {
                type  cml_data_types:CML_HOSTPNAME_T {
                    length "0..255";
                }
                mandatory true;
                description "";
            } // END of reflectorIpTst definition.


            leaf reflectorPortTst  {
                type  cml_data_types:CML_UINT16_T {
                     range "1025..65535";
                }
                mandatory true;
                description "";
            } // END of reflectorPortTst definition.


        } // End of controlLightTestSessions-list
    } // END of twampLightControl-container definition.
    } // END of twampLightControl-container definition.


}
