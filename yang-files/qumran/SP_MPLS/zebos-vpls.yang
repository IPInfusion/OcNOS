/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-vpls.yang
*
*/

submodule zebos-vpls {

    belongs-to  zebos { prefix zebos; }

    import cml_data_types {
        prefix cml_data_types;
    }

    import feature_list {
        prefix feature_list;
    }

    organization
        "IP Infusion Inc.";

    contact
        "Address: 3965 Freedom Circle, Suite 200, Santa Clara, CA 95054
         Phone: +1 408-400-1900
         E-mail: support@ipinfusion.com
         Web: http://www.ipinfusion.com/";

    description
        "";


    revision "2018-06-21" {
        description " Initial Version.";
        reference "";
    }



    grouping vpls-grouping {
    description
        "vpls";
        list vpls {
            key "vplsName";
            description
                "vpls";
            leaf vplsName  {
                type  cml_data_types:CML_STRING_T {
                    length "0..255";
                }
                description "";
            } // END of vplsName definition.


            leaf vplsId  {
                type  cml_data_types:CML_UINT32_T {
                     range "1..4294967295";
                }
                mandatory true;
                description "";
            } // END of vplsId definition.


            leaf vplsSvcTpid  {
                type  cml_data_types:CML_NSM_SVC_TPID_T;
                description "";
            } // END of vplsSvcTpid definition.


            leaf vplsMtu  {
                type  cml_data_types:CML_UINT16_T {
                     range "576..65535";
                }
                default "1500";
                description "";
            } // END of vplsMtu definition.


            leaf vplsDescLine  {
                type  cml_data_types:CML_LINE_T {
                    length "0..255";
                }
                default "NULL";
                description "";
            } // END of vplsDescLine definition.


            leaf learningDisable  {
                type  cml_data_types:CML_BOOL_T;
                description "";
            } // END of learningDisable definition.


            leaf learningLimit  {
                if-feature feature_list:NOT_HAVE_TRIDENT2;
                if-feature feature_list:NOT_HAVE_TRIDENT2PLUS;
                type  cml_data_types:CML_UINT32_T {
                     range "5..32767";
                }
                default "32767";
                description "";
            } // END of learningLimit definition.


            leaf redRole  {
                type  cml_data_types:CML_VPLS_REDUNDANCY_ROLE_T;
                default "primary";
                description "";
            } // END of redRole definition.


            leaf preconfiguredAcName  {
                type  cml_data_types:CML_STRING_T {
                    length "0..255";
                }
                description "";
            } // END of preconfiguredAcName definition.



            list svcInstanceInfoList {
                key "ifpName";
                config false;
                description
                    "svcInstanceInfoList";
                leaf ifpName  {
                    type  cml_data_types:CML_STRING_T {
                        length "0..255";
                    }
                    description "";
                } // END of ifpName definition.


                leaf svcCust  {
                    type  cml_data_types:CML_STRING_T {
                        length "0..255";
                    }
                    description "";
                } // END of svcCust definition.



                list svcMatchList {
                    key "index";
                    config false;
                    description
                        "svcMatchList";
                    leaf index  {
                        type  cml_data_types:CML_UINT16_T;
                        description "";
                    } // END of index definition.


                    leaf svcAllMatch  {
                        type  cml_data_types:CML_STRING_T {
                            length "0..255";
                        }
                        description "";
                    } // END of svcAllMatch definition.


                    leaf svcOvidMatch  {
                        type  cml_data_types:CML_UINT16_T;
                        description "";
                    } // END of svcOvidMatch definition.


                    leaf svcIvidMatch  {
                        type  cml_data_types:CML_UINT16_T;
                        description "";
                    } // END of svcIvidMatch definition.


                    leaf svcOvidMatchMax  {
                        type  cml_data_types:CML_UINT16_T;
                        description "";
                    } // END of svcOvidMatchMax definition.


                } // End of svcMatchList-list

                list svcActionList {
                    key "index";
                    config false;
                    description
                        "svcActionList";
                    leaf index  {
                        type  cml_data_types:CML_UINT16_T;
                        description "";
                    } // END of index definition.


                    leaf actionType  {
                        type  cml_data_types:CML_STRING_T {
                            length "0..255";
                        }
                        description "";
                    } // END of actionType definition.


                    leaf actionVal  {
                        type  cml_data_types:CML_UINT16_T;
                        description "";
                    } // END of actionVal definition.


                    leaf actionTpid  {
                        type  cml_data_types:CML_STRING_T {
                            length "0..255";
                        }
                        description "";
                    } // END of actionTpid definition.


                } // End of svcActionList-list
            } // End of svcInstanceInfoList-list

            list vplsVcName {
                key "vcName";
                description
                    "vplsVcName";
                leaf vcName  {
                    type  cml_data_types:CML_STRING_T {
                        length "0..255";
                    }
                    description "";
                } // END of vcName definition.


                leaf vcType  {
                    type  cml_data_types:CML_NSM_VPLS_VC_SPOKE_TYPE_T;
                    default "ethernet";
                    description "";
                } // END of vcType definition.


                leaf tunnelName  {
                    if-feature feature_list:HAVE_MPLS_TP;
                    type  cml_data_types:CML_STRING_T {
                        length "0..255";
                    }
                    description "";
                } // END of tunnelName definition.


            } // End of vplsVcName-list

            list vplsProfile {
                if-feature feature_list:HAVE_QOS;
                key "vplsProfileType";
                description
                    "vplsProfile";
                leaf vplsProfileType  {
                    type  cml_data_types:CML_VPLS_QOS_MAP_PROFILE_TYPE_T;
                    description "";
                } // END of vplsProfileType definition.


                leaf vplsProfileName  {
                    type  cml_data_types:CML_STRING_T {
                        length "0..255";
                    }
                    mandatory true;
                    description "";
                } // END of vplsProfileName definition.


            } // End of vplsProfile-list

            list vplsmac {
                key "macAddr";
                description
                    "vplsmac";
                leaf macAddr  {
                    type  cml_data_types:CML_STRING_T {
                        length "0..255";
                    }
                    description "";
                } // END of macAddr definition.


                leaf vlanId  {
                    type  cml_data_types:CML_UINT16_T {
                         range "1..4094";
                    }
                    description "";
                } // END of vlanId definition.


                leaf ifName  {
                    type  cml_data_types:CML_STRING_T {
                        length "0..255";
                    }
                    mandatory true;
                    description "";
                } // END of ifName definition.


            } // End of vplsmac-list

            list vplsPeer {
                key "peerId";
                description
                    "vplsPeer";
                leaf peerId  {
                    type  cml_data_types:CML_IPV4_ADDR_T;
                    description "";
                } // END of peerId definition.


                leaf globalId  {
                    if-feature feature_list:HAVE_MPLS_TP;
                    type  cml_data_types:CML_UINT32_T {
                         range "1..4294967295";
                    }
                    description "";
                } // END of globalId definition.


                leaf tunnelId  {
                    type  cml_data_types:CML_STRING_T {
                        length "0..255";
                    }
                    description "";
                } // END of tunnelId definition.


                leaf tunnelName  {
                    type  cml_data_types:CML_STRING_T {
                        length "0..255";
                    }
                    description "";
                } // END of tunnelName definition.


                leaf tunnelDir  {
                    type  cml_data_types:CML_NSM_VPLS_PEER_TUNNEL_DIR_T;
                    default "forward";
                    description "";
                } // END of tunnelDir definition.


                leaf ccName  {
                    if-feature feature_list:HAVE_MPLS_TP;
                    type  cml_data_types:CML_STRING_T {
                        length "0..255";
                    }
                    description "";
                } // END of ccName definition.


                leaf iccName  {
                    if-feature feature_list:HAVE_MPLS_TP;
                    type  cml_data_types:CML_STRING_T {
                        length "0..255";
                    }
                    description "";
                } // END of iccName definition.


                leaf fecTypeVc  {
                    type  cml_data_types:CML_NSM_VPLS_PEER_TYPE_T;
                    mandatory true;
                    description "";
                } // END of fecTypeVc definition.


            } // End of vplsPeer-list
            container vplsSignaling {
                presence "yes";
                description
                    "vplsSignaling";
                leaf signalLdp  {
                    type  cml_data_types:CML_BOOL_T;
                    mandatory true;
                    description "";
                } // END of signalLdp definition.


                leaf macwithdrawal  {
                    type  cml_data_types:CML_BOOL_T;
                    default false;
                    description "";
                } // END of macwithdrawal definition.


                leaf vplsType  {
                    type  cml_data_types:CML_NSM_VPLS_TYPE_T;
                    description "";
                } // END of vplsType definition.



                list signalLdpVplsPeer {
                    key "sigPeerId";
                    description
                        "signalLdpVplsPeer";
                    leaf sigPeerId  {
                        type  cml_data_types:CML_IPV4_ADDR_T;
                        description "";
                    } // END of sigPeerId definition.


                    leaf agi  {
                        type  cml_data_types:CML_STRING_T {
                            length "0..255";
                        }
                        description "";
                    } // END of agi definition.


                    leaf saii  {
                        type  cml_data_types:CML_STRING_T {
                            length "0..255";
                        }
                        description "";
                    } // END of saii definition.


                    leaf taii  {
                        type  cml_data_types:CML_STRING_T {
                            length "0..255";
                        }
                        description "";
                    } // END of taii definition.


                    leaf sigTunnelId  {
                        type  cml_data_types:CML_STRING_T {
                            length "0..255";
                        }
                        default "NULL";
                        description "";
                    } // END of sigTunnelId definition.


                    leaf sigTunnelDir  {
                        type  cml_data_types:CML_NSM_VPLS_PEER_TUNNEL_DIR_T;
                        default "forward";
                        description "";
                    } // END of sigTunnelDir definition.


                } // End of signalLdpVplsPeer-list
            } // END of vplsSignaling-container definition.
            container bgpSignaling {
                presence "yes";
                description
                    "bgpSignaling";
                leaf signalBgp  {
                    type  cml_data_types:CML_BOOL_T;
                    mandatory true;
                    description "";
                } // END of signalBgp definition.


                leaf veId  {
                    type  cml_data_types:CML_INT32_T {
                         range "1..64";
                    }
                    description "";
                } // END of veId definition.


            } // END of bgpSignaling-container definition.
        } // End of vpls-list
    } // END of vpls-grouping definition.


    grouping vplsFib-grouping {
    description
        "vplsFib";
        list vplsFib {
            key "vplsId";
            description
                "vplsFib";
            leaf vplsId  {
                type  cml_data_types:CML_UINT32_T {
                     range "1..4294967295";
                }
                description "";
            } // END of vplsId definition.



            list peer {
                key "egressAddr";
                description
                    "peer";
                leaf egressAddr  {
                    type  cml_data_types:CML_IPV4_ADDR_T;
                    description "";
                } // END of egressAddr definition.


                uses vplsFibCommon;
            } // End of peer-list

            list spoke {
                key "vcName";
                description
                    "spoke";
                leaf vcName  {
                    type  cml_data_types:CML_STRING_T {
                        length "0..255";
                    }
                    description "";
                } // END of vcName definition.


                uses vplsFibCommon;
            } // End of spoke-list
        } // End of vplsFib-list
    } // END of vplsFib-grouping definition.


    grouping vplsSvcTemp-grouping {
    description
        "vplsSvcTemp";
        list vplsSvcTemp {
            key "vplsSvcTemp";
            description
                "vplsSvcTemp";
            leaf vplsSvcTemp  {
                type  cml_data_types:CML_STRING_T {
                    length "0..255";
                }
                description "";
            } // END of vplsSvcTemp definition.



            list svcTempName {
                key "svcTempName";
                description
                    "svcTempName";
                leaf svcTempName  {
                    type  cml_data_types:CML_STRING_T {
                        length "0..255";
                    }
                    description "";
                } // END of svcTempName definition.


                leaf svcAdminRole  {
                    type  cml_data_types:CML_NSM_MPLS_ADMIN_STATUS_T;
                    description "";
                } // END of svcAdminRole definition.


                leaf svcAcDescription  {
                    type  cml_data_types:CML_STRING_T {
                        length "0..255";
                    }
                    description "";
                } // END of svcAcDescription definition.


                leaf svcVplsMacLearning  {
                    type  cml_data_types:CML_NSM_MPLS_VPLS_LEARNING_T;
                    description "";
                } // END of svcVplsMacLearning definition.


                leaf svcAllowL2Bpdu  {
                    type  cml_data_types:CML_BOOL_T;
                    description "";
                } // END of svcAllowL2Bpdu definition.



                list vcProfile {
                    if-feature feature_list:HAVE_QOS;
                    key "svcProfileType";
                    description
                        "vcProfile";
                    leaf svcProfileType  {
                        type  cml_data_types:CML_VPLS_QOS_MAP_PROFILE_TYPE_T;
                        description "";
                    } // END of svcProfileType definition.


                    leaf svcProfileName  {
                        type  cml_data_types:CML_STRING_T {
                            length "0..255";
                        }
                        mandatory true;
                        description "";
                    } // END of svcProfileName definition.


                } // End of vcProfile-list
            } // End of svcTempName-list
        } // End of vplsSvcTemp-list
    } // END of vplsSvcTemp-grouping definition.


    grouping vplsEther-grouping {
    description
        "vplsEther";
        list vplsEther {
            key "ifvplsName";
            description
                "vplsEther";
            leaf ifvplsName  {
                type  cml_data_types:CML_STRING_T {
                    length "0..255";
                }
                description "";
            } // END of ifvplsName definition.


            leaf EtherVcType  {
                type  cml_data_types:CML_NSM_MPLS_IF_ETHER_VCTYPE_T;
                default "ethernet";
                description "";
            } // END of EtherVcType definition.


            leaf svlanId  {
                type  cml_data_types:CML_UINT16_T {
                     range "1..4095";
                }
                description "";
            } // END of svlanId definition.


            leaf etherAction  {
                type  cml_data_types:NSM_VPLS_ETHER_ACTION_T;
                description "";
            } // END of etherAction definition.


            leaf tpid  {
                type  cml_data_types:CML_NSM_MPLS_TPID_T;
                description "";
            } // END of tpid definition.


            leaf adminRole  {
                type  cml_data_types:CML_NSM_MPLS_ADMIN_STATUS_T;
                description "";
            } // END of adminRole definition.


            leaf acDescription  {
                type  cml_data_types:CML_LINE_T {
                    length "0..255";
                }
                description "";
            } // END of acDescription definition.


            leaf vplsMacLearning  {
                type  cml_data_types:CML_NSM_MPLS_VPLS_LEARNING_T;
                description "";
            } // END of vplsMacLearning definition.


            leaf allowL2Bpdu  {
                type  cml_data_types:CML_BOOL_T;
                description "";
            } // END of allowL2Bpdu definition.


            leaf vcProfileType  {
                if-feature feature_list:HAVE_QOS;
                type  cml_data_types:CML_VPLS_QOS_MAP_PROFILE_TYPE_T;
                description "";
            } // END of vcProfileType definition.


            leaf vcProfileName  {
                if-feature feature_list:HAVE_QOS;
                type  cml_data_types:CML_STRING_T {
                    length "0..255";
                }
                description "";
            } // END of vcProfileName definition.


        } // End of vplsEther-list
    } // END of vplsEther-grouping definition.


    grouping vplsVlan-grouping {
    description
        "vplsVlan";
        list vplsVlan {
            key "vlanIfvplsName";
            description
                "vplsVlan";
            leaf vlanIfvplsName  {
                type  cml_data_types:CML_STRING_T {
                    length "0..255";
                }
                description "";
            } // END of vlanIfvplsName definition.



            list vlanIf {
                key "vlanId";
                description
                    "vlanIf";
                leaf vlanId  {
                    type  cml_data_types:CML_UINT16_T {
                         range "1..4095";
                    }
                    description "";
                } // END of vlanId definition.


                leaf innerVlan  {
                    type  cml_data_types:CML_UINT16_T {
                         range "1..4095";
                    }
                    description "";
                } // END of innerVlan definition.


                leaf vlanAction  {
                    type  cml_data_types:NSM_VPLS_VLAN_ACTION_T;
                    description "";
                } // END of vlanAction definition.


                leaf tpid  {
                    type  cml_data_types:CML_NSM_MPLS_TPID_T;
                    description "";
                } // END of tpid definition.


                leaf vlanAdminRole  {
                    type  cml_data_types:CML_NSM_MPLS_ADMIN_STATUS_T;
                    description "";
                } // END of vlanAdminRole definition.


                leaf vlanAcDescription  {
                    type  cml_data_types:CML_LINE_T {
                        length "0..255";
                    }
                    description "";
                } // END of vlanAcDescription definition.


                leaf vlanVplsMacLearning  {
                    type  cml_data_types:CML_NSM_MPLS_VPLS_LEARNING_T;
                    description "";
                } // END of vlanVplsMacLearning definition.


                leaf vlanAllowL2Bpdu  {
                    type  cml_data_types:CML_BOOL_T;
                    description "";
                } // END of vlanAllowL2Bpdu definition.


                leaf vlanProfileType  {
                    if-feature feature_list:HAVE_QOS;
                    type  cml_data_types:CML_VPLS_QOS_MAP_PROFILE_TYPE_T;
                    description "";
                } // END of vlanProfileType definition.


                leaf vlanProfileName  {
                    if-feature feature_list:HAVE_QOS;
                    type  cml_data_types:CML_STRING_T {
                        length "0..255";
                    }
                    description "";
                } // END of vlanProfileName definition.


            } // End of vlanIf-list
        } // End of vplsVlan-list
    } // END of vplsVlan-grouping definition.
    grouping vplsFibCommon {
        description
            "vplsFibCommon";
        leaf inLabel  {
            type  cml_data_types:CML_UINT32_T {
                 range "16..52443";
            }
            mandatory true;
            description "";
        } // END of inLabel definition.


        leaf outLabel  {
            type  cml_data_types:CML_UINT32_T {
                 range "16..52443";
            }
            mandatory true;
            description "";
        } // END of outLabel definition.


        leaf outIfName  {
            type  cml_data_types:CML_STRING_T {
                length "0..255";
            }
            mandatory true;
            description "";
        } // END of outIfName definition.


    } // END of vplsFibCommon definition.


}
