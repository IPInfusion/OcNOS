/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-if-ip.yang
*
*/

module ipi-if-ip {

    namespace   "http://www.ipinfusion.com/yang/ocnos/ipi-if-ip";

    prefix "ipi-if-ip";

    import cml-data-types {
        prefix cml-data-types;
    }

    import vr {
        prefix vr;
    }

    import vrf {
        prefix vrf;
    }

    import ipi-interface {
        prefix ipi-interface;
    }

    import ietf-inet-types {
        prefix inet;
    }

    import feature-list {
        prefix feature-list;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for IP interface module";


    revision "2018-06-21" {
        description " Initial Version.";
        reference " Openconfig Yang model : https://github.com/openconfig/public/blob/master/release/models/interfaces/openconfig-if-ip.yang.";
    }

    grouping ipv4-interface-config {
        description
            "Configuration data for IPv4 per interface";
        leaf primary-ip-addr  {
            type  inet:ipv4-prefix;
            description "Use this attribute to specify that an IP address and prefix length will be used by this interface. If the secondary parameter is not specified, this attribute overwrites the primary IP address. If the secondary parameter is specified, this attribute adds a new IP address to the interface. The secondary address cannot be configured in the absence of a primary IP address. The primary address cannot be removed when a secondary address is present.";
        } // END of primary-ip-addr definition.

        leaf prefix-length  {
            type  uint8;
            description "The subnet mask associated with the IPv4 address of this entry. The value of the mask is an IPv4 address with all the network bits set to 1 and all the hosts bits set to 0.";
        } // END of prefix-length definition.

        leaf ip-addr-label  {
            type  cml-data-types:CML_LINE_T;
            default "NULL";
            description "Label of this address. IP label cannot be deleted independently. It can only be deleted in conjunction with IP address";
        } // END of ip-addr-label definition.

        leaf proxy-arp  {
            if-feature feature-list:NOT_HAVE_NDD;
            type  boolean;
            description "Local proxy ARP is used to resolve MAC addresses to IP addresses in the same Layer 3 network such as, private VLANs that are Layer 2-separated. Local proxy ARP supports all types of interfaces supported by ARP and unnumbered interfaces";
        } // END of proxy-arp definition.

        leaf arp-ageing-timeout  {
            if-feature feature-list:NOT_HAVE_NDD;
            type  uint32 {
                 range "1..3000"  {
                    description "ARP Ageing timeout in sec";
                 }
            }
            default "3000";
            description "This attribute is used to set ARP Ageing timeout in sec and arp age timeout value to interface";
        } // END of arp-ageing-timeout definition.

        leaf ipv4-unnumbered-if-name  {
            if-feature feature-list:HAVE_NSM_IF_UNNUMBERED;
            type  string;
            description "This attribute is used to Enable IP processing without an explicit address";
        } // END of ipv4-unnumbered-if-name definition.

        leaf remote-address  {
            if-feature feature-list:HAVE_NSM_IF_UNNUMBERED;
            type  string;
            description "This attribute is used to set the remote address of the PPP link";
        } // END of remote-address definition.

    } // END of ipv4-interface-config definition.
    grouping ipv4-sec-addr-config {
        description
            "Per IPv4 secondary adresss configuration data for the interface";
        leaf ip-address  {
            type  inet:ipv4-prefix;
            description "Use this attribute to specify a secondary IP address that will be  used by this interface. The secondary address cannot be configured in the absence of a primary IP address. The primary address cannot be removed when a secondary address is present.";
        } // END of ip-address definition.

        leaf ip-label  {
            type  cml-data-types:CML_LINE_T;
            default "NULL";
            description "Use this attribute to specify a descriptive label for this IPv4 address. IP label cannot be deleted independently. It can only be deleted in conjunction with IP address";
        } // END of ip-label definition.

    } // END of ipv4-sec-addr-config definition.
    grouping ipv4-interface-state {
        description
            "IPv4 operational state for the interface";
        leaf dhcp-ip-adddress  {
            if-feature feature-list:HAVE_DHCP_CLIENT;
            type  inet:ipv4-prefix;
            config false;
            description "This attribute displays the IPv4 address allocated by DHCP";
        } // END of dhcp-ip-adddress definition.

        leaf ipv4-enabled-status  {
            type  boolean;
            config false;
            description "This attribute displays IPv4 enable status";
        } // END of ipv4-enabled-status definition.

    } // END of ipv4-interface-state definition.
    grouping ipv6-interface-config {
        description
            "Configuration data for IPv6 per interface";
        leaf ipv6-unnumbered-if-name  {
            if-feature feature-list:HAVE_NSM_IF_UNNUMBERED;
            if-feature feature-list:HAVE_IPV6;
            type  string;
            description "Use this attribute to enable IP processing without an explicit address";
        } // END of ipv6-unnumbered-if-name definition.

    } // END of ipv6-interface-config definition.
    grouping ipv6-addr-config {
        description
            "Per IPV6 address configuration data for the interface";
        leaf ipv6-address  {
            type  inet:ipv6-prefix;
            description "Use this attribute to set the IPv6 address of an interface";
        } // END of ipv6-address definition.

        leaf anycast  {
            type  boolean;
            default false;
            description "Use this attribute to set the anycast flag for the IPv6 address of an interface";
        } // END of anycast definition.

    } // END of ipv6-addr-config definition.
    grouping ipv6-interface-state {
        description
            "IPv6 operational state for the interface";
        leaf dhcp-ipv6-adddress  {
            if-feature feature-list:HAVE_DHCP_CLIENT;
            if-feature feature-list:HAVE_IPV6;
            type  inet:ipv6-prefix;
            config false;
            description "This attribute is used to describes DHCP IPv6 Address";
        } // END of dhcp-ipv6-adddress definition.

        leaf ipv6-enabled-status  {
            if-feature feature-list:HAVE_IPV6;
            type  boolean;
            config false;
            description "This attribute describes the IPv6 capability status";
        } // END of ipv6-enabled-status definition.

        leaf forwarding-status  {
            if-feature feature-list:HAVE_IPV6;
            type  boolean;
            config false;
            description "This attribute describes the IPv6 Forwarding status";
        } // END of forwarding-status definition.

    } // END of ipv6-interface-state definition.
    grouping ip-global-config {
        description
            "Global IP related configuration data for the router";
        leaf router-id  {
            type  string;
            description "Router id of the router - an unsigned 32-bit integer expressed in dotted quad notation";
        } // END of router-id definition.

        leaf enable-auto-router-id-selection  {
            type  boolean;
            description "Turn on Automatic Selection of Router ID";
        } // END of enable-auto-router-id-selection definition.

        leaf enable-ip-forwarding  {
            type  boolean;
            description "Enable IP forwarding for the router";
        } // END of enable-ip-forwarding definition.

        leaf enable-ipv6-forwarding  {
            if-feature feature-list:HAVE_IPV6;
            type  boolean;
            description "Enable IPv6 forwarding for the router";
        } // END of enable-ipv6-forwarding definition.

        leaf default-vrf-enable-icmp-broadcast  {
            type  boolean;
            description "This attribute is used to control ICMP echo broadcast reply. It ignores ICMP echo broacast when set to true";
        } // END of default-vrf-enable-icmp-broadcast definition.

    } // END of ip-global-config definition.
    grouping ip-vrf-config {
        description
            "Per VRF configuration data for the router";
        leaf ip-forwarding  {
            type  boolean;
            description "Turn on IP forwarding for the VRF instance";
        } // END of ip-forwarding definition.

        leaf ipv6-forwarding  {
            if-feature feature-list:HAVE_IPV6;
            type  boolean;
            description "Turn on IPv6 forwarding for the VRF instance";
        } // END of ipv6-forwarding definition.

        leaf enable-icmp-broadcast  {
            type  boolean;
            description "This attribute is used to control ICMP echo broadcast reply for VRF instance. It ignores ICMP echo broacast when set to true";
        } // END of enable-icmp-broadcast definition.

    } // END of ip-vrf-config definition.
    grouping ipv4-neighbor-config {
        description
            "Per IPv4 neighbor configuration data";
        leaf arp-ip-address  {
            type  inet:ipv4-address;
            description "The IPv4 address of the neighbor. 
           Neighbor entries are analagous to static ARP entries, they
           create a correspondence between IP and link-layer addresses
        ";
        } // END of arp-ip-address definition.

        leaf ipv4-link-layer-address  {
            type  cml-data-types:CML_MAC_ADDR_T;
            mandatory true;
            description "The link-layer address of the neighbor";
        } // END of ipv4-link-layer-address definition.

        leaf is-arp-proxy  {
            type  boolean;
            mandatory true;
            description "This flag controls if proxy ARP requests need to be responded to for this ARP entry.";
        } // END of is-arp-proxy definition.

    } // END of ipv4-neighbor-config definition.
    grouping ipv6-neighbor-config {
        description
            "Per IPv6 neighbor configuration data";
        leaf neighbor-address  {
            type  inet:ipv6-address;
            description "IPv6 address of the neighbor";
        } // END of neighbor-address definition.

        leaf if-name  {
            type  string;
            mandatory true;
            description "Interface name on which this IPv6 neigbor entry is created";
        } // END of if-name definition.

        leaf ipv6-link-layer-address  {
            type  cml-data-types:CML_MAC_ADDR_T;
            mandatory true;
            description "This attribute is used to set MAC (hardware) address";
        } // END of ipv6-link-layer-address definition.

    } // END of ipv6-neighbor-config definition.

    grouping  ipv4-grouping {
    description
        "Parameters for the IPv4 address family";
    container ipv4 {
        description
            "Parameters for the IPv4 address family";

        list secondary-addresses {
            key "ip-address";
            description
                "List of secondary IPv4 Addresses for the interface";
            leaf ip-address  {
                type  leafref {
                    path  "../config/ip-address";
                }
                description "Use this attribute to specify a secondary IP address that will be  used by this interface. The secondary address cannot be configured in the absence of a primary IP address. The primary address cannot be removed when a secondary address is present.";
            } // END of ip-address definition.

            container config {
                description
                    "IPv4 secondary address configuration data for the interface";
                uses ipv4-sec-addr-config;
            } // END of config-container definition.
            container state {
                config false;
                description
                    "IPv4 secondary address list operational information";
                uses ipv4-sec-addr-config;
            } // END of state-container definition.
        } // End of secondary-addresses-list
        container config {
            description
                "Top-level IPv4 configuration data for the interface";
            uses ipv4-interface-config;
        } // END of config-container definition.
        container state {
            config false;
            description
                "Top-level IPv4 operational state data for the interface";
            uses ipv4-interface-config;
            uses ipv4-interface-state;
        } // END of state-container definition.
    } // END of ipv4-container definition.
    } // END of ipv4-grouping definition.

    grouping  ipv6-grouping {
    description
        "Parameters for the IPv6 address family";
    container ipv6 {
        description
            "Parameters for the IPv6 address family";

        list addresses {
            if-feature feature-list:HAVE_IPV6;
            key "ipv6-address";
            description
                "List of IPv6 Addresses for the interface";
            leaf ipv6-address  {
                type  leafref {
                    path  "../config/ipv6-address";
                }
                description "Use this attribute to set the IPv6 address of an interface";
            } // END of ipv6-address definition.

            container config {
                description
                    "IPv6 address configuration data for the interface";
                uses ipv6-addr-config;
            } // END of config-container definition.
            container state {
                config false;
                description
                    "IPv6 address list operational data for the interface";
                uses ipv6-addr-config;
            } // END of state-container definition.
        } // End of addresses-list
        container config {
            description
                "Top-level IPv6 configuration data for the interface";
            uses ipv6-interface-config;
        } // END of config-container definition.
        container state {
            config false;
            description
                "Top-level IPv6 operational state data for the interface";
            uses ipv6-interface-config;
            uses ipv6-interface-state;
        } // END of state-container definition.
    } // END of ipv6-container definition.
    } // END of ipv6-grouping definition.

    grouping  ip-global-grouping {
    description
        "Global configuration container for the router";
    container ip-global {
        description
            "Global configuration container for the router";

        list vrf {
            if-feature feature-list:HAVE_VRF;
            key "vrfName";
            description
                "List of Virtual Routing and Forwarding instances on the router";
            leaf vrfName  {
                type  leafref {
                    path  "/vr:vr/vrf:vrf/vrf:vrfName";
                }
                description "VPN routing/forwarding Instance name";
            } // END of vrfName definition.

            container config {
                description
                    "Configuration parameters relating to a VRF instance";
                uses ip-vrf-config;
            } // END of config-container definition.
            container state {
                config false;
                description
                    "Configuration parameters relating to a VRF instance";
                uses ip-vrf-config;
            } // END of state-container definition.
        } // End of vrf-list
        container config {
            description
                "Global configuration parameters for the router";
            uses ip-global-config;
        } // END of config-container definition.
        container state {
            config false;
            description
                "Global operational parameters for the router";
            uses ip-global-config;
        } // END of state-container definition.
        container arp {
            description
                "Top level container for ARP and IPv6 neighbor entries for the system";

            list ipv4-static-neighbors {
                if-feature feature-list:HAVE_L3;
                if-feature feature-list:NOT_HAVE_NDD;
                key "arp-ip-address";
                description
                    "Static ARP List";
                leaf arp-ip-address  {
                    type  leafref {
                        path  "../config/arp-ip-address";
                    }
                    description "The IPv4 address of the neighbor.
             Neighbor entries are analagous to static ARP entries, they
             create a correspondence between IP and link-layer addresses
            ";
                } // END of arp-ip-address definition.

                container config {
                    description
                        "Configuration data for each configured IPv4 neighbor";
                    uses ipv4-neighbor-config;
                } // END of config-container definition.
                container state {
                    config false;
                    description
                        "Operational data for each configured IPv4 neighbor";
                    uses ipv4-neighbor-config;
                } // END of state-container definition.
            } // End of ipv4-static-neighbors-list

            list ipv6-static-neighbors {
                if-feature feature-list:HAVE_L3;
                if-feature feature-list:HAVE_IPV6;
                if-feature feature-list:NOT_HAVE_NDD;
                key "neighbor-address";
                description
                    "IPv6 Static neighbors table";
                leaf neighbor-address  {
                    type  leafref {
                        path  "../config/neighbor-address";
                    }
                    description "IPv6 address of the neighbor";
                } // END of neighbor-address definition.

                container config {
                    description
                        "Configuration data for each configured IPv6 neighbor";
                    uses ipv6-neighbor-config;
                } // END of config-container definition.
                container state {
                    config false;
                    description
                        "Operational data for each configured IPv6 neighbor";
                    uses ipv6-neighbor-config;
                } // END of state-container definition.
            } // End of ipv6-static-neighbors-list
        } // END of arp-container definition.
    } // END of ip-global-container definition.
    } // END of ip-global-grouping definition.

    augment /ipi-interface:interfaces/ipi-interface:interface {
        description
            "Parameters for the IPv4 address family";
        uses ipv4-grouping;
    }

    augment /ipi-interface:interfaces/ipi-interface:interface {
        description
            "Parameters for the IPv6 address family";
        uses ipv6-grouping;
    }

        uses ip-global-grouping;

}
