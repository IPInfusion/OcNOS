/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-synce.yang
*
*/

submodule zebos-synce {

    belongs-to  zebos { prefix zebos; }

    import cml_data_types {
        prefix cml_data_types;
    }

    organization
        "IP Infusion Inc.";

    contact
        "Address: 3965 Freedom Circle, Suite 200, Santa Clara, CA 95054
         Phone: +1 408-400-1900
         E-mail: support@ipinfusion.com
         Web: http://www.ipinfusion.com/";

    description
        "Synchronous Ethernet configurations";


    revision "2017-12-01" {
        description "Initial version of datamodel with Backend mapping .";
        reference "";
    }



    grouping externalSynceInterface-grouping {
    description
        "External SyncE interface related operations";
        list externalSynceInterface {
            key "externalSynceIfModeChange";
            description
                "External SyncE interface related operations";
            leaf externalSynceIfModeChange  {
                type  cml_data_types:CML_EXTERNAL_SYNCE_INTERFACE_T;
                description "";
            } // END of externalSynceIfModeChange definition.


            leaf externalSynceModeSetSynchronous  {
                type  cml_data_types:CML_SYNCE_MODE_OPTION_T;
                default "non-synchronous";
                description " Configure the synce interface mode";
            } // END of externalSynceModeSetSynchronous definition.


            leaf externalSynceInputSrcValSet  {
                type  cml_data_types:CML_UINT32_T {
                     range "0..255";
                }
                default "255";
                description " Configure input-sources";
            } // END of externalSynceInputSrcValSet definition.


            leaf externalSynceSetWTRTimer  {
                type  cml_data_types:CML_UINT32_T {
                     range "0..12";
                }
                default "5";
                description " Configure Wait-to-Restore timer";
            } // END of externalSynceSetWTRTimer definition.


            leaf externalSynceHoldOffTimer  {
                type  cml_data_types:CML_UINT32_T {
                     range "300..1800";
                }
                default "300";
                description "Configure Hold-off timer";
            } // END of externalSynceHoldOffTimer definition.


            leaf externalSynceSetQualityLevel  {
                type  cml_data_types:CML_STRING_T {
                    length "0..255";
                }
                description "Configure QL-value";
            } // END of externalSynceSetQualityLevel definition.


        } // End of externalSynceInterface-list
    } // END of externalSynceInterface-grouping definition.

    grouping  synceGlobals-grouping {
    description
        "synce global structure";
    container synceGlobals {
        presence "yes";
        description
            "synce global structure";
        leaf synceModeChange  {
            type  cml_data_types:CML_EMPTY_T;
            mandatory true;
            description "";
        } // END of synceModeChange definition.


        leaf synceOptionSetVal  {
            type  cml_data_types:CML_SYNCE_SYNC_OPTION_T;
            description "Set the synchronization option";
        } // END of synceOptionSetVal definition.


        leaf synceClockSelectionMode  {
            type  cml_data_types:CML_SYNCE_CLK_SELECTION_MODE_T;
            description "Configure selection mode for source clock";
        } // END of synceClockSelectionMode definition.


        leaf ifName  {
            type  cml_data_types:CML_STRING_T {
                length "0..255";
            }
            config false;
            description "The input interface which is locked for clock synchronization";
        } // END of ifName definition.


        leaf esmcState  {
            type  cml_data_types:CML_SYNCE_ESMC_STATE_T;
            config false;
            description "ESMC State";
        } // END of esmcState definition.


        leaf isSelectedSource  {
            type  cml_data_types:CML_SYNCE_IS_SRC_SELECTED_T;
            config false;
            description "Source has been selected";
        } // END of isSelectedSource definition.


        leaf qlVal  {
            type  cml_data_types:CML_STRING_T {
                length "0..255";
            }
            config false;
            description "Quality level value";
        } // END of qlVal definition.


        leaf clkState  {
            type  cml_data_types:CML_SYNCE_CLOCK_STATE_T;
            config false;
            description "Clock state.";
        } // END of clkState definition.


    } // END of synceGlobals-container definition.
    } // END of synceGlobals-container definition.

    grouping  synceInterface-grouping {
    description
        "SyncE interface related operations";
    container synceInterface {
        description
            "SyncE interface related operations";
        leaf synceIfModeChange  {
            type  cml_data_types:CML_BOOL_T;
            description "";
        } // END of synceIfModeChange definition.


        leaf synceModeSetSynchronous  {
            type  cml_data_types:CML_SYNCE_MODE_OPTION_T;
            default "non-synchronous";
            description " Configure the synce interface mode";
        } // END of synceModeSetSynchronous definition.


        leaf synceInputSrcValSet  {
            type  cml_data_types:CML_UINT32_T {
                 range "0..255";
            }
            default "255";
            description " Configure input-sources";
        } // END of synceInputSrcValSet definition.


        leaf synceOutputSrcSet  {
            type  cml_data_types:CML_BOOL_T;
            description " Configure interface as output-source";
        } // END of synceOutputSrcSet definition.


        leaf synceSetWTRTimer  {
            type  cml_data_types:CML_UINT32_T {
                 range "0..12";
            }
            default "5";
            description " Configure Wait-to-Restore timer";
        } // END of synceSetWTRTimer definition.


        leaf synceHoldOffTimer  {
            type  cml_data_types:CML_UINT32_T {
                 range "300..1800";
            }
            default "300";
            description "Configure Hold-off timer";
        } // END of synceHoldOffTimer definition.


        leaf synceSetQualityLevel  {
            type  cml_data_types:CML_STRING_T {
                length "0..255";
            }
            description "Configure QL-value";
        } // END of synceSetQualityLevel definition.


        leaf synceClkSrcId  {
            type  cml_data_types:CML_UINT32_T {
                 range "1..255";
            }
            description "Configure clock-source-identifier";
        } // END of synceClkSrcId definition.


        leaf synceSetLockout  {
            type  cml_data_types:CML_BOOL_T;
            description "set lockout";
        } // END of synceSetLockout definition.


        leaf synceClearLockout  {
            type  cml_data_types:CML_BOOL_T;
            description "clear lockout";
        } // END of synceClearLockout definition.


        leaf synceSourceSelect  {
            type  cml_data_types:CML_SYNCE_SOURCE_SELECT_T;
            description " Configure force or manual switch for a source";
        } // END of synceSourceSelect definition.


        leaf synceClearSwitchSrc  {
            type  cml_data_types:CML_BOOL_T;
            description "clear switch-source";
        } // END of synceClearSwitchSrc definition.


        leaf esmcState  {
            type  cml_data_types:CML_SYNCE_ESMC_STATE_T;
            config false;
            description "ESMC State";
        } // END of esmcState definition.


        leaf isSelectedSource  {
            type  cml_data_types:CML_SYNCE_IS_SRC_SELECTED_T;
            config false;
            description "Source has been selected";
        } // END of isSelectedSource definition.


        leaf qlVal  {
            type  cml_data_types:CML_STRING_T {
                length "0..255";
            }
            config false;
            description "Quality level value";
        } // END of qlVal definition.


        leaf cntrs  {
            type  cml_data_types:CML_UINT32_T;
            config false;
            description "If configured as input source then esmc recv, else esmc sent.";
        } // END of cntrs definition.


        leaf ifpConfPriority  {
            type  cml_data_types:CML_UINT8_T;
            config false;
            description "Priority of the input-source interface";
        } // END of ifpConfPriority definition.


        leaf holdOffTime  {
            type  cml_data_types:CML_UINT32_T;
            config false;
            description "Hold-Off timer for handling signal-Fail condition";
        } // END of holdOffTime definition.


        leaf wtrTime  {
            type  cml_data_types:CML_UINT32_T;
            config false;
            description "WTR timer for handling signal-Fail condition";
        } // END of wtrTime definition.


        leaf signalFail  {
            type  cml_data_types:CML_SYNCE_IS_SF_T;
            config false;
            description "indicate the signal-Fail state at interface";
        } // END of signalFail definition.


        leaf externalCmd  {
            type  cml_data_types:CML_SYNCE_EXTERNAL_CMDS_T;
            config false;
            description "the external commands active on this interface";
        } // END of externalCmd definition.


    } // END of synceInterface-container definition.
    } // END of synceInterface-container definition.

    grouping  synceDebug-grouping {
    description
        "synce debugging";
    container synceDebug {
        description
            "synce debugging";
        leaf synceDebugSet  {
            type  cml_data_types:CML_SYNCE_DEBUG_T;
            description "Debugging functions";
        } // END of synceDebugSet definition.


    } // END of synceDebug-container definition.
    } // END of synceDebug-container definition.


}
