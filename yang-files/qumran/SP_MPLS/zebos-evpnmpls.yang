/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-evpnmpls.yang
*
*/

submodule zebos-evpnmpls {

    belongs-to  zebos { prefix zebos; }

    import cml_data_types {
        prefix cml_data_types;
    }

    import feature_list {
        prefix feature_list;
    }

    include zebos-vrf;
    organization
        "IP Infusion Inc.";

    contact
        "Address: 3965 Freedom Circle, Suite 200, Santa Clara, CA 95054
         Phone: +1 408-400-1900
         E-mail: support@ipinfusion.com
         Web: http://www.ipinfusion.com/";

    description
        "";


    revision "2018-12-28" {
        description " Initial Version.";
        reference "";
    }



    grouping EvpnTenant-grouping {
    description
        "Tunnel Side Configurations including tenant information";
        list EvpnTenant {
            if-feature feature_list:HAVE_MPLS;
            key "evpnId";
            description
                "Tunnel Side Configurations including tenant information";
            leaf evpnId  {
                type  cml_data_types:CML_UINT32_T {
                     range "1..16777215";
                }
                description "Tenant Identifier";
            } // END of evpnId definition.


            leaf vrfNameEVPN  {
                type  cml_data_types:CML_STRING_T {
                    length "1..12";
                }
                description "Associate mac vrf to the tenant";
            } // END of vrfNameEVPN definition.


        } // End of EvpnTenant-list
    } // END of EvpnTenant-grouping definition.

    grouping  evpnVtepIPGlobal-grouping {
    description
        "nvo mpls vtep-ip-global configuration";
    container evpnVtepIPGlobal {
        if-feature feature_list:HAVE_MPLS;
        description
            "nvo mpls vtep-ip-global configuration";
        leaf evpnVtepIpv4  {
            type  cml_data_types:CML_IPV4_ADDR_T;
            description "VTEP global ip address";
        } // END of evpnVtepIpv4 definition.


    } // END of evpnVtepIPGlobal-container definition.
    } // END of evpnVtepIPGlobal-container definition.

    grouping  evpnInterface-grouping {
    description
        "MPLS-EVPN related interface commands";
    container evpnInterface {
        if-feature feature_list:HAVE_MPLS;
        description
            "MPLS-EVPN related interface commands";
        leaf evidInstance  {
            type  cml_data_types:CML_INT32_T {
                 range "1..16777215";
            }
            description "Map already created MPLS evid";
        } // END of evidInstance definition.


        leaf dynamicLearningDisable  {
            type  cml_data_types:CML_BOOL_T;
            default false;
            description "";
        } // END of dynamicLearningDisable definition.



        list evpnAccessPortHostConfigs {
            if-feature feature_list:HAVE_MPLS;
            key "macMAC";
            description
                "Access Port Host configurations";
            leaf macMAC  {
                type  cml_data_types:CML_MAC_ADDR_T {
                    length "0..255";
                }
                description "Configure static MAC only Host under Access Circuit";
            } // END of macMAC definition.


            leaf hostIpv4  {
                type  cml_data_types:CML_IPV4_ADDR_T;
                description "Destination IPv4 Address";
            } // END of hostIpv4 definition.


            leaf hostIpv6  {
                type  cml_data_types:CML_IPV6_ADDR_T;
                description "Destination IPv6 Address";
            } // END of hostIpv6 definition.


        } // End of evpnAccessPortHostConfigs-list
    } // END of evpnInterface-container definition.
    } // END of evpnInterface-container definition.


}
