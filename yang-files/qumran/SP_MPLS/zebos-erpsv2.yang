/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-erpsv2.yang
*
*/

submodule zebos-erpsv2 {

    belongs-to  zebos { prefix zebos; }

    import cml_data_types {
        prefix cml_data_types;
    }

    import ietf-inet-types {
        prefix inet;
    }

    organization
        "IP Infusion Inc.";

    contact
        "Address: 3965 Freedom Circle, Suite 200, Santa Clara, CA 95054
         Phone: +1 408-400-1900
         E-mail: support@ipinfusion.com
         Web: http://www.ipinfusion.com/";

    reference "Rec. ITU-T G.8032/Y.1344 (08/2015)";

    description
        "This module describes configuration and operational data model for ITU.T G.8032 Ethernet Ring Protocol (ERP)";


    revision "2018-05-25" {
        description "Initial version for ERPSv2 module..";
        reference "";
    }



    typedef  ERPS_REVERSION_MODE {
        type enumeration {
            enum revertive {
                value 0;
                description "Represents revertive mode operation of a G.8032 ethernet ring.";
            }
            enum non-revertive {
                value 1;
                description "Represents non-revertive mode operation of a G.8032 ethernet ring.";
            }
        }
        description "This typedef defines G.8032 ring protection operation mode.";
        reference "";
    }

    typedef  ERPS_LINK_STATE {
        type enumeration {
            enum invalid {
                value 0;
                description "Represents Ring port is in initialization state.";
            }
            enum normal {
                value 1;
                description "Ring port is in normal state and ready to forward traffic ring controlled data traffic.";
            }
            enum blocked {
                value 2;
                description "Ring port is blocked and it is not forwarding any data traffic. In normal operations a port is blocked if it is a RPL port.";
            }
            enum failed {
                value 3;
                description "Ring port has local failure. Port is blocked and it is not forwarding any traffic.";
            }
            enum blocked-failed {
                value 4;
                description "Ring port has local failure. Port is blocked and it is not forwarding any traffic.";
            }
            enum local-ms {
                value 5;
                description "Ring port has been blocked by administrative manual switch action.";
            }
            enum local-fs {
                value 6;
                description "Ring port has been blocked by administrative force switch action.";
            }
        }
        description "This typedef defines G.8032 erps link operation state.";
        reference "";
    }

    typedef  ERPS_INSTANCE_TCN_STATE {
        type enumeration {
            enum disable {
                value 0;
                description "Disable";
            }
            enum enable {
                value 1;
                description "Enable";
            }
        }
        description "TCN state type";
        reference "";
    }

    typedef  ERPS_RPL_PORT_TYPE {
        type enumeration {
            enum non-owner {
                value 2;
                description "Represents normal node in the ring.";
            }
            enum owner {
                value 3;
                description "Represents owner node in the ring.";
            }
            enum neighbor {
                value 4;
                description "Represents neighbour node in the ring.";
            }
            enum next-neighbor {
                value 5;
                description "Represents next-neighbour node in the ring.";
            }
        }
        description "Ring port role types.";
        reference "";
    }

    typedef  ERPS_RING_STATE {
        type enumeration {
            enum invalid-state {
                value 0;
                description "None";
            }
            enum initializing {
                value 1;
                description "Ring protocol state machine is initializing and it is not yet operational.";
            }
            enum pending {
                value 2;
                description "Ring does not have any failure or administrative condition however RPL is blocked. In case of revertive mode operation wait-to-restore timer is running.";
            }
            enum idle {
                value 3;
                description "Ring is operational in normal state, RPL link is blocked and no failure or administrative condition exists. Owner node is transmitting R-APS (NR, RB) PDUs.";
            }
            enum force-switch {
                value 4;
                description "User has force-switched ring. This state overrides protection state.";
            }
            enum protection {
                value 5;
                description "One or more failure condition exists on the ring. Failed nodes are transmitting R-APS (SF) PDUs. Upon reaching to protection state ring unblocks RPL link to allow user traffic.";
            }
            enum manual-switch {
                value 6;
                description "User has manually switched ring. This is usually done to perform maintenance operation on the ring node.";
            }
        }
        description "Protocol states for a ring instance.";
        reference "";
    }

    typedef  ERPS_RING_TYPE {
        type enumeration {
            enum major-ring {
                value 1;
                description "G.8032 major ring. In this type of rings, nodes are connected in full circular topology";
            }
            enum sub-ring {
                value 2;
                description "G.8032 sub-ring or open-ring";
            }
        }
        description "Ring types.";
        reference "";
    }

    grouping physicalRing-grouping {
    description
        "This container defines configuration model of G.8032 rings. Collection of G.8032 rings configurations on a device.";
        list physicalRing {
            key "ringName";
            description
                "This container defines configuration model of G.8032 rings. Collection of G.8032 rings configurations on a device.";
            leaf ringName  {
                type  cml_data_types:CML_STRING_T {
                    length "1..255";
                }
                description "G.8032 ring name. This attribue uniquely identifies a ring on the network device.";
            } // END of ringName definition.


            leaf eastIf  {
                type  cml_data_types:CML_STRING_T {
                    length "1..33";
                }
                description "East port associated to the protection ring";
            } // END of eastIf definition.


            leaf westIf  {
                type  cml_data_types:CML_STRING_T {
                    length "1..33";
                }
                description "West port associated to the protection ring";
            } // END of westIf definition.


            leaf description  {
                type  cml_data_types:CML_LINE_T {
                    length "1..255";
                }
                description "Textual description of the ring.";
            } // END of description definition.


        } // End of physicalRing-list
    } // END of physicalRing-grouping definition.


    grouping profile-grouping {
    description
        "This container defines G.8032 ring profiles.";
        list profile {
            key "profileName";
            description
                "This container defines G.8032 ring profiles.";
            leaf profileName  {
                type  cml_data_types:CML_STRING_T {
                    length "1..32";
                }
                description "G.8032 ring profile name";
            } // END of profileName definition.


            leaf waitToRestore  {
                type  cml_data_types:CML_UINT32_T {
                     range "1..12";
                }
                default "5";
                description "In revertive mode the 'wait to restore' (WTR) timer
                    is used to prevent frequent operation of the
                    protection switching due to intermittent signal
                    failure defects.
                    When recovering from a Signal fail, the delay timer
                    must be long enough to allow the recovering network to
                    become stable.
                    WTR timer is activated on RPL owner node. When WTR
                    timer is expired RPL owner node initiates the
                    reversion process by transmitting an R-APS (NR, RB)
                    message.";
            } // END of waitToRestore definition.


            leaf holdOff  {
                type  cml_data_types:CML_UINT16_T {
                     range "0..10000";
                }
                default "0";
                units "milliseconds";
                description "The hold-off timer is used to coordinate the timing of
                    protection switches.
                    When a new defect or more severe defect occurs
                    (new SF), this event is not to be reported immediately
                    to protection switching if the provisioned hold-off
                    timer value is non-zero. Instead, the hold-off timer
                    is started. When the hold-off timer expires, the trail
                    that started the timer is checked as to whether a
                    defect still exists. If one does exist, that defect is
                    reported to protection switching.
                    Hold off timer values SHOULD be specified in multiple of
                    100.";
            } // END of holdOff definition.


            leaf guardTimer  {
                type  cml_data_types:CML_UINT16_T {
                     range "10..2000";
                }
                default "500";
                units "milliseconds";
                description "The guard timer is used to prevent Ethernet ring nodes
                    from acting upon outdated R-APS messages and prevents
                    the possibility of forming a closed loop.
                    This timer period SHOULD be greater than the maximum
                    expected forwarding delay in which an R-APS message
                    traverses the entire ring.
                    The period of the guard timer MAY be configured by the
                    operator in 10 ms steps between 10 ms and 2 seconds.";
            } // END of guardTimer definition.


            leaf waitToBlock  {
                type  cml_data_types:CML_UINT32_T;
                config false;
                description "The time period the RPL owner node waits efore reverting the
                    protection state to idle state when fault is recovered in the ring ";
            } // END of waitToBlock definition.


            leaf protectionMode  {
                type  ERPS_REVERSION_MODE;
                default "revertive";
                description "This leaf defines G.8032 ring protection mode. A ring
                   may operate in revertive or non-revertive mode.
                   In revertive operation, after the condition(s) causing a
                   switch has cleared, the traffic channel is restored to
                   the working transport entity, i.e., blocked on the RPL.
                   In non-revertive operation, the traffic channel
                   continues to use the RPL, if it has not failed, after a
                   switch condition has cleared.";
            } // END of protectionMode definition.


        } // End of profile-list
    } // END of profile-grouping definition.


    grouping erpInstance-grouping {
    description
        "A physical topology ring may contain one or more ring instances. Each ring instance is responsible for protection of a subset of VLAN traffic on the physical ring.";
        list erpInstance {
            key "instName";
            description
                "A physical topology ring may contain one or more ring instances. Each ring instance is responsible for protection of a subset of VLAN traffic on the physical ring.";
            leaf instName  {
                type  cml_data_types:CML_STRING_T {
                    length "1..255";
                }
                description "ERPS instance identifier";
            } // END of instName definition.


            leaf currentState  {
                type  ERPS_RING_STATE;
                config false;
                description "The current state of the ERPS instance";
            } // END of currentState definition.


            leaf prevState  {
                type  ERPS_RING_STATE;
                config false;
                description "The previous state of the ERPS instance";
            } // END of prevState definition.


            leaf profileName  {
                type  cml_data_types:CML_STRING_T {
                    length "1..32";
                }
                description "G.8032 ring profile name. If this profile exists
                    in the profile configuration list, profile
                    parameters will be imported from it, default
                    values will be used otherwise.";
            } // END of profileName definition.


            leaf ringName  {
                type  cml_data_types:CML_STRING_T {
                    length "1..255";
                }
                description "This parameter specifies the physical ring instance to associated with the ERPS instance";
            } // END of ringName definition.


            leaf-list dataTrafficVlan  {
                type  cml_data_types:CML_RANGE_T {
                    length "1..255";
                }
                description "List of VLAN-IDs, protected by ring instance. For
                    example '2, 3-7, 9, 10-100'
                    VLAN-IDs MUST not overlap with VLAN-IDs of any other
                    instance of the same physical ring.";
            } // END of dataTrafficVlan definition.


            leaf level  {
                type  cml_data_types:CML_UINT8_T {
                     range "0..7";
                }
                description "Maintainance Endpoint Level (MEL) at which R-APS
                    PDU is transmitted.All nodes in the ring must be
                    configured with same APS level value.";
            } // END of level definition.


            leaf ringId  {
                type  cml_data_types:CML_UINT8_T {
                     range "1..239";
                }
                description "G.8032 ring instance identifier (Ring ID).";
            } // END of ringId definition.


            leaf rapsChannelVlan  {
                type  cml_data_types:CML_UINT16_T {
                     range "2..4094";
                }
                description "Ring wide control vlan-id used by ERPS instance to send and recieve the RAPS messages in the ring";
            } // END of rapsChannelVlan definition.


            leaf tcnPropagation  {
                type  ERPS_INSTANCE_TCN_STATE;
                description "Allows topology change notification (TCN) propagation to the ERPS ring if it is enabled";
            } // END of tcnPropagation definition.


            leaf-list tcnInstList  {
                type  cml_data_types:CML_STRING_T {
                    length "0..255";
                }
                description "List of Instance that are to be notified when TCN occurs for this instance if topology change notification (TCN) propagation is enabled";
            } // END of tcnInstList definition.


            leaf ringType  {
                type  ERPS_RING_TYPE;
                default "major-ring";
                description "Defines type of a ethernet ring. A ring can be configured as major ring where ring nodes are connected in closed loop or as a sub-ring when a ring may not have a complete closed loop";
            } // END of ringType definition.


            leaf virtualChannel  {
                type  cml_data_types:CML_UINT16_T {
                     range "2..4094";
                }
                description "Ring wide vlan-id used by ERPS instance to send and receive RAPS message in the subring, by allowing the RAPS messages of the sub-ring to flow through the major ring";
            } // END of virtualChannel definition.


            leaf attachToInstance  {
                type  cml_data_types:CML_STRING_T {
                    length "1..31";
                }
                description "This parameter specifies the ERPS instance on major ring which allows the RAPS messages of Sub-ring, so RAPS message will be sent to other nodes in the sub-ring";
            } // END of attachToInstance definition.


            leaf nonVirtualChannel  {
                type  cml_data_types:CML_BOOL_T;
                description "Creates a non-virtual channel";
            } // END of nonVirtualChannel definition.


            leaf description  {
                type  cml_data_types:CML_LINE_T {
                    length "1..255";
                }
                description "Textual description of the erps-instance.";
            } // END of description definition.


            container instanceRole {
                presence "yes";
                description
                    "RPL role related to erps instance";
                leaf instRole  {
                    type  ERPS_RPL_PORT_TYPE;
                    mandatory true;
                    description "RPL role for the ring instance (default role is non-owner).";
                } // END of instRole definition.


                leaf instRolePortId  {
                    type  cml_data_types:ERPS_PORT_ID_TYPE;
                    description "This identifies the ring port for which role is configured";
                } // END of instRolePortId definition.


            } // END of instanceRole-container definition.
            container apsStatistics {
                config false;
                description
                    "R-APS packet statistics";
                leaf txRaps  {
                    type  cml_data_types:CML_UINT32_T;
                    description "Number of R-APS messages transmitted";
                } // END of txRaps definition.


                leaf rxRaps  {
                    type  cml_data_types:CML_UINT32_T;
                    description "Number of R-APS messages received";
                } // END of rxRaps definition.


            } // END of apsStatistics-container definition.
            container eastLink {
                description
                    "Data definitions related to East interface associated to a Protection Ring";
                uses ringLink;
            } // END of eastLink-container definition.
            container westLink {
                description
                    "Data definitions related to west interface associated to a Protection Ring";
                uses ringLink;
            } // END of westLink-container definition.
        } // End of erpInstance-list
    } // END of erpInstance-grouping definition.
    grouping ringLink {
        description
            "Grouping for ring link";
        container link {
            config false;
            description
                "Link details interface name, state of the link associated with ERPS instance";
            leaf ifName  {
                type  cml_data_types:CML_STRING_T {
                    length "1..33";
                }
                description "Name of West port associated with the ERPS instance";
            } // END of ifName definition.


            leaf state  {
                type  ERPS_LINK_STATE;
                description "This parameter indicates the state of the west port associated with the ERPS instance";
            } // END of state definition.


        } // END of link-container definition.
        container remote {
            config false;
            description
                "Remote node-id, bpr values, used by flush logic of the ERP control process.";
            leaf nodeId  {
                type  cml_data_types:CML_MAC_ADDR_T {
                    length "0..255";
                }
                description "Node ID of the last R-APS message received over the ring port. During initialization this value is set to 00:00:00:00:00:00 by ERP control process.";
            } // END of nodeId definition.


            leaf bpr  {
                type  cml_data_types:CML_UINT8_T {
                     range "0..1";
                }
                description "Blocked port reference (BPR) of the last R-APS message received over the ring port. During initialization this value is set to 0 by ERP control process.";
            } // END of bpr definition.


        } // END of remote-container definition.
    } // END of ringLink definition.


}
