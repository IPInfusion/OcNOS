/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-igmp.yang
*
*/

submodule zebos-igmp {

    belongs-to  zebos { prefix zebos; }

    import cml_data_types {
        prefix cml_data_types;
    }

    include zebos-vrf;
    organization
        "IP Infusion Inc.";

    contact
        "Address: 3965 Freedom Circle, Suite 200, Santa Clara, CA 95054
         Phone: +1 408-400-1900
         E-mail: support@ipinfusion.com
         Web: http://www.ipinfusion.com/";

    description
        "";


    revision "2018-06-21" {
        description " Initial Version.";
        reference "";
    }



    grouping mrib4Igmp-grouping {
    description
        "mrib4Igmp";
        list mrib4Igmp {
            key "vrfName";
            description
                "mrib4Igmp";
            leaf vrfName  {
                type  cml_data_types:CML_STRING_T {
                    length "0..255";
                }
                description "";
            } // END of vrfName definition.


            leaf disableSsmMap  {
                type  cml_data_types:CML_BOOL_T;
                default true;
                description "";
            } // END of disableSsmMap definition.


            leaf stateIGMPLimit  {
                type  cml_data_types:CML_UINT32_T {
                     range "1..2097152";
                }
                default "1";
                description "";
            } // END of stateIGMPLimit definition.


            leaf exceptionAccessList  {
                type  cml_data_types:CML_STRING_T {
                    length "0..255";
                }
                description "";
            } // END of exceptionAccessList definition.


            leaf tosCheck  {
                type  cml_data_types:CML_BOOL_T;
                default false;
                description "";
            } // END of tosCheck definition.


            leaf igi_num_grecs  {
                type  cml_data_types:CML_UINT32_T;
                config false;
                description "";
            } // END of igi_num_grecs definition.


            leaf ssmStaticFlag  {
                type  cml_data_types:CML_STRING_T {
                    length "0..255";
                }
                config false;
                description "";
            } // END of ssmStaticFlag definition.


            leaf debugFlag  {
                type  cml_data_types:CML_IGMP_DEBUG_T;
                description "";
            } // END of debugFlag definition.


            leaf termdebugFlag  {
                type  cml_data_types:CML_IGMP_DEBUG_T;
                description "";
            } // END of termdebugFlag definition.



            list ssmStatic {
                key "staticAccessListName";
                description
                    "ssmStatic";
                leaf staticAccessListName  {
                    type  cml_data_types:CML_STRING_T {
                        length "0..255";
                    }
                    description "";
                } // END of staticAccessListName definition.


                leaf-list staticSourceAddr  {
                    type  cml_data_types:CML_IPV4_ADDR_T;
                    description "";
                } // END of staticSourceAddr definition.


            } // End of ssmStatic-list
        } // End of mrib4Igmp-list
    } // END of mrib4Igmp-grouping definition.
    grouping SourceGroup {
        description
            "SourceGroup";
        leaf SGInterfaceName  {
            type  cml_data_types:CML_STRING_T {
                length "0..255";
            }
            config false;
            description "";
        } // END of SGInterfaceName definition.


        leaf groupFlags  {
            type  cml_data_types:CML_STRING_T {
                length "0..255";
            }
            config false;
            description "";
        } // END of groupFlags definition.


        leaf groupUpTime  {
            type  cml_data_types:CML_STRING_T {
                length "0..255";
            }
            config false;
            description "";
        } // END of groupUpTime definition.


        leaf groupMode  {
            type  cml_data_types:CML_STRING_T {
                length "0..255";
            }
            config false;
            description "";
        } // END of groupMode definition.


        leaf groupExpiry  {
            type  cml_data_types:CML_STRING_T {
                length "0..255";
            }
            config false;
            description "";
        } // END of groupExpiry definition.


        leaf groupSFlags  {
            type  cml_data_types:CML_STRING_T {
                length "0..255";
            }
            config false;
            description "";
        } // END of groupSFlags definition.


        leaf lastReporter  {
            type  cml_data_types:CML_STRING_T {
                length "0..255";
            }
            config false;
            description "";
        } // END of lastReporter definition.


        leaf t_igr_v1_host_present  {
            type  cml_data_types:CML_UINT32_T;
            config false;
            description "";
        } // END of t_igr_v1_host_present definition.


        leaf t_igr_v2_host_present  {
            type  cml_data_types:CML_UINT32_T;
            config false;
            description "";
        } // END of t_igr_v2_host_present definition.



        list src_b_tib_grp {
            key "srcBAddr";
            config false;
            description
                "srcCMLSEPbCMLSEPtibCMLSEPgrp";
            leaf srcBAddr  {
                type  cml_data_types:CML_STRING_T {
                    length "0..255";
                }
                description "";
            } // END of srcBAddr definition.


            leaf srcBUpTime  {
                type  cml_data_types:CML_STRING_T {
                    length "0..255";
                }
                description "";
            } // END of srcBUpTime definition.


            leaf srcBExpiry  {
                type  cml_data_types:CML_STRING_T {
                    length "0..255";
                }
                description "";
            } // END of srcBExpiry definition.


            leaf srcBstr  {
                type  cml_data_types:CML_STRING_T {
                    length "0..255";
                }
                description "";
            } // END of srcBstr definition.


            leaf srcBSFlags  {
                type  cml_data_types:CML_STRING_T {
                    length "0..255";
                }
                description "";
            } // END of srcBSFlags definition.


        } // End of src_b_tib_grp-list
    } // END of SourceGroup definition.
    grouping Source_tib_grp {
        description
            "SourceCMLSEPtibCMLSEPgrp";

        list src_a_tib_grp {
            key "MultisourceAddr";
            description
                "srcCMLSEPaCMLSEPtibCMLSEPgrp";
            leaf MultisourceAddr  {
                type  cml_data_types:CML_IPV4_ADDR_T;
                description "";
            } // END of MultisourceAddr definition.


            leaf srcAUpTime  {
                type  cml_data_types:CML_STRING_T {
                    length "0..255";
                }
                config false;
                description "";
            } // END of srcAUpTime definition.


            leaf srcAExpiry  {
                type  cml_data_types:CML_STRING_T {
                    length "0..255";
                }
                config false;
                description "";
            } // END of srcAExpiry definition.


            leaf srcAStr  {
                type  cml_data_types:CML_STRING_T {
                    length "0..255";
                }
                config false;
                description "";
            } // END of srcAStr definition.


            leaf srcASFlags  {
                type  cml_data_types:CML_STRING_T {
                    length "0..255";
                }
                config false;
                description "";
            } // END of srcASFlags definition.


        } // End of src_a_tib_grp-list
    } // END of Source_tib_grp definition.

    grouping  mrib4IgmpInterface-grouping {
    description
        "IGMP interface related operations";
    container mrib4IgmpInterface {
        description
            "IGMP interface related operations";
        leaf proxyIfName  {
            type  cml_data_types:CML_STRING_T {
                length "0..255";
            }
            default "NULL";
            description "";
        } // END of proxyIfName definition.


        leaf setIGMPIfFlag  {
            type  cml_data_types:CML_BOOL_T;
            description "";
        } // END of setIGMPIfFlag definition.


        leaf lastMaxQueryCount  {
            type  cml_data_types:CML_UINT32_T {
                 range "2..7";
            }
            default "2";
            description "";
        } // END of lastMaxQueryCount definition.


        leaf lastMaxQueryInterval  {
            type  cml_data_types:CML_UINT32_T {
                 range "1000..25500";
            }
            default "1000";
            description "";
        } // END of lastMaxQueryInterval definition.


        leaf proxyreportInterval  {
            type  cml_data_types:CML_UINT32_T {
                 range "1000..25500";
            }
            default "1000";
            description "";
        } // END of proxyreportInterval definition.


        leaf querierTimeout  {
            type  cml_data_types:CML_UINT16_T {
                 range "60..300";
            }
            default "255";
            description "";
        } // END of querierTimeout definition.


        leaf queryInterval  {
            type  cml_data_types:CML_UINT32_T {
                 range "1..18000";
            }
            default "125";
            description "";
        } // END of queryInterval definition.


        leaf startUpQueryInterval  {
            type  cml_data_types:CML_UINT32_T {
                 range "1..18000";
            }
            default "31";
            description "";
        } // END of startUpQueryInterval definition.


        leaf queryCount  {
            type  cml_data_types:CML_UINT32_T {
                 range "2..10";
            }
            default "2";
            description "";
        } // END of queryCount definition.


        leaf responseInterval  {
            type  cml_data_types:CML_UINT32_T {
                 range "1..240";
            }
            default "10";
            description "";
        } // END of responseInterval definition.


        leaf robustnessVariableVal  {
            type  cml_data_types:CML_UINT32_T {
                 range "2..7";
            }
            default "2";
            description "";
        } // END of robustnessVariableVal definition.


        leaf versionNumber  {
            type  cml_data_types:CML_UINT16_T {
                 range "1..3";
            }
            default "3";
            description "";
        } // END of versionNumber definition.


        leaf setIGMPIfRaFlag  {
            type  cml_data_types:CML_BOOL_T;
            description "";
        } // END of setIGMPIfRaFlag definition.


        leaf setIGMPIfOfflinkFlag  {
            type  cml_data_types:CML_BOOL_T;
            description "";
        } // END of setIGMPIfOfflinkFlag definition.


        leaf setIGMPIfPxyFlag  {
            type  cml_data_types:CML_BOOL_T;
            description "";
        } // END of setIGMPIfPxyFlag definition.


        leaf accessListName  {
            type  cml_data_types:CML_STRING_T {
                length "0..255";
            }
            default "NULL";
            description "";
        } // END of accessListName definition.


        leaf immediateGroupListName  {
            type  cml_data_types:CML_STRING_T {
                length "0..255";
            }
            default "NULL";
            description "";
        } // END of immediateGroupListName definition.


        leaf stateIGMPIFLimit  {
            type  cml_data_types:CML_UINT32_T {
                 range "1..2097152";
            }
            default "1";
            description "";
        } // END of stateIGMPIFLimit definition.


        leaf ifExceptionAccessList  {
            type  cml_data_types:CML_STRING_T {
                length "0..255";
            }
            default "NULL";
            description "";
        } // END of ifExceptionAccessList definition.


        leaf interfaceName  {
            type  cml_data_types:CML_STRING_T {
                length "0..255";
            }
            config false;
            description "";
        } // END of interfaceName definition.


        leaf state  {
            type  cml_data_types:CML_STRING_T {
                length "0..255";
            }
            config false;
            description "";
        } // END of state definition.


        leaf hostVersion  {
            type  cml_data_types:CML_STRING_T {
                length "0..255";
            }
            config false;
            description "";
        } // END of hostVersion definition.


        leaf InternetAddr  {
            type  cml_data_types:CML_STRING_T {
                length "0..255";
            }
            config false;
            description "";
        } // END of InternetAddr definition.


        leaf proxyOperationalStatus  {
            type  cml_data_types:CML_STRING_T {
                length "0..255";
            }
            config false;
            description "";
        } // END of proxyOperationalStatus definition.


        leaf OtherQuerierAddr  {
            type  cml_data_types:CML_STRING_T {
                length "0..255";
            }
            config false;
            description "";
        } // END of OtherQuerierAddr definition.


        leaf ifIndex  {
            type  cml_data_types:CML_UINT32_T;
            config false;
            description "";
        } // END of ifIndex definition.


        leaf grpMemInterval  {
            type  cml_data_types:CML_UINT32_T;
            config false;
            description "";
        } // END of grpMemInterval definition.


        leaf joinReceivedCount  {
            type  cml_data_types:CML_UINT32_T;
            config false;
            description "";
        } // END of joinReceivedCount definition.


        leaf leaveReceivedCount  {
            type  cml_data_types:CML_UINT32_T;
            config false;
            description "";
        } // END of leaveReceivedCount definition.


        leaf stats_igif_num_reports  {
            type  cml_data_types:CML_UINT32_T;
            config false;
            description "";
        } // END of stats_igif_num_reports definition.


        leaf stat_igif_num_v1_reports  {
            type  cml_data_types:CML_UINT32_T;
            config false;
            description "";
        } // END of stat_igif_num_v1_reports definition.


        leaf stat_igif_num_v3_reports  {
            type  cml_data_types:CML_UINT32_T;
            config false;
            description "";
        } // END of stat_igif_num_v3_reports definition.


        leaf interfaceLimit  {
            type  cml_data_types:CML_UINT32_T;
            config false;
            description "";
        } // END of interfaceLimit definition.


        leaf limitExceptAccessList  {
            type  cml_data_types:CML_STRING_T {
                length "0..255";
            }
            config false;
            description "";
        } // END of limitExceptAccessList definition.


        leaf mcastgCount  {
            type  cml_data_types:CML_UINT32_T;
            config false;
            description "";
        } // END of mcastgCount definition.


        leaf querierState  {
            type  cml_data_types:CML_STRING_T {
                length "0..255";
            }
            config false;
            description "";
        } // END of querierState definition.


        leaf igmpState  {
            type  cml_data_types:CML_STRING_T {
                length "0..255";
            }
            config false;
            description "";
        } // END of igmpState definition.


        leaf igif_querier_wcount  {
            type  cml_data_types:CML_UINT16_T;
            config false;
            description "";
        } // END of igif_querier_wcount definition.


        leaf igif_num_reports  {
            type  cml_data_types:CML_UINT16_T;
            config false;
            description "";
        } // END of igif_num_reports definition.



        list staticGroup {
            key "multicastStaticGroup";
            description
                "staticGroup";
            leaf multicastStaticGroup  {
                type  cml_data_types:CML_IPV4_ADDR_T;
                description "";
            } // END of multicastStaticGroup definition.


            uses SourceGroup;
        } // End of staticGroup-list

        list staticGroupSource {
            key "multicastStaticGroupAddr";
            description
                "staticGroupSource";
            leaf multicastStaticGroupAddr  {
                type  cml_data_types:CML_IPV4_ADDR_T;
                description "";
            } // END of multicastStaticGroupAddr definition.


            leaf isSsmMapped  {
                type  cml_data_types:CML_BOOL_T;
                description "";
            } // END of isSsmMapped definition.


            uses SourceGroup;
            uses Source_tib_grp;
        } // End of staticGroupSource-list

        list joinGroup {
            key "joinGroupAddr";
            description
                "joinGroup";
            leaf joinGroupAddr  {
                type  cml_data_types:CML_IPV4_ADDR_T;
                description "";
            } // END of joinGroupAddr definition.


            uses SourceGroup;
        } // End of joinGroup-list

        list joinGroupSource {
            key "joinGroupSourceAddr";
            description
                "joinGroupSource";
            leaf joinGroupSourceAddr  {
                type  cml_data_types:CML_IPV4_ADDR_T;
                description "";
            } // END of joinGroupSourceAddr definition.


            uses Source_tib_grp;
            uses SourceGroup;
        } // End of joinGroupSource-list

        list ProxyGroup {
            key "ProxyGroupAddr";
            config false;
            description
                "ProxyGroup";
            leaf ProxyInterfaceName  {
                type  cml_data_types:CML_STRING_T {
                    length "0..255";
                }
                description "";
            } // END of ProxyInterfaceName definition.


            leaf ProxyGroupAddr  {
                type  cml_data_types:CML_STRING_T {
                    length "0..255";
                }
                description "";
            } // END of ProxyGroupAddr definition.


            leaf ProxyGroupMode  {
                type  cml_data_types:CML_STRING_T {
                    length "0..255";
                }
                description "";
            } // END of ProxyGroupMode definition.


            leaf ProxyGroupState  {
                type  cml_data_types:CML_STRING_T {
                    length "0..255";
                }
                description "";
            } // END of ProxyGroupState definition.


            leaf ProxyGroupMemberState  {
                type  cml_data_types:CML_STRING_T {
                    length "0..255";
                }
                description "";
            } // END of ProxyGroupMemberState definition.


            leaf src_a_tib_addr  {
                type  cml_data_types:CML_STRING_T {
                    length "0..255";
                }
                description "";
            } // END of src_a_tib_addr definition.


            leaf src_b_tib_addr  {
                type  cml_data_types:CML_STRING_T {
                    length "0..255";
                }
                description "";
            } // END of src_b_tib_addr definition.


        } // End of ProxyGroup-list
    } // END of mrib4IgmpInterface-container definition.
    } // END of mrib4IgmpInterface-container definition.


}
