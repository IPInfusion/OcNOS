/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-sr.yang
*
*/

submodule zebos-sr {

    belongs-to  zebos { prefix zebos; }

    import cml_data_types {
        prefix cml_data_types;
    }

    import feature_list {
        prefix feature_list;
    }

    include zebos-vrf;
    description
        "Segment-Routing";


    revision "2018-06-21" {
        description " Initial Version.";
        reference "";
    }


    grouping  srNsm-grouping {
    description
        "srNsm";
    container srNsm {
        if-feature feature_list:HAVE_SR_MPLS;
        description
            "srNsm";

        list segmentRouting {
            key "srNsmMs";
            description
                "segmentRouting";
            leaf srNsmMs  {
                type  cml_data_types:CML_BOOL_T;
                description "";
            } // END of srNsmMs definition.


            leaf srmsPref  {
                type  cml_data_types:CML_UINT8_T {
                     range "1..255";
                }
                description "";
            } // END of srmsPref definition.



            list prefixSidMap {
                key "srNsmPrefix";
                description
                    "prefixSidMap";
                leaf srNsmPrefix  {
                    type  cml_data_types:CML_BOOL_T;
                    description "";
                } // END of srNsmPrefix definition.


                container prefixMap4 {
                    if-feature feature_list:HAVE_SR_MPLS;
                    presence "yes";
                    description
                        "prefixMap4";
                    leaf srNsmMsIpv4  {
                        type  cml_data_types:CML_BOOL_T;
                        mandatory true;
                        description "";
                    } // END of srNsmMsIpv4 definition.



                    list msIpv4Entry {
                        key "msStartIpv4";
                        description
                            "msIpv4Entry";
                        leaf msStartIpv4  {
                            type  cml_data_types:CML_IPV4_PREFIX_T;
                            description "";
                        } // END of msStartIpv4 definition.


                        leaf msEndIpv4  {
                            type  cml_data_types:CML_STRING_T {
                                length "0..255";
                            }
                            config false;
                            description "";
                        } // END of msEndIpv4 definition.


                        leaf sidStart  {
                            type  cml_data_types:CML_UINT16_T {
                                 range "0..7999";
                            }
                            description "";
                        } // END of sidStart definition.


                        leaf sidEnd  {
                            type  cml_data_types:CML_UINT16_T;
                            config false;
                            description "";
                        } // END of sidEnd definition.


                        leaf range  {
                            type  cml_data_types:CML_UINT16_T {
                                 range "1..7999";
                            }
                            description "";
                        } // END of range definition.


                        leaf attached  {
                            type  cml_data_types:CML_BOOL_T;
                            description "";
                        } // END of attached definition.


                    } // End of msIpv4Entry-list
                } // END of prefixMap4-container definition.
                container prefixMap6 {
                    if-feature feature_list:HAVE_IPV6;
                    if-feature feature_list:HAVE_SR_MPLS;
                    presence "yes";
                    description
                        "prefixMap6";
                    leaf srNsmMsIpv6  {
                        type  cml_data_types:CML_BOOL_T;
                        mandatory true;
                        description "";
                    } // END of srNsmMsIpv6 definition.



                    list msIpv6Entry {
                        key "msStartIpv6";
                        description
                            "msIpv6Entry";
                        leaf msStartIpv6  {
                            type  cml_data_types:CML_IPV6_PREFIX_T;
                            description "";
                        } // END of msStartIpv6 definition.


                        leaf msEndIpv6  {
                            type  cml_data_types:CML_STRING_T {
                                length "0..255";
                            }
                            config false;
                            description "";
                        } // END of msEndIpv6 definition.


                        leaf sidStart  {
                            type  cml_data_types:CML_UINT16_T {
                                 range "0..7999";
                            }
                            description "";
                        } // END of sidStart definition.


                        leaf sidEnd  {
                            type  cml_data_types:CML_UINT16_T;
                            config false;
                            description "";
                        } // END of sidEnd definition.


                        leaf range  {
                            type  cml_data_types:CML_UINT16_T {
                                 range "1..7999";
                            }
                            description "";
                        } // END of range definition.


                        leaf attached  {
                            type  cml_data_types:CML_BOOL_T;
                            description "";
                        } // END of attached definition.


                    } // End of msIpv6Entry-list
                } // END of prefixMap6-container definition.
            } // End of prefixSidMap-list
        } // End of segmentRouting-list
        container srgb {
            if-feature feature_list:HAVE_SR_MPLS;
            description
                "srgb";
            leaf baseSid  {
                type  cml_data_types:CML_UINT32_T {
                     range "16000..23999";
                }
                default "16000";
                description "";
            } // END of baseSid definition.


            leaf last  {
                type  cml_data_types:CML_UINT32_T {
                     range "16000..23999";
                }
                default "23999";
                description "";
            } // END of last definition.


        } // END of srgb-container definition.
    } // END of srNsm-container definition.
    } // END of srNsm-container definition.


}
