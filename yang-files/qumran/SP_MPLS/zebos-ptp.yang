/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-ptp.yang
*
*/

submodule zebos-ptp {

    belongs-to  zebos { prefix zebos; }

    import cml_data_types {
        prefix cml_data_types;
    }

    import feature_list {
        prefix feature_list;
    }

    include zebos-interface;
    organization
        "IP Infusion Inc.";

    contact
        "Address: 3965 Freedom Circle, Suite 200, Santa Clara, CA 95054
         Phone: +1 408-400-1900
         E-mail: support@ipinfusion.com
         Web: http://www.ipinfusion.com/";

    description
        "";


    revision "2017-12-17" {
        description "Initial support for PTP.";
        reference "";
    }



    grouping ptp-grouping {
    description
        "PTP clock";
        list ptp {
            key "ptpInstance";
            description
                "PTP clock";
            leaf ptpInstance  {
                type  cml_data_types:CML_PTP_INSTANCE_T;
                description "PTP clock instance";
            } // END of ptpInstance definition.


            leaf ptpProfile  {
                type  cml_data_types:CML_PTP_PROFILE_T;
                mandatory true;
                description "";
            } // END of ptpProfile definition.


            leaf ptpDebug  {
                type  cml_data_types:CML_BOOL_T;
                description "";
            } // END of ptpDebug definition.



            list externalClock {
                key "ptpExternalClockId";
                description
                    "List of external input/output clock interfaces";
                leaf ptpExternalClockId  {
                    type  cml_data_types:CML_UINT16_T {
                         range "1..4";
                    }
                    description "External input/output interface ID";
                } // END of ptpExternalClockId definition.


                leaf clockIOType  {
                    type  cml_data_types:CML_PTP_CLOCK_IO_TYPE_T;
                    mandatory true;
                    description "External input/output type";
                } // END of clockIOType definition.


                leaf externalClockType  {
                    type  cml_data_types:CML_PTP_EXT_INTERFACE_T;
                    mandatory true;
                    description "External interface type";
                } // END of externalClockType definition.


                leaf externalClockName  {
                    type  cml_data_types:CML_STRING_T {
                        length "0..255";
                    }
                    mandatory true;
                    description "External interface name";
                } // END of externalClockName definition.


            } // End of externalClock-list

            list port {
                if-feature feature_list:HAVE_PTP_HW_OFFLOAD;
                key "ptpPortNumber";
                description
                    "List of port data sets of the clock";
                leaf ptpPortNumber  {
                    type  cml_data_types:CML_UINT16_T {
                         range "1..31";
                    }
                    description "Port number";
                } // END of ptpPortNumber definition.


                leaf portLocalPriority  {
                    type  cml_data_types:CML_UINT8_T {
                         range "1..255";
                    }
                    default "128";
                    description "The local priority attribute of the PTP port clock";
                } // END of portLocalPriority definition.


                leaf portState  {
                    type  cml_data_types:CML_PTP_PORT_STATE_T;
                    default "initializing";
                    config false;
                    description "Current state associated with the port";
                } // END of portState definition.


                leaf ifName  {
                    type  cml_data_types:CML_STRING_T {
                        length "0..255";
                    }
                    description "Reference to the configured underlying interface that is used by this PTP Port";
                } // END of ifName definition.


                leaf logMinDelayReqInterval  {
                    type  cml_data_types:CML_INT8_T {
                         range "-4..-4";
                    }
                    default "-4";
                    description "The base-two logarithm of the minDelayReqInterval (the minimum permitted mean time interval between successive Delay_Req messages)";
                } // END of logMinDelayReqInterval definition.


                leaf logAnnounceInterval  {
                    type  cml_data_types:CML_INT8_T {
                         range "-3..-3";
                    }
                    default "-3";
                    description "The base-two logarithm of the mean announceInterval (mean time interval between successive Announce messages)";
                } // END of logAnnounceInterval definition.


                leaf announceReceiptTimeout  {
                    type  cml_data_types:CML_INT8_T {
                         range "3..3";
                    }
                    default "3";
                    description "The number of announceInterval that have to pass without receipt of an Announce message before the occurrence of the event ANNOUNCE_RECEIPT_TIMEOUT_ EXPIRES";
                } // END of announceReceiptTimeout definition.


                leaf logSyncInterval  {
                    type  cml_data_types:CML_INT8_T {
                         range "-4..-4";
                    }
                    default "-4";
                    description "The base-two logarithm of the mean SyncInterval for multicast messages";
                } // END of logSyncInterval definition.


                leaf delayMechanism  {
                    type  cml_data_types:CML_PTP_DELAY_MECHANISM_T;
                    default "E2E";
                    description "The propagation delay measuring option used by the port in computing meanPathDelay";
                } // END of delayMechanism definition.


                leaf versionNumber  {
                    type  cml_data_types:CML_INT8_T {
                         range "2..2";
                    }
                    default "2";
                    description "The PTP version in use on the port";
                } // END of versionNumber definition.


                leaf masterOnly  {
                    type  cml_data_types:CML_BOOL_T;
                    description "When set the port is a master-only port";
                } // END of masterOnly definition.


            } // End of port-list

            list virtualPort {
                key "ptpVirtualPortNumber";
                description
                    "PTP virtual port";
                leaf ptpVirtualPortNumber  {
                    type  cml_data_types:CML_UINT16_T {
                         range "1..1";
                    }
                    description "Virtual port number";
                } // END of ptpVirtualPortNumber definition.


                leaf virtualPortTodFormat  {
                    type  cml_data_types:CML_PTP_TOD_FORMAT_T;
                    mandatory true;
                    description "Time of day format";
                } // END of virtualPortTodFormat definition.


                leaf virtualPortLocalPriority  {
                    type  cml_data_types:CML_UINT8_T {
                         range "1..255";
                    }
                    default "128";
                    description "The local priority attribute of the PTP virtual port clock";
                } // END of virtualPortLocalPriority definition.


                uses clockQuality;
            } // End of virtualPort-list
            container tod {
                if-feature feature_list:HAVE_PTP_HW_OFFLOAD;
                description
                    "External time of day interface";
                leaf todIOType  {
                    type  cml_data_types:CML_PTP_CLOCK_IO_TYPE_T;
                    description "Type of tod input/output";
                } // END of todIOType definition.


                leaf todFormat  {
                    type  cml_data_types:CML_PTP_TOD_FORMAT_T;
                    description "Time of day format";
                } // END of todFormat definition.


            } // END of tod-container definition.
            container defaultDataset {
                if-feature feature_list:HAVE_PTP_HW_OFFLOAD;
                description
                    "The default data set of the clock";
                leaf domain  {
                    type  cml_data_types:CML_UINT8_T {
                         range "24..43";
                    }
                    default "24";
                    description "The domain number of the current domain";
                } // END of domain definition.


                leaf twoStep  {
                    type  cml_data_types:CML_BOOL_T;
                    default false;
                    description "When set, the clock is a two-step clock; otherwise, the clock is a one-step clock";
                } // END of twoStep definition.


                leaf clockIdentity  {
                    type  cml_data_types:CML_STRING_T {
                        length "0..255";
                    }
                    config false;
                    description "The clockIdentity of the local clock";
                } // END of clockIdentity definition.


                leaf numberPorts  {
                    type  cml_data_types:CML_UINT16_T {
                         range "1..31";
                    }
                    default "1";
                    description "The number of PTP ports on the instance";
                } // END of numberPorts definition.


                leaf priority1  {
                    type  cml_data_types:CML_UINT8_T {
                         range "128..128";
                    }
                    default "128";
                    description "The priority1 attribute of the local clock";
                } // END of priority1 definition.


                leaf priority2  {
                    type  cml_data_types:CML_UINT8_T {
                         range "0..255";
                    }
                    default "128";
                    description "The priority2 attribute of the local clock";
                } // END of priority2 definition.


                leaf slaveOnly  {
                    type  cml_data_types:CML_BOOL_T;
                    default false;
                    description "When set the clock is a slave-only clock";
                } // END of slaveOnly definition.


                leaf localPriority  {
                    type  cml_data_types:CML_UINT8_T {
                         range "1..255";
                    }
                    default "128";
                    description "The local priority attribute of the local clock";
                } // END of localPriority definition.


                leaf maxStepsRemoved  {
                    type  cml_data_types:CML_UINT8_T {
                         range "1..255";
                    }
                    default "255";
                    description "The maximum number of communication paths between the local clock and the grandmaster clock";
                } // END of maxStepsRemoved definition.


                container clockQuality {
                    description
                        "clockQuality";
                    uses clockQuality;
                } // END of clockQuality-container definition.
            } // END of defaultDataset-container definition.
            container currentDataset {
                if-feature feature_list:HAVE_PTP_HW_OFFLOAD;
                config false;
                description
                    "The current data set of the clock";
                leaf stepsRemoved  {
                    type  cml_data_types:CML_UINT16_T;
                    default "0";
                    description "The number of communication paths traversed between the local clock and the grandmaster clock";
                } // END of stepsRemoved definition.


                leaf offsetFromMaster  {
                    type  cml_data_types:CML_PTP_TIME_INTERVAL_T;
                    description "The current value of the time difference between a master and a slave clock as computed by the slave";
                } // END of offsetFromMaster definition.


                leaf meanPathDelay  {
                    type  cml_data_types:CML_PTP_TIME_INTERVAL_T;
                    description "The current value of the mean propagation time between a master and a slave clock as computed by the slave";
                } // END of meanPathDelay definition.


            } // END of currentDataset-container definition.
            container parent {
                if-feature feature_list:HAVE_PTP_HW_OFFLOAD;
                config false;
                description
                    "The parent data set of the clock";
                leaf grandmasterIdentity  {
                    type  cml_data_types:CML_PTP_CLOCK_IDENTITY_T {
                        length "0..255";
                    }
                    description "The clockIdentity attribute of the grandmaster clock";
                } // END of grandmasterIdentity definition.


                leaf grandmasterPriority1  {
                    type  cml_data_types:CML_UINT8_T;
                    description "The priority1 attribute of the grandmaster clock";
                } // END of grandmasterPriority1 definition.


                leaf grandmasterPriority2  {
                    type  cml_data_types:CML_UINT8_T;
                    description "The priority2 attribute of the grandmaster clock";
                } // END of grandmasterPriority2 definition.


                container parentPortIdentity {
                    if-feature feature_list:HAVE_PTP_HW_OFFLOAD;
                    config false;
                    description
                        "The portIdentity of the port on the master, it contains two members: clockIdentity and portNumber";
                    leaf clockIdentity  {
                        type  cml_data_types:CML_STRING_T {
                            length "0..255";
                        }
                        description "Identity of the clock";
                    } // END of clockIdentity definition.


                    leaf port_Number  {
                        type  cml_data_types:CML_UINT16_T;
                        description "Port number";
                    } // END of port_Number definition.


                } // END of parentPortIdentity-container definition.
                container grandmasterClockQuality {
                    if-feature feature_list:HAVE_PTP_HW_OFFLOAD;
                    config false;
                    description
                        "The clockQuality of the grandmaster clock";
                    leaf clockClass  {
                        type  cml_data_types:CML_UINT8_T;
                        description "The clockClass denotes the traceability of the time or frequency distributed by the clock";
                    } // END of clockClass definition.


                    leaf clockAccuracy  {
                        type  cml_data_types:CML_UINT8_T;
                        description "The clockAccuracy indicates the expected accuracy of the clock";
                    } // END of clockAccuracy definition.


                    leaf offsetScaledLogVariance  {
                        type  cml_data_types:CML_UINT16_T;
                        description "The offsetScaledLogVariance provides an estimate of the variations of the clock from a linear timescale when it is not synchronized to another clock using the protocol";
                    } // END of offsetScaledLogVariance definition.


                } // END of grandmasterClockQuality-container definition.
            } // END of parent-container definition.
            container timeProperties {
                if-feature feature_list:HAVE_PTP_HW_OFFLOAD;
                config false;
                description
                    "The timeProperties data set of the clock";
                leaf currentUtcOffsetValid  {
                    type  cml_data_types:CML_BOOL_T;
                    description "When set, the current UTC offset is valid";
                } // END of currentUtcOffsetValid definition.


                leaf currentUtcOffset  {
                    type  cml_data_types:CML_INT16_T;
                    description "The offset between TAI and UTC when the epoch of the PTP system is the PTP epoch, i.e., when ptp-timescale is TRUE; otherwise, the value has no meaning";
                } // END of currentUtcOffset definition.


                leaf leap59  {
                    type  cml_data_types:CML_BOOL_T;
                    description "When set, the last minute of the current UTC day contains 59 seconds";
                } // END of leap59 definition.


                leaf leap61  {
                    type  cml_data_types:CML_BOOL_T;
                    description "When set, the last minute of the current UTC day contains 61 seconds";
                } // END of leap61 definition.


                leaf timeTraceable  {
                    type  cml_data_types:CML_BOOL_T;
                    description "When set, the timescale and the currentUtcOffset are traceable to a primary reference";
                } // END of timeTraceable definition.


                leaf frequencyTraceable  {
                    type  cml_data_types:CML_BOOL_T;
                    description "When set, the frequency determining the timescale is traceable to a primary reference";
                } // END of frequencyTraceable definition.


                leaf ptpTimescale  {
                    type  cml_data_types:CML_BOOL_T;
                    description "When set, the clock timescale of the grandmaster clock is PTP; otherwise, the timescale is ARB (arbitrary)";
                } // END of ptpTimescale definition.


                leaf timeSource  {
                    type  cml_data_types:CML_PTP_TIME_SOURCE_T;
                    description "The source of time used by the grandmaster clock";
                } // END of timeSource definition.


                leaf ptpTimeOfDay  {
                    type  cml_data_types:CML_STRING_T {
                        length "0..255";
                    }
                    description "PTP time of day expressed as Coordinated Universal Time (UTC)";
                } // END of ptpTimeOfDay definition.


            } // END of timeProperties-container definition.
            container ptpStats {
                if-feature feature_list:HAVE_PTP_HW_OFFLOAD;
                config false;
                description
                    "ptpStats";
                leaf ptpPacketsTransmitted  {
                    type  cml_data_types:CML_UINT32_T;
                    description "PTP packets transmitted";
                } // END of ptpPacketsTransmitted definition.


                leaf ptpPacketsReceived  {
                    type  cml_data_types:CML_UINT32_T;
                    description "PTP packets received";
                } // END of ptpPacketsReceived definition.


                leaf ptpPacketsDiscarded  {
                    type  cml_data_types:CML_UINT32_T;
                    description "PTP packets discarded";
                } // END of ptpPacketsDiscarded definition.


                leaf ptpIPv4PacketsReceived  {
                    type  cml_data_types:CML_UINT32_T;
                    description "PTP IPv4 packets received";
                } // END of ptpIPv4PacketsReceived definition.


                leaf ptpIPv6PacketsReceived  {
                    type  cml_data_types:CML_UINT32_T;
                    description "PTP IPv6 packets received";
                } // END of ptpIPv6PacketsReceived definition.


                leaf ptpL2PacketsReceived  {
                    type  cml_data_types:CML_UINT32_T;
                    description "PTP L2 packets received";
                } // END of ptpL2PacketsReceived definition.


                leaf ptpRxQueueOverflows  {
                    type  cml_data_types:CML_UINT32_T;
                    description "PTP RX queue overflows";
                } // END of ptpRxQueueOverflows definition.



                list ptpPortStats {
                    if-feature feature_list:HAVE_PTP_HW_OFFLOAD;
                    key "ptpPortStatsId";
                    config false;
                    description
                        "ptpPortStats";
                    leaf ptpPortStatsId  {
                        type  cml_data_types:CML_UINT16_T;
                        description "PTP port stats index";
                    } // END of ptpPortStatsId definition.


                    leaf ptpPortPacketsTransmitted  {
                        type  cml_data_types:CML_UINT32_T;
                        description "PTP port packets transmitted";
                    } // END of ptpPortPacketsTransmitted definition.


                    leaf ptpPortPacketsReceived  {
                        type  cml_data_types:CML_UINT32_T;
                        description "PTP port packets received";
                    } // END of ptpPortPacketsReceived definition.


                    leaf ptpPortPacketsDiscarded  {
                        type  cml_data_types:CML_UINT32_T;
                        description "PTP port packets discarded";
                    } // END of ptpPortPacketsDiscarded definition.


                } // End of ptpPortStats-list
            } // END of ptpStats-container definition.
        } // End of ptp-list
    } // END of ptp-grouping definition.
    grouping clockQuality {
        description
            "Clock Derived data type for quality of a clock, which contains clockClass, clockAccuracy and offsetScaledLogVariance";
        leaf clockClass  {
            type  cml_data_types:CML_UINT8_T {
                 range "0..255";
            }
            default "248";
            description "The clockClass denotes the traceability of the time or frequency distributed by the clock";
        } // END of clockClass definition.


        leaf clockAccuracy  {
            type  cml_data_types:CML_UINT8_T {
                 range "0..255";
            }
            default "254";
            description "The clockAccuracy indicates the expected accuracy of the clock";
        } // END of clockAccuracy definition.


        leaf offsetScaledLogVariance  {
            type  cml_data_types:CML_UINT16_T {
                 range "0..65535";
            }
            default "65535";
            description "The offsetScaledLogVariance provides an estimate of the variations of the clock from a linear timescale when it is not synchronized to another clock using the protocol";
        } // END of offsetScaledLogVariance definition.


    } // END of clockQuality definition.


}
