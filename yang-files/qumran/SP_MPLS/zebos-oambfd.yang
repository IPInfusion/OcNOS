/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-oambfd.yang
*
*/

submodule zebos-oambfd {

    belongs-to  zebos { prefix zebos; }

    import cml_data_types {
        prefix cml_data_types;
    }

    import feature_list {
        prefix feature_list;
    }

    include zebos-interface;
    organization
        "IP Infusion Inc.";

    contact
        "Address: 3965 Freedom Circle, Suite 200, Santa Clara, CA 95054
         Phone: +1 408-400-1900
         E-mail: support@ipinfusion.com
         Web: http://www.ipinfusion.com/";

    description
        "";


    revision "2018-06-21" {
        description " Initial Version.";
        reference "";
    }



    grouping bfdSession-grouping {
    description
        "bfd Session table for runtime attrs";
        list bfdSession {
            key "bfdSessionIndex";
            config false;
            description
                "bfd Session table for runtime attrs";
            leaf bfdSessionIndex  {
                type  cml_data_types:CML_UINT32_T;
                description "";
            } // END of bfdSessionIndex definition.


            leaf bfdSessRemoteDisc  {
                type  cml_data_types:CML_UINT32_T;
                description "";
            } // END of bfdSessRemoteDisc definition.


            leaf bfdLlType  {
                type  cml_data_types:CML_OAMBFD_SESS_LOWER_LAYER_T;
                description "";
            } // END of bfdLlType definition.


            leaf bfdSessionType  {
                type  cml_data_types:CML_OAMBFD_SESSION_TYPE_T;
                description "";
            } // END of bfdSessionType definition.


            leaf bfdSessionState  {
                type  cml_data_types:CML_OAMBFD_SESSION_STATE_T;
                description "";
            } // END of bfdSessionState definition.


            leaf bfdSessionUptime  {
                type  cml_data_types:CML_STRING_T {
                    length "0..255";
                }
                description "";
            } // END of bfdSessionUptime definition.


            leaf bfdRemoteAddr  {
                type  cml_data_types:CML_STRING_T {
                    length "0..255";
                }
                description "";
            } // END of bfdRemoteAddr definition.


            leaf bfdSessIfIdx  {
                type  cml_data_types:CML_UINT32_T;
                description "";
            } // END of bfdSessIfIdx definition.


            leaf bfdSessVersion  {
                type  cml_data_types:CML_UINT32_T;
                description "";
            } // END of bfdSessVersion definition.


            leaf bfdSessLocDisc  {
                type  cml_data_types:CML_UINT32_T;
                description "";
            } // END of bfdSessLocDisc definition.


            leaf bfdSessLocAddr  {
                type  cml_data_types:CML_STRING_T {
                    length "0..255";
                }
                description "";
            } // END of bfdSessLocAddr definition.


            leaf bfdRemotePort  {
                type  cml_data_types:CML_UINT32_T;
                description "";
            } // END of bfdRemotePort definition.


            leaf bfdLocalPort  {
                type  cml_data_types:CML_UINT32_T;
                description "";
            } // END of bfdLocalPort definition.


            leaf bfdLocalEchoPort  {
                type  cml_data_types:CML_UINT32_T;
                description "";
            } // END of bfdLocalEchoPort definition.


            leaf bfdMplsLspType  {
                type  cml_data_types:CML_UINT32_T;
                description "";
            } // END of bfdMplsLspType definition.


            leaf bfdMplsTnlName  {
                type  cml_data_types:CML_STRING_T {
                    length "0..255";
                }
                description "";
            } // END of bfdMplsTnlName definition.


            leaf bfdMplsFecAddr  {
                type  cml_data_types:CML_STRING_T {
                    length "0..255";
                }
                description "";
            } // END of bfdMplsFecAddr definition.


            leaf bfdMplsLspPingItvl  {
                type  cml_data_types:CML_UINT32_T;
                description "";
            } // END of bfdMplsLspPingItvl definition.


            leaf bfdMplsFtnIndx  {
                type  cml_data_types:CML_UINT32_T;
                description "";
            } // END of bfdMplsFtnIndx definition.


            leaf bfdMplsMinTx  {
                type  cml_data_types:CML_UINT32_T;
                description "";
            } // END of bfdMplsMinTx definition.


            leaf bfdMplsMinRx  {
                type  cml_data_types:CML_UINT32_T;
                description "";
            } // END of bfdMplsMinRx definition.


            leaf bfdMplsMult  {
                type  cml_data_types:CML_UINT32_T;
                description "";
            } // END of bfdMplsMult definition.


            leaf bfdMplsTnlLabel  {
                type  cml_data_types:CML_UINT32_T;
                description "";
            } // END of bfdMplsTnlLabel definition.


            leaf bfdVccvVcId  {
                type  cml_data_types:CML_UINT32_T;
                description "";
            } // END of bfdVccvVcId definition.


            leaf bfdVccvInVcLabel  {
                type  cml_data_types:CML_UINT32_T;
                description "";
            } // END of bfdVccvInVcLabel definition.


            leaf bfdVccvOutVcLabel  {
                type  cml_data_types:CML_UINT32_T;
                description "";
            } // END of bfdVccvOutVcLabel definition.


            leaf bfdVccvCcType  {
                type  cml_data_types:CML_UINT32_T;
                description "";
            } // END of bfdVccvCcType definition.


            leaf bfdVccvCvType  {
                type  cml_data_types:CML_UINT32_T;
                description "";
            } // END of bfdVccvCvType definition.


            leaf bfdVccvAcIx  {
                type  cml_data_types:CML_UINT32_T;
                description "";
            } // END of bfdVccvAcIx definition.


            leaf bfdVccvTnlLabel  {
                type  cml_data_types:CML_UINT32_T;
                description "";
            } // END of bfdVccvTnlLabel definition.


            leaf bfdVccvPeerAddr  {
                type  cml_data_types:CML_UINT32_T;
                description "";
            } // END of bfdVccvPeerAddr definition.


            leaf bfdMplstpMegName  {
                type  cml_data_types:CML_STRING_T {
                    length "0..255";
                }
                description "";
            } // END of bfdMplstpMegName definition.


            leaf bfdMplstpMeName  {
                type  cml_data_types:CML_STRING_T {
                    length "0..255";
                }
                description "";
            } // END of bfdMplstpMeName definition.


            leaf bfdMplstpPathType  {
                type  cml_data_types:CML_UINT8_T;
                description "";
            } // END of bfdMplstpPathType definition.


            leaf bfdSessOptionFlag  {
                type  cml_data_types:CML_OAMBFD_SESSION_FLAGS_T;
                description "";
            } // END of bfdSessOptionFlag definition.


            leaf bfdSessPerfDiag  {
                type  cml_data_types:CML_OAMBFD_PERFORM_DIAG_T;
                description "";
            } // END of bfdSessPerfDiag definition.


            leaf bfdSessMinTx  {
                type  cml_data_types:CML_UINT32_T;
                description "";
            } // END of bfdSessMinTx definition.


            leaf bfdSessMinRx  {
                type  cml_data_types:CML_UINT32_T;
                description "";
            } // END of bfdSessMinRx definition.


            leaf bfdSessMultplier  {
                type  cml_data_types:CML_UINT32_T;
                description "";
            } // END of bfdSessMultplier definition.


            leaf bfdSessNegTx  {
                type  cml_data_types:CML_UINT32_T;
                description "";
            } // END of bfdSessNegTx definition.


            leaf bfdSessNegRx  {
                type  cml_data_types:CML_UINT32_T;
                description "";
            } // END of bfdSessNegRx definition.


            leaf bfdSessNegMultiplier  {
                type  cml_data_types:CML_UINT32_T;
                description "";
            } // END of bfdSessNegMultiplier definition.


            leaf bfdSessEchoTx  {
                type  cml_data_types:CML_UINT32_T;
                description "";
            } // END of bfdSessEchoTx definition.


            leaf bfdSessEchoRx  {
                type  cml_data_types:CML_UINT32_T;
                description "";
            } // END of bfdSessEchoRx definition.


            leaf bfdSessEchoIntvl  {
                type  cml_data_types:CML_UINT32_T;
                description "";
            } // END of bfdSessEchoIntvl definition.


            leaf bfdSessStorTye  {
                type  cml_data_types:CML_UINT32_T;
                description "";
            } // END of bfdSessStorTye definition.


            leaf bfdSessDownTime  {
                type  cml_data_types:CML_STRING_T {
                    length "0..255";
                }
                description "";
            } // END of bfdSessDownTime definition.


            leaf bfdSessDisconTime  {
                type  cml_data_types:CML_STRING_T {
                    length "0..255";
                }
                description "";
            } // END of bfdSessDisconTime definition.


            leaf bfdSessAuthKeyId  {
                type  cml_data_types:CML_UINT32_T;
                description "";
            } // END of bfdSessAuthKeyId definition.


            leaf bfdSessPktIn  {
                type  cml_data_types:CML_STRING_T {
                    length "0..255";
                }
                description "";
            } // END of bfdSessPktIn definition.


            leaf bfdSessPktOut  {
                type  cml_data_types:CML_STRING_T {
                    length "0..255";
                }
                description "";
            } // END of bfdSessPktOut definition.


            leaf bfdSessEchoOut  {
                type  cml_data_types:CML_STRING_T {
                    length "0..255";
                }
                description "";
            } // END of bfdSessEchoOut definition.


            leaf bfdSessIpv6EchoOut  {
                if-feature feature_list:HAVE_IPV6;
                type  cml_data_types:CML_STRING_T {
                    length "0..255";
                }
                description "";
            } // END of bfdSessIpv6EchoOut definition.


            leaf bfdSessIpv6PktOut  {
                if-feature feature_list:HAVE_IPV6;
                type  cml_data_types:CML_STRING_T {
                    length "0..255";
                }
                description "";
            } // END of bfdSessIpv6PktOut definition.


            leaf bfdSessIpv6PktIn  {
                if-feature feature_list:HAVE_IPV6;
                type  cml_data_types:CML_STRING_T {
                    length "0..255";
                }
                description "";
            } // END of bfdSessIpv6PktIn definition.


            leaf bfdSessUpCount  {
                type  cml_data_types:CML_UINT32_T;
                description "";
            } // END of bfdSessUpCount definition.


            leaf bfdSessUpTime  {
                type  cml_data_types:CML_STRING_T {
                    length "0..255";
                }
                description "";
            } // END of bfdSessUpTime definition.


            leaf bfdSessHoldCntr  {
                type  cml_data_types:CML_UINT32_T;
                description "";
            } // END of bfdSessHoldCntr definition.


            leaf bfdSessHoldDown  {
                type  cml_data_types:CML_UINT32_T;
                description "";
            } // END of bfdSessHoldDown definition.


            leaf bfdSessFwdHelloCntr  {
                type  cml_data_types:CML_UINT32_T;
                description "";
            } // END of bfdSessFwdHelloCntr definition.


            leaf bfdSessPktVersion  {
                type  cml_data_types:CML_UINT32_T;
                description "";
            } // END of bfdSessPktVersion definition.


            leaf bfdSessPktDiag  {
                type  cml_data_types:CML_UINT32_T;
                description "";
            } // END of bfdSessPktDiag definition.


            leaf bfdSessPktState  {
                type  cml_data_types:CML_UINT32_T;
                description "";
            } // END of bfdSessPktState definition.


            leaf bfdSessPktDemandEn  {
                type  cml_data_types:CML_UINT32_T;
                description "";
            } // END of bfdSessPktDemandEn definition.


            leaf bfdSessPktPollSeq  {
                type  cml_data_types:CML_UINT32_T;
                description "";
            } // END of bfdSessPktPollSeq definition.


            leaf bfdSessPktFlagState  {
                type  cml_data_types:CML_STRING_T {
                    length "0..255";
                }
                description "";
            } // END of bfdSessPktFlagState definition.


            leaf bfdSessPktMult  {
                type  cml_data_types:CML_UINT32_T;
                description "";
            } // END of bfdSessPktMult definition.


            leaf bfdSessPktLength  {
                type  cml_data_types:CML_UINT32_T;
                description "";
            } // END of bfdSessPktLength definition.


            leaf bfdSessPktMyDisc  {
                type  cml_data_types:CML_UINT32_T;
                description "";
            } // END of bfdSessPktMyDisc definition.


            leaf bfdSessPktUrDisc  {
                type  cml_data_types:CML_UINT32_T;
                description "";
            } // END of bfdSessPktUrDisc definition.


            leaf bfdSessPktMinTx  {
                type  cml_data_types:CML_UINT32_T;
                description "";
            } // END of bfdSessPktMinTx definition.


            leaf bfdSessPktMinRx  {
                type  cml_data_types:CML_UINT32_T;
                description "";
            } // END of bfdSessPktMinRx definition.


            leaf bfdSessPktMinEchoIntvl  {
                type  cml_data_types:CML_UINT32_T;
                description "";
            } // END of bfdSessPktMinEchoIntvl definition.



            list bfdSessionClientInfo {
                key "bfdSessProtoClientId";
                config false;
                description
                    "BFD session client Info";
                leaf bfdSessProtoClientId  {
                    type  cml_data_types:CML_UINT32_T;
                    description "";
                } // END of bfdSessProtoClientId definition.


                leaf bfdSessClientFlag  {
                    type  cml_data_types:CML_STRING_T {
                        length "0..255";
                    }
                    description "";
                } // END of bfdSessClientFlag definition.


            } // End of bfdSessionClientInfo-list
        } // End of bfdSession-list
    } // END of bfdSession-grouping definition.


    grouping bfdInterface-grouping {
    description
        "BFD interface related operations";
        list bfdInterface {
            key "ifName";
            description
                "BFD interface related operations";
            leaf ifName  {
                type  cml_data_types:CML_STRING_T {
                    length "0..255";
                }
                description "";
            } // END of ifName definition.


            leaf isBfdDisable  {
                type  cml_data_types:CML_BOOL_T;
                description "";
            } // END of isBfdDisable definition.


            leaf bfdIfTransmitIntvl  {
                type  cml_data_types:CML_UINT32_T {
                     range "3..999";
                }
                description "";
            } // END of bfdIfTransmitIntvl definition.


            leaf bfdIfRecieveIntvl  {
                type  cml_data_types:CML_UINT32_T {
                     range "3..999";
                }
                description "";
            } // END of bfdIfRecieveIntvl definition.


            leaf bfdIfHelloMultiplier  {
                type  cml_data_types:CML_UINT32_T {
                     range "3..50";
                }
                description "";
            } // END of bfdIfHelloMultiplier definition.


            leaf bfdEchoInterval  {
                type  cml_data_types:CML_UINT32_T {
                     range "50..4294967";
                }
                description "";
            } // END of bfdEchoInterval definition.


            leaf bfdIfSrcAddr  {
                type  cml_data_types:CML_IPV4_ADDR_T;
                description "";
            } // END of bfdIfSrcAddr definition.


            leaf bfdIfAuthType  {
                type  cml_data_types:CML_BFD_MULTIHOP_AUTH_TYPE_T;
                description "";
            } // END of bfdIfAuthType definition.


            leaf bfdIfKeyChain  {
                if-feature feature_list:NOT_HAVE_BFD_HW_OFFLOAD;
                type  cml_data_types:CML_LINE_T {
                    length "0..255";
                }
                description "";
            } // END of bfdIfKeyChain definition.


            leaf bfdIfKeyId  {
                type  cml_data_types:CML_UINT32_T {
                     range "0..255";
                }
                description "";
            } // END of bfdIfKeyId definition.


            leaf bfdIfKeyStr  {
                type  cml_data_types:CML_LINE_T {
                    length "0..255";
                }
                description "";
            } // END of bfdIfKeyStr definition.


            leaf bfdIfIndex  {
                type  cml_data_types:CML_UINT32_T;
                config false;
                description "";
            } // END of bfdIfIndex definition.


            leaf bfdIfState  {
                type  cml_data_types:CML_STRING_T {
                    length "0..255";
                }
                config false;
                description "";
            } // END of bfdIfState definition.


            container bfdSessionSingleHopIpv4 {
                description
                    "bfd single hop session";

                list bfdIpv4ShUserIntfSessSrc {
                    key "bfdIpv4ShUserSrcAddr";
                    description
                        "BFD ipv4 user intf src related configs";
                    leaf bfdIpv4ShUserSrcAddr  {
                        type  cml_data_types:CML_IPV4_ADDR_T;
                        description "";
                    } // END of bfdIpv4ShUserSrcAddr definition.



                    list bfdIpv4ShUserIntfSessDest {
                        key "bfdIpv4ShUserDestAddr";
                        description
                            "BFD ipv4 user intf dest related configs";
                        leaf bfdIpv4ShUserDestAddr  {
                            type  cml_data_types:CML_IPV4_ADDR_T;
                            description "";
                        } // END of bfdIpv4ShUserDestAddr definition.


                        uses bfdSessionAttr;
                    } // End of bfdIpv4ShUserIntfSessDest-list
                } // End of bfdIpv4ShUserIntfSessSrc-list
            } // END of bfdSessionSingleHopIpv4-container definition.
            container bfdSessionMultiHopIpv4 {
                description
                    "bfd single hop session";

                list bfdIpv4MhUserIntfSessSrc {
                    key "bfdIpv4MhUserSrcAddr";
                    description
                        "BFD ipv4 user intf src related configs";
                    leaf bfdIpv4MhUserSrcAddr  {
                        type  cml_data_types:CML_IPV4_ADDR_T;
                        description "";
                    } // END of bfdIpv4MhUserSrcAddr definition.



                    list bfdIpv4MhUserIntfSessDest {
                        key "bfdIpv4MhUserDestAddr";
                        description
                            "BFD ipv4 user intf dest related configs";
                        leaf bfdIpv4MhUserDestAddr  {
                            type  cml_data_types:CML_IPV4_ADDR_T;
                            description "";
                        } // END of bfdIpv4MhUserDestAddr definition.


                        leaf multihopIpv4  {
                            type  cml_data_types:CML_BFD_MULTI_HOP_TYPE_T;
                            description "";
                        } // END of multihopIpv4 definition.


                        uses bfdSessionAttr;
                    } // End of bfdIpv4MhUserIntfSessDest-list
                } // End of bfdIpv4MhUserIntfSessSrc-list
            } // END of bfdSessionMultiHopIpv4-container definition.
            container bfdSessionSingleHopIpv6 {
                description
                    "bfd single hop session";

                list bfdIpv6ShUserIntfSessSrc {
                    key "bfdIpv6ShUserSrcAddr";
                    description
                        "BFD ipv4 user intf src related configs";
                    leaf bfdIpv6ShUserSrcAddr  {
                        type  cml_data_types:CML_IPV6_ADDR_T;
                        description "";
                    } // END of bfdIpv6ShUserSrcAddr definition.



                    list bfdIpv6ShUserIntfSessDest {
                        key "bfdIpv6ShUserDestAddr";
                        description
                            "BFD ipv6 user intf dest related configs";
                        leaf bfdIpv6ShUserDestAddr  {
                            type  cml_data_types:CML_IPV6_ADDR_T;
                            description "";
                        } // END of bfdIpv6ShUserDestAddr definition.


                        uses bfdSessionAttr;
                    } // End of bfdIpv6ShUserIntfSessDest-list
                } // End of bfdIpv6ShUserIntfSessSrc-list
            } // END of bfdSessionSingleHopIpv6-container definition.
            container bfdSessionMultiHopIpv6 {
                description
                    "bfd single hop session";

                list bfdIpv6MhUserIntfSessSrc {
                    key "bfdIpv6MhUserSrcAddr";
                    description
                        "BFD ipv6 user intf src related configs";
                    leaf bfdIpv6MhUserSrcAddr  {
                        type  cml_data_types:CML_IPV6_ADDR_T;
                        description "";
                    } // END of bfdIpv6MhUserSrcAddr definition.



                    list bfdIpv6MhUserIntfSessDest {
                        key "bfdIpv6MhUserDestAddr";
                        description
                            "BFD ipv6 user intf dest related configs";
                        leaf bfdIpv6MhUserDestAddr  {
                            type  cml_data_types:CML_IPV6_ADDR_T;
                            description "";
                        } // END of bfdIpv6MhUserDestAddr definition.


                        leaf multihopIpv6  {
                            type  cml_data_types:CML_BFD_MULTI_HOP_TYPE_T;
                            description "";
                        } // END of multihopIpv6 definition.


                        uses bfdSessionAttr;
                    } // End of bfdIpv6MhUserIntfSessDest-list
                } // End of bfdIpv6MhUserIntfSessSrc-list
            } // END of bfdSessionMultiHopIpv6-container definition.
        } // End of bfdInterface-list
    } // END of bfdInterface-grouping definition.


    grouping confModeDebug-grouping {
    description
        "config mode debug commands";
        list confModeDebug {
            key "vrId";
            description
                "config mode debug commands";
            leaf vrId  {
                type  cml_data_types:CML_INT32_T;
                description "";
            } // END of vrId definition.


            leaf isConfDebugAll  {
                type  cml_data_types:CML_BOOL_T;
                description "";
            } // END of isConfDebugAll definition.


            leaf confModePackets  {
                type  cml_data_types:CML_BOOL_T;
                description "";
            } // END of confModePackets definition.


            leaf confModeEvents  {
                type  cml_data_types:CML_BOOL_T;
                description "";
            } // END of confModeEvents definition.


            leaf confModeIpcErr  {
                type  cml_data_types:CML_BOOL_T;
                description "";
            } // END of confModeIpcErr definition.


            leaf confModeIpcEvent  {
                type  cml_data_types:CML_BOOL_T;
                description "";
            } // END of confModeIpcEvent definition.


            leaf confModeSession  {
                type  cml_data_types:CML_BOOL_T;
                description "";
            } // END of confModeSession definition.


            leaf confModeNsm  {
                type  cml_data_types:CML_BOOL_T;
                description "";
            } // END of confModeNsm definition.


        } // End of confModeDebug-list
    } // END of confModeDebug-grouping definition.


    grouping execModeDebug-grouping {
    description
        "exec mode debug commands";
        list execModeDebug {
            key "vrId";
            description
                "exec mode debug commands";
            leaf vrId  {
                type  cml_data_types:CML_INT32_T;
                description "";
            } // END of vrId definition.


            leaf isExecDebugAll  {
                type  cml_data_types:CML_BOOL_T;
                description "";
            } // END of isExecDebugAll definition.


            leaf execModePackets  {
                type  cml_data_types:CML_BOOL_T;
                description "";
            } // END of execModePackets definition.


            leaf execModeEvents  {
                type  cml_data_types:CML_BOOL_T;
                description "";
            } // END of execModeEvents definition.


            leaf execModeIpcErr  {
                type  cml_data_types:CML_BOOL_T;
                description "";
            } // END of execModeIpcErr definition.


            leaf execModeIpcEvent  {
                type  cml_data_types:CML_BOOL_T;
                description "";
            } // END of execModeIpcEvent definition.


            leaf execModeSession  {
                type  cml_data_types:CML_BOOL_T;
                description "";
            } // END of execModeSession definition.


            leaf execModeNsm  {
                type  cml_data_types:CML_BOOL_T;
                description "";
            } // END of execModeNsm definition.


        } // End of execModeDebug-list
    } // END of execModeDebug-grouping definition.
    grouping bfdSessionAttr {
        description
            "bfdSessionAttr";
        leaf demandMode  {
            type  cml_data_types:CML_BOOL_T;
            description "";
        } // END of demandMode definition.


        leaf nonPersistant  {
            type  cml_data_types:CML_BOOL_T;
            description "";
        } // END of nonPersistant definition.


        leaf adminDown  {
            type  cml_data_types:CML_BOOL_T;
            description "";
        } // END of adminDown definition.


    } // END of bfdSessionAttr definition.

    grouping  bfd-grouping {
    description
        "BFD basic configurations";
    container bfd {
        description
            "BFD basic configurations";
        leaf enGtsmProtection  {
            if-feature feature_list:HAVE_BFD_MONO;
            if-feature feature_list:NOT_HAVE_BFD_HW_OFFLOAD;
            type  cml_data_types:CML_BFD_SESSION_STATE_T;
            description "";
        } // END of enGtsmProtection definition.


        leaf bfdNotfEn  {
            if-feature feature_list:HAVE_BFD_MONO;
            type  cml_data_types:CML_BFD_SESSION_STATE_T;
            description "";
        } // END of bfdNotfEn definition.


        leaf bfdGbTransmitIntvl  {
            if-feature feature_list:HAVE_BFD_MONO;
            type  cml_data_types:CML_UINT32_T {
                 range "3..999";
            }
            description "";
        } // END of bfdGbTransmitIntvl definition.


        leaf bfdGbRecieveIntvl  {
            if-feature feature_list:HAVE_BFD_MONO;
            type  cml_data_types:CML_UINT32_T {
                 range "3..999";
            }
            description "";
        } // END of bfdGbRecieveIntvl definition.


        leaf bfdGbHelloMultiplier  {
            if-feature feature_list:HAVE_BFD_MONO;
            type  cml_data_types:CML_UINT32_T {
                 range "3..50";
            }
            description "";
        } // END of bfdGbHelloMultiplier definition.


        leaf isEchoSet  {
            if-feature feature_list:HAVE_BFD_MONO;
            type  cml_data_types:CML_BOOL_T;
            description "";
        } // END of isEchoSet definition.


        leaf gtsmTtl  {
            if-feature feature_list:HAVE_BFD_MONO;
            if-feature feature_list:NOT_HAVE_BFD_HW_OFFLOAD;
            type  cml_data_types:CML_UINT8_T {
                 range "1..255";
            }
            default "255";
            description "";
        } // END of gtsmTtl definition.


        leaf bfdStartTime  {
            if-feature feature_list:HAVE_BFD_MONO;
            type  cml_data_types:CML_STRING_T {
                length "0..255";
            }
            config false;
            description "";
        } // END of bfdStartTime definition.


        leaf bfdSessionCount  {
            if-feature feature_list:HAVE_BFD_MONO;
            type  cml_data_types:CML_UINT32_T;
            config false;
            description "";
        } // END of bfdSessionCount definition.


        leaf bfdAdminState  {
            if-feature feature_list:HAVE_BFD_MONO;
            type  cml_data_types:CML_OAMBFD_ADMIN_STATE_T;
            config false;
            description "";
        } // END of bfdAdminState definition.


        leaf bfdImageType  {
            if-feature feature_list:HAVE_BFD_MONO;
            type  cml_data_types:CML_OAMBFD_IMAGE_TYPE_T;
            config false;
            description "";
        } // END of bfdImageType definition.


        leaf bfdLocalDisc  {
            if-feature feature_list:HAVE_BFD_MONO;
            type  cml_data_types:CML_UINT32_T;
            config false;
            description "";
        } // END of bfdLocalDisc definition.


        leaf slowTimerIntvl  {
            if-feature feature_list:HAVE_BFD_MONO;
            type  cml_data_types:CML_UINT32_T {
                 range "1000..30000";
            }
            default "2000";
            description "";
        } // END of slowTimerIntvl definition.



        list bfdMultihopKeyChain {
            if-feature feature_list:HAVE_BFD_MONO;
            key "bfdMultihopAddr";
            description
                "BFD multihop peer configs";
            leaf bfdMultihopAddr  {
                type  cml_data_types:CML_IP_ADDR_T {
                    length "0..255";
                }
                description "";
            } // END of bfdMultihopAddr definition.


            leaf bfdAuthType  {
                type  cml_data_types:CML_BFD_MULTIHOP_AUTH_TYPE_T;
                description "";
            } // END of bfdAuthType definition.


            leaf bfdKeyChain  {
                if-feature feature_list:NOT_HAVE_BFD_HW_OFFLOAD;
                type  cml_data_types:CML_LINE_T {
                    length "0..255";
                }
                description "";
            } // END of bfdKeyChain definition.


            leaf bfdMultihopKeyId  {
                type  cml_data_types:CML_UINT32_T {
                     range "0..255";
                }
                description "";
            } // END of bfdMultihopKeyId definition.


            leaf bfdKeyStr  {
                type  cml_data_types:CML_LINE_T {
                    length "0..255";
                }
                description "";
            } // END of bfdKeyStr definition.


            leaf bfdTransmitIntvl  {
                type  cml_data_types:CML_UINT32_T {
                     range "50..999";
                }
                description "";
            } // END of bfdTransmitIntvl definition.


            leaf bfdRecieveIntvl  {
                type  cml_data_types:CML_UINT32_T {
                     range "50..999";
                }
                description "";
            } // END of bfdRecieveIntvl definition.


            leaf bfdHelloMultiplier  {
                type  cml_data_types:CML_UINT32_T {
                     range "3..50";
                }
                default "3";
                description "";
            } // END of bfdHelloMultiplier definition.


        } // End of bfdMultihopKeyChain-list
    } // END of bfd-container definition.
    } // END of bfd-container definition.

    grouping  oamMpls-grouping {
    description
        "Oam mpls configs";
    container oamMpls {
        if-feature feature_list:HAVE_MPLS_OAM;
        description
            "Oam mpls configs";
        leaf mplsPingReq  {
            type  cml_data_types:CML_BOOL_T;
            description "";
        } // END of mplsPingReq definition.


        leaf mplsPingReply  {
            type  cml_data_types:CML_BOOL_T;
            description "";
        } // END of mplsPingReply definition.


    } // END of oamMpls-container definition.
    } // END of oamMpls-container definition.


}
