/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-cfm.yang
*
*/

submodule zebos-cfm {

    belongs-to  zebos { prefix zebos; }

    import cml_data_types {
        prefix cml_data_types;
    }

    import ietf-inet-types {
        prefix inet;
    }

    import feature_list {
        prefix feature_list;
    }

    include zebos-interface;
    organization
        "IP Infusion Inc.";

    contact
        "Address: 3965 Freedom Circle, Suite 200, Santa Clara, CA 95054
         Phone: +1 408-400-1900
         E-mail: support@ipinfusion.com
         Web: http://www.ipinfusion.com/";

    description
        "Continuity Check management";


    revision "2018-12-28" {
        description "Revised on 2018-12-28.";        reference "";    }

    revision "2018-06-21" {
        description "Revised on 2018-06-21.";        reference "";    }



    typedef  CML_CFM_MIP_T {
        type enumeration {
            enum none {
                value 1;
                description "No mip can be created for this vid";
            }
            enum default {
                value 2;
                description "MIP can be created if no lower active level or MEP at next lower active level";
            }
            enum explicit {
                value 3;
                description "MEP is needed at the next lower active level";
            }
        }
        description "";
        reference "";
    }

    typedef  CML_CFM_ID_PERMISSION_T {
        type enumeration {
            enum none {
                value 1;
                description "The Sender ID TLV is not to be sent";
            }
            enum chassis {
                value 2;
                description "The Chassis ID Length, Chassis ID Subtype, and Chassis ID fields of the Sender ID TLV are to be sent, but not the Management Address Length or Management Address fields";
            }
            enum manage {
                value 3;
                description "The Management Address Length and Management Address of the Sender ID TLV are to be sent, but the Chassis ID Length is to be transmitted with a 0 value, and the Chassis ID Subtype and Chassis ID fields not sen";
            }
            enum chassis-manage {
                value 4;
                description "The Chassis ID Length, Chassis ID Subtype, Chassis ID, Management Address Length, and Management Address fields are all to be sent";
            }
            enum defer {
                value 5;
                description "The contents of the Sender ID TLV are determined by the Maintenance Domain managed object";
            }
        }
        description "";
        reference "";
    }

    typedef  CML_CFM_ERR_CONDITION_T {
        type enumeration {
            enum cfm-leak {
                value 1;
                description "Cfm-leaks";
            }
            enum conflicting-vids {
                value 2;
                description "Conflicting-vids";
            }
            enum excessive-levels {
                value 3;
                description "Excessive-levels";
            }
            enum overlapped-levels {
                value 4;
                description "Overlapped-levels";
            }
        }
        description "";
        reference "";
    }

    typedef  CML_CFM_MD_TYPE_T {
        type enumeration {
            enum no-name {
                value 1;
                description "No Maintenace Domain Name. MA type can be integer or ITU-T Carrier code (ICC) based format defined by ITU-T Y.1731";
            }
            enum character-string {
                value 4;
                description "MD name type is Character string. MA type can be string only";
            }
        }
        description "";
        reference "";
    }

    typedef  CML_CFM_MA_TYPE_T {
        type enumeration {
            enum string {
                value 2;
                description "Enter a string as the ma-name. MD type should be string";
            }
            enum integer {
                value 3;
                description "Enter a integer as ma-name. MD type should be no-name";
            }
            enum itu-t {
                value 32;
                description "ITU-T Carrier code (ICC) based format defined by ITU-T Y.1731. MD type should be no-name";
            }
        }
        description "";
        reference "";
    }

    typedef  CML_CFM_MA_MIP_T {
        type enumeration {
            enum none {
                value 1;
                description "No mip can be created for this vid";
            }
            enum default {
                value 2;
                description "MIP can be created if no lower active level or MEP at next lower active level";
            }
            enum explicit {
                value 3;
                description "MEP is needed at the next lower active level";
            }
            enum defer {
                value 4;
                description "Use the mip-creation permissions of the md to which this ma belongs";
            }
        }
        description "";
        reference "";
    }

    typedef  CML_CFM_MEP_DIR_T {
        type enumeration {
            enum down {
                value 1;
                description "Down mep";
            }
            enum up {
                value 2;
                description "Up mep";
            }
        }
        description "";
        reference "";
    }

    typedef  CML_CFM_MEP_STATE_T {
        type enumeration {
            enum false {
                value 0;
                description "Mep is to cease functioning";
            }
            enum true {
                value 1;
                description "Mep is to function normally";
            }
        }
        description "";
        reference "";
    }

    typedef  CML_CFM_MEP_UNI_T {
        type enumeration {
            enum uni-mep {
                value 1;
                description "Uni-meg mep to intimate the UNI Type";
            }
        }
        description "";
        reference "";
    }

    typedef  CML_CFM_CCM_INTERVAL_T {
        type enumeration {
            enum 1 {
                value 1;
                description "CCI Interval 3 millisecond";
            }
            enum 2 {
                value 2;
                description "CCI Interval 10 millisecond";
            }
            enum 3 {
                value 3;
                description "CCI Interval 100 millisecond";
            }
            enum 4 {
                value 4;
                description "CCI Interval 1 second(default)";
            }
            enum 5 {
                value 5;
                description "CCI Interval 10 second";
            }
        }
        description "";
        reference "";
    }

    typedef  CFM_MEP_CC_T {
        type enumeration {
            enum disable {
                value 0;
                description "Disable continuity check";
            }
            enum enable {
                value 1;
                description "Enable continuity check";
            }
        }
        description "";
        reference "";
    }

    typedef  CFM_AUTO_RMEP_T {
        type enumeration {
            enum disable {
                value 0;
                description "Disable auto rmep learning";
            }
            enum enable {
                value 1;
                description "Enable auto rmep learning";
            }
        }
        description "";
        reference "";
    }

    typedef  CML_CFM_MEP_AIS_T {
        type enumeration {
            enum disable {
                value 0;
                description "Disable alarm indication signal";
            }
            enum enable {
                value 1;
                description "Enable alarm indication signal";
            }
        }
        description "";
        reference "";
    }

    typedef  CML_CFM_AIS_MEP_DEFECTS_T {
        type enumeration {
            enum all {
                value 0;
                description "All defects";
            }
            enum defRDICCM {
                value 1;
                description "DefRDICCM";
            }
            enum defMACstatus {
                value 2;
                description "DefMACstatus";
            }
            enum defRemoteCCM {
                value 3;
                description "DefRemoteCCM";
            }
            enum defErrorCCM {
                value 4;
                description "DefErrorCCM";
            }
            enum defXconCCM {
                value 5;
                description "DefXconCCM";
            }
        }
        description "";
        reference "";
    }

    typedef  CML_MEP_LOW_DEFECTS_T {
        type enumeration {
            enum defRDICCM {
                value 1;
                description "DefRDICCM";
            }
            enum defMACstatus {
                value 2;
                description "DefMACstatus";
            }
            enum defRemoteCCM {
                value 3;
                description "DefRemoteCCM";
            }
            enum defErrorCCM {
                value 4;
                description "DefErrorCCM";
            }
            enum defXconCCM {
                value 5;
                description "DefXconCCM";
            }
        }
        description "";
        reference "";
    }

    typedef  CML_MEP_DEFECTS_T {
        type enumeration {
            enum none {
                value 1;
                description "No defects since FNG_RESET";
            }
            enum defRDICCM {
                value 2;
                description "DefRDICCM";
            }
            enum defMACstatus {
                value 3;
                description "DefMACstatus";
            }
            enum defRemoteCCM {
                value 4;
                description "DefRemoteCCM";
            }
            enum defErrorCCM {
                value 5;
                description "DefErrorCCM";
            }
            enum defXconCCM {
                value 6;
                description "DefXconCCM";
            }
        }
        description "";
        reference "";
    }

    typedef  CML_MEP_DEFECTS_BIT_T {
        type bits {
            bit DefRDICCM {
                position 0;
                description "A remote MEP is reported the RDI bit in its last CCM.";
            }
            bit DefMACstatus {
                position 1;
                description "Either some remote MEP is reporting its Interface Status TLV as not isUp, or all remote MEPs are reporting a Port Status TLV that contains some value other than psUp.";
            }
            bit DefRemoteCCM {
                position 2;
                description "The MEP is not receiving valid CCMs from at least one of the remote MEPs.";
            }
            bit DefErrorCCM {
                position 3;
                description "The MEP has received at least one invalid CCM whose CCM Interval has not yet timed out.";
            }
            bit DefXconCCM {
                position 4;
                description "The MEP has received at least one CCM from either another MAID or a lower MD Level whose CCM Interval has not yet timed out.";
            }
        }
        description "";
        reference "";
    }

    typedef  CML_MEASUREMENTTYPE_T {
        type enumeration {
            enum lmm {
                value 1;
                description "LMM SOAM PDU generated and received LMR responses tracked.";
            }
            enum slm {
                value 2;
                description "SLM SOAM PDU generated and received SLR responses tracked(default).";
            }
            enum ccm {
                value 3;
                description "CCM SOAM PDU generated and received CCM PDUs tracked";
            }
        }
        description "";
        reference "";
    }

    typedef  CML_MEASUREMENTTYPE_REPLY_T {
        type enumeration {
            enum lmm {
                value 1;
                description "LMM SOAM PDU generated and received LMR responses tracked.";
            }
            enum slm {
                value 2;
                description "SLM SOAM PDU generated and received SLR responses tracked(default).";
            }
        }
        description "";
        reference "";
    }

    typedef  CML_SESSION_STATUS_T {
        type enumeration {
            enum active {
                value 1;
                description "Indicates the measurement instance is active";
            }
            enum not-active {
                value 2;
                description "Indicates the measurement instance is not active";
            }
        }
        description "";
        reference "";
    }

    typedef  CML_CFM_AIS_INTERVAL_T {
        type enumeration {
            enum one-second {
                value 1;
                description "TX interval one second";
            }
            enum one-minute {
                value 60;
                description "TX interval one minute";
            }
        }
        description "";
        reference "";
    }

    typedef  CML_MEP_FNG_STATE_T {
        type enumeration {
            enum reset {
                value 0;
                description "No defect has been present since the fng-reset-time timer expired or since the state machine was last reset.";
            }
            enum defect {
                value 1;
                description "A defect is present but not for a long enough time to be reported (fng-alarm-time).";
            }
            enum report-defect {
                value 2;
                description "A momentary state during which the defect is reported by sending a fault-alarm notificationif that action is enabled.";
            }
            enum defect-reported {
                value 3;
                description "A defect is present and some defect has been reported";
            }
            enum defect-clearing {
                value 4;
                description "No defect is present but the fng-reset-time timer has not yet expired.";
            }
        }
        description "";
        reference "";
    }

    typedef  CML_CFM_RELAY_ACTION_T {
        type enumeration {
            enum hit {
                value 0;
                description "Indicates the LTM reached an MP whose MAC address matches the target MAC address.";
            }
            enum filtering-database {
                value 1;
                description "Indicates the Egress Port was determined by consulting the Filtering Database.";
            }
            enum mip-ccm-database {
                value 2;
                description "Indicates the Egress Port was determined by consulting the MIP CCM Database.";
            }
        }
        description "";
        reference "";
    }

    typedef  CML_CFM_INGRESS_ACTION_T {
        type enumeration {
            enum ok {
                value 0;
                description "Indicates the target data frame would be passed through to the MAC Relay Entity";
            }
            enum down {
                value 1;
                description "Indicates the Bridge Ports MAC Operational parameter is false";
            }
            enum blocked {
                value 2;
                description "Indicates the target data frame would not be forwarded if received on this Port due to active topology enforement";
            }
            enum vid {
                value 3;
                description "Indicates the ingress port is not in the member set of the LTMs VID, and ingress filtering is enabled, so the target data frame would be filtered by ingress filtering";
            }
        }
        description "";
        reference "";
    }

    typedef  CML_PORT_STATUS_T {
        type enumeration {
            enum no-status-tlv {
                value 0;
                description "Indicates either that no CCM has been received or that no port status TLV was present in the last CCM received";
            }
            enum blocked {
                value 1;
                description "Ordinary data cannot pass freely through the port on which the remote MEP resides. Value of enableRmepDefect is equal to false";
            }
            enum up {
                value 2;
                description "Ordinary data can pass freely through the port on which the remote MEP resides. Value of enableRmepDefect is equal to true";
            }
        }
        description "";
        reference "";
    }

    typedef  CML_INTF_STATUS_T {
        type enumeration {
            enum no-status-tlv {
                value 0;
                description "Indicates either that no CCM has been received or that no interface status TLV was present in the last CCM received";
            }
            enum up {
                value 1;
                description "The interface is ready to pass packets";
            }
            enum down {
                value 2;
                description "The interface cannot pass packets";
            }
            enum testing {
                value 3;
                description "The interface is in some test mode";
            }
            enum unknown {
                value 4;
                description "The interface status cannot be determined for some reason";
            }
            enum dormant {
                value 5;
                description "The interface is not in a state to pass packets but is in a pending state, waiting for some external event";
            }
            enum not-present {
                value 6;
                description "Some component of the interface is missing";
            }
            enum lower-layer-down {
                value 7;
                description "The interface is down due to state of the lower layer interfaces";
            }
        }
        description "";
        reference "";
    }

    typedef  CML_CFM_EGRESS_ACTION_T {
        type enumeration {
            enum ok {
                value 0;
                description "Indicates the targeted data frame would be forwarded";
            }
            enum down {
                value 1;
                description "Indicates the Egress Port can be identified but that Bridge Ports MAC Operational parameter is false.";
            }
            enum blocked {
                value 2;
                description "Indicates the Egress Port can be identified but the data frame would not pass through the the Egress Port due to active topology management i.e the Bridge Port is not in the Forwarding state";
            }
            enum vid {
                value 3;
                description "Indicates the Egress Port can be identified but the Bridge Port is not in the LTMs VIDs member set, so would be filtered by egress filtering";
            }
        }
        description "";
        reference "";
    }

    typedef  CML_CFM_PORTID_SUBTYPE_T {
        type enumeration {
            enum interface-alias {
                value 1;
                description "The ifAlias field from the Interfaces Group MIB";
            }
            enum port-component {
                value 2;
                description "EntPhysicalAlias when entPhysClass has a value of port(10) or backplane(4)";
            }
            enum mac-address {
                value 3;
                description "A MAC address";
            }
            enum network-address {
                value 4;
                description "network-address is an octet string that identifies a particular network address family and an associated network address that are encoded in network octet order";
            }
            enum interface-name {
                value 5;
                description "The ifName field from the Interfaces Group MIB";
            }
            enum agent-circuit-id {
                value 6;
                description "Agent circuit ID";
            }
            enum local {
                value 7;
                description "A locally defined identifier";
            }
        }
        description "";
        reference "";
    }

    typedef  CML_CHASSISID_SUBTYPE_T {
        type enumeration {
            enum chassis-component {
                value 1;
                description "This leaf contains the content of EntPhysicalAlias when entPhysClass has a value of chassis(3)";
            }
            enum interface-alias {
                value 2;
                description "The IfAlias field from the Interfaces Group MIB";
            }
            enum port-component {
                value 3;
                description "The EntPhysicalAlias from the Interfaces Group MIB when entPhysClass has a value of port(10) or backplane(4)";
            }
            enum mac-address-type {
                value 4;
                description "An IEEE 802-2001 Ethernet MAC Addressd";
            }
            enum network-address {
                value 5;
                description "network-address is an octet string that identifies a particular network address family and an associated network address that are encoded in network octet order";
            }
            enum interface-name {
                value 6;
                description "ifName";
            }
            enum local {
                value 7;
                description "A locally assigned alpha-numeric string.";
            }
        }
        description "";
        reference "";
    }

    typedef  CML_DM_MEASUREMENTTYPE_T {
        type enumeration {
            enum dmm {
                value 1;
                description "DMM SOAM PDU generated. DMR responses received.";
            }
            enum dm1-transmitted {
                value 2;
                description "1DM SOAM PDU generated.";
            }
            enum dm1-received {
                value 3;
                description "1DM SOAM PDU received and tracked.";
            }
        }
        description "";
        reference "";
    }

    typedef  CML_CFM_DM_INTERVAL_T {
        type enumeration {
            enum 1s {
                value 4;
                description "DM PDU Interval 1 second";
            }
            enum 10s {
                value 5;
                description "DM PDU Interval 10 second";
            }
        }
        description "";
        reference "";
    }

    typedef  CML_DM_DATAPATTERN_T {
        type enumeration {
            enum zeroes {
                value 1;
                description "Indicates the Data TLV contains all zeros.";
            }
            enum ones {
                value 2;
                description "Indicates the Data TLV contains all ones.";
            }
        }
        description "";
        reference "";
    }

    typedef  CML_DM_MEASUREMENTBINTYPE_T {
        type enumeration {
            enum frame-delay {
                value 1;
                description "Indicates a measurement bin for two-way Frame Delay.";
            }
            enum inter-frame-delay-variation {
                value 4;
                description "Indicates a measurement bin for two-way Inter-frame Delay Variation.";
            }
        }
        description "";
        reference "";
    }

    typedef  CML_CFM_DEBUG_T {
        type bits {
            bit events {
                position 0;
                description "Enable event debugs";
            }
            bit rx {
                position 1;
                description "Enable rx debugs";
            }
            bit tx {
                position 2;
                description "Enable tx debugs";
            }
            bit loopback {
                position 3;
                description "Enable loopback debugs";
            }
            bit traceroute {
                position 4;
                description "Enable traceroute debugs";
            }
        }
        description "";
        reference "";
    }

    grouping configurationErrorList-grouping {
    description
        "The Configuration Error List managed object provides a list of Bridge Ports, aggregated ports, and VIDs that are incorrectly configured";
        list configurationErrorList {
            key "vlanIdentifier";
            config false;
            description
                "The Configuration Error List managed object provides a list of Bridge Ports, aggregated ports, and VIDs that are incorrectly configured";
            leaf vlanIdentifier  {
                type  cml_data_types:CML_UINT16_T;
                description "A VLAN identifier specifying which VLAN to check for Bridge Ports or aggregated ports in error";
            } // END of vlanIdentifier definition.


            leaf ifName  {
                type  cml_data_types:CML_STRING_T {
                    length "0..255";
                }
                description "An interface, either a Bridge Port or an aggregated IEEE 802.3 port within a Bridge Port. The value is expected to uniquely identify a single interface on the system. The structure of the identifier is implementation specific";
            } // END of ifName definition.


            leaf errorConditions  {
                type  CML_CFM_ERR_CONDITION_T;
                description "A list of possible errors on a Bridge Port";
            } // END of errorConditions definition.


        } // End of configurationErrorList-list
    } // END of configurationErrorList-grouping definition.


    grouping maintenanceDomain-grouping {
    description
        "A Maintenance Domain managed object is required in order to create an MA with a MAID that includes that Maintenance Domains Name. From this Maintenance  Domain managed object, all Maintenance Association managed objects associated with that Maintenance Domain managed object can be accessed, and thus controlled.";
        list maintenanceDomain {
            key "mdName";
            description
                "A Maintenance Domain managed object is required in order to create an MA with a MAID that includes that Maintenance Domains Name. From this Maintenance  Domain managed object, all Maintenance Association managed objects associated with that Maintenance Domain managed object can be accessed, and thus controlled.";
            leaf mdName  {
                type  cml_data_types:CML_STRING_T {
                    length "0..255";
                }
                description "A unique identifier of a Maintenance Domain";
            } // END of mdName definition.



            list maintenanceAssociation {
                key "maName";
                description
                    "This list represents Maintenance Entity Groups (Y.1731) or Maintenance Associations (802.1ag). MEGs/MAs are sets of MEPs, each configured to the same service inside a common OAM domain.";
                leaf maName  {
                    type  cml_data_types:CML_STRING_T {
                        length "0..6";
                    }
                    description "The value union for the Maintenance Association Name. The type must correspond to the configuration name-type according to the";
                } // END of maName definition.



                list maintenanceAssociationEndPoint {
                    key "mepIdentifier";
                    description
                        "The list of Maintenance association End Points in a specific Maintance Association.";
                    leaf mepIdentifier  {
                        type  cml_data_types:CML_UINT16_T;
                        description "Integer that is unique among all the MEPs in the same MA. Other definition is: a small integer, unique over a given Maintenance Association, identifying a specific Maintenance association End Point";
                    } // END of mepIdentifier definition.


                    uses maintenanceAssociationEndPoint-Grouping;
                } // End of maintenanceAssociationEndPoint-list
                uses maintenanceAssociation-Grouping;
            } // End of maintenanceAssociation-list
            uses maintenanceDomain-Grouping;
        } // End of maintenanceDomain-list
    } // END of maintenanceDomain-grouping definition.


    grouping cfmOverMplsService-grouping {
    description
        "A Maintenance Domain for mpls";
        list cfmOverMplsService {
            if-feature feature_list:HAVE_MPLS_VC;
            key "bridgeType";
            description
                "A Maintenance Domain for mpls";
            leaf bridgeType  {
                type  cml_data_types:CFM_BRIDGE_TYPE;
                description "";
            } // END of bridgeType definition.


            leaf tracerouteCacheEnable  {
                type  cml_data_types:CML_BOOL_T;
                default false;
                description "";
            } // END of tracerouteCacheEnable definition.


            leaf tracerouteCacheSize  {
                type  cml_data_types:CML_UINT32_T;
                default "100";
                description "";
            } // END of tracerouteCacheSize definition.



            list mplsMaintenanceDomain {
                if-feature feature_list:HAVE_MPLS_VC;
                key "mdName";
                description
                    "A Maintenance Domain managed object is required in order to create an MA with a MAID that includes that Maintenance Domains Name. From this Maintenance  Domain managed object, all Maintenance Association managed objects associated with that Maintenance Domain managed object can be accessed, and thus controlled.";
                leaf mdName  {
                    type  cml_data_types:CML_STRING_T {
                        length "0..255";
                    }
                    description "A unique identifier of a Maintenance Domain";
                } // END of mdName definition.



                list maintenanceAssociation {
                    if-feature feature_list:HAVE_MPLS_VC;
                    key "maName";
                    description
                        "This list represents Maintenance Entity Groups (Y.1731) or Maintenance Associations (802.1ag). MEGs/MAs are sets of MEPs, each configured to the same service inside a common OAM domain.";
                    leaf maName  {
                        type  cml_data_types:CML_STRING_T {
                            length "0..6";
                        }
                        description "The value union for the Maintenance Association Name. The type must correspond to the configuration name-type according to the";
                    } // END of maName definition.



                    list maintenanceAssociationEndPoint {
                        if-feature feature_list:HAVE_MPLS_VC;
                        key "mepIdentifier";
                        description
                            "The list of Maintenance association End Points in a specific Maintance Association.";
                        leaf mepIdentifier  {
                            type  cml_data_types:CML_UINT16_T;
                            description "Integer that is unique among all the MEPs in the same MA. Other definition is: a small integer, unique over a given Maintenance Association, identifying a specific Maintenance association End Point";
                        } // END of mepIdentifier definition.


                        leaf vcName  {
                            type  cml_data_types:CML_STRING_T {
                                length "0..255";
                            }
                            description "Virtual Circuit";
                        } // END of vcName definition.


                        uses maintenanceAssociationEndPoint-Grouping;
                    } // End of maintenanceAssociationEndPoint-list
                    uses maintenanceAssociation-Grouping;
                } // End of maintenanceAssociation-list
                uses maintenanceDomain-Grouping;
            } // End of mplsMaintenanceDomain-list
        } // End of cfmOverMplsService-list
    } // END of cfmOverMplsService-grouping definition.


    grouping profile-information-grouping {
    description
        "The ID of a Maintenance Domain of the MEP";
        list profile-information {
            if-feature feature_list:Y1731_HW_OFFLOAD;
            key "lmProfileName";
            description
                "The ID of a Maintenance Domain of the MEP";
            leaf lmProfileName  {
                type  cml_data_types:CML_STRING_T {
                    length "0..64";
                }
                description "";
            } // END of lmProfileName definition.


            leaf measurementType  {
                type  CML_MEASUREMENTTYPE_T;
                default "slm";
                description "";
            } // END of measurementType definition.


            leaf measurementInterval  {
                type  cml_data_types:CML_UINT32_T {
                     range "1..525600";
                }
                default "15";
                units "minutes";
                description "";
            } // END of measurementInterval definition.


            leaf messagePeriod  {
                type  CML_CFM_CCM_INTERVAL_T;
                default "4";
                description "";
            } // END of messagePeriod definition.


            leaf intervalsStored  {
                type  cml_data_types:CML_UINT32_T {
                     range "2..1000";
                }
                default "32";
                description "";
            } // END of intervalsStored definition.


        } // End of profile-information-list
    } // END of profile-information-grouping definition.


    grouping dmProfileInformation-grouping {
    description
        "DM Profile Information created for a MEP";
        list dmProfileInformation {
            if-feature feature_list:Y1731_HW_OFFLOAD;
            key "dmProfileName";
            description
                "DM Profile Information created for a MEP";
            leaf dmProfileName  {
                type  cml_data_types:CML_STRING_T {
                    length "0..64";
                }
                description "This attribute contains the profile name for the SOAM DM Session";
            } // END of dmProfileName definition.


            uses delayMeasurementConfigurationGroup;
        } // End of dmProfileInformation-list
    } // END of dmProfileInformation-grouping definition.
    grouping lossMeasurementStatsGroup {
        description
            "This grouping includes statistics objects for a SOAM Loss Measurement session.";
        leaf forwardTransmittedFrames  {
            type  cml_data_types:CML_GAUGE32_T;
            config false;
            description "This object contains the number of frames transmitted in the forward direction by this MEP. For a PM Session of types lmm or ccm this includes Ethernet Service Frames and SOAM PDUs that are in a higher MEG level only. For a PM Session of type slm this includes the count of SOAM ETH-SLM frames only.";
        } // END of forwardTransmittedFrames definition.


        leaf forwardReceivedFrames  {
            type  cml_data_types:CML_GAUGE32_T;
            config false;
            description "This object contains the number of frames received in the forward  direction by this MEP. For a PM Session of types lmm or ccm this includes Ethernet ervice Frames and SOAM PDUs that are in a higher MEG level only.For a PM Session of type slm this includes the count of SOAM  ETH-SLM frames only.";
        } // END of forwardReceivedFrames definition.


        leaf forwardFrameLossRatio  {
            type  cml_data_types:CML_FLOAT_PRECISION_4_T;
            config false;
            units "milli-percent";
            description "This object contains the frame loss ratio in the forward direction calculated by this MEP for this Measurement Interval. The FLR value is a ratio that is expressed as a  percent with a value of 0 through 100000.";
        } // END of forwardFrameLossRatio definition.


        leaf forwardAccumulatedLoss  {
            type  cml_data_types:CML_UINT32_T {
                 range "0..100000";
            }
            config false;
            units "milli-percent";
            description "";
        } // END of forwardAccumulatedLoss definition.


        leaf backwardTransmittedFrames  {
            type  cml_data_types:CML_GAUGE32_T;
            config false;
            description "This object contains the number of frames transmitted in the backward direction by this MEP. For a PM Session of type lmm or ccm this includes Ethernet ervice Frames and SOAM PDUs that are in a higher MEG level only. For a PM Session of type slm this in cludes the count of SOAM ETH-SLM frames only.";
        } // END of backwardTransmittedFrames definition.


        leaf backwardReceivedFrames  {
            type  cml_data_types:CML_GAUGE32_T;
            config false;
            description "This object contains the number of frames received in the backward direction by this MEP. For a PM Session of type lmm this includes Ethernet Service          Frames and SOAM PDUs that are in a higher MEG level only.For a PM Session of type slm this includes the count of SOAM ETH-SLM frames only.";
        } // END of backwardReceivedFrames definition.


        leaf backwardFrameLossRatio  {
            type  cml_data_types:CML_FLOAT_PRECISION_4_T;
            config false;
            units "milli-percent";
            description "This object contains the frame loss ratio in the  backward direction calculated by this MEP for this Measurement Interval. The FLR value is a ratio that is expressed as a percent with a value of 0 (ratio 0.00) through 100000 (ratio 1.00)";
        } // END of backwardFrameLossRatio definition.


        leaf backwardAccumulatedLoss  {
            type  cml_data_types:CML_UINT32_T {
                 range "0..100000";
            }
            config false;
            units "milli-percent";
            description "";
        } // END of backwardAccumulatedLoss definition.


    } // END of lossMeasurementStatsGroup definition.
    grouping loss-measurement-configuration-group {
        description
            "This grouping includes configuration objects for the Frame Loss     Measurement function defined in [Y.1731] and [MEF SOAM PM IA].";
        leaf measurementType  {
            type  CML_MEASUREMENTTYPE_T;
            default "slm";
            description "";
        } // END of measurementType definition.


        leaf measurementInterval  {
            type  cml_data_types:CML_UINT32_T {
                 range "1..525600";
            }
            default "15";
            units "minutes";
            description "";
        } // END of measurementInterval definition.


        leaf messagePeriod  {
            type  CML_CFM_CCM_INTERVAL_T;
            default "4";
            description "";
        } // END of messagePeriod definition.


        leaf intervalsStored  {
            type  cml_data_types:CML_UINT32_T {
                 range "2..1000";
            }
            default "32";
            description "";
        } // END of intervalsStored definition.


    } // END of loss-measurement-configuration-group definition.
    grouping delayMeasurementStatsGroup {
        description
            "This grouping includes statistics objects for a SOAM Delay Measurement session.";
        leaf dmSuspectStatus  {
            type  cml_data_types:CML_BOOL_T;
            config false;
            description "The object is to be set to false at the start of a measurement interval. It is set to true when there is a discontinuity in the performance measurements during the Measurement Interval.";
        } // END of dmSuspectStatus definition.


        leaf frameDelayTwoWayMin  {
            type  cml_data_types:CML_GAUGE32_T;
            config false;
            units "microseconds";
            description "This object contains the minimum two-way frame delay calculated by this MEP for this Measurement Interval";
        } // END of frameDelayTwoWayMin definition.


        leaf frameDelayTwoWayMax  {
            type  cml_data_types:CML_GAUGE32_T;
            config false;
            units "microseconds";
            description "This object contains the minimum two-way frame delay calculated by this MEP for this Measurement Interval";
        } // END of frameDelayTwoWayMax definition.


        leaf frameDelayTwoWayAverage  {
            type  cml_data_types:CML_GAUGE32_T;
            config false;
            units "microseconds";
            description "This object contains the average two-way frame delay calculated by this MEP for this Measurement Interval";
        } // END of frameDelayTwoWayAverage definition.


        leaf interFrameDelayVariationTwoWayMin  {
            type  cml_data_types:CML_GAUGE32_T;
            config false;
            units "microseconds";
            description "This object contains the minimum two-way inter-frame delay interval calculated by this MEP for this Measurement Interval";
        } // END of interFrameDelayVariationTwoWayMin definition.


        leaf interFrameDelayVariationTwoWayMax  {
            type  cml_data_types:CML_GAUGE32_T;
            config false;
            units "microseconds";
            description "This object contains the maximum two-way inter-frame delay interval calculated by this MEP for this Measurement Interval";
        } // END of interFrameDelayVariationTwoWayMax definition.


        leaf interFrameDelayVariationTwoWayAverage  {
            type  cml_data_types:CML_GAUGE32_T;
            config false;
            units "microseconds";
            description "This object contains the average two-way inter-frame delay interval calculated by this MEP for this Measurement Interval";
        } // END of interFrameDelayVariationTwoWayAverage definition.


    } // END of delayMeasurementStatsGroup definition.
    grouping delayMeasurementBinsContentGroup {
        description
            "This grouping contains result management objects for a SOAM Delay Measurement session.";
        leaf binNumber  {
            type  cml_data_types:CML_UINT32_T {
                 range "2..10";
            }
            description "This object specifies the bin number for the configured boundary";
        } // END of binNumber definition.


        leaf lowerBoundThreshold  {
            type  cml_data_types:CML_UINT32_T {
                 range "1..2147483647";
            }
            mandatory true;
            units "microseconds";
            description "This object specifies the lower boundary for a measurement bin. The measurementboundary for each measurement bin is to be larger than the measurement boundary of the preceding measurement bin";
        } // END of lowerBoundThreshold definition.


    } // END of delayMeasurementBinsContentGroup definition.
    grouping delayMeasurementConfigurationGroup {
        description
            "This grouping includes configuration objects for the Delay Measurement function defined in [Y.1731] and [MEF SOAM PM IA].";
        leaf measurementType  {
            type  CML_DM_MEASUREMENTTYPE_T;
            default "dmm";
            description "";
        } // END of measurementType definition.


        leaf measurementInterval  {
            type  cml_data_types:CML_UINT32_T {
                 range "1..1440";
            }
            default "15";
            units "minutes";
            description "";
        } // END of measurementInterval definition.


        leaf messagePeriod  {
            type  CML_CFM_DM_INTERVAL_T;
            default "1s";
            description "";
        } // END of messagePeriod definition.


        leaf numberIntervalsStored  {
            type  cml_data_types:CML_UINT32_T {
                 range "2..1000";
            }
            default "32";
            description "";
        } // END of numberIntervalsStored definition.


        leaf binsPerFdInterval  {
            type  cml_data_types:CML_UINT32_T {
                 range "2..10";
            }
            default "3";
            description "";
        } // END of binsPerFdInterval definition.


        leaf binsPerIfdvInterval  {
            type  cml_data_types:CML_UINT32_T {
                 range "2..10";
            }
            default "2";
            description "";
        } // END of binsPerIfdvInterval definition.


        leaf priority  {
            type  cml_data_types:CML_UINT32_T {
                 range "0..7";
            }
            default "2";
            description "";
        } // END of priority definition.


        leaf frameSize  {
            type  cml_data_types:CML_UINT32_T {
                 range "64..9600";
            }
            default "64";
            description "";
        } // END of frameSize definition.


        leaf dataPattern  {
            type  CML_DM_DATAPATTERN_T;
            default "zeroes";
            description "";
        } // END of dataPattern definition.



        list binThreshold {
            if-feature feature_list:Y1731_HW_OFFLOAD;
            key "measurementBinType";
            description
                "This list contains the measurement bin objects for a SOAM Delay Measurement session.";
            leaf measurementBinType  {
                type  CML_DM_MEASUREMENTBINTYPE_T;
                description "This object specifies whether the bin number is for Frame Delay, Inter-Frame Delay Variation or Frame Delay Range";
            } // END of measurementBinType definition.



            list binContent {
                description
                    "This list contains the Delay Measurement bin threshold configuration values for DM Performance Monitoring.";
                uses delayMeasurementBinsContentGroup;
            } // End of binContent-list
        } // End of binThreshold-list
    } // END of delayMeasurementConfigurationGroup definition.
    grouping defaultMdLevel-grouping {
        description
            "defaultMdLevelCMLSEPgrouping";
        leaf defMdLevel  {
            type  cml_data_types:CML_INT32_T {
                 range "0..7";
            }
            description "The MD Level at which MHFs are to be created";
        } // END of defMdLevel definition.


        leaf mhfCreation  {
            type  CML_CFM_MIP_T;
            description "This parameter indicates whether the management entity can create MHFs for this VID(s)";
        } // END of mhfCreation definition.


        leaf defaultIdPermission  {
            type  CML_CFM_ID_PERMISSION_T;
            config false;
            description "This parameter indicates what, if anything, is to be included in the Sender ID TLV transmitted by MPs configured in a default MD Level";
        } // END of defaultIdPermission definition.



        list defaultMdLevel {
            key "primaryVid";
            description
                "Data definitions related to the default MD level associated with specific VIDs";
            leaf primaryVid  {
                type  cml_data_types:CML_UINT16_T;
                description "The primary VID on the MD";
            } // END of primaryVid definition.


            leaf-list vid  {
                type  cml_data_types:CML_UINT16_T;
                config false;
                description "The primary VID on the MD";
            } // END of vid definition.


            leaf status  {
                type  cml_data_types:CML_BOOL_T;
                config false;
                description "State of this list entry. The value 'true' if there is no entry in the maintenance-assoication list entry defining an MA for the  same VLAN ID and MD Level as this table's entry, and on which MA an Up MEP is defined, else 'false'";
            } // END of status definition.


            leaf mdLevel  {
                type  cml_data_types:CML_INT32_T {
                     range "0..7";
                }
                description "The MD Level at which MHFs are to be created";
            } // END of mdLevel definition.


            leaf mhfCreation  {
                type  CML_CFM_MIP_T;
                description "This parameter indicates whether the management entity can create MHFs for this VID(s)";
            } // END of mhfCreation definition.


            leaf defaultIdPermission  {
                type  CML_CFM_ID_PERMISSION_T;
                config false;
                description "This parameter indicates what, if anything, is to be included in the Sender ID TLV transmitted by MPs configured in a default MD Level";
            } // END of defaultIdPermission definition.


        } // End of defaultMdLevel-list
    } // END of defaultMdLevel-grouping definition.
    grouping maintenanceDomain-Grouping {
        description
            "maintenanceDomainCMLSEPGrouping";
        leaf nameType  {
            type  CML_CFM_MD_TYPE_T;
            description "Type discriminator for the value union described in the 'name' leaf";
        } // END of nameType definition.


        leaf mdLevel  {
            type  cml_data_types:CML_INT32_T {
                 range "0..7";
            }
            mandatory true;
            description "Integer identifying the Maintenance Domain Level (MD Level)";
        } // END of mdLevel definition.


        leaf mhfCreation  {
            type  CML_CFM_MIP_T;
            mandatory true;
            description "This parameter indicates whether the management entity can create MHFs for this VID(s)";
        } // END of mhfCreation definition.


        leaf idPermission  {
            type  CML_CFM_ID_PERMISSION_T;
            config false;
            description "This parameter indicates what, if anything, is to be included in the Sender ID TLV transmitted by MPs configured in a default MD Level";
        } // END of idPermission definition.


    } // END of maintenanceDomain-Grouping definition.
    grouping maintenanceAssociation-Grouping {
        description
            "maintenanceAssociationCMLSEPGrouping";
        leaf nameType  {
            type  CML_CFM_MA_TYPE_T;
            description "Name type discriminator for the 'name' leaf";
        } // END of nameType definition.


        leaf vid  {
            type  cml_data_types:CML_UINT16_T;
            mandatory true;
            description "The VID(s) monitored by this MA, or 0, if the MA is not attached to any VID. The first VID returned is the MA's Primary VID";
        } // END of vid definition.


        leaf mhfCreation  {
            type  CML_CFM_MA_MIP_T;
            mandatory true;
            description "This parameter indicates whether the management entity can create MHFs for this VID(s)";
        } // END of mhfCreation definition.


        leaf idPermission  {
            type  CML_CFM_ID_PERMISSION_T;
            config false;
            description "This parameter indicates what, if anything, is to be included in the Sender ID TLV transmitted by MPs configured in a default MD Level";
        } // END of idPermission definition.


        leaf ccmInterval  {
            type  CML_CFM_CCM_INTERVAL_T;
            description "The interval between CCM transmissions to be used by all MEPs in the MA";
        } // END of ccmInterval definition.


        leaf rmepAutoDiscovery  {
            type  CFM_AUTO_RMEP_T;
            default "disable";
            description "Enable the MEP to accept continuity check messages from all remote MEP";
        } // END of rmepAutoDiscovery definition.



        list remoteMeps {
            key "rmepId";
            description
                "The list of remote MEPs in the MEP CCM database";
            leaf rmepId  {
                type  cml_data_types:CML_UINT16_T;
                description "A list of the MEPIDs of the MEPs in the MA";
            } // END of rmepId definition.


            leaf macAddress  {
                type  cml_data_types:CML_STRING_T {
                    length "0..255";
                }
                config false;
                description "The MAC address of the MEP";
            } // END of macAddress definition.


        } // End of remoteMeps-list
    } // END of maintenanceAssociation-Grouping definition.
    grouping maintenanceAssociationEndPoint-Grouping {
        description
            "maintenanceAssociationEndPointCMLSEPGrouping";
        leaf ifName  {
            type  cml_data_types:CML_STRING_T {
                length "0..255";
            }
            mandatory true;
            description "An interface, either a Bridge Port or an aggregated IEEE 802.3 port within a Bridge Port, to which the MEP is attached. Each interface in the system is uniquely identified by an interface-name. The structure and content of the name is outside the scope of this specification";
        } // END of ifName definition.


        leaf direction  {
            type  CML_CFM_MEP_DIR_T;
            mandatory true;
            description "A value indicating the direction in which the MEP faces on the interface";
        } // END of direction definition.


        leaf localVid  {
            type  cml_data_types:CML_UINT16_T;
            default "0";
            description " Local vid on which MEP will send frames.This can be one of the MA's vids, for frame tx this vid will be used";
        } // END of localVid definition.


        leaf administrativeState  {
            type  CML_CFM_MEP_STATE_T;
            description "The administrative state of the MEP";
        } // END of administrativeState definition.


        leaf isSlmResponder  {
            if-feature feature_list:Y1731_HW_OFFLOAD;
            type  CML_MEASUREMENTTYPE_REPLY_T;
            default "slm";
            description "Enable the MEP to respond for each Loss Message";
        } // END of isSlmResponder definition.


        leaf isDmResponder  {
            if-feature feature_list:Y1731_HW_OFFLOAD;
            type  cml_data_types:CML_BOOL_T;
            default false;
            description "Enable the MEP to respond DMRs for each DMMs of the peer";
        } // END of isDmResponder definition.


        leaf macAddress  {
            type  cml_data_types:CML_UINT16_T;
            config false;
            description "The MAC address of the MEP";
        } // END of macAddress definition.


        leaf ccmLtmPriority  {
            type  cml_data_types:CML_UINT16_T;
            description "The priority parameter for CCMs and LTMs transmitted by the MEP";
        } // END of ccmLtmPriority definition.


        leaf uniMep  {
            type  CML_CFM_MEP_UNI_T;
            description "Flag to indicate mep as uni-meg and which is used intimate CFM uni meg status to NSM for uni type";
        } // END of uniMep definition.



        list remoteMep {
            if-feature feature_list:CCM_HW_OFFLOAD;
            key "rmepId";
            config false;
            description
                "The list of remote MEPs in the MEP CCM database";
            leaf rmepId  {
                type  cml_data_types:CML_UINT32_T;
                description "The MEPID of a remote MEP";
            } // END of rmepId definition.


            leaf rmepState  {
                type  cml_data_types:CML_UINT8_T;
                description "An enumerated value indicating the operational state of the Remote MEP state machine for this remote MEP.";
            } // END of rmepState definition.


            leaf stateChgTime  {
                type  cml_data_types:CML_TIMESTAMP_T;
                description "The time (SysUpTime, IETF RFC 3418) at which the Remote MEP state machine last entered either the RMEP_FAILED or RMEP_OK.";
            } // END of stateChgTime definition.


            leaf rmepMac  {
                type  cml_data_types:CML_STRING_T {
                    length "0..255";
                }
                description "The MAC address of the remote MEP.";
            } // END of rmepMac definition.


            leaf lastRdi  {
                type  cml_data_types:CML_BOOL_T;
                description "An indication of the state of the RDI bit in the last received CCM";
            } // END of lastRdi definition.


            leaf portStatus  {
                type  CML_PORT_STATUS_T;
                description "The enumerated value from the Interface Status TLV from the last CCM received from the remote MEP.";
            } // END of portStatus definition.


            leaf interfaceStatus  {
                type  CML_INTF_STATUS_T;
                description "The enumerated value from the Port Status TLV from the last CCM received from the remote MEP.";
            } // END of interfaceStatus definition.


            leaf chassisIdSubType  {
                type  CML_CHASSISID_SUBTYPE_T;
                description "The chassis-id-subtype contains the chassis ID entity that is listed in the chassis ID field. This is a combination of the 'Chassis ID Subtype' and 'chsssis ID' fields";
            } // END of chassisIdSubType definition.


            leaf chassisId  {
                type  cml_data_types:CML_STRING_T {
                    length "0..255";
                }
                description "The chassis ID";
            } // END of chassisId definition.


            leaf mgmtAddrDomain  {
                type  cml_data_types:CML_STRING_T {
                    length "0..255";
                }
                description "";
            } // END of mgmtAddrDomain definition.


            leaf mgmtAddr  {
                type  cml_data_types:CML_STRING_T {
                    length "0..255";
                }
                description "Data definitions related to the management address fields defined in a Sender ID TLV";
            } // END of mgmtAddr definition.


        } // End of remoteMep-list
        container continuityCheck {
            description
                "Data definitions related to the Continuity Check function.";
            leaf cciEnabled  {
                type  CFM_MEP_CC_T;
                default "disable";
                description "An indicator of whether the MEP is or is not to generate CCMs";
            } // END of cciEnabled definition.


            leaf fngState  {
                type  CML_MEP_FNG_STATE_T;
                config false;
                description "A value indicating the current state of the MEP Fault Notification Generator state machine";
            } // END of fngState definition.


            leaf lowestFaultPriorityDefect  {
                type  CML_MEP_LOW_DEFECTS_T;
                default "defMACstatus";
                description "The lowest priority defect that is allowed to generate a Fault Alarm. The non-existence of this leaf means that no defects are to be reported";
            } // END of lowestFaultPriorityDefect definition.


            leaf highestPriorityDefectFound  {
                type  CML_MEP_DEFECTS_T;
                config false;
                description "Value indicating the highest-priority defect that has been present since the MEP Fault Notification Generator state machine           was last in the FNG_RESET state The non-existence of this leaf represents that no defect has been present since the last FNG_RESET state";
            } // END of highestPriorityDefectFound definition.


            leaf fngAlarmTime  {
                type  cml_data_types:CML_STRING_T {
                    length "0..255";
                }
                default "250";
                description "The time that defects must be present before a Fault Alarm is issued";
            } // END of fngAlarmTime definition.


            leaf fngResetTime  {
                type  cml_data_types:CML_STRING_T {
                    length "0..255";
                }
                default "1000";
                description "The time that defects must be absent before resetting a Fault AlarmThe time that defects must be absent before resetting a Fault Alarm";
            } // END of fngResetTime definition.


            leaf activeDefects  {
                type  CML_MEP_DEFECTS_BIT_T;
                config false;
                description "A bit field of potential active defects. The values are the same as the content of the fault-alarm-defect-type";
            } // END of activeDefects definition.


            leaf lastErrorCcm  {
                type  cml_data_types:CML_STRING_T {
                    length "0..255";
                }
                config false;
                description "The last-received CCM that triggered an invalid-ccm fault";
            } // END of lastErrorCcm definition.


            leaf lastCrossConnectCcm  {
                type  cml_data_types:CML_STRING_T {
                    length "0..255";
                }
                config false;
                description "The last-received CCM that triggered a cross-connect-ccm fault";
            } // END of lastCrossConnectCcm definition.


            leaf ccmSequenceErrorCount  {
                type  cml_data_types:CML_UINT32_T;
                config false;
                description "The total number of out-of-sequence CCMs received from all remote MEPs";
            } // END of ccmSequenceErrorCount definition.


            leaf sentCcms  {
                type  cml_data_types:CML_UINT32_T;
                config false;
                description "The total number of CCMs transmitted";
            } // END of sentCcms definition.


        } // END of continuityCheck-container definition.
        container alarmIndicationSignal {
            description
                "alarm indication signal";
            leaf aisEnabled  {
                type  CML_CFM_MEP_AIS_T;
                default "disable";
                description "status of signal";
            } // END of aisEnabled definition.


            leaf mdLevel  {
                type  cml_data_types:CML_INT32_T {
                     range "0..7";
                }
                description "The MD Level at which MHFs are to be created";
            } // END of mdLevel definition.


            leaf aisInterval  {
                type  CML_CFM_AIS_INTERVAL_T;
                default "one-second";
                description "alarm indication signal interval";
            } // END of aisInterval definition.


        } // END of alarmIndicationSignal-container definition.
        container loopback {
            config false;
            description
                "Data definitions related to the Loopback function";
            leaf repliesReceived  {
                type  cml_data_types:CML_UINT32_T;
                description "The total number of valid, in-order LBRs received.";
            } // END of repliesReceived definition.


            leaf repliesTransmitted  {
                type  cml_data_types:CML_UINT32_T;
                description "The total number of LBRs transmitted";
            } // END of repliesTransmitted definition.


            leaf outOfOrderRepliesReceived  {
                type  cml_data_types:CML_UINT32_T;
                description "The total number of valid, out-of-order LBRs received";
            } // END of outOfOrderRepliesReceived definition.


            leaf badMsu  {
                type  cml_data_types:CML_UINT32_T;
                description "The total number of LBRs received whose mac_service_data_unit did not match (except for the OpCode) that of the corresponding LBM";
            } // END of badMsu definition.


        } // END of loopback-container definition.
        container linktrace {
            config false;
            description
                "Data definitions related to the Linktrace function";
            leaf unexpectedRepliesReceived  {
                type  cml_data_types:CML_UINT32_T;
                description "The total number of unexpected LTRs received.";
            } // END of unexpectedRepliesReceived definition.



            list linktrace {
                key "transactionId";
                config false;
                description
                    "The list of entries in a Linktrace database.";
                leaf transactionId  {
                    type  cml_data_types:CML_UINT32_T;
                    description "The LTM Transaction Identifier to which the LTR entries will be attached";
                } // END of transactionId definition.


                leaf targetMacAddr  {
                    type  cml_data_types:CML_MAC_ADDRESS_T {
                        length "0..255";
                    }
                    description "Target MAC address or MEP ID for the Linktrace session.";
                } // END of targetMacAddr definition.


                leaf ttl  {
                    type  cml_data_types:CML_UINT8_T;
                    default "64";
                    description "An initial value for the LTM TTL field reference";
                } // END of ttl definition.



                list reply {
                    key "index";
                    config false;
                    description
                        "The list of LTRs associated with a specific Linktrace transaction.";
                    leaf index  {
                        type  cml_data_types:CML_UINT32_T;
                        description "An index to distinguish among multiple LTRs with the same LTR transaction-id field value";
                    } // END of index definition.


                    leaf replyTtl  {
                        type  cml_data_types:CML_UINT32_T;
                        default "64";
                        description "An initial value for the LTM TTL field reference";
                    } // END of replyTtl definition.


                    leaf relayAction  {
                        type  CML_CFM_RELAY_ACTION_T;
                        description "An initial value for the LTM TTL field reference";
                    } // END of relayAction definition.


                    leaf chassisIdSubType  {
                        type  CML_CHASSISID_SUBTYPE_T;
                        description "The chassis-id-subtype contains the chassis ID entity that is listed in the chassis ID field. This is a combination of the 'Chassis ID Subtype' and 'chsssis ID' fields";
                    } // END of chassisIdSubType definition.


                    leaf chassisId  {
                        type  cml_data_types:CML_STRING_T {
                            length "0..255";
                        }
                        description "The chassis ID";
                    } // END of chassisId definition.


                    leaf mgmtAddrDomain  {
                        type  cml_data_types:CML_STRING_T {
                            length "0..255";
                        }
                        description "";
                    } // END of mgmtAddrDomain definition.


                    leaf mgmtAddr  {
                        type  cml_data_types:CML_STRING_T {
                            length "0..255";
                        }
                        description "Data definitions related to the management address fields defined in a Sender ID TLV";
                    } // END of mgmtAddr definition.


                    leaf ingressAction  {
                        type  CML_CFM_INGRESS_ACTION_T;
                        description "An enumerated value indicating the value returned in the Ingress Action field. This leaf is not present if no value is returned in the LTR.";
                    } // END of ingressAction definition.


                    leaf ingressMac  {
                        type  cml_data_types:CML_MAC_ADDRESS_T {
                            length "0..255";
                        }
                        description "The MAC address returned in the Ingress MAC Address field.";
                    } // END of ingressMac definition.


                    leaf ingressPortId  {
                        type  cml_data_types:CML_STRING_T {
                            length "0..255";
                        }
                        description "The Ingress Port ID field and the corresponding port ID value.";
                    } // END of ingressPortId definition.


                    leaf ingressPortIdSubtype  {
                        type  CML_CFM_PORTID_SUBTYPE_T;
                        description "Data definitions associated with the Port ID TLV";
                    } // END of ingressPortIdSubtype definition.


                    leaf egressAction  {
                        type  CML_CFM_EGRESS_ACTION_T;
                        description "An enumerated value indicating the value returned in the Egress Action field. This leaf is not present if no value is returned in the LTR";
                    } // END of egressAction definition.


                    leaf egressMac  {
                        type  cml_data_types:CML_MAC_ADDRESS_T {
                            length "0..255";
                        }
                        description "The MAC address returned in the Ingress MAC Address field.";
                    } // END of egressMac definition.


                    leaf egressPortId  {
                        type  cml_data_types:CML_STRING_T {
                            length "0..255";
                        }
                        description "The egress Port ID field and the corresponding port ID value.";
                    } // END of egressPortId definition.


                    leaf egressPortIdSubtype  {
                        type  CML_CFM_PORTID_SUBTYPE_T;
                        description "Data definitions associated with the Port ID TLV";
                    } // END of egressPortIdSubtype definition.


                } // End of reply-list
            } // End of linktrace-list
        } // END of linktrace-container definition.
        container delayMeasurements {
            if-feature feature_list:Y1731_HW_OFFLOAD;
            config false;
            description
                "This container contains a collection of data definitions related to Delay Measurements.";
            leaf sessionId  {
                type  cml_data_types:CML_STRING_T {
                    length "0..255";
                }
                description "This object uniquely identifies a scheduled measurement. It is automatically generated by the server on creation of a new measurement";
            } // END of sessionId definition.


            leaf sessionStatus  {
                type  CML_SESSION_STATUS_T;
                description "This object indicates the current status of the DM session";
            } // END of sessionStatus definition.


            leaf frameDelayTwoWay  {
                type  cml_data_types:CML_GAUGE32_T;
                units "microseconds";
                description "This object contains the two-way frame delay calculated by this MEP from the last received SOAM PDU";
            } // END of frameDelayTwoWay definition.


            leaf interframeDelayVariationTwoWay  {
                type  cml_data_types:CML_GAUGE32_T;
                units "microseconds";
                description "This object contains the last two-way inter-frame delay interval calculated by this MEP";
            } // END of interframeDelayVariationTwoWay definition.



            list delayHistoryStats {
                if-feature feature_list:Y1731_HW_OFFLOAD;
                key "historyId";
                config false;
                description
                    "This list contains the results for history Measurement Intervals in a SOAM Delay Measurement session.";
                leaf historyId  {
                    type  cml_data_types:CML_UINT32_T;
                    description "The identifier for the Measurement Interval within this DM session";
                } // END of historyId definition.


                leaf endTime  {
                    type  cml_data_types:CML_DATE_TIME_T {
                        length "0..255";
                    }
                    description "The time that the Measurement Interval ended";
                } // END of endTime definition.


                leaf elapsedTime  {
                    type  cml_data_types:CML_UINT32_T;
                    description "The length of time that the Measurement Interval ran for, in 0.01 seconds";
                } // END of elapsedTime definition.



                list binThreshold {
                    if-feature feature_list:Y1731_HW_OFFLOAD;
                    key "measurementBinType";
                    config false;
                    description
                        "This list contains the measurement bin objects for a SOAM Delay Measurement session.";
                    leaf measurementBinType  {
                        type  CML_DM_MEASUREMENTBINTYPE_T;
                        description "This object specifies whether the bin number is for Frame Delay or Inter-Frame Delay Variation or Frame Delay Range";
                    } // END of measurementBinType definition.



                    list binContent {
                        config false;
                        description
                            "This list contains the Delay Measurement bin threshold configuration values for DM Performance Monitoring.";
                        leaf binCounter  {
                            type  cml_data_types:CML_GAUGE32_T;
                            description "This object contains the count of the number of completed measurements initiated in this Measurement Interval whose value falls within the range specified for this bin (that is, greater than or equal to the measurement boundary for the bin, and (unless the bin is the last bin) less than the measurement boundary for the following bin";
                        } // END of binCounter definition.


                        uses delayMeasurementBinsContentGroup;
                    } // End of binContent-list
                } // End of binThreshold-list
                uses delayMeasurementStatsGroup;
            } // End of delayHistoryStats-list
            container delayCurrentStats {
                if-feature feature_list:Y1731_HW_OFFLOAD;
                config false;
                description
                    "This container contains the results for the current Measurement Interval in a SOAM Delay Measurement session gathered during the interval indicated by measurement interval.";
                leaf startTime  {
                    type  cml_data_types:CML_DATE_TIME_T {
                        length "0..255";
                    }
                    description "The time that the current Measurement Interval started";
                } // END of startTime definition.


                leaf elapsedTime  {
                    type  cml_data_types:CML_UINT32_T;
                    description "The time that the current Measurement Interval has been running, in 0.01 seconds";
                } // END of elapsedTime definition.



                list binThreshold {
                    if-feature feature_list:Y1731_HW_OFFLOAD;
                    key "measurementBinType";
                    config false;
                    description
                        "This list contains the measurement bin objects for a SOAM Delay Measurement session.";
                    leaf measurementBinType  {
                        type  CML_DM_MEASUREMENTBINTYPE_T;
                        description "This object specifies whether the bin number is for Frame Delay or  Inter-Frame Delay Variation or Frame Delay Range";
                    } // END of measurementBinType definition.



                    list binContent {
                        config false;
                        description
                            "This list contains the Delay Measurement bin threshold configuration values for DM Performance Monitoring.";
                        leaf binCounter  {
                            type  cml_data_types:CML_GAUGE32_T;
                            description "This object contains the count of the number of completed measurements initiated in this Measurement Interval whose value falls within the range specified for this bin (that is, greater than or equal to the measurement boundary for the bin, and (unless the bin is the last bin) less than the measurement boundary for the following bin";
                        } // END of binCounter definition.


                        uses delayMeasurementBinsContentGroup;
                    } // End of binContent-list
                } // End of binThreshold-list
                uses delayMeasurementStatsGroup;
            } // END of delayCurrentStats-container definition.
        } // END of delayMeasurements-container definition.
        container lossMeasurements {
            if-feature feature_list:Y1731_HW_OFFLOAD;
            config false;
            description
                "This container contains a collection of data definitions re-lated to Loss Measurements.";
            leaf sessionId  {
                type  cml_data_types:CML_UINT32_T;
                description "";
            } // END of sessionId definition.


            leaf sessionStatus  {
                type  CML_SESSION_STATUS_T;
                description "";
            } // END of sessionStatus definition.



            list historyMeasurementStats {
                if-feature feature_list:Y1731_HW_OFFLOAD;
                key "historyId";
                config false;
                description
                    "Contain information about first Measurement Interval completes in a LM session";
                leaf historyId  {
                    type  cml_data_types:CML_UINT32_T;
                    description "";
                } // END of historyId definition.


                leaf endTime  {
                    type  cml_data_types:CML_DATE_TIME_T {
                        length "0..255";
                    }
                    description "";
                } // END of endTime definition.


                leaf elapsedTime  {
                    type  cml_data_types:CML_UINT32_T;
                    description "";
                } // END of elapsedTime definition.


                leaf forwardTransmittedFrames  {
                    type  cml_data_types:CML_GAUGE32_T;
                    description "This object contains the number of frames transmitted in the forward direction by this MEP. For a PM Session of types lmm or ccm this includes Ethernet Service Frames and SOAM PDUs that are in a higher MEG level only. For a PM Session of type slm this includes the count of SOAM ETH-SLM frames only.";
                } // END of forwardTransmittedFrames definition.


                leaf forwardReceivedFrames  {
                    type  cml_data_types:CML_GAUGE32_T;
                    description "This object contains the number of frames received in the forward  direction by this MEP. For a PM Session of types lmm or ccm this includes Ethernet ervice Frames and SOAM PDUs that are in a higher MEG level only.For a PM Session of type slm this includes the count of SOAM  ETH-SLM frames only.";
                } // END of forwardReceivedFrames definition.


                leaf forwardFrameLossRatio  {
                    type  cml_data_types:CML_FLOAT_PRECISION_4_T;
                    units "milli-percent";
                    description "This object contains the frame loss ratio in the forward direction calculated by this MEP for this Measurement Interval. The FLR value is a ratio that is expressed as a  percent with a value of 0 through 100000.";
                } // END of forwardFrameLossRatio definition.


                leaf forwardAccumulatedLoss  {
                    type  cml_data_types:CML_UINT32_T {
                         range "0..100000";
                    }
                    units "milli-percent";
                    description "";
                } // END of forwardAccumulatedLoss definition.


                leaf backwardTransmittedFrames  {
                    type  cml_data_types:CML_GAUGE32_T;
                    description "This object contains the number of frames transmitted in the backward direction by this MEP. For a PM Session of type lmm or ccm this includes Ethernet ervice Frames and SOAM PDUs that are in a higher MEG level only. For a PM Session of type slm this in cludes the count of SOAM ETH-SLM frames only.";
                } // END of backwardTransmittedFrames definition.


                leaf backwardReceivedFrames  {
                    type  cml_data_types:CML_GAUGE32_T;
                    description "This object contains the number of frames received in the backward direction by this MEP. For a PM Session of type lmm this includes Ethernet Service          Frames and SOAM PDUs that are in a higher MEG level only.For a PM Session of type slm this includes the count of SOAM ETH-SLM frames only.";
                } // END of backwardReceivedFrames definition.


                leaf backwardFrameLossRatio  {
                    type  cml_data_types:CML_FLOAT_PRECISION_4_T;
                    units "milli-percent";
                    description "This object contains the frame loss ratio in the  backward direction calculated by this MEP for this Measurement Interval. The FLR value is a ratio that is expressed as a percent with a value of 0 (ratio 0.00) through 100000 (ratio 1.00)";
                } // END of backwardFrameLossRatio definition.


                leaf backwardAccumulatedLoss  {
                    type  cml_data_types:CML_UINT32_T {
                         range "0..100000";
                    }
                    units "milli-percent";
                    description "";
                } // END of backwardAccumulatedLoss definition.


            } // End of historyMeasurementStats-list
        } // END of lossMeasurements-container definition.
    } // END of maintenanceAssociationEndPoint-Grouping definition.

    grouping  cfmTraceroute-grouping {
    description
        "cfmTraceroute";
    container cfmTraceroute {
        description
            "cfmTraceroute";
        leaf tracerouteCacheEnable  {
            type  cml_data_types:CML_BOOL_T;
            default false;
            description "";
        } // END of tracerouteCacheEnable definition.


        leaf tracerouteCacheSize  {
            type  cml_data_types:CML_UINT32_T;
            default "100";
            description "";
        } // END of tracerouteCacheSize definition.


    } // END of cfmTraceroute-container definition.
    } // END of cfmTraceroute-container definition.

    grouping  cfmGlobalConfig-grouping {
    description
        "cfmGlobalConfig";
    container cfmGlobalConfig {
        description
            "cfmGlobalConfig";
        leaf cfmDebug  {
            type  CML_CFM_DEBUG_T;
            description "";
        } // END of cfmDebug definition.


    } // END of cfmGlobalConfig-container definition.
    } // END of cfmGlobalConfig-container definition.

    grouping  defaultMdLevels-grouping {
    description
        "Data definitions related to the global default MD level and the default MD levels associated with specific VIDs";
    container defaultMdLevels {
        description
            "Data definitions related to the global default MD level and the default MD levels associated with specific VIDs";
        uses defaultMdLevel-grouping;
    } // END of defaultMdLevels-container definition.
    } // END of defaultMdLevels-container definition.


}
