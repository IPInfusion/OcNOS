/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-hqos.yang
*
*/

submodule zebos-hqos {

    belongs-to  zebos { prefix zebos; }

    import cml_data_types {
        prefix cml_data_types;
    }

    import feature_list {
        prefix feature_list;
    }

    organization
        "IP Infusion Inc.";

    contact
        "Address: 3965 Freedom Circle, Suite 200, Santa Clara, CA 95054
         Phone: +1 408-400-1900
         E-mail: support@ipinfusion.com
         Web: http://www.ipinfusion.com/";

    description
        "quality of service";


    revision "2017-08-07" {
        description " Initial Version.";
        reference "";
    }

    grouping aclFilter {
        description
            "aclFilter";
        leaf filterType  {
            type  cml_data_types:CML_FILTER_TYPE_T;
            description "";
        } // END of filterType definition.


        leaf common  {
            type  cml_data_types:CML_INT32_T;
            description "";
        } // END of common definition.


        container mfilter {
            description
                "mfilter structure in quality of service";
            leaf extended  {
                type  cml_data_types:CML_INT32_T;
                description "";
            } // END of extended definition.


            leaf pktFormat  {
                type  cml_data_types:CML_INT32_T;
                description "";
            } // END of pktFormat definition.


            leaf-list filterA  {
                type  cml_data_types:CML_INT8_T;
                description "";
            } // END of filterA definition.


            leaf-list Amask  {
                type  cml_data_types:CML_INT8_T;
                description "";
            } // END of Amask definition.


            leaf-list filterM  {
                type  cml_data_types:CML_INT8_T;
                description "";
            } // END of filterM definition.


            leaf-list Mmask  {
                type  cml_data_types:CML_INT8_T;
                description "";
            } // END of Mmask definition.


            leaf priority  {
                type  cml_data_types:CML_INT32_T;
                description "";
            } // END of priority definition.


        } // END of mfilter-container definition.
        container ifilter {
            description
                "ipv4 filter structure in quality of service";
            leaf flag  {
                type  cml_data_types:CML_INT32_T;
                description "";
            } // END of flag definition.


            leaf addr  {
                type  cml_data_types:CML_IPV4_ADDR_T;
                description "";
            } // END of addr definition.


            leaf addrMask  {
                type  cml_data_types:CML_IPV4_ADDR_T;
                description "";
            } // END of addrMask definition.


            leaf mask  {
                type  cml_data_types:CML_IPV4_ADDR_T;
                description "";
            } // END of mask definition.


            leaf maskMask  {
                type  cml_data_types:CML_IPV4_ADDR_T;
                description "";
            } // END of maskMask definition.


            leaf addrConfig  {
                type  cml_data_types:CML_IPV4_ADDR_T;
                description "";
            } // END of addrConfig definition.


            leaf maskConfig  {
                type  cml_data_types:CML_IPV4_ADDR_T;
                description "";
            } // END of maskConfig definition.


            leaf proto  {
                type  cml_data_types:CML_INT16_T;
                description "";
            } // END of proto definition.


            leaf isIanaValue  {
                type  cml_data_types:CML_INT8_T;
                description "";
            } // END of isIanaValue definition.


        } // END of ifilter-container definition.
        container ip6filter {
            description
                "ipv6 filter structure in quality of service";
            leaf flag  {
                type  cml_data_types:CML_INT32_T;
                description "";
            } // END of flag definition.


            leaf saddr  {
                type  cml_data_types:CML_IPV6_ADDR_T;
                description "";
            } // END of saddr definition.


            leaf saddrMask  {
                type  cml_data_types:CML_IPV6_ADDR_T;
                description "";
            } // END of saddrMask definition.


            leaf daddr  {
                type  cml_data_types:CML_IPV6_ADDR_T;
                description "";
            } // END of daddr definition.


            leaf daddrMask  {
                type  cml_data_types:CML_IPV6_ADDR_T;
                description "";
            } // END of daddrMask definition.


            leaf saddrConfig  {
                type  cml_data_types:CML_IPV6_ADDR_T;
                description "";
            } // END of saddrConfig definition.


            leaf daddrConfig  {
                type  cml_data_types:CML_IPV4_ADDR_T;
                description "";
            } // END of daddrConfig definition.


            leaf proto  {
                type  cml_data_types:CML_INT16_T;
                description "";
            } // END of proto definition.


            leaf isIanaValue  {
                type  cml_data_types:CML_INT8_T;
                description "";
            } // END of isIanaValue definition.


        } // END of ip6filter-container definition.
        container zfilter {
            description
                "zfilter structure in quality of service";
            leaf exact  {
                type  cml_data_types:CML_INT32_T;
                description "";
            } // END of exact definition.


            leaf prefix  {
                type  cml_data_types:CML_STRING_T {
                    length "0..255";
                }
                description "";
            } // END of prefix definition.


        } // END of zfilter-container definition.
        container zextfilter {
            description
                "qos zebos ext structure in quality of service";
            leaf extProtocol  {
                type  cml_data_types:CML_INT32_T;
                description "";
            } // END of extProtocol definition.


            leaf sprefix  {
                type  cml_data_types:CML_STRING_T {
                    length "0..255";
                }
                description "";
            } // END of sprefix definition.


            leaf sportOp  {
                type  cml_data_types:CML_QOS_OPERATION_T;
                description "";
            } // END of sportOp definition.


            leaf sport  {
                type  cml_data_types:CML_INT32_T;
                description "";
            } // END of sport definition.


            leaf dprefix  {
                type  cml_data_types:CML_STRING_T {
                    length "0..255";
                }
                description "";
            } // END of dprefix definition.


            leaf dportOp  {
                type  cml_data_types:CML_QOS_OPERATION_T;
                description "";
            } // END of dportOp definition.


            leaf dport  {
                type  cml_data_types:CML_INT32_T;
                description "";
            } // END of dport definition.


        } // END of zextfilter-container definition.
    } // END of aclFilter definition.

    grouping  qosInterface-grouping {
    description
        "interface qif list in quality of service";
    container qosInterface {
        description
            "interface qif list in quality of service";
        leaf trustType  {
            type  cml_data_types:CML_BOOL_T;
            description "";
        } // END of trustType definition.



        list servicepolicyTypeQos {
            key "serviceDirection";
            description
                "map Qos Profile to interface";
            leaf serviceDirection  {
                type  cml_data_types:CML_QOS_DIRECTION_T;
                description "";
            } // END of serviceDirection definition.


            leaf servicePolicyName  {
                type  cml_data_types:CML_STRING_T {
                    length "0..255";
                }
                mandatory true;
                description "";
            } // END of servicePolicyName definition.



            list cmapList {
                key "cmapId";
                config false;
                description
                    "List of class-maps attached to policy-map";
                leaf cmapId  {
                    type  cml_data_types:CML_UINT32_T;
                    description "";
                } // END of cmapId definition.


                leaf cmapName  {
                    type  cml_data_types:CML_STRING_T {
                        length "0..255";
                    }
                    description "";
                } // END of cmapName definition.


                leaf matchPkts  {
                    type  cml_data_types:CML_UINT64_T;
                    description "";
                } // END of matchPkts definition.


                leaf matchBytes  {
                    type  cml_data_types:CML_UINT64_T;
                    description "";
                } // END of matchBytes definition.


                leaf transmittedPkts  {
                    type  cml_data_types:CML_UINT64_T;
                    description "";
                } // END of transmittedPkts definition.


                leaf transmittedBytes  {
                    type  cml_data_types:CML_UINT64_T;
                    description "";
                } // END of transmittedBytes definition.


                leaf droppedPkts  {
                    type  cml_data_types:CML_UINT64_T;
                    description "";
                } // END of droppedPkts definition.


                leaf droppedBytes  {
                    type  cml_data_types:CML_UINT64_T;
                    description "";
                } // END of droppedBytes definition.


                leaf cmapStatsValid  {
                    type  cml_data_types:CML_BOOL_T;
                    description "";
                } // END of cmapStatsValid definition.



                list childCmapList {
                    key "childCmapId";
                    config false;
                    description
                        "List of child class-maps attached to parent class-map node at level 1";
                    leaf childCmapId  {
                        type  cml_data_types:CML_UINT32_T;
                        description "";
                    } // END of childCmapId definition.


                    leaf childCmapName  {
                        type  cml_data_types:CML_STRING_T {
                            length "0..255";
                        }
                        description "";
                    } // END of childCmapName definition.


                    leaf childMatchPkts  {
                        type  cml_data_types:CML_UINT64_T;
                        description "";
                    } // END of childMatchPkts definition.


                    leaf childMatchBytes  {
                        type  cml_data_types:CML_UINT64_T;
                        description "";
                    } // END of childMatchBytes definition.


                    leaf childTransmittedPkts  {
                        type  cml_data_types:CML_UINT64_T;
                        description "";
                    } // END of childTransmittedPkts definition.


                    leaf childTransmittedBytes  {
                        type  cml_data_types:CML_UINT64_T;
                        description "";
                    } // END of childTransmittedBytes definition.


                    leaf childDroppedPkts  {
                        type  cml_data_types:CML_UINT64_T;
                        description "";
                    } // END of childDroppedPkts definition.


                    leaf childDroppedBytes  {
                        type  cml_data_types:CML_UINT64_T;
                        description "";
                    } // END of childDroppedBytes definition.


                    leaf childCmapStatsValid  {
                        type  cml_data_types:CML_BOOL_T;
                        description "";
                    } // END of childCmapStatsValid definition.


                } // End of childCmapList-list
            } // End of cmapList-list
        } // End of servicepolicyTypeQos-list

        list qosRemarkInterface {
            key "qosIntfRemarkType";
            description
                "enable/disable qos (cos/dei/dscp) remark on interface";
            leaf qosIntfRemarkType  {
                type  cml_data_types:CML_QOS_REMARK_TYPE_T;
                description "";
            } // END of qosIntfRemarkType definition.


            leaf qosIntfRemarkEnable  {
                type  cml_data_types:CML_REMARK_ENABLE_DISABLE_T;
                mandatory true;
                description "";
            } // END of qosIntfRemarkEnable definition.


        } // End of qosRemarkInterface-list

        list cosifQueue {
            if-feature feature_list:NOT_HAVE_QOS_MAPPING_PROFILE;
            key "CosTblSize";
            description
                "cos queue values mapping at interface level";
            leaf CosTblSize  {
                type  cml_data_types:CML_INT8_T {
                     range "0..7";
                }
                description "";
            } // END of CosTblSize definition.


            leaf InterfaceCosQueueId  {
                type  cml_data_types:CML_INT32_T {
                     range "0..7";
                }
                mandatory true;
                description "";
            } // END of InterfaceCosQueueId definition.


        } // End of cosifQueue-list

        list dscpifQueue {
            if-feature feature_list:NOT_HAVE_QOS_MAPPING_PROFILE;
            key "DscpTblSize";
            description
                "dscp queue mapping structure in quality of service";
            leaf DscpTblSize  {
                type  cml_data_types:CML_INT32_T {
                     range "0..63";
                }
                description "";
            } // END of DscpTblSize definition.


            leaf dscpQueueMapTbl  {
                type  cml_data_types:CML_INT32_T {
                     range "0..7";
                }
                mandatory true;
                description "";
            } // END of dscpQueueMapTbl definition.


        } // End of dscpifQueue-list
        container servicepolicyTypeQueuing {
            description
                "Queuing Policy-map";
            leaf serviceQueuing  {
                type  cml_data_types:CML_STRING_T {
                    length "0..255";
                }
                description "Use this attribute to attach a service-policy of type queuing to the interface";
            } // END of serviceQueuing definition.



            list queuingCmapList {
                key "cmapId";
                config false;
                description
                    "List of queuing class-maps in queuing policy-map";
                leaf cmapId  {
                    type  cml_data_types:CML_UINT32_T;
                    description "A unique number corresponding to a class-map.";
                } // END of cmapId definition.


                leaf cmapName  {
                    type  cml_data_types:CML_STRING_T {
                        length "0..255";
                    }
                    description "Name of the queuing class-map.";
                } // END of cmapName definition.



                list queueStats {
                    if-feature feature_list:HAVE_SERVICE_QUEUING_2;
                    key "queueId";
                    config false;
                    description
                        "queuing statistics for queuing class-map";
                    leaf queueId  {
                        type  cml_data_types:CML_UINT8_T;
                        description "An unique number associated with the queue";
                    } // END of queueId definition.


                    leaf totalOutputPkts  {
                        type  cml_data_types:CML_UINT64_T;
                        description "Total number of packets transmitted out of the queue";
                    } // END of totalOutputPkts definition.


                    leaf greenPkts  {
                        type  cml_data_types:CML_UINT64_T;
                        description "Number of green packets transmitted out of the queue";
                    } // END of greenPkts definition.


                    leaf nonGreenPkts  {
                        type  cml_data_types:CML_UINT64_T;
                        description "Number of yellow and red (when applicable) packets transmitted out of the queue";
                    } // END of nonGreenPkts definition.


                    leaf totalDroppedPkts  {
                        type  cml_data_types:CML_UINT64_T;
                        description "Total number of packets dropped in the queue";
                    } // END of totalDroppedPkts definition.


                    leaf greenDroppedPkts  {
                        type  cml_data_types:CML_UINT64_T;
                        description "Number of green packets dropped in the queue";
                    } // END of greenDroppedPkts definition.


                    leaf yellowDroppedPkts  {
                        type  cml_data_types:CML_UINT64_T;
                        description "Number of yellow packets dropped in the queue";
                    } // END of yellowDroppedPkts definition.


                    leaf redDroppedPkts  {
                        type  cml_data_types:CML_UINT64_T;
                        description "Number of red packets dropped in the queue";
                    } // END of redDroppedPkts definition.


                    leaf rateKbps  {
                        type  cml_data_types:CML_FLOAT_T;
                        description "Queue rate in kbps";
                    } // END of rateKbps definition.


                    leaf rateMbps  {
                        type  cml_data_types:CML_FLOAT_T;
                        description "Queue rate in mbps";
                    } // END of rateMbps definition.


                    leaf rateGbps  {
                        type  cml_data_types:CML_FLOAT_T;
                        description "Queue rate in gbps";
                    } // END of rateGbps definition.


                } // End of queueStats-list

                list queuingChild1CmapList {
                    key "child1CmapId";
                    config false;
                    description
                        "List of queuing class-maps attached to child queuing policy-map";
                    leaf child1CmapId  {
                        type  cml_data_types:CML_UINT32_T;
                        description "A unique number corresponding to child class-map.";
                    } // END of child1CmapId definition.


                    leaf child1CmapName  {
                        type  cml_data_types:CML_STRING_T {
                            length "0..255";
                        }
                        description "Name of the child queuing class-map.";
                    } // END of child1CmapName definition.



                    list child1QueueStats {
                        if-feature feature_list:HAVE_SERVICE_QUEUING_2;
                        key "child1QueueId";
                        config false;
                        description
                            "queuing statistics for child queuing class-map";
                        leaf child1QueueId  {
                            type  cml_data_types:CML_UINT8_T;
                            description "An unique number associated with the queue";
                        } // END of child1QueueId definition.


                        leaf child1TotalOutputPkts  {
                            type  cml_data_types:CML_UINT64_T;
                            description "Total number of packets transmitted out of the queue";
                        } // END of child1TotalOutputPkts definition.


                        leaf child1GreenPkts  {
                            type  cml_data_types:CML_UINT64_T;
                            description "Number of green packets transmitted out of the queue";
                        } // END of child1GreenPkts definition.


                        leaf child1NonGreenPkts  {
                            type  cml_data_types:CML_UINT64_T;
                            description "Number of yellow and red (when applicable) packets transmitted out of the queue";
                        } // END of child1NonGreenPkts definition.


                        leaf child1TotalDroppedPkts  {
                            type  cml_data_types:CML_UINT64_T;
                            description "Total number of packets dropped in the queue";
                        } // END of child1TotalDroppedPkts definition.


                        leaf child1GreenDroppedPkts  {
                            type  cml_data_types:CML_UINT64_T;
                            description "Number of green packets dropped in the queue";
                        } // END of child1GreenDroppedPkts definition.


                        leaf child1YellowDroppedPkts  {
                            type  cml_data_types:CML_UINT64_T;
                            description "Number of yellow packets dropped in the queue";
                        } // END of child1YellowDroppedPkts definition.


                        leaf child1RedDroppedPkts  {
                            type  cml_data_types:CML_UINT64_T;
                            description "Number of red packets dropped in the queue";
                        } // END of child1RedDroppedPkts definition.


                        leaf child1rateKbps  {
                            type  cml_data_types:CML_FLOAT_T;
                            description "Queue rate in kbps";
                        } // END of child1rateKbps definition.


                        leaf child1rateMbps  {
                            type  cml_data_types:CML_FLOAT_T;
                            description "Queue rate in mbps";
                        } // END of child1rateMbps definition.


                        leaf child1rateGbps  {
                            type  cml_data_types:CML_FLOAT_T;
                            description "Queue rate in gbps";
                        } // END of child1rateGbps definition.


                    } // End of child1QueueStats-list

                    list queuingChild2CmapList {
                        key "child2CmapId";
                        config false;
                        description
                            "List of queuing class-maps attached to 2nd level child queuing policy-map";
                        leaf child2CmapId  {
                            type  cml_data_types:CML_UINT32_T;
                            description "A unique number corresponding to child class-map.";
                        } // END of child2CmapId definition.


                        leaf child2CmapName  {
                            type  cml_data_types:CML_STRING_T {
                                length "0..255";
                            }
                            description "Name of the child queuing class-map.";
                        } // END of child2CmapName definition.



                        list child2QueueStats {
                            if-feature feature_list:HAVE_SERVICE_QUEUING_2;
                            key "child2QueueId";
                            config false;
                            description
                                "queuing statistics for child queuing class-map";
                            leaf child2QueueId  {
                                type  cml_data_types:CML_UINT8_T;
                                description "An unique number associated with the queue";
                            } // END of child2QueueId definition.


                            leaf child2TotalOutputPkts  {
                                type  cml_data_types:CML_UINT64_T;
                                description "Total number of packets transmitted out of the queue";
                            } // END of child2TotalOutputPkts definition.


                            leaf child2GreenPkts  {
                                type  cml_data_types:CML_UINT64_T;
                                description "Number of green packets transmitted out of the queue";
                            } // END of child2GreenPkts definition.


                            leaf child2NonGreenPkts  {
                                type  cml_data_types:CML_UINT64_T;
                                description "Number of yellow and red (when applicable) packets transmitted out of the queue";
                            } // END of child2NonGreenPkts definition.


                            leaf child2TotalDroppedPkts  {
                                type  cml_data_types:CML_UINT64_T;
                                description "Total number of packets dropped in the queue";
                            } // END of child2TotalDroppedPkts definition.


                            leaf child2GreenDroppedPkts  {
                                type  cml_data_types:CML_UINT64_T;
                                description "Number of green packets dropped in the queue";
                            } // END of child2GreenDroppedPkts definition.


                            leaf child2YellowDroppedPkts  {
                                type  cml_data_types:CML_UINT64_T;
                                description "Number of yellow packets dropped in the queue";
                            } // END of child2YellowDroppedPkts definition.


                            leaf child2RedDroppedPkts  {
                                type  cml_data_types:CML_UINT64_T;
                                description "Number of red packets dropped in the queue";
                            } // END of child2RedDroppedPkts definition.


                            leaf child2rateKbps  {
                                type  cml_data_types:CML_FLOAT_T;
                                description "Queue rate in kbps";
                            } // END of child2rateKbps definition.


                            leaf child2rateMbps  {
                                type  cml_data_types:CML_FLOAT_T;
                                description "Queue rate in mbps";
                            } // END of child2rateMbps definition.


                            leaf child2rateGbps  {
                                type  cml_data_types:CML_FLOAT_T;
                                description "Queue rate in gbps";
                            } // END of child2rateGbps definition.


                        } // End of child2QueueStats-list
                    } // End of queuingChild2CmapList-list
                } // End of queuingChild1CmapList-list
            } // End of queuingCmapList-list
        } // END of servicepolicyTypeQueuing-container definition.
        container qosProfile {
            if-feature feature_list:HAVE_QOS_MAPPING_PROFILE;
            description
                "Map Qos Profile to interface";
            leaf dscpToQueueMapProfile  {
                type  cml_data_types:CML_STRING_T {
                    length "0..255";
                }
                description "";
            } // END of dscpToQueueMapProfile definition.


            leaf dscpToDscpMapProfile  {
                if-feature feature_list:HAVE_CUSTOM2_QOS;
                type  cml_data_types:CML_STRING_T {
                    length "0..255";
                }
                description "";
            } // END of dscpToDscpMapProfile definition.


            leaf cosToQueueMapProfile  {
                type  cml_data_types:CML_STRING_T {
                    length "0..255";
                }
                description "";
            } // END of cosToQueueMapProfile definition.


            leaf queueToCosMapProfile  {
                type  cml_data_types:CML_STRING_T {
                    length "0..255";
                }
                description "";
            } // END of queueToCosMapProfile definition.


            leaf expEncapMapProfile  {
                if-feature feature_list:HAVE_DIFFSERV;
                if-feature feature_list:HAVE_CUSTOM2_QOS;
                type  cml_data_types:CML_STRING_T {
                    length "0..255";
                }
                description "";
            } // END of expEncapMapProfile definition.


        } // END of qosProfile-container definition.
        container untagPrio {
            description
                "untagged Priority";
            leaf untagPrio  {
                type  cml_data_types:CML_INT32_T {
                     range "0..7";
                }
                description "";
            } // END of untagPrio definition.


        } // END of untagPrio-container definition.
        container portShapeRate {
            description
                "Configure Traffic Shaping on interface";
            leaf trafficShapeRate  {
                type  cml_data_types:CML_INT32_T {
                     range "1..1000000000";
                }
                description "";
            } // END of trafficShapeRate definition.


            leaf shapeRateType  {
                if-feature feature_list:HAVE_CUSTOM2_QOS;
                type  cml_data_types:CML_HQOS_SHAPE_RATE_TYPE_T;
                description "";
            } // END of shapeRateType definition.


            leaf trafficShapeBurst  {
                if-feature feature_list:NOT_HAVE_CUSTOM2_QOS;
                type  cml_data_types:CML_INT32_T {
                     range "1..1000000";
                }
                description "";
            } // END of trafficShapeBurst definition.


        } // END of portShapeRate-container definition.
    } // END of qosInterface-container definition.
    } // END of qosInterface-container definition.

    grouping  qos-grouping {
    description
        "nsm master structure having quality of service";
    container qos {
        description
            "nsm master structure having quality of service";
        container acl {
            description
                "acl master of quality of service";
            leaf name  {
                type  cml_data_types:CML_STRING_T {
                    length "0..255";
                }
                description "";
            } // END of name definition.


            leaf remark  {
                type  cml_data_types:CML_STRING_T {
                    length "0..255";
                }
                description "";
            } // END of remark definition.


            leaf aclType  {
                type  cml_data_types:CML_INT32_T;
                description "";
            } // END of aclType definition.


            leaf attached  {
                type  cml_data_types:CML_INT32_T;
                description "";
            } // END of attached definition.



            list accessNum {
                key "aclType";
                description
                    "access list structure in quality of service";
                leaf aclType  {
                    type  cml_data_types:CML_INT32_T;
                    description "";
                } // END of aclType definition.


                uses aclFilter;
            } // End of accessNum-list

            list accessString {
                key "aclType";
                description
                    "access list structure in quality of service";
                leaf aclType  {
                    type  cml_data_types:CML_INT32_T;
                    description "";
                } // END of aclType definition.


                uses aclFilter;
            } // End of accessString-list
        } // END of acl-container definition.
        container qosGlobal {
            description
                "global structure of quality of service";
            leaf state  {
                type  cml_data_types:CML_HQOS_ENABLE_DISABLE_T;
                default "disable";
                description "";
            } // END of state definition.


            leaf blockSize  {
                if-feature feature_list:HAVE_FLEXPORT;
                if-feature feature_list:HAVE_SERVICE_QUEUING_1;
                type  cml_data_types:CML_INT8_T {
                     range "1..8";
                }
                description "";
            } // END of blockSize definition.


            leaf-list dscpQueueMapTbl  {
                type  cml_data_types:CML_INT8_T;
                description "";
            } // END of dscpQueueMapTbl definition.


            leaf-list dscpDscpMapTbl  {
                type  cml_data_types:CML_INT8_T;
                description "";
            } // END of dscpDscpMapTbl definition.


            leaf-list cosQueueMapTblModified  {
                type  cml_data_types:CML_INT8_T;
                description "";
            } // END of cosQueueMapTblModified definition.


            leaf-list cosCosMapTbl  {
                type  cml_data_types:CML_INT8_T;
                description "";
            } // END of cosCosMapTbl definition.


            leaf statistics  {
                type  cml_data_types:CML_BOOL_T;
                description "";
            } // END of statistics definition.



            list dscpml {
                key "name";
                description
                    "nsm dscp mut list structure in quality of service";
                leaf name  {
                    type  cml_data_types:CML_STRING_T {
                        length "0..255";
                    }
                    description "";
                } // END of name definition.


                leaf aclName  {
                    type  cml_data_types:CML_STRING_T {
                        length "0..255";
                    }
                    description "";
                } // END of aclName definition.


                leaf-list dscpMutD  {
                    type  cml_data_types:CML_INT8_T;
                    description "";
                } // END of dscpMutD definition.


            } // End of dscpml-list

            list dcosl {
                key "name";
                description
                    "nsm dscp cos list in quality of service";
                leaf name  {
                    type  cml_data_types:CML_STRING_T {
                        length "0..255";
                    }
                    description "";
                } // END of name definition.


                leaf aclName  {
                    type  cml_data_types:CML_STRING_T {
                        length "0..255";
                    }
                    description "";
                } // END of aclName definition.


                leaf-list dscpMutD  {
                    type  cml_data_types:CML_INT8_T;
                    description "";
                } // END of dscpMutD definition.


            } // End of dcosl-list

            list cos {
                key "name";
                description
                    "nsm agp list in quality of service";
                leaf name  {
                    type  cml_data_types:CML_STRING_T {
                        length "0..255";
                    }
                    description "";
                } // END of name definition.


                leaf aclName  {
                    type  cml_data_types:CML_STRING_T {
                        length "0..255";
                    }
                    description "";
                } // END of aclName definition.


            } // End of cos-list

            list aggPolice {
                if-feature feature_list:HAVE_EXTENDED_QOS;
                key "aggpoliceName";
                description
                    "aggregate police structure of quality of service";
                leaf aggpoliceName  {
                    type  cml_data_types:CML_STRING_T {
                        length "0..255";
                    }
                    description "";
                } // END of aggpoliceName definition.


                leaf aggpoliceType  {
                    type  cml_data_types:CML_UINT32_T;
                    description "";
                } // END of aggpoliceType definition.


                leaf aggAvg  {
                    type  cml_data_types:CML_UINT32_T {
                         range "1..720000000";
                    }
                    description "";
                } // END of aggAvg definition.


                leaf aggcirType  {
                    type  cml_data_types:CML_QOS_RATE_T;
                    description "";
                } // END of aggcirType definition.


                leaf aggPir  {
                    type  cml_data_types:CML_UINT32_T {
                         range "1..720000000";
                    }
                    description "";
                } // END of aggPir definition.


                leaf aggpirType  {
                    type  cml_data_types:CML_QOS_RATE_T;
                    description "";
                } // END of aggpirType definition.


                leaf aggburst  {
                    type  cml_data_types:CML_UINT32_T {
                         range "1..4161";
                    }
                    description "";
                } // END of aggburst definition.


                leaf aggbcType  {
                    type  cml_data_types:CML_BURST_TYPE_T;
                    description "";
                } // END of aggbcType definition.


                leaf aggexcessBurst  {
                    type  cml_data_types:CML_UINT32_T {
                         range "1..4161";
                    }
                    description "";
                } // END of aggexcessBurst definition.


                leaf aggbeType  {
                    type  cml_data_types:CML_BURST_TYPE_T;
                    description "";
                } // END of aggbeType definition.


                leaf aggconfPoliceVal  {
                    if-feature feature_list:NOT_HAVE_CUSTOM2_QOS;
                    type  cml_data_types:CML_INT32_T;
                    description "";
                } // END of aggconfPoliceVal definition.


                leaf aggconfAct  {
                    if-feature feature_list:NOT_HAVE_CUSTOM2_QOS;
                    type  cml_data_types:CML_CONFORM_ACTION_T;
                    description "";
                } // END of aggconfAct definition.


                leaf aggpoliceDscp  {
                    if-feature feature_list:NOT_HAVE_CUSTOM2_QOS;
                    type  cml_data_types:CML_INT32_T;
                    description "";
                } // END of aggpoliceDscp definition.


                leaf aggexdAct  {
                    if-feature feature_list:NOT_HAVE_CUSTOM2_QOS;
                    type  cml_data_types:CML_EXCEED_ACTION_T;
                    description "";
                } // END of aggexdAct definition.


                leaf aggvotPoliceVal  {
                    if-feature feature_list:NOT_HAVE_CUSTOM2_QOS;
                    type  cml_data_types:CML_INT32_T;
                    description "";
                } // END of aggvotPoliceVal definition.


                leaf aggvotAct  {
                    if-feature feature_list:NOT_HAVE_CUSTOM2_QOS;
                    type  cml_data_types:CML_VIOLATE_ACTION_T;
                    description "";
                } // END of aggvotAct definition.


            } // End of aggPolice-list

            list cosQueue {
                if-feature feature_list:NOT_HAVE_QOS_MAPPING_PROFILE;
                key "CosTblSize";
                description
                    "cos queue values mapping structure in quality of service";
                leaf CosTblSize  {
                    type  cml_data_types:CML_INT8_T {
                         range "0..7";
                    }
                    description "";
                } // END of CosTblSize definition.


                leaf cosQueueMapTbl  {
                    type  cml_data_types:CML_INT32_T {
                         range "0..7";
                    }
                    mandatory true;
                    description "";
                } // END of cosQueueMapTbl definition.


            } // End of cosQueue-list

            list dscpQueue {
                if-feature feature_list:NOT_HAVE_QOS_MAPPING_PROFILE;
                key "DscpTblSize";
                description
                    "dscp queue values mapping structure in quality of service";
                leaf DscpTblSize  {
                    type  cml_data_types:CML_INT32_T {
                         range "0..63";
                    }
                    description "";
                } // END of DscpTblSize definition.


                leaf dscpQueueMapTbl  {
                    type  cml_data_types:CML_INT32_T {
                         range "0..7";
                    }
                    mandatory true;
                    description "";
                } // END of dscpQueueMapTbl definition.


            } // End of dscpQueue-list

            list expClass {
                if-feature feature_list:HAVE_DIFFSERV;
                if-feature feature_list:NOT_HAVE_QOS_MAPPING_PROFILE;
                key "ExpTblSize";
                description
                    "mpls exp values mapping structure in quality of service";
                leaf ExpTblSize  {
                    type  cml_data_types:CML_INT32_T {
                         range "0..7";
                    }
                    description "";
                } // END of ExpTblSize definition.


                leaf expQueueMapTbl  {
                    type  cml_data_types:CML_INT32_T {
                         range "0..7";
                    }
                    mandatory true;
                    description "";
                } // END of expQueueMapTbl definition.


            } // End of expClass-list

            list classExp {
                if-feature feature_list:HAVE_DIFFSERV;
                if-feature feature_list:NOT_HAVE_QOS_MAPPING_PROFILE;
                key "queueExpTblSize";
                description
                    "mpls class to exp values mapping structure in quality of service";
                leaf queueExpTblSize  {
                    type  cml_data_types:CML_INT32_T {
                         range "0..7";
                    }
                    description "";
                } // END of queueExpTblSize definition.


                leaf queueExpMapTbl  {
                    type  cml_data_types:CML_INT32_T {
                         range "0..7";
                    }
                    mandatory true;
                    description "";
                } // END of queueExpMapTbl definition.


            } // End of classExp-list

            list cosqprofilelist {
                if-feature feature_list:HAVE_VXLAN;
                if-feature feature_list:NOT_HAVE_DUNE;
                key "cosQProfile";
                description
                    "cos_queue_profile_tree having quality of service";
                leaf cosQProfile  {
                    type  cml_data_types:CML_UINT32_T {
                         range "1..64";
                    }
                    description "";
                } // END of cosQProfile definition.


                leaf cosQueueDir  {
                    type  cml_data_types:CML_VXLAN_QOS_DIR_T;
                    mandatory true;
                    description "";
                } // END of cosQueueDir definition.



                list cosqmaptree {
                    if-feature feature_list:HAVE_VXLAN;
                    key "profileCos";
                    description
                        "cos_queue_profile_tree having quality of service";
                    leaf profileCos  {
                        type  cml_data_types:CML_UINT8_T {
                             range "0..7";
                        }
                        description "";
                    } // END of profileCos definition.


                    leaf cosQueue  {
                        type  cml_data_types:CML_UINT8_T {
                             range "0..7";
                        }
                        mandatory true;
                        description "";
                    } // END of cosQueue definition.


                } // End of cosqmaptree-list
            } // End of cosqprofilelist-list

            list dscpqprofilelist {
                if-feature feature_list:HAVE_VXLAN;
                if-feature feature_list:NOT_HAVE_DUNE;
                key "dscpQProfile";
                description
                    "dscp_queue_profile_tree having quality of service";
                leaf dscpQProfile  {
                    type  cml_data_types:CML_UINT32_T {
                         range "65..128";
                    }
                    description "";
                } // END of dscpQProfile definition.



                list Ingress {
                    if-feature feature_list:HAVE_VXLAN;
                    if-feature feature_list:NOT_HAVE_DUNE;
                    key "dscpIngressQueueDir";
                    description
                        "dscp_queue_profile_tree having quality of service";
                    leaf dscpIngressQueueDir  {
                        type  cml_data_types:CML_VXLAN_QOS_INGRESS_DIR_T;
                        description "";
                    } // END of dscpIngressQueueDir definition.


                    leaf dscpqosString  {
                        type  cml_data_types:CML_EMPTY_T;
                        description "";
                    } // END of dscpqosString definition.



                    list dscpqmapingresstree {
                        if-feature feature_list:HAVE_VXLAN;
                        if-feature feature_list:NOT_HAVE_DUNE;
                        key "profileIngressDscp";
                        description
                            "dscp_queue_profile_tree having quality of service";
                        leaf profileIngressDscp  {
                            type  cml_data_types:CML_UINT8_T {
                                 range "0..63";
                            }
                            description "";
                        } // END of profileIngressDscp definition.


                        leaf dscpIngressQueue  {
                            type  cml_data_types:CML_UINT8_T {
                                 range "0..7";
                            }
                            mandatory true;
                            description "";
                        } // END of dscpIngressQueue definition.


                    } // End of dscpqmapingresstree-list
                } // End of Ingress-list

                list Egress {
                    if-feature feature_list:HAVE_VXLAN;
                    if-feature feature_list:NOT_HAVE_DUNE;
                    key "dscpQueueDir";
                    description
                        "dscp_queue_profile_tree having quality of service";
                    leaf dscpQueueDir  {
                        type  cml_data_types:CML_VXLAN_QOS_EGRESS_DIR_T;
                        description "";
                    } // END of dscpQueueDir definition.


                    leaf dscpqosString  {
                        type  cml_data_types:CML_EMPTY_T;
                        description "";
                    } // END of dscpqosString definition.



                    list dscpqmaptree {
                        key "profileDscp";
                        description
                            "dscp_queue_profile_tree having quality of service";
                        leaf profileDscp  {
                            type  cml_data_types:CML_UINT8_T {
                                 range "0..63";
                            }
                            description "";
                        } // END of profileDscp definition.


                        leaf dscpQueue  {
                            type  cml_data_types:CML_UINT8_T {
                                 range "0..7";
                            }
                            mandatory true;
                            description "";
                        } // END of dscpQueue definition.


                    } // End of dscpqmaptree-list
                } // End of Egress-list
            } // End of dscpqprofilelist-list

            list cosQueueToProfileMapList {
                key "cosQueueToProfileMap";
                description
                    "cos to queue profile mapping";
                leaf cosQueueToProfileMap  {
                    type  cml_data_types:CML_STRING_T {
                        length "0..255";
                    }
                    description "";
                } // END of cosQueueToProfileMap definition.



                list cosDeiQueueToProfileMapTree {
                    if-feature feature_list:NOT_HAVE_CUSTOM2_QOS;
                    key "profileMapCosQ";
                    description
                        "cos_queue_profile_map_tree";
                    leaf profileMapCosQ  {
                        type  cml_data_types:CML_UINT8_T {
                             range "0..7";
                        }
                        description "";
                    } // END of profileMapCosQ definition.



                    list cosDeiToProfileMapTree {
                        key "cosDeiMap";
                        description
                            "cos_queue_profile_map_tree";
                        leaf cosDeiMap  {
                            type  cml_data_types:CML_QOS_DEI_TYPE_T;
                            description "";
                        } // END of cosDeiMap definition.


                        leaf cosQueueMap  {
                            type  cml_data_types:CML_UINT8_T {
                                 range "0..7";
                            }
                            mandatory true;
                            description "";
                        } // END of cosQueueMap definition.


                        leaf cosColorMap  {
                            type  cml_data_types:CML_QOS_COLOR_TYPE_T;
                            mandatory true;
                            description "";
                        } // END of cosColorMap definition.


                    } // End of cosDeiToProfileMapTree-list
                } // End of cosDeiQueueToProfileMapTree-list

                list cosQueueToProfileMapTree {
                    if-feature feature_list:HAVE_CUSTOM2_QOS;
                    key "profileMapCosQ";
                    description
                        "cos_queue_profile_map_tree";
                    leaf profileMapCosQ  {
                        type  cml_data_types:CML_UINT8_T {
                             range "0..7";
                        }
                        description "";
                    } // END of profileMapCosQ definition.


                    leaf cosQueueMap  {
                        type  cml_data_types:CML_UINT8_T {
                             range "0..7";
                        }
                        mandatory true;
                        description "";
                    } // END of cosQueueMap definition.


                } // End of cosQueueToProfileMapTree-list
            } // End of cosQueueToProfileMapList-list

            list queueCosToProfileMapList {
                key "queueColorToCosProfileMap";
                description
                    "queue, color to cos profile mapping";
                leaf queueColorToCosProfileMap  {
                    type  cml_data_types:CML_STRING_T {
                        length "0..255";
                    }
                    description "";
                } // END of queueColorToCosProfileMap definition.



                list queueToCosProfileMapTree {
                    key "profileMapQueueCos";
                    description
                        "queue_color_cos_profile_map_tree";
                    leaf profileMapQueueCos  {
                        type  cml_data_types:CML_UINT8_T {
                             range "0..7";
                        }
                        description "";
                    } // END of profileMapQueueCos definition.



                    list ColorToCosProfileMapTree {
                        key "profileMapColorCos";
                        description
                            "queue_color_cos_profile_map_tree";
                        leaf profileMapColorCos  {
                            type  cml_data_types:CML_QOS_COLOR_TYPE_T;
                            description "";
                        } // END of profileMapColorCos definition.


                        leaf QueueCosMap  {
                            type  cml_data_types:CML_UINT8_T {
                                 range "0..7";
                            }
                            mandatory true;
                            description "";
                        } // END of QueueCosMap definition.


                    } // End of ColorToCosProfileMapTree-list
                } // End of queueToCosProfileMapTree-list
            } // End of queueCosToProfileMapList-list

            list dscpToQueueProfileMapList {
                key "dscpQueueToProfileMap";
                description
                    "dscp to queue profile mapping";
                leaf dscpQueueToProfileMap  {
                    type  cml_data_types:CML_STRING_T {
                        length "0..255";
                    }
                    description "";
                } // END of dscpQueueToProfileMap definition.



                list dscpQueueProfileMapTree {
                    if-feature feature_list:NOT_HAVE_CUSTOM2_QOS;
                    key "profileMapDscpQueue";
                    description
                        "dscp_queue_profile_map_tree";
                    leaf profileMapDscpQueue  {
                        type  cml_data_types:CML_UINT8_T {
                             range "0..63";
                        }
                        description "";
                    } // END of profileMapDscpQueue definition.


                    leaf dscpQueueMap  {
                        type  cml_data_types:CML_UINT8_T {
                             range "0..7";
                        }
                        mandatory true;
                        description "";
                    } // END of dscpQueueMap definition.


                    leaf dscpColorMap  {
                        type  cml_data_types:CML_QOS_COLOR_TYPE_T;
                        default "all";
                        description "";
                    } // END of dscpColorMap definition.


                } // End of dscpQueueProfileMapTree-list

                list dscpQueueOutDscpProfileMapTree {
                    if-feature feature_list:HAVE_CUSTOM2_QOS;
                    key "profileMapDscpQueue";
                    description
                        "dscp_queue_out_dscp_profile_map_tree";
                    leaf profileMapDscpQueue  {
                        type  cml_data_types:CML_UINT8_T {
                             range "0..63";
                        }
                        description "";
                    } // END of profileMapDscpQueue definition.


                    leaf dscpQueueMap  {
                        type  cml_data_types:CML_UINT8_T {
                             range "0..7";
                        }
                        mandatory true;
                        description "";
                    } // END of dscpQueueMap definition.


                    leaf dscpColorMap  {
                        type  cml_data_types:CML_QOS_COLOR_TYPE_T;
                        default "all";
                        description "";
                    } // END of dscpColorMap definition.


                    leaf dscpOutDscp  {
                        type  cml_data_types:CML_UINT8_T {
                             range "0..63";
                        }
                        description "";
                    } // END of dscpOutDscp definition.


                } // End of dscpQueueOutDscpProfileMapTree-list
            } // End of dscpToQueueProfileMapList-list

            list queueColorToDscpProfileMapList {
                key "queueColorToDscpProfileMap";
                description
                    "queue, color to dscp profile mapping";
                leaf queueColorToDscpProfileMap  {
                    type  cml_data_types:CML_STRING_T {
                        length "0..255";
                    }
                    description "";
                } // END of queueColorToDscpProfileMap definition.



                list queueToDscpProfileMapTree {
                    key "profileMapQueueDscp";
                    description
                        "queue_dscp_profile_map_tree";
                    leaf profileMapQueueDscp  {
                        type  cml_data_types:CML_UINT8_T {
                             range "0..7";
                        }
                        description "";
                    } // END of profileMapQueueDscp definition.



                    list ColorToDscpProfileMapTree {
                        key "profileMapColorDscp";
                        description
                            "queue_color_dscp_profile_map_tree";
                        leaf profileMapColorDscp  {
                            type  cml_data_types:CML_QOS_COLOR_TYPE_T;
                            description "";
                        } // END of profileMapColorDscp definition.


                        leaf QueueDscpMap  {
                            type  cml_data_types:CML_UINT8_T {
                                 range "0..63";
                            }
                            mandatory true;
                            description "";
                        } // END of QueueDscpMap definition.


                    } // End of ColorToDscpProfileMapTree-list
                } // End of queueToDscpProfileMapTree-list
            } // End of queueColorToDscpProfileMapList-list

            list inDscpToOutDscpProfileMapList {
                if-feature feature_list:HAVE_CUSTOM2_QOS;
                key "inDscpToOutDscpProfileMap";
                description
                    "in-dscp to out-dscp profile mapping";
                leaf inDscpToOutDscpProfileMap  {
                    type  cml_data_types:CML_STRING_T {
                        length "0..255";
                    }
                    description "";
                } // END of inDscpToOutDscpProfileMap definition.



                list inDscpOutDscpProfileMapTree {
                    key "profileMapInDscp";
                    description
                        "InDscp_OutDscp_profile_map_tree";
                    leaf profileMapInDscp  {
                        type  cml_data_types:CML_UINT8_T {
                             range "0..63";
                        }
                        description "";
                    } // END of profileMapInDscp definition.



                    list ColorToOutDscpProfileMapTree {
                        key "profileMapColorDscp";
                        description
                            "InDscp_OutDscp_profile_map_tree";
                        leaf profileMapColorDscp  {
                            type  cml_data_types:CML_QOS_COLOR_TYPE_T;
                            description "";
                        } // END of profileMapColorDscp definition.


                        leaf profileMapOutDscp  {
                            type  cml_data_types:CML_UINT8_T {
                                 range "0..63";
                            }
                            mandatory true;
                            description "";
                        } // END of profileMapOutDscp definition.


                    } // End of ColorToOutDscpProfileMapTree-list
                } // End of inDscpOutDscpProfileMapTree-list
            } // End of inDscpToOutDscpProfileMapList-list

            list expToQueueProfileMapList {
                if-feature feature_list:HAVE_DIFFSERV;
                if-feature feature_list:HAVE_QOS_MAPPING_PROFILE;
                key "expToQueueProfileMap";
                description
                    "exp to queue profile mapping";
                leaf expToQueueProfileMap  {
                    type  cml_data_types:CML_PROFILE_NAME_T;
                    description "";
                } // END of expToQueueProfileMap definition.



                list expToQueueProfileMapTree {
                    if-feature feature_list:HAVE_QOS_MAPPING_PROFILE;
                    if-feature feature_list:HAVE_DIFFSERV;
                    key "profileMapExp";
                    description
                        "exp_queue_profile_map_tree";
                    leaf profileMapExp  {
                        type  cml_data_types:CML_UINT8_T {
                             range "0..7";
                        }
                        description "";
                    } // END of profileMapExp definition.


                    leaf profileMapQueue  {
                        type  cml_data_types:CML_UINT8_T {
                             range "0..7";
                        }
                        mandatory true;
                        description "";
                    } // END of profileMapQueue definition.


                    leaf queueColorMap  {
                        type  cml_data_types:CML_QOS_COLOR_TYPE_T;
                        default "all";
                        description "";
                    } // END of queueColorMap definition.


                } // End of expToQueueProfileMapTree-list
            } // End of expToQueueProfileMapList-list

            list expEncapProfileMapList {
                if-feature feature_list:HAVE_CUSTOM2_QOS;
                if-feature feature_list:HAVE_DIFFSERV;
                if-feature feature_list:HAVE_QOS_MAPPING_PROFILE;
                key "expEncapProfileMap";
                description
                    "exp encapsulation profile mapping";
                leaf expEncapProfileMap  {
                    type  cml_data_types:CML_STRING_T {
                        length "0..255";
                    }
                    description "";
                } // END of expEncapProfileMap definition.



                list dscpToExpProfileMapTree {
                    if-feature feature_list:HAVE_QOS_MAPPING_PROFILE;
                    if-feature feature_list:HAVE_DIFFSERV;
                    if-feature feature_list:HAVE_CUSTOM2_QOS;
                    key "dscpExpEncap";
                    description
                        "dscp_exp_profile_map_tree";
                    leaf dscpExpEncap  {
                        type  cml_data_types:CML_UINT8_T {
                             range "0..63";
                        }
                        description "";
                    } // END of dscpExpEncap definition.


                    leaf l3ProfileMapExp  {
                        type  cml_data_types:CML_UINT8_T {
                             range "0..7";
                        }
                        mandatory true;
                        description "";
                    } // END of l3ProfileMapExp definition.


                } // End of dscpToExpProfileMapTree-list

                list queueToExpProfileMapTree {
                    if-feature feature_list:HAVE_QOS_MAPPING_PROFILE;
                    if-feature feature_list:HAVE_DIFFSERV;
                    if-feature feature_list:HAVE_CUSTOM2_QOS;
                    key "queueExpEncap";
                    description
                        "queue_color_exp_profile_map_tree";
                    leaf queueExpEncap  {
                        type  cml_data_types:CML_UINT8_T {
                             range "0..7";
                        }
                        description "";
                    } // END of queueExpEncap definition.



                    list colorToExpProfileMapTree {
                        key "colorExpEncap";
                        description
                            "queue_color_exp_profile_map_tree";
                        leaf colorExpEncap  {
                            type  cml_data_types:CML_QOS_COLOR_TYPE_T;
                            description "";
                        } // END of colorExpEncap definition.


                        leaf l2ProfileMapExp  {
                            type  cml_data_types:CML_UINT8_T {
                                 range "0..7";
                            }
                            mandatory true;
                            description "";
                        } // END of l2ProfileMapExp definition.


                    } // End of colorToExpProfileMapTree-list
                } // End of queueToExpProfileMapTree-list
            } // End of expEncapProfileMapList-list

            list qosRemark {
                key "qosRemarkType";
                description
                    "enable/disable qos (cos/dei/dscp) remark";
                leaf qosRemarkType  {
                    type  cml_data_types:CML_QOS_REMARK_TYPE_T;
                    description "";
                } // END of qosRemarkType definition.


            } // End of qosRemark-list

            list classDepMatchAny {
                key "name";
                description
                    "class default queue mapping structure in quality of service";
                leaf name  {
                    type  cml_data_types:CML_STRING_T {
                        length "0..255";
                    }
                    description "";
                } // END of name definition.


                leaf cmapType  {
                    type  cml_data_types:CML_QOS_CMAPDEF_TYPE_T;
                    description "";
                } // END of cmapType definition.


                leaf cmapMatchCriteria  {
                    type  cml_data_types:CML_CMAP_MATCH_ANY_CRITERIA_T;
                    description "";
                } // END of cmapMatchCriteria definition.


            } // End of classDepMatchAny-list

            list classMatchAnyMap {
                key "name";
                description
                    "match-any class-map for type qos";
                leaf name  {
                    type  cml_data_types:CML_STRING_T {
                        length "0..255";
                    }
                    description "";
                } // END of name definition.


                leaf cmapType  {
                    type  cml_data_types:CML_QOS_CMAP_QOS_TYPE_T;
                    description "";
                } // END of cmapType definition.


                leaf cmapMatchCriteria  {
                    type  cml_data_types:CML_CMAP_MATCH_ANY_CRITERIA_T;
                    description "";
                } // END of cmapMatchCriteria definition.


                leaf aclName  {
                    type  cml_data_types:CML_STRING_T {
                        length "0..255";
                    }
                    description "";
                } // END of aclName definition.


                leaf etherType  {
                    type  cml_data_types:CML_RANGE_T {
                        length "0..255";
                    }
                    description "";
                } // END of etherType definition.



                list cos {
                    key "cos";
                    description
                        "cos structure in quality of service";
                    leaf matchType  {
                        type  cml_data_types:CML_HQOS_MATCH_NOT_T;
                        mandatory true;
                        description "";
                    } // END of matchType definition.


                    leaf cos  {
                        type  cml_data_types:CML_RANGE_T {
                            length "1..255";
                        }
                        description "";
                    } // END of cos definition.


                } // End of cos-list

                list cosInner {
                    key "cos";
                    description
                        "cos inner structure in quality of service";
                    leaf innerType  {
                        type  cml_data_types:CML_HQOS_MATCH_NOT_T;
                        mandatory true;
                        description "";
                    } // END of innerType definition.


                    leaf cos  {
                        type  cml_data_types:CML_RANGE_T {
                            length "1..255";
                        }
                        description "";
                    } // END of cos definition.


                } // End of cosInner-list

                list cmapRtp {
                    key "rtp";
                    description
                        "match rtp structure in quality of service";
                    leaf rtpType  {
                        type  cml_data_types:CML_HQOS_MATCH_NOT_RTP_T;
                        mandatory true;
                        description "";
                    } // END of rtpType definition.


                    leaf rtp  {
                        type  cml_data_types:CML_RANGE_T {
                            length "1..255";
                        }
                        description "";
                    } // END of rtp definition.


                } // End of cmapRtp-list

                list vlan {
                    key "vlan";
                    description
                        "vlan configuration in quality of service";
                    leaf vlanType  {
                        type  cml_data_types:CML_HQOS_MATCH_NOT_VLAN_T;
                        mandatory true;
                        description "";
                    } // END of vlanType definition.


                    leaf vlan  {
                        type  cml_data_types:CML_RANGE_T {
                            length "1..255";
                        }
                        description "";
                    } // END of vlan definition.


                } // End of vlan-list

                list vlanInner {
                    key "vlanInner";
                    description
                        "inner vlan structure in quality of service";
                    leaf vlanInnerType  {
                        type  cml_data_types:CML_HQOS_MATCH_NOT_VLAN_T;
                        mandatory true;
                        description "";
                    } // END of vlanInnerType definition.


                    leaf vlanInner  {
                        type  cml_data_types:CML_RANGE_T {
                            length "1..255";
                        }
                        description "";
                    } // END of vlanInner definition.


                } // End of vlanInner-list

                list cmapExp {
                    if-feature feature_list:HAVE_DIFFSERV;
                    key "exp";
                    description
                        "mpls exp structure in quality of service";
                    leaf expType  {
                        type  cml_data_types:CML_HQOS_MATCH_NOT_MPLS_EXP_T;
                        mandatory true;
                        description "";
                    } // END of expType definition.


                    leaf exp  {
                        type  cml_data_types:CML_RANGE_T {
                            length "1..255";
                        }
                        description "";
                    } // END of exp definition.


                } // End of cmapExp-list

                list cmapTrafficType {
                    key "trafficType";
                    description
                        "cmap traffic-type information";
                    leaf negate  {
                        type  cml_data_types:CML_HQOS_TRAFFIC_TYPE_NOT_T;
                        mandatory true;
                        description "";
                    } // END of negate definition.


                    leaf trafficType  {
                        type  cml_data_types:CML_HQOS_TRAFFIC_TYPE_T;
                        description "";
                    } // END of trafficType definition.


                } // End of cmapTrafficType-list

                list cmapDscp {
                    key "dscp";
                    description
                        "cmap dscp structure in quality of service";
                    leaf dscpType  {
                        type  cml_data_types:CML_HQOS_MATCH_NOT_DSCP_T;
                        mandatory true;
                        description "";
                    } // END of dscpType definition.


                    leaf dscp  {
                        type  cml_data_types:CML_QOS_DSCP_VAL_T {
                            length "1..255";
                        }
                        description "";
                    } // END of dscp definition.


                } // End of cmapDscp-list

                list cmapIpPrec {
                    key "precedence";
                    description
                        "ip precedence structure in quality of service";
                    leaf precedenceType  {
                        type  cml_data_types:CML_HQOS_MATCH_NOT_PRECEDENCE_T;
                        mandatory true;
                        description "";
                    } // END of precedenceType definition.


                    leaf precedence  {
                        type  cml_data_types:CML_QOS_PREC_VAL_T {
                            length "1..255";
                        }
                        description "";
                    } // END of precedence definition.


                } // End of cmapIpPrec-list

                list layer4 {
                    key "layer4";
                    description
                        "layer4 configuration in quality of service";
                    leaf layer4Type  {
                        type  cml_data_types:CML_HQOS_MATCH_NOT_LAYER4_T;
                        mandatory true;
                        description "";
                    } // END of layer4Type definition.


                    leaf protocolType  {
                        type  cml_data_types:CML_HQOS_LAYER4_PROTOCOL_T;
                        mandatory true;
                        description "";
                    } // END of protocolType definition.


                    leaf portType  {
                        type  cml_data_types:CML_HQOS_LAYER4_PORT_T;
                        mandatory true;
                        description "";
                    } // END of portType definition.


                    leaf layer4  {
                        type  cml_data_types:CML_RANGE_T {
                            length "1..255";
                        }
                        description "";
                    } // END of layer4 definition.


                } // End of layer4-list
            } // End of classMatchAnyMap-list

            list classQosMap {
                key "name";
                description
                    "match-all class-map of type qos";
                leaf name  {
                    type  cml_data_types:CML_STRING_T {
                        length "0..255";
                    }
                    description "";
                } // END of name definition.


                leaf cmapType  {
                    type  cml_data_types:CML_QOS_CMAP_QOS_TYPE_T;
                    description "";
                } // END of cmapType definition.


                leaf cmapMatchCriteria  {
                    type  cml_data_types:CML_CMAP_MATCH_CRITERIA_T;
                    description "";
                } // END of cmapMatchCriteria definition.


                leaf priority  {
                    type  cml_data_types:CML_UINT8_T;
                    description "";
                } // END of priority definition.


                leaf cmapMatchId  {
                    type  cml_data_types:CML_UINT16_T;
                    description "";
                } // END of cmapMatchId definition.


                leaf matchCount  {
                    type  cml_data_types:CML_UINT16_T;
                    description "";
                } // END of matchCount definition.


                leaf cmapMatchSet  {
                    type  cml_data_types:CML_UINT8_T;
                    description "";
                } // END of cmapMatchSet definition.


                leaf matchAclCount  {
                    type  cml_data_types:CML_UINT16_T;
                    description "";
                } // END of matchAclCount definition.


                leaf aclNameSet  {
                    type  cml_data_types:CML_STRING_T {
                        length "0..255";
                    }
                    config false;
                    description "";
                } // END of aclNameSet definition.


                leaf srcMac  {
                    type  cml_data_types:CML_INT8_T;
                    config false;
                    description "";
                } // END of srcMac definition.


                leaf dstMac  {
                    type  cml_data_types:CML_INT8_T;
                    config false;
                    description "";
                } // END of dstMac definition.


                leaf trafficNum  {
                    if-feature feature_list:HAVE_CUSTOM1_QOS;
                    type  cml_data_types:CML_INT8_T;
                    config false;
                    description "";
                } // END of trafficNum definition.


                leaf aclName  {
                    type  cml_data_types:CML_STRING_T {
                        length "0..255";
                    }
                    description "";
                } // END of aclName definition.


                leaf cosMatch  {
                    if-feature feature_list:HAVE_FLEXPORT;
                    if-feature feature_list:HAVE_SERVICE_QUEUING_1;
                    type  cml_data_types:CML_RANGE_T {
                        length "1..255";
                    }
                    description "";
                } // END of cosMatch definition.


                leaf vlanMatch  {
                    if-feature feature_list:HAVE_FLEXPORT;
                    if-feature feature_list:HAVE_SERVICE_QUEUING_1;
                    type  cml_data_types:CML_INT32_T {
                         range "1..4094";
                    }
                    description "";
                } // END of vlanMatch definition.


                leaf etherType  {
                    type  cml_data_types:CML_RANGE_T {
                        length "0..255";
                    }
                    description "";
                } // END of etherType definition.


                leaf negate  {
                    type  cml_data_types:CML_HQOS_TRAFFIC_TYPE_NOT_T;
                    description "";
                } // END of negate definition.


                leaf trafficType  {
                    type  cml_data_types:CML_HQOS_TRAFFIC_TYPE_T;
                    description "";
                } // END of trafficType definition.


                leaf-list ethertypeList  {
                    type  cml_data_types:CML_STRING_T {
                        length "0..255";
                    }
                    description "";
                } // END of ethertypeList definition.


                container trust {
                    config false;
                    description
                        "trust structure in quality of service";
                    leaf cosDscpPrecInd  {
                        type  cml_data_types:CML_INT8_T;
                        description "";
                    } // END of cosDscpPrecInd definition.


                } // END of trust-container definition.
                container qosGrp {
                    description
                        "qos group match structure in quality of service";
                    leaf flag  {
                        type  cml_data_types:CML_UINT32_T;
                        description "";
                    } // END of flag definition.


                    leaf num  {
                        if-feature feature_list:HAVE_CUSTOM1_QOS;
                        type  cml_data_types:CML_UINT32_T {
                             range "1..2000";
                        }
                        description "";
                    } // END of num definition.


                    leaf-list cmapQosGroup  {
                        type  cml_data_types:CML_UINT8_T;
                        description "";
                    } // END of cmapQosGroup definition.


                } // END of qosGrp-container definition.
                container cos {
                    description
                        "cos structure in quality of service";
                    leaf num  {
                        type  cml_data_types:CML_UINT32_T;
                        config false;
                        description "";
                    } // END of num definition.


                    leaf matchType  {
                        type  cml_data_types:CML_HQOS_MATCH_NOT_T;
                        description "";
                    } // END of matchType definition.


                    leaf cos  {
                        type  cml_data_types:CML_RANGE_T {
                            length "0..255";
                        }
                        description "";
                    } // END of cos definition.


                } // END of cos-container definition.
                container cosInner {
                    description
                        "cos inner structure in quality of service";
                    leaf num  {
                        type  cml_data_types:CML_UINT32_T;
                        config false;
                        description "";
                    } // END of num definition.


                    leaf innerType  {
                        type  cml_data_types:CML_HQOS_MATCH_NOT_T;
                        description "";
                    } // END of innerType definition.


                    leaf cos  {
                        type  cml_data_types:CML_RANGE_T {
                            length "0..255";
                        }
                        description "";
                    } // END of cos definition.


                } // END of cosInner-container definition.
                container cmapDscp {
                    description
                        "cmap dscp structure in quality of service";
                    leaf num  {
                        type  cml_data_types:CML_INT8_T;
                        config false;
                        description "";
                    } // END of num definition.


                    leaf dscpType  {
                        type  cml_data_types:CML_HQOS_MATCH_NOT_DSCP_T;
                        description "";
                    } // END of dscpType definition.


                    leaf dscp  {
                        type  cml_data_types:CML_QOS_DSCP_VAL_T {
                            length "0..255";
                        }
                        description "";
                    } // END of dscp definition.


                    leaf ipv6Num  {
                        type  cml_data_types:CML_INT8_T;
                        description "";
                    } // END of ipv6Num definition.


                } // END of cmapDscp-container definition.
                container cmapIpPrec {
                    description
                        "ip precedence structure in quality of service";
                    leaf num  {
                        type  cml_data_types:CML_INT8_T;
                        config false;
                        description "";
                    } // END of num definition.


                    leaf precedenceType  {
                        type  cml_data_types:CML_HQOS_MATCH_NOT_PRECEDENCE_T;
                        description "";
                    } // END of precedenceType definition.


                    leaf precedence  {
                        type  cml_data_types:CML_QOS_PREC_VAL_T {
                            length "0..255";
                        }
                        description "";
                    } // END of precedence definition.


                } // END of cmapIpPrec-container definition.
                container cmapRtp {
                    description
                        "match rtp structure in quality of service";
                    leaf num  {
                        type  cml_data_types:CML_INT8_T;
                        config false;
                        description "";
                    } // END of num definition.


                    leaf rtpType  {
                        type  cml_data_types:CML_HQOS_MATCH_NOT_RTP_T;
                        description "";
                    } // END of rtpType definition.


                    leaf rtp  {
                        type  cml_data_types:CML_RANGE_T {
                            length "0..255";
                        }
                        description "";
                    } // END of rtp definition.


                } // END of cmapRtp-container definition.
                container vlan {
                    description
                        "vlan configuration in quality of service";
                    leaf vlanType  {
                        type  cml_data_types:CML_HQOS_MATCH_NOT_VLAN_T;
                        description "";
                    } // END of vlanType definition.


                    leaf vlan  {
                        type  cml_data_types:CML_RANGE_T {
                            length "0..255";
                        }
                        description "";
                    } // END of vlan definition.


                } // END of vlan-container definition.
                container vlanInner {
                    description
                        "inner vlan structure in quality of service";
                    leaf vlanInnerType  {
                        type  cml_data_types:CML_HQOS_MATCH_NOT_VLAN_T;
                        description "";
                    } // END of vlanInnerType definition.


                    leaf vlanInner  {
                        type  cml_data_types:CML_RANGE_T {
                            length "0..255";
                        }
                        description "";
                    } // END of vlanInner definition.


                } // END of vlanInner-container definition.
                container cmapExp {
                    if-feature feature_list:HAVE_DIFFSERV;
                    description
                        "mpls exp structure in quality of service";
                    leaf expType  {
                        type  cml_data_types:CML_HQOS_MATCH_NOT_MPLS_EXP_T;
                        description "";
                    } // END of expType definition.


                    leaf exp  {
                        type  cml_data_types:CML_STRING_T {
                            length "0..255";
                        }
                        description "";
                    } // END of exp definition.


                } // END of cmapExp-container definition.
                container layer4 {
                    description
                        "layer4 configuration in quality of service";
                    leaf layer4Type  {
                        type  cml_data_types:CML_HQOS_MATCH_NOT_LAYER4_T;
                        description "";
                    } // END of layer4Type definition.


                    leaf protocolType  {
                        type  cml_data_types:CML_HQOS_LAYER4_PROTOCOL_T;
                        description "";
                    } // END of protocolType definition.


                    leaf portType  {
                        type  cml_data_types:CML_HQOS_LAYER4_PORT_T;
                        description "";
                    } // END of portType definition.


                    leaf layer4  {
                        type  cml_data_types:CML_RANGE_T {
                            length "0..255";
                        }
                        description "";
                    } // END of layer4 definition.


                } // END of layer4-container definition.
            } // End of classQosMap-list

            list classMapQueuing {
                if-feature feature_list:HAVE_SERVICE_QUEUING_2;
                key "cmapName";
                description
                    "match-any class-map of type queuing";
                leaf cmapQueuingType  {
                    type  cml_data_types:CML_QOS_CMAP_QUEUING_TYPE_T;
                    mandatory true;
                    description "";
                } // END of cmapQueuingType definition.


                leaf cmapName  {
                    type  cml_data_types:CML_STRING_T {
                        length "1..32";
                    }
                    description "";
                } // END of cmapName definition.



                list matchQueue {
                    if-feature feature_list:HAVE_SERVICE_QUEUING_2;
                    key "matchQueueNumber";
                    description
                        "match type queue";
                    leaf matchQueueNumber  {
                        type  cml_data_types:CML_INT8_T {
                             range "0..7";
                        }
                        description "";
                    } // END of matchQueueNumber definition.


                } // End of matchQueue-list
                container matchService {
                    if-feature feature_list:HAVE_SERVICE_QUEUING_2;
                    description
                        "match type service-template";
                    leaf serviceTemplateName  {
                        type  cml_data_types:CML_STRING_T {
                            length "0..255";
                        }
                        description "";
                    } // END of serviceTemplateName definition.


                } // END of matchService-container definition.
                container matchInterface {
                    if-feature feature_list:HAVE_SERVICE_QUEUING_2;
                    description
                        "match type interface";
                    leaf interfaceName  {
                        type  cml_data_types:CML_STRING_T {
                            length "0..255";
                        }
                        description "";
                    } // END of interfaceName definition.


                } // END of matchInterface-container definition.
                container matchVlan {
                    if-feature feature_list:HAVE_SERVICE_QUEUING_2;
                    description
                        "match type vlan";
                    leaf vlanId  {
                        type  cml_data_types:CML_INT32_T {
                             range "1..4094";
                        }
                        description "";
                    } // END of vlanId definition.


                } // END of matchVlan-container definition.
            } // End of classMapQueuing-list

            list pmap {
                key "pmapName";
                description
                    "pmap list in quality of service";
                leaf pmapName  {
                    type  cml_data_types:CML_STRING_T {
                        length "0..255";
                    }
                    description "";
                } // END of pmapName definition.


                leaf pmapType  {
                    type  cml_data_types:CML_PMAP_TYPE_T;
                    description "";
                } // END of pmapType definition.


                leaf aclName  {
                    type  cml_data_types:CML_STRING_T {
                        length "0..255";
                    }
                    description "";
                } // END of aclName definition.


                leaf aclAttached  {
                    type  cml_data_types:CML_UINT8_T;
                    description "";
                } // END of aclAttached definition.


                leaf numAclsAttached  {
                    type  cml_data_types:CML_INT32_T;
                    description "";
                } // END of numAclsAttached definition.


                leaf defaultClassAttach  {
                    type  cml_data_types:CML_INT8_T;
                    description "";
                } // END of defaultClassAttach definition.


                leaf seqNum  {
                    type  cml_data_types:CML_INT16_T;
                    description "";
                } // END of seqNum definition.


                leaf cmapCount  {
                    type  cml_data_types:CML_INT16_T;
                    description "";
                } // END of cmapCount definition.


                leaf attached  {
                    type  cml_data_types:CML_INT32_T;
                    description "";
                } // END of attached definition.


                leaf-list clName  {
                    type  cml_data_types:CML_STRING_T {
                        length "0..255";
                    }
                    description "";
                } // END of clName definition.


                leaf queuingFlag  {
                    type  cml_data_types:CML_INT8_T;
                    description "";
                } // END of queuingFlag definition.


                leaf bandwidthMax  {
                    type  cml_data_types:CML_INT32_T;
                    description "";
                } // END of bandwidthMax definition.


                leaf shapeMax  {
                    type  cml_data_types:CML_INT32_T;
                    description "";
                } // END of shapeMax definition.


                leaf bandwidthRemaining  {
                    type  cml_data_types:CML_INT32_T;
                    description "";
                } // END of bandwidthRemaining definition.


                leaf bandwidthRemFlag  {
                    type  cml_data_types:CML_INT8_T;
                    description "";
                } // END of bandwidthRemFlag definition.


                leaf bandwidthRateType  {
                    type  cml_data_types:CML_INT8_T;
                    description "";
                } // END of bandwidthRateType definition.


                leaf shapeRateType  {
                    type  cml_data_types:CML_INT8_T;
                    description "";
                } // END of shapeRateType definition.


                leaf bandwidthRefCount  {
                    type  cml_data_types:CML_INT8_T;
                    description "";
                } // END of bandwidthRefCount definition.


                leaf shapeRefCount  {
                    type  cml_data_types:CML_INT8_T;
                    description "";
                } // END of shapeRefCount definition.


                leaf bandwidthTotal  {
                    type  cml_data_types:CML_INT32_T;
                    description "";
                } // END of bandwidthTotal definition.


                leaf thresholdRefCount  {
                    type  cml_data_types:CML_INT8_T;
                    description "";
                } // END of thresholdRefCount definition.


                leaf thresholdType  {
                    type  cml_data_types:CML_INT8_T;
                    description "";
                } // END of thresholdType definition.


                leaf matchNotProto  {
                    type  cml_data_types:CML_INT8_T;
                    description "";
                } // END of matchNotProto definition.


                leaf priorityCount  {
                    type  cml_data_types:CML_INT8_T;
                    description "";
                } // END of priorityCount definition.


                leaf servicePolicyAttach  {
                    type  cml_data_types:CML_INT8_T;
                    description "";
                } // END of servicePolicyAttach definition.


                leaf schedQueBmp  {
                    type  cml_data_types:CML_INT8_T;
                    description "";
                } // END of schedQueBmp definition.


                leaf servicePolicyCount  {
                    type  cml_data_types:CML_INT32_T;
                    description "";
                } // END of servicePolicyCount definition.


                leaf policerCount  {
                    type  cml_data_types:CML_INT8_T;
                    description "";
                } // END of policerCount definition.


                leaf noUpdate  {
                    type  cml_data_types:CML_INT8_T;
                    description "";
                } // END of noUpdate definition.



                list cmapTree {
                    key "cmapName";
                    description
                        "Applying class on policy structure in quality of service";
                    leaf cmapName  {
                        type  cml_data_types:CML_STRING_T {
                            length "0..255";
                        }
                        description "";
                    } // END of cmapName definition.


                    leaf cmapId  {
                        type  cml_data_types:CML_PMAP_TYPE_T;
                        description "";
                    } // END of cmapId definition.


                    leaf userCfgPriority  {
                        type  cml_data_types:CML_INT16_T {
                             range "1..1000";
                        }
                        description "";
                    } // END of userCfgPriority definition.


                    leaf aggrePolice  {
                        if-feature feature_list:HAVE_EXTENDED_QOS;
                        type  cml_data_types:CML_STRING_T {
                            length "0..255";
                        }
                        description "";
                    } // END of aggrePolice definition.


                    leaf mode  {
                        if-feature feature_list:NOT_HAVE_CUSTOM2_QOS;
                        type  cml_data_types:CML_QOS_MODE_TYPE_T;
                        description "";
                    } // END of mode definition.


                    leaf servicePolicyQos  {
                        type  cml_data_types:CML_STRING_T {
                            length "0..255";
                        }
                        description "";
                    } // END of servicePolicyQos definition.


                    container police {
                        description
                            "police structure of quality of service";
                        leaf policeType  {
                            type  cml_data_types:CML_QOS_POLICE_TYPE_T;
                            description "";
                        } // END of policeType definition.


                        leaf cir  {
                            type  cml_data_types:CML_UINT32_T {
                                 range "1..720000000";
                            }
                            description "";
                        } // END of cir definition.


                        leaf cirType  {
                            type  cml_data_types:CML_QOS_RATE_T;
                            description "";
                        } // END of cirType definition.


                        leaf eir  {
                            if-feature feature_list:HAVE_CUSTOM2_QOS;
                            type  cml_data_types:CML_UINT32_T {
                                 range "1..720000000";
                            }
                            description "";
                        } // END of eir definition.


                        leaf pir  {
                            if-feature feature_list:NOT_HAVE_CUSTOM2_QOS;
                            type  cml_data_types:CML_UINT32_T {
                                 range "1..2000000000";
                            }
                            description "";
                        } // END of pir definition.


                        leaf eirType  {
                            if-feature feature_list:HAVE_CUSTOM2_QOS;
                            type  cml_data_types:CML_QOS_RATE_T;
                            description "";
                        } // END of eirType definition.


                        leaf pirType  {
                            if-feature feature_list:NOT_HAVE_CUSTOM2_QOS;
                            type  cml_data_types:CML_QOS_RATE_T;
                            description "";
                        } // END of pirType definition.


                        leaf burst  {
                            type  cml_data_types:CML_UINT32_T {
                                 range "1..4161";
                            }
                            description "";
                        } // END of burst definition.


                        leaf bcType  {
                            type  cml_data_types:CML_BURST_TYPE_T;
                            description "";
                        } // END of bcType definition.


                        leaf excessBurst  {
                            type  cml_data_types:CML_UINT32_T {
                                 range "1..4161";
                            }
                            description "";
                        } // END of excessBurst definition.


                        leaf beType  {
                            type  cml_data_types:CML_BURST_TYPE_T;
                            description "";
                        } // END of beType definition.


                        leaf confPoliceVal  {
                            if-feature feature_list:NOT_HAVE_CUSTOM2_QOS;
                            type  cml_data_types:CML_INT32_T;
                            description "";
                        } // END of confPoliceVal definition.


                        leaf confAct  {
                            if-feature feature_list:NOT_HAVE_CUSTOM2_QOS;
                            type  cml_data_types:CML_CONFORM_ACTION_T;
                            description "";
                        } // END of confAct definition.


                        leaf policeDscp  {
                            if-feature feature_list:NOT_HAVE_CUSTOM2_QOS;
                            type  cml_data_types:CML_INT32_T;
                            description "";
                        } // END of policeDscp definition.


                        leaf exdAct  {
                            if-feature feature_list:NOT_HAVE_CUSTOM2_QOS;
                            type  cml_data_types:CML_EXCEED_ACTION_T;
                            description "";
                        } // END of exdAct definition.


                        leaf votPoliceVal  {
                            if-feature feature_list:NOT_HAVE_CUSTOM2_QOS;
                            type  cml_data_types:CML_INT32_T;
                            description "";
                        } // END of votPoliceVal definition.


                        leaf votAct  {
                            if-feature feature_list:NOT_HAVE_CUSTOM2_QOS;
                            type  cml_data_types:CML_VIOLATE_ACTION_T;
                            description "";
                        } // END of votAct definition.


                    } // END of police-container definition.
                    container setS {
                        description
                            "setting class on policy structure in quality of service";
                        leaf ifIndex  {
                            type  cml_data_types:CML_INT8_T;
                            config false;
                            description "";
                        } // END of ifIndex definition.


                        leaf qosGroupId  {
                            if-feature feature_list:HAVE_QOS;
                            type  cml_data_types:CML_INT8_T;
                            config false;
                            description "";
                        } // END of qosGroupId definition.


                        leaf level  {
                            if-feature feature_list:HAVE_CUSTOM1_QOS;
                            type  cml_data_types:CML_EMPTY_T;
                            description "";
                        } // END of level definition.


                        leaf setCosValue  {
                            type  cml_data_types:CML_UINT8_T {
                                 range "0..7";
                            }
                            description "";
                        } // END of setCosValue definition.


                        leaf setDscpValue  {
                            type  cml_data_types:CML_QOS_SET_DSCP_VAL_T;
                            description "";
                        } // END of setDscpValue definition.


                        leaf setPrecValue  {
                            type  cml_data_types:CML_QOS_SET_PREC_VAL_T;
                            description "";
                        } // END of setPrecValue definition.


                        leaf setQueueValue  {
                            type  cml_data_types:CML_UINT8_T {
                                 range "0..7";
                            }
                            description "";
                        } // END of setQueueValue definition.


                        leaf portType  {
                            if-feature feature_list:HAVE_EXTENDED_QOS;
                            if-feature feature_list:NOT_HAVE_CUSTOM2_QOS;
                            type  cml_data_types:CML_REDIRECT_MIRROR_PORT_T;
                            description "";
                        } // END of portType definition.


                        leaf ifName  {
                            if-feature feature_list:HAVE_EXTENDED_QOS;
                            if-feature feature_list:NOT_HAVE_CUSTOM2_QOS;
                            type  cml_data_types:CML_STRING_T {
                                length "0..255";
                            }
                            description "";
                        } // END of ifName definition.


                        leaf vlanRange  {
                            if-feature feature_list:NOT_HAVE_CUSTOM2_QOS;
                            type  cml_data_types:CML_UINT16_T {
                                 range "1..4094";
                            }
                            description "";
                        } // END of vlanRange definition.


                        leaf cosRange  {
                            type  cml_data_types:CML_UINT16_T {
                                 range "0..7";
                            }
                            description "";
                        } // END of cosRange definition.


                    } // END of setS-container definition.
                    container nsmQosShape {
                        description
                            "qos shape structure in quality of service";
                        leaf rate  {
                            type  cml_data_types:CML_INT32_T {
                                 range "1..483000000";
                            }
                            description "";
                        } // END of rate definition.


                        leaf rateType  {
                            type  cml_data_types:CML_HQOS_SHAPE_TYPE_T;
                            description "";
                        } // END of rateType definition.


                        leaf inputRate  {
                            type  cml_data_types:CML_INT32_T;
                            description "";
                        } // END of inputRate definition.


                        leaf netShapeRate  {
                            type  cml_data_types:CML_INT32_T;
                            description "";
                        } // END of netShapeRate definition.


                    } // END of nsmQosShape-container definition.
                    container qosQueuing {
                        description
                            "qos queuing structure in quality of service";
                        leaf pqueueFlag  {
                            if-feature feature_list:HAVE_QOS;
                            type  cml_data_types:CML_UINT8_T;
                            config false;
                            description "";
                        } // END of pqueueFlag definition.


                        leaf flag  {
                            if-feature feature_list:HAVE_QOS;
                            type  cml_data_types:CML_INT32_T;
                            config false;
                            description "";
                        } // END of flag definition.


                        leaf CompensationValue  {
                            if-feature feature_list:HAVE_CUSTOM2_QOS;
                            type  cml_data_types:CML_INT32_T {
                                 range "-64..64";
                            }
                            description "";
                        } // END of CompensationValue definition.


                        leaf wredWeight  {
                            if-feature feature_list:HAVE_CUSTOM2_QOS;
                            type  cml_data_types:CML_INT8_T {
                                 range "0..31";
                            }
                            description "";
                        } // END of wredWeight definition.


                        leaf wrrSpFlag  {
                            if-feature feature_list:NOT_HAVE_CUSTOM2_QOS;
                            type  cml_data_types:CML_QOS_WRR_SP_T;
                            description "";
                        } // END of wrrSpFlag definition.


                        leaf wfqWeightValue  {
                            if-feature feature_list:HAVE_CUSTOM2_QOS;
                            type  cml_data_types:CML_INT8_T {
                                 range "1..63";
                            }
                            description "";
                        } // END of wfqWeightValue definition.


                        leaf spLevelValue  {
                            if-feature feature_list:HAVE_CUSTOM2_QOS;
                            type  cml_data_types:CML_INT8_T {
                                 range "0..7";
                            }
                            description "";
                        } // END of spLevelValue definition.


                        leaf servicePolicy  {
                            type  cml_data_types:CML_STRING_T {
                                length "0..255";
                            }
                            description "";
                        } // END of servicePolicy definition.



                        list qosWredList {
                            if-feature feature_list:HAVE_CUSTOM2_QOS;
                            key "wredColor";
                            description
                                "qos wred structure in quality of service";
                            leaf wredColor  {
                                type  cml_data_types:CML_QOS_COLOR_TYPE_T;
                                description "";
                            } // END of wredColor definition.


                            leaf minThreshold  {
                                type  cml_data_types:CML_INT32_T {
                                     range "1..629145600";
                                }
                                description "";
                            } // END of minThreshold definition.


                            leaf minType  {
                                type  cml_data_types:CML_HQOS_THRESHOLD_TYPE_T;
                                description "";
                            } // END of minType definition.


                            leaf maxThreshold  {
                                type  cml_data_types:CML_INT32_T {
                                     range "1..629145600";
                                }
                                description "";
                            } // END of maxThreshold definition.


                            leaf maxType  {
                                type  cml_data_types:CML_HQOS_THRESHOLD_TYPE_T;
                                description "";
                            } // END of maxType definition.


                            leaf dropProb  {
                                type  cml_data_types:CML_INT32_T {
                                     range "1..100";
                                }
                                description "";
                            } // END of dropProb definition.


                        } // End of qosWredList-list
                        container qosWred {
                            if-feature feature_list:NOT_HAVE_CUSTOM2_QOS;
                            description
                                "qos wred structure in quality of service";
                            leaf minThreshold  {
                                type  cml_data_types:CML_INT32_T {
                                     range "1..524288";
                                }
                                description "";
                            } // END of minThreshold definition.


                            leaf maxThreshold  {
                                type  cml_data_types:CML_INT32_T {
                                     range "1..524288";
                                }
                                description "";
                            } // END of maxThreshold definition.


                            leaf dropProb  {
                                type  cml_data_types:CML_INT32_T {
                                     range "1..100";
                                }
                                description "";
                            } // END of dropProb definition.


                            leaf minThresholdYp  {
                                type  cml_data_types:CML_INT32_T {
                                     range "1..524288";
                                }
                                description "";
                            } // END of minThresholdYp definition.


                            leaf maxThresholdYp  {
                                type  cml_data_types:CML_INT32_T {
                                     range "1..524288";
                                }
                                description "";
                            } // END of maxThresholdYp definition.


                            leaf dropProbYp  {
                                type  cml_data_types:CML_INT32_T {
                                     range "1..100";
                                }
                                description "";
                            } // END of dropProbYp definition.


                            leaf minThresholdRp  {
                                type  cml_data_types:CML_INT32_T {
                                     range "1..524288";
                                }
                                description "";
                            } // END of minThresholdRp definition.


                            leaf maxThresholdRp  {
                                type  cml_data_types:CML_INT32_T {
                                     range "1..524288";
                                }
                                description "";
                            } // END of maxThresholdRp definition.


                            leaf dropProbRp  {
                                type  cml_data_types:CML_INT32_T;
                                description "";
                            } // END of dropProbRp definition.


                            leaf wredExpWeight  {
                                type  cml_data_types:CML_INT8_T {
                                     range "0..15";
                                }
                                description "";
                            } // END of wredExpWeight definition.


                            leaf minType  {
                                type  cml_data_types:CML_HQOS_THRESHOLD_TYPE_T;
                                description "";
                            } // END of minType definition.


                            leaf maxType  {
                                type  cml_data_types:CML_HQOS_THRESHOLD_TYPE_T;
                                description "";
                            } // END of maxType definition.


                            leaf minTypeYp  {
                                type  cml_data_types:CML_HQOS_THRESHOLD_TYPE_T;
                                description "";
                            } // END of minTypeYp definition.


                            leaf maxTypeYp  {
                                type  cml_data_types:CML_HQOS_THRESHOLD_TYPE_T;
                                description "";
                            } // END of maxTypeYp definition.


                            leaf minTypeRp  {
                                type  cml_data_types:CML_HQOS_THRESHOLD_TYPE_T;
                                description "";
                            } // END of minTypeRp definition.


                            leaf maxTypeRp  {
                                type  cml_data_types:CML_HQOS_THRESHOLD_TYPE_T;
                                description "";
                            } // END of maxTypeRp definition.


                            leaf-list cos  {
                                type  cml_data_types:CML_INT8_T;
                                description "";
                            } // END of cos definition.


                        } // END of qosWred-container definition.
                        container tailDrop {
                            description
                                "tail drop structure in quality of service";
                            leaf cos  {
                                type  cml_data_types:CML_INT32_T;
                                description "";
                            } // END of cos definition.


                            leaf maxThreshold  {
                                type  cml_data_types:CML_INT32_T {
                                     range "1..629145600";
                                }
                                description "";
                            } // END of maxThreshold definition.


                            leaf maxTypeTailDrop  {
                                type  cml_data_types:CML_HQOS_THRESHOLD_TYPE_T;
                                description "";
                            } // END of maxTypeTailDrop definition.


                        } // END of tailDrop-container definition.
                        container qosBandwidth {
                            description
                                "qos bandwidth structure in quality of service";
                            leaf inputRate  {
                                type  cml_data_types:CML_INT32_T;
                                description "";
                            } // END of inputRate definition.


                            leaf rate  {
                                type  cml_data_types:CML_INT32_T {
                                     range "1..1000000000";
                                }
                                description "";
                            } // END of rate definition.


                            leaf rateType  {
                                type  cml_data_types:CML_HQOS_SHAPE_TYPE_T;
                                description "";
                            } // END of rateType definition.


                        } // END of qosBandwidth-container definition.
                    } // END of qosQueuing-container definition.
                } // End of cmapTree-list

                list protoCmapl {
                    key "name";
                    description
                        "nsm cmap list in quality of service";
                    leaf name  {
                        type  cml_data_types:CML_STRING_T {
                            length "0..255";
                        }
                        description "";
                    } // END of name definition.


                } // End of protoCmapl-list
            } // End of pmap-list
            container wrrMode {
                if-feature feature_list:HAVE_SERVICE_QUEUING_1;
                description
                    "Weighted Round Robin Mode";
                leaf weightedRound  {
                    type  cml_data_types:CML_INT32_T {
                         range "1..127";
                    }
                    description "";
                } // END of weightedRound definition.


                leaf nonUnicastQueues  {
                    type  cml_data_types:CML_INT32_T {
                         range "1..127";
                    }
                    description "";
                } // END of nonUnicastQueues definition.


                leaf sp  {
                    type  cml_data_types:CML_BOOL_T;
                    description "";
                } // END of sp definition.


            } // END of wrrMode-container definition.
            container redDropValue {
                if-feature feature_list:HAVE_CUSTOM2_QOS;
                description
                    "enable/disable redDrop";
                leaf redDropSet  {
                    type  cml_data_types:CML_BOOL_T;
                    description "";
                } // END of redDropSet definition.


            } // END of redDropValue-container definition.
        } // END of qosGlobal-container definition.
    } // END of qos-container definition.
    } // END of qos-container definition.


}
