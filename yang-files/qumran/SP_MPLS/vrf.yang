/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : vrf.yang
*
*/

module vrf {

    namespace   "http://www.ipinfusion.com/yang/ocnos/vrf";

    prefix "vrf";

    import ietf-inet-types {
        prefix inet;
    }

    import cml-data-types {
        prefix cml-data-types;
    }

    import vr {
        prefix vr;
    }

    import feature-list {
        prefix feature-list;
    }

    organization
        "IP Infusion Inc.";

    contact
        "Address: 3965 Freedom Circle, Suite 200, Santa Clara, CA 95054
         Phone: +1 408-400-1900
         E-mail: support@ipinfusion.com
         Web: http://www.ipinfusion.com/";

    description
        "VPN Routing/Forwarding";


    revision "2018-06-21" {
        description " Initial Version.";
        reference "Initial Version";
    }



    grouping vrf-grouping {
    description
        "vrf";
        list vrf {
            key "vrfName";
            description
                "vrf";
            leaf vrfName  {
                type  string {
                    length "1..32";
                }
                description "";
            } // END of vrfName definition.

            leaf macVrf  {
                if-feature feature-list:HAVE_BGP_EVPN;
                type  boolean;
                description "";
            } // END of macVrf definition.

            leaf vrfId  {
                type  uint32;
                config false;
                description "";
            } // END of vrfId definition.

            leaf fibId  {
                type  uint8;
                config false;
                description "";
            } // END of fibId definition.

            leaf description  {
                type  cml-data-types:CML_LINE_T;
                description "";
            } // END of description definition.

            leaf routerId  {
                type  inet:ipv4-address;
                description "vrf router id";
            } // END of routerId definition.

        } // End of vrf-list
    } // END of vrf-grouping definition.

    augment /vr:vr {
        description
            "vrf";
        uses vrf-grouping;
    }

    
rpc clear-default-router-id {
  description "";
}
    
rpc clear-router-id-vrf {
  description "";
        input  {
            leaf vrfName  {
                type string;

                mandatory true;
                description "";
            }
        }
}

}
