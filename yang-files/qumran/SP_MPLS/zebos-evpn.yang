/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-evpn.yang
*
*/

submodule zebos-evpn {

    belongs-to  zebos { prefix zebos; }

    import cml_data_types {
        prefix cml_data_types;
    }

    import feature_list {
        prefix feature_list;
    }

    organization
        "IP Infusion Inc.";

    contact
        "Address: 3965 Freedom Circle, Suite 200, Santa Clara, CA 95054
         Phone: +1 408-400-1900
         E-mail: support@ipinfusion.com
         Web: http://www.ipinfusion.com/";

    description
        "";


    revision "2018-12-28" {
        description " Initial Version.";
        reference "";
    }


    grouping  multihoming-grouping {
    description
        "evpn multihoming enable";
    container multihoming {
        if-feature feature_list:HAVE_NVO;
        description
            "evpn multihoming enable";
        leaf mutihomingEnable  {
            type  cml_data_types:CML_BOOL_T;
            default false;
            description "Enable EVPN multihoming";
        } // END of mutihomingEnable definition.


    } // END of multihoming-container definition.
    } // END of multihoming-container definition.

    grouping  evpn-service-type-grouping {
    description
        "EVPN Service Type";
    container evpn-service-type {
        description
            "EVPN Service Type";
        leaf service_type  {
            type  cml_data_types:CML_EVPN_SERVICE_TYPE_T;
            description "Vlan-Based EVPN-Service Type";
        } // END of service_type definition.


    } // END of evpn-service-type-container definition.
    } // END of evpn-service-type-container definition.


}
