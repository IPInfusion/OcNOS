/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos.yang
*
*/

module zebos {

    yang-version   1;

    namespace   "http://www.ipinfusion.com/CMLSchema/zebos";

    prefix "zebos";

    import cml_data_types {
        prefix cml_data_types;
    }

    import feature_list {
        prefix feature_list;
    }

    include zebos-vr;
    include zebos-vrf;
    include zebos-interface;
    include zebos-broadcom;
    include zebos-vlan;
    include zebos-switchportinterface;
    include zebos-bridge;
    include zebos-mstp;
    include zebos-lacp;
    include zebos-lag;
    include zebos-lldpv2;
    include zebos-rib;
    include zebos-ospf;
    include zebos-ospfv3;
    include zebos-bgp;
    include zebos-oambfd;
    include zebos-vrrp;
    include zebos-plist;
    include zebos-isis;
    include zebos-keychain;
    include zebos-pim;
    include zebos-pim4;
    include zebos-vxlan;
    include zebos-syslog;
    include zebos-snmp;
    include zebos-featuredhcp;
    include zebos-radius;
    include zebos-tacacs;
    include zebos-usermgmt;
    include zebos-ssh;
    include zebos-telnet;
    include zebos-ntp;
    include zebos-aaa;
    include zebos-dhcpr;
    include zebos-dns;
    include zebos-dhcpc;
    include zebos-sflow;
    include zebos-libsyslog;
    include zebos-license;
    include zebos-pserv;
    include zebos-mrib4;
    include zebos-igmp;
    include zebos-igmpsnooping;
    include zebos-routemap;
    include zebos-pbrport;
    include zebos-libsnmp;
    include zebos-hqos;
    include zebos-cmm;
    include zebos-auth;
    include zebos-rip;
    include zebos-acl;
    include zebos-aclinterface;
    include zebos-nsmsnmp;
    include zebos-ras;
    include zebos-rpf;
    include zebos-linktrack;
    include zebos-pmirror;
    include zebos-hsl;
    include zebos-authradius;
    include zebos-ripng;
    include zebos-ndd;
    include zebos-vlog;
    include zebos-synce;
    include zebos-imi;
    include zebos-rtadv;
    include zebos-imiLogging;
    include zebos-nat;
    include zebos-erpsv2;
    include zebos-cfm;
    include zebos-ptp;
    include zebos-evpn;
    include zebos-customstats;
    include zebos-sysupdate;
    organization
        "IP Infusion Inc.";

    contact
        "Address: 3965 Freedom Circle, Suite 200, Santa Clara, CA 95054
         Phone: +1 408-400-1900
         E-mail: support@ipinfusion.com
         Web: http://www.ipinfusion.com/";

    description
        "ZebOS Managed Object";


    revision "2018-12-28" {
        description " Provider bridge static MAC support for Qumran platform.";
        reference "";
    }

    revision "2018-06-21" {
        description " Initial Version.";
        reference "";
    }


    uses ifArbiter-grouping;
    uses cpuInterface-grouping;
    uses hwTCAMutilization-grouping;
    uses lacpMaster-grouping;
    uses lacpdebug-grouping;
    uses lldpDebug-grouping;
    uses oamMpls-grouping;
    uses hostpSyslog-grouping;
    uses snmp-grouping;
    uses radiusDebug-grouping;
    uses debugTacacs-grouping;
    uses userDebug-grouping;
    uses debugSSHconfig-grouping;
    uses debugTELNETconfig-grouping;
    uses sourceNTP-grouping;
    uses debugNTP-grouping;
    uses AAAUserConfigs-grouping;
    uses console-grouping;
    uses debugAaa-grouping;
    uses dhcprelay-grouping;
    uses dhcprelay6-grouping;
    uses debugDns-grouping;
    uses sflow-grouping;
    uses debugsflow-grouping;
    uses ACLsFlow-grouping;
    uses log-grouping;
    uses licenseServer-grouping;
    uses pservd-grouping;
    uses cmmSoftwareProcessMgmt-grouping;
    uses igmpConfig-grouping;
    uses snmpTrap-grouping;
    uses debugAgentx-grouping;
    uses cmmGlobals-grouping;
    uses cmmDdm-grouping;
    uses cmmCpuLoadThresh-grouping;
    uses cmmCpuCoreThresh-grouping;
    uses cmmAlarmVariable-grouping;
    uses debugdot1x-grouping;
    uses logginghsl-grouping;
    uses logging-grouping;
    uses synceGlobals-grouping;
    uses synceDebug-grouping;
    uses loggingCli-grouping;
    uses memInfo-grouping;
    uses loggingcli-grouping;
    uses imiNatTimeouts-grouping;
    uses cfmGlobalConfig-grouping;
    uses installers-grouping;
    uses vr-grouping;
    uses bfdSession-grouping;
    uses confModeDebug-grouping;
    uses execModeDebug-grouping;
    uses rsyslog-grouping;
    uses radius-grouping;
    uses tacacs-grouping;
    uses usermgmt-grouping;
    uses sshVrfInstance-grouping;
    uses telnetVrfInstance-grouping;
    uses ntp-grouping;
    uses aaa-grouping;
    uses aaaAuthOptions-grouping;
    uses dhcprelayinterface-grouping;
    uses dhcp6nterface-grouping;
    uses dns-grouping;
    uses logginglevel-grouping;
    uses cmmSoftwareProcessObjects-grouping;
    uses cmmStackUnitTable-grouping;
    uses cmmTimeSyncClockTable-grouping;
    uses nsmsnmp-grouping;
    uses interfaceTrack-grouping;
    uses imiNatAddressPool-grouping;
    uses imi_rule_acl-grouping;
    uses imiRuleLocaladdr-grouping;
    uses imiRuleAclDestIn-grouping;
    uses imiRuleLocaladdrDestIn-grouping;
    uses imiRuleAclSrcOut-grouping;
    uses imiRuleLocaladdrSrcOut-grouping;
    uses imiRuleAclOutDest-grouping;
    uses imiRuleLocaladdrOutDest-grouping;
    uses imiRuleLocaladdrStatic-grouping;
    uses configurationErrorList-grouping;
    uses profile-information-grouping;
    uses dmProfileInformation-grouping;
    uses ptp-grouping;

    rpc vrf-clear-default-router-id {
        if-feature feature_list:HAVE_L3;
        description "";
        reference "";
        input  {
            leaf vrId  {
                type cml_data_types:CML_UINT32_T;

                mandatory true;
                description "";
            }
        }
    }

    rpc vrf-clear-router-id-vrf {
        if-feature feature_list:HAVE_VRF;
        description "";
        reference "";
        input  {
            leaf vrId  {
                type cml_data_types:CML_UINT32_T;

                mandatory true;
                description "";
            }
            leaf vrfName  {
                type cml_data_types:CML_STRING_T {
                    length "0..255";
                }

                mandatory true;
                description "";
            }
        }
    }

    rpc interface-clear-arp-cache {
        if-feature feature_list:HAVE_L3;
        description "";
        reference "";
        input  {
            leaf vrId  {
                type cml_data_types:CML_INT32_T;

                mandatory true;
                description "";
            }
        }
    }

    rpc interface-clear-ipv6-neighbors {
        if-feature feature_list:HAVE_L3;
        if-feature feature_list:HAVE_IPV6;
        description "";
        reference "";
        input  {
            leaf vrId  {
                type cml_data_types:CML_INT32_T;

                mandatory true;
                description "";
            }
        }
    }

    rpc interface-clear-interface-counter {
        description "";
        reference "";
        input  {
            leaf vrId  {
                type cml_data_types:CML_INT32_T;

                mandatory true;
                description "";
            }
            leaf ifName  {
                type cml_data_types:CML_STRING_T {
                    length "0..255";
                }

                mandatory true;
                description "";
            }
        }
    }

    rpc interface-clear-interface-cpu-counter {
        if-feature feature_list:HAVE_BROADCOM;
        description "";
        reference "";
        input  {
            leaf vrId  {
                type cml_data_types:CML_INT32_T;

                mandatory true;
                description "";
            }
        }
    }

    rpc interface-clear-interface-fec {
        description "";
        reference "";
        input  {
            leaf vrId  {
                type cml_data_types:CML_INT32_T;

                mandatory true;
                description "";
            }
            leaf ifName  {
                type cml_data_types:CML_STRING_T {
                    length "0..255";
                }

                mandatory true;
                description "";
            }
        }
    }

    rpc interface-clear-interface-error-disable {
        description "";
        reference "";
        input  {
            leaf vrId  {
                type cml_data_types:CML_INT32_T;

                mandatory true;
                description "";
            }
            leaf ifName  {
                type cml_data_types:CML_STRING_T {
                    length "0..255";
                }

                mandatory true;
                description "";
            }
        }
    }

    rpc interface-nsm-snmp-restart {
        if-feature feature_list:HAVE_SNMP;
        description "";
        reference "";
    }

    rpc interface-hardware-register-get {
        description "";
        reference "";
        input  {
            leaf address  {
                type cml_data_types:CML_STRING_T {
                    length "0..255";
                }

                mandatory true;
                description "";
            }
        }
    }

    rpc interface-hardware-register-set {
        description "";
        reference "";
        input  {
            leaf setAddress  {
                type cml_data_types:CML_STRING_T {
                    length "0..255";
                }

                mandatory true;
                description "";
            }
            leaf value  {
                type cml_data_types:CML_STRING_T {
                    length "0..255";
                }

                mandatory true;
                description "";
            }
        }
    }

    rpc vlan-clearvlanAccessList {
        description "";
        reference "";
        input  {
            leaf vrId  {
                type cml_data_types:CML_UINT32_T;

                mandatory true;
                description "";
            }
            leaf accessMapName  {
                type cml_data_types:CML_STRING_T {
                    length "0..255";
                }

                mandatory true;
                description "";
            }
        }
    }

    rpc switchportinterface-clear-l2protocol-interface-counter {
        description "";
        reference "";
        input  {
            leaf vrId  {
                type cml_data_types:CML_INT32_T;

                mandatory true;
                description "";
            }
            leaf ifName  {
                type cml_data_types:CML_STRING_T {
                    length "0..255";
                }

                mandatory true;
                description "";
            }
            leaf protoProcess  {
                type cml_data_types:CML_L2PROCESS_CLEAR_T;

                mandatory true;
                description "";
            }
        }
    }

    rpc bridge-clearcvlan {
        description "";
        reference "";
        input  {
            leaf macType  {
                type cml_data_types:CML_MACTYPE_T;

                mandatory true;
                description "";
            }
            leaf bridgeId  {
                type cml_data_types:CML_STRING_T {
                    length "0..255";
                }

                mandatory true;
                description "";
            }
            leaf cvlanId  {
                type cml_data_types:CML_INT32_T;

                mandatory true;
                description "";
            }
            leaf sVlanId  {
                type cml_data_types:CML_INT32_T;

                mandatory true;
                description "";
            }
        }
    }

    rpc bridge-cleardynamiccvlan {
        description "";
        reference "";
        input  {
            leaf bridgeId  {
                type cml_data_types:CML_STRING_T {
                    length "0..255";
                }

                mandatory true;
                description "";
            }
            leaf cvlanId  {
                type cml_data_types:CML_INT32_T;

                mandatory true;
                description "";
            }
            leaf sVlanId  {
                type cml_data_types:CML_INT32_T;

                mandatory true;
                description "";
            }
        }
    }

    rpc bridge-clearFbbMacTable {
        description "";
        reference "";
        input  {
            leaf macType  {
                type cml_data_types:CML_MACTYPE_T;

                mandatory true;
                description "";
            }
            leaf bridgeId  {
                type cml_data_types:CML_STRING_T {
                    length "0..255";
                }

                mandatory true;
                description "";
            }
        }
    }

    rpc bridge-clearFbbMacAddr {
        description "";
        reference "";
        input  {
            leaf macType  {
                type cml_data_types:CML_MACTYPE_T;

                mandatory true;
                description "";
            }
            leaf macAddr  {
                type cml_data_types:CML_STRING_T {
                    length "0..255";
                }

                mandatory true;
                description "";
            }
            leaf bridgeId  {
                type cml_data_types:CML_STRING_T {
                    length "0..255";
                }

                mandatory true;
                description "";
            }
        }
    }

    rpc bridge-clearFbbMacPort {
        description "";
        reference "";
        input  {
            leaf macType  {
                type cml_data_types:CML_MACTYPE_T;

                mandatory true;
                description "";
            }
            leaf ifName  {
                type cml_data_types:CML_STRING_T {
                    length "0..255";
                }

                mandatory true;
                description "";
            }
            leaf bridgeId  {
                type cml_data_types:CML_STRING_T {
                    length "0..255";
                }

                mandatory true;
                description "";
            }
        }
    }

    rpc bridge-clearFbbVlanPort {
        description "";
        reference "";
        input  {
            leaf macType  {
                type cml_data_types:CML_MACTYPE_T;

                mandatory true;
                description "";
            }
            leaf vlanId  {
                type cml_data_types:CML_UINT32_T;

                mandatory true;
                description "";
            }
            leaf bridgeId  {
                type cml_data_types:CML_STRING_T {
                    length "0..255";
                }

                mandatory true;
                description "";
            }
        }
    }

    rpc bridge-clearvxlan {
        description "";
        reference "";
        input  {
            leaf vrId  {
                type cml_data_types:CML_UINT32_T;

                mandatory true;
                description "";
            }
            leaf vxlan  {
                type cml_data_types:CML_BOOL_T;

                mandatory true;
                description "";
            }
        }
    }

    rpc bridge-clearbridge {
        description "";
        reference "";
        input  {
            leaf vrId  {
                type cml_data_types:CML_UINT32_T;

                mandatory true;
                description "";
            }
            leaf bridgeId  {
                type cml_data_types:CML_STRING_T {
                    length "0..255";
                }

                mandatory true;
                description "";
            }
        }
    }

    rpc bridge-clearDynamicMacAddr {
        description "";
        reference "";
        input  {
            leaf vrId  {
                type cml_data_types:CML_UINT32_T;

                mandatory true;
                description "";
            }
            leaf macAddr  {
                type cml_data_types:CML_STRING_T {
                    length "0..255";
                }

                mandatory true;
                description "";
            }
            leaf bridgeId  {
                type cml_data_types:CML_STRING_T {
                    length "0..255";
                }

                mandatory true;
                description "";
            }
        }
    }

    rpc bridge-clearDynamicMacPort {
        description "";
        reference "";
        input  {
            leaf vrId  {
                type cml_data_types:CML_UINT32_T;

                mandatory true;
                description "";
            }
            leaf ifName  {
                type cml_data_types:CML_STRING_T {
                    length "0..255";
                }

                mandatory true;
                description "";
            }
            leaf bridgeId  {
                type cml_data_types:CML_STRING_T {
                    length "0..255";
                }

                mandatory true;
                description "";
            }
        }
    }

    rpc bridge-clearDynamicMacPortMstpInst {
        description "";
        reference "";
        input  {
            leaf vrId  {
                type cml_data_types:CML_UINT32_T;

                mandatory true;
                description "";
            }
            leaf ifName  {
                type cml_data_types:CML_STRING_T {
                    length "0..255";
                }

                mandatory true;
                description "";
            }
            leaf instanceId  {
                type cml_data_types:CML_UINT32_T;

                mandatory true;
                description "";
            }
            leaf bridgeId  {
                type cml_data_types:CML_STRING_T {
                    length "0..255";
                }

                mandatory true;
                description "";
            }
        }
    }

    rpc bridge-clearDynamicMacVlan {
        description "";
        reference "";
        input  {
            leaf vrId  {
                type cml_data_types:CML_UINT32_T;

                mandatory true;
                description "";
            }
            leaf vlanId  {
                type cml_data_types:CML_INT32_T;

                mandatory true;
                description "";
            }
            leaf bridgeId  {
                type cml_data_types:CML_STRING_T {
                    length "0..255";
                }

                mandatory true;
                description "";
            }
        }
    }

    rpc bridge-clearnsmipc {
        if-feature feature_list:HAVE_ASYNC;
        description "";
        reference "";
        input  {
            leaf vrId  {
                type cml_data_types:CML_UINT32_T;

                mandatory true;
                description "";
            }
        }
    }

    rpc bridge-clearallowed-ethertypestatistics {
        if-feature feature_list:HAVE_ALLOWED_ETHERTYPE;
        description "";
        reference "";
        input  {
            leaf vrId  {
                type cml_data_types:CML_UINT32_T;

                mandatory true;
                description "";
            }
        }
    }

    rpc bridge-clearallowed-ethertypestatisticsIFNAME {
        if-feature feature_list:HAVE_ALLOWED_ETHERTYPE;
        description "";
        reference "";
        input  {
            leaf vrId  {
                type cml_data_types:CML_UINT32_T;

                mandatory true;
                description "";
            }
            leaf ifName  {
                type cml_data_types:CML_STRING_T {
                    length "0..255";
                }

                mandatory true;
                description "";
            }
        }
    }

    rpc bridge-clear-rbridge-trill-vlan-vId {
        if-feature feature_list:HAVE_TRILLD;
        description "";
        reference "";
        input  {
            leaf vrId  {
                type cml_data_types:CML_UINT32_T;

                mandatory true;
                description "";
            }
            leaf vId  {
                type cml_data_types:CML_INT32_T;

                mandatory true;
                description "";
            }
            leaf bridgeId  {
                type cml_data_types:CML_STRING_T {
                    length "0..255";
                }

                mandatory true;
                description "";
            }
        }
    }

    rpc bridge-clear-rbridge-trill-egress-nickname {
        if-feature feature_list:HAVE_TRILLD;
        description "";
        reference "";
        input  {
            leaf vrId  {
                type cml_data_types:CML_UINT32_T;

                mandatory true;
                description "";
            }
            leaf egressNickname  {
                type cml_data_types:CML_STRING_T {
                    length "0..255";
                }

                mandatory true;
                description "";
            }
            leaf bridgeId  {
                type cml_data_types:CML_STRING_T {
                    length "0..255";
                }

                mandatory true;
                description "";
            }
        }
    }

    rpc bridge-clear-rbridge-trill-all {
        if-feature feature_list:HAVE_TRILLD;
        description "";
        reference "";
        input  {
            leaf vrId  {
                type cml_data_types:CML_UINT32_T;

                mandatory true;
                description "";
            }
            leaf bridgeId  {
                type cml_data_types:CML_STRING_T {
                    length "0..255";
                }

                mandatory true;
                description "";
            }
        }
    }

    rpc mstp-clearDetectedProtocols {
        description "";
        reference "";
        input  {
            leaf vrId  {
                type cml_data_types:CML_UINT32_T;

                mandatory true;
                description "";
            }
            leaf bridgeId  {
                type cml_data_types:CML_STRING_T {
                    length "0..255";
                }

                mandatory true;
                description "";
            }
        }
    }

    rpc mstp-clearDetectedProtocolsinterface {
        description "";
        reference "";
        input  {
            leaf vrId  {
                type cml_data_types:CML_UINT32_T;

                mandatory true;
                description "";
            }
            leaf interface  {
                type cml_data_types:CML_STRING_T {
                    length "0..255";
                }

                mandatory true;
                description "";
            }
        }
    }

    rpc mstp-clear-spanning-tree-statistics-instance-bridge {
        if-feature feature_list:HAVE_MSTPD;
        if-feature feature_list:HAVE_PROVIDER_BRIDGE;
        if-feature feature_list:HAVE_B_BEB;
        description "";
        reference "";
        input  {
            leaf vrId  {
                type cml_data_types:CML_UINT32_T;

                mandatory true;
                description "";
            }
            leaf bridgeId  {
                type cml_data_types:CML_STRING_T {
                    length "0..255";
                }

                mandatory true;
                description "";
            }
            leaf instanceTypeId  {
                type cml_data_types:CML_MSTP_INSTANCE_TYPE_T;

                mandatory true;
                description "";
            }
        }
    }

    rpc mstp-clear-spanning-tree-statistics-interface-vlan-vlanId-bridge-bridgeId {
        if-feature feature_list:HAVE_MSTPD;
        if-feature feature_list:HAVE_PROVIDER_BRIDGE;
        if-feature feature_list:HAVE_B_BEB;
        description "";
        reference "";
        input  {
            leaf vrId  {
                type cml_data_types:CML_UINT32_T;

                mandatory true;
                description "";
            }
            leaf bridgeId  {
                type cml_data_types:CML_STRING_T {
                    length "0..255";
                }

                mandatory true;
                description "";
            }
            leaf ifName  {
                type cml_data_types:CML_STRING_T {
                    length "0..255";
                }

                mandatory true;
                description "";
            }
            leaf vlanStatId  {
                type cml_data_types:CML_UINT16_T {
                    range "2..4094";
                }

                mandatory true;
                description "";
            }
        }
    }

    rpc mstp-clear-spanning-tree-statistics-interface-bridge {
        description "";
        reference "";
        input  {
            leaf vrId  {
                type cml_data_types:CML_UINT32_T;

                mandatory true;
                description "";
            }
            leaf bridgeId  {
                type cml_data_types:CML_STRING_T {
                    length "0..255";
                }

                mandatory true;
                description "";
            }
            leaf ifName  {
                type cml_data_types:CML_STRING_T {
                    length "0..255";
                }

                mandatory true;
                description "";
            }
        }
    }

    rpc mstp-clearspanning-treestatisticsbridgebridgeId {
        description "";
        reference "";
        input  {
            leaf vrId  {
                type cml_data_types:CML_UINT32_T;

                mandatory true;
                description "";
            }
            leaf bridgeId  {
                type cml_data_types:CML_STRING_T {
                    length "0..255";
                }

                mandatory true;
                description "";
            }
        }
    }

    rpc mstp-clearspanning-treestatisticsvlanvlanIdbridgebridgeId {
        description "";
        reference "";
        input  {
            leaf vrId  {
                type cml_data_types:CML_UINT32_T;

                mandatory true;
                description "";
            }
            leaf bridgeId  {
                type cml_data_types:CML_STRING_T {
                    length "0..255";
                }

                mandatory true;
                description "";
            }
            leaf vlanStatId  {
                type cml_data_types:CML_UINT16_T {
                    range "2..4094";
                }

                mandatory true;
                description "";
            }
        }
    }

    rpc mstp-clear-spanning-tree-statistics-interface-instance {
        description "";
        reference "";
        input  {
            leaf vrId  {
                type cml_data_types:CML_UINT32_T;

                mandatory true;
                description "";
            }
            leaf bridgeId  {
                type cml_data_types:CML_STRING_T {
                    length "0..255";
                }

                mandatory true;
                description "";
            }
            leaf ifName  {
                type cml_data_types:CML_STRING_T {
                    length "0..255";
                }

                mandatory true;
                description "";
            }
            leaf instanceTypeId  {
                type cml_data_types:CML_MSTP_INSTANCE_TYPE_T;

                mandatory true;
                description "";
            }
        }
    }

    rpc mstp-mstp-snmp-restart {
        if-feature feature_list:HAVE_SNMP;
        description "";
        reference "";
    }

    rpc lag-lacp-snmp-restart {
        if-feature feature_list:HAVE_SNMP;
        description "";
        reference "";
    }

    rpc lag-clear-all-lacp-counters {
        description "";
        reference "";
    }

    rpc lag-clear-lacp-counters {
        description "";
        reference "";
        input  {
            leaf portPriority  {
                type cml_data_types:CML_UINT16_T {
                    range "1..65535";
                }

                mandatory true;
                description "";
            }
        }
    }

    rpc lldpv2-clear-lldp-counter {
        description "";
        reference "";
        input  {
            leaf vrId  {
                type cml_data_types:CML_INT32_T;

                mandatory true;
                description "";
            }
        }
    }

    rpc lldpv2-lldp-snmp-restart {
        if-feature feature_list:HAVE_SNMP;
        description "";
        reference "";
        input  {
            leaf vrId  {
                type cml_data_types:CML_INT32_T;

                mandatory true;
                description "";
            }
        }
    }

    rpc rib-snmpRestart {
        if-feature feature_list:HAVE_SNMP;
        description "";
        reference "";
    }

    rpc rib-clearIpRouteKernel {
        description "";
        reference "";
        input  {
            leaf vrId  {
                type cml_data_types:CML_UINT32_T;

                mandatory true;
                description "";
            }
        }
    }

    rpc rib-clearIpKernelRoute {
        description "";
        reference "";
        input  {
            leaf vrId  {
                type cml_data_types:CML_UINT32_T;

                mandatory true;
                description "";
            }
        }
    }

    rpc rib-clearIpv6RouteKernel {
        if-feature feature_list:HAVE_IPV6;
        description "";
        reference "";
        input  {
            leaf vrId  {
                type cml_data_types:CML_UINT32_T;

                mandatory true;
                description "";
            }
        }
    }

    rpc rib-clearIpRouteAll {
        description "";
        reference "";
        input  {
            leaf vrId  {
                type cml_data_types:CML_UINT32_T;

                mandatory true;
                description "Virtual router id";
            }
            leaf starPrint  {
                type cml_data_types:CML_STRING_T {
                    length "0..255";
                }

                mandatory true;
                description "all route";
            }
        }
    }

    rpc rib-clearIpRoutePrefix {
        description "";
        reference "";
        input  {
            leaf vrId  {
                type cml_data_types:CML_UINT32_T;

                mandatory true;
                description "Virtual router id";
            }
            leaf prefixAddr  {
                type cml_data_types:CML_IPV4_PREFIX_T;

                mandatory true;
                description "Prefix to be cleared(e.g. 10.0.0.0/8)";
            }
        }
    }

    rpc rib-clearIpv4RouteAll {
        description "";
        reference "";
        input  {
            leaf vrId  {
                type cml_data_types:CML_UINT32_T;

                mandatory true;
                description "Virtual router id";
            }
            leaf starPrint  {
                type cml_data_types:CML_STRING_T {
                    length "0..255";
                }

                mandatory true;
                description "all routes";
            }
        }
    }

    rpc rib-clearIpv4RoutePrefix {
        description "";
        reference "";
        input  {
            leaf vrId  {
                type cml_data_types:CML_UINT32_T;

                mandatory true;
                description "Virtual router id";
            }
            leaf prefixAddr  {
                type cml_data_types:CML_IPV4_PREFIX_T;

                mandatory true;
                description "Prefix to be cleared(e.g. 3ffe:506::/32)";
            }
        }
    }

    rpc rib-clearIpv6RouteAll {
        if-feature feature_list:HAVE_IPV6;
        description "";
        reference "";
        input  {
            leaf vrId  {
                type cml_data_types:CML_UINT32_T;

                mandatory true;
                description "Virtual router id";
            }
            leaf starPrint  {
                type cml_data_types:CML_STRING_T {
                    length "0..255";
                }

                mandatory true;
                description "all routes";
            }
        }
    }

    rpc rib-clearIpv6RoutePrefix {
        description "";
        reference "";
        input  {
            leaf vrId  {
                type cml_data_types:CML_UINT32_T;

                mandatory true;
                description "Virtual router id";
            }
            leaf prefixIpv6Addr  {
                type cml_data_types:CML_IPV6_PREFIX_T;

                mandatory true;
                description "";
            }
        }
    }

    rpc rib-clearIpVrfRouteAll {
        if-feature feature_list:HAVE_VRF;
        description "";
        reference "";
        input  {
            leaf vrId  {
                type cml_data_types:CML_UINT32_T;

                mandatory true;
                description "Virtual router id";
            }
            leaf vrfName  {
                type cml_data_types:CML_STRING_T {
                    length "0..255";
                }

                mandatory true;
                description "vrf name";
            }
            leaf starPrint  {
                type cml_data_types:CML_STRING_T {
                    length "0..255";
                }

                mandatory true;
                description "all routes";
            }
        }
    }

    rpc rib-clearIpVrfRoutePrefix {
        if-feature feature_list:HAVE_VRF;
        description "";
        reference "";
        input  {
            leaf vrId  {
                type cml_data_types:CML_UINT32_T;

                mandatory true;
                description "Virtual router id";
            }
            leaf vrfName  {
                type cml_data_types:CML_STRING_T {
                    length "0..255";
                }

                mandatory true;
                description "vrf name";
            }
            leaf prefixAddr  {
                type cml_data_types:CML_IPV4_PREFIX_T;

                mandatory true;
                description "Prefix to be cleared(e.g. 10.0.0.0/8)";
            }
        }
    }

    rpc rib-clearIpv4VrfRouteAll {
        if-feature feature_list:HAVE_VRF;
        description "";
        reference "";
        input  {
            leaf vrId  {
                type cml_data_types:CML_UINT32_T;

                mandatory true;
                description "Virtual router id";
            }
            leaf vrfName  {
                type cml_data_types:CML_STRING_T {
                    length "0..255";
                }

                mandatory true;
                description "vrf name";
            }
            leaf starPrint  {
                type cml_data_types:CML_STRING_T {
                    length "0..255";
                }

                mandatory true;
                description "all routes";
            }
        }
    }

    rpc rib-clearIpv4VrfRoutePrefix {
        if-feature feature_list:HAVE_VRF;
        description "";
        reference "";
        input  {
            leaf vrId  {
                type cml_data_types:CML_UINT32_T;

                mandatory true;
                description "Virtual router id";
            }
            leaf vrfName  {
                type cml_data_types:CML_STRING_T {
                    length "0..255";
                }

                mandatory true;
                description "vrf name";
            }
            leaf prefixAddr  {
                type cml_data_types:CML_IPV4_PREFIX_T;

                mandatory true;
                description "Prefix to be cleared(e.g. 10.0.0.0/8)";
            }
        }
    }

    rpc rib-clearIpv6VrdRouteAll {
        if-feature feature_list:HAVE_VRF;
        if-feature feature_list:HAVE_IPV6;
        description "";
        reference "";
        input  {
            leaf vrId  {
                type cml_data_types:CML_UINT32_T;

                mandatory true;
                description "Virtual router id";
            }
            leaf vrfName  {
                type cml_data_types:CML_STRING_T {
                    length "0..255";
                }

                mandatory true;
                description "vrf name";
            }
            leaf starPrint  {
                type cml_data_types:CML_STRING_T {
                    length "0..255";
                }

                mandatory true;
                description "all routes";
            }
        }
    }

    rpc rib-clearIpv6RoutePrefixVrf {
        description "";
        reference "";
        input  {
            leaf vrId  {
                type cml_data_types:CML_UINT32_T;

                mandatory true;
                description "Virtual router id";
            }
            leaf vrfName  {
                type cml_data_types:CML_STRING_T {
                    length "0..255";
                }

                mandatory true;
                description "Virtual router id";
            }
            leaf prefixIpv6Addr  {
                type cml_data_types:CML_IPV6_PREFIX_T;

                mandatory true;
                description "Prefix to be cleared(e.g. 3ffe:506::/32)";
            }
        }
    }

    rpc ospf-restart-ospf-graceful {
        if-feature feature_list:HAVE_RESTART;
        description "";
        reference "";
        input  {
            leaf vrId  {
                type cml_data_types:CML_UINT32_T;

                mandatory true;
                description "";
            }
            leaf restartGracePeriod  {
                type cml_data_types:CML_UINT32_T {
                    range "2..1800";
                }

                mandatory true;
                description "Grace period in seconds";
            }
        }
    }

    rpc ospf-restart-ospf-hitless {
        if-feature feature_list:HAVE_RESTART;
        description "";
        reference "";
        input  {
            leaf vrId  {
                type cml_data_types:CML_UINT32_T;

                mandatory true;
                description "";
            }
            leaf hitlessGracePeriod  {
                type cml_data_types:CML_UINT32_T {
                    range "2..1800";
                }

                mandatory true;
                description "";
            }
        }
    }

    rpc ospf-ospf-snmp-restart {
        if-feature feature_list:HAVE_SNMP;
        description "";
        reference "";
    }

    rpc ospf-clear-ospf-process {
        description "";
        reference "";
        input  {
            leaf vrId  {
                type cml_data_types:CML_UINT32_T;

                mandatory true;
                description "";
            }
        }
    }

    rpc ospf-clear-ospf-process-id {
        description "";
        reference "";
        input  {
            leaf vrId  {
                type cml_data_types:CML_UINT32_T;

                mandatory true;
                description "";
            }
            leaf procId  {
                type cml_data_types:CML_UINT32_T {
                    range "0..65535";
                }

                mandatory true;
                description "";
            }
        }
    }

    rpc ospfv3-ospf6-clear {
        description "";
        reference "";
        input  {
            leaf vrId  {
                type cml_data_types:CML_UINT32_T;

                mandatory true;
                description "Virtual Router ID numeric";
            }
            leaf ospfProcess  {
                type cml_data_types:CML_STRING_T {
                    length "0..255";
                }

                mandatory true;
                description "";
            }
        }
    }

    rpc ospfv3-ospf6-restart-hitless {
        description "";
        reference "";
        input  {
            leaf vrId  {
                type cml_data_types:CML_UINT32_T;

                mandatory true;
                description "";
            }
            leaf gracePeriod  {
                type cml_data_types:CML_UINT32_T {
                    range "2..1800";
                }

                mandatory true;
                description "";
            }
        }
    }

    rpc ospfv3-ospf6-restart {
        description "";
        reference "";
        input  {
            leaf vrId  {
                type cml_data_types:CML_UINT32_T;

                mandatory true;
                description "";
            }
            leaf gracePeriod  {
                type cml_data_types:CML_UINT32_T {
                    range "2..1800";
                }

                mandatory true;
                description "";
            }
        }
    }

    rpc ospfv3-ospf6-snmp-restart {
        if-feature feature_list:HAVE_SNMP;
        description "";
        reference "";
    }

    rpc bgp-restartBgp {
        if-feature feature_list:HAVE_RESTART;
        description "";
        reference "";
    }

    rpc bgp-clearBgpStatistics {
        description "";
        reference "";
    }

    rpc bgp-clearIpBgpAll {
        description "";
        reference "";
        input  {
            leaf view  {
                type cml_data_types:CML_STRING_T {
                    length "0..255";
                }

                mandatory true;
                description "bgp view name (default=NULL)";
            }
            leaf afi  {
                type cml_data_types:CML_AFI_TYPE_T;

                mandatory true;
                description "BGP 'afi' Types";
            }
            leaf safi  {
                type cml_data_types:CML_SAFI_TYPE_T;

                mandatory true;
                description "BGP 'safi' Types";
            }
            leaf clearType  {
                type cml_data_types:CML_CLEAR_TYPE_T;

                mandatory true;
                description "BGP 'clear' Types";
            }
            leaf clearSoft  {
                type cml_data_types:CML_CLEAR_SOFT_T;

                mandatory true;
                description "clear flag for peer soft, route flap dampening and table map";
            }
            leaf arg  {
                type cml_data_types:CML_HOSTNAME_T {
                    length "0..255";
                }

                mandatory true;
                description "input arguments (peer Address, prefix address, peer-group name, bgp As)";
            }
            leaf vrId  {
                type cml_data_types:CML_UINT32_T;

                mandatory true;
                description "";
            }
        }
    }

    rpc bgp-clearIpBgpAllPeerVrf {
        description "";
        reference "";
        input  {
            leaf vrfName  {
                type cml_data_types:CML_STRING_T {
                    length "0..255";
                }

                mandatory true;
                description "vrf name";
            }
            leaf afi  {
                type cml_data_types:CML_AFI_TYPE_T;

                mandatory true;
                description "BGP 'afi' Types";
            }
            leaf safi  {
                type cml_data_types:CML_SAFI_TYPE_T;

                mandatory true;
                description "BGP 'safi' Types";
            }
            leaf clearType  {
                type cml_data_types:CML_CLEAR_TYPE_T;

                mandatory true;
                description "BGP 'clear' Types";
            }
            leaf clearSoft  {
                type cml_data_types:CML_CLEAR_SOFT_T;

                mandatory true;
                description "clear flag for peer soft, route flap dampening and table map";
            }
            leaf arg  {
                type cml_data_types:CML_IP_PREFIX_ADDR_T {
                    length "0..255";
                }

                mandatory true;
                description "input arguments (peer Address, prefix address, peer-group name, bgp As)";
            }
            leaf vrId  {
                type cml_data_types:CML_UINT32_T;

                mandatory true;
                description "";
            }
        }
    }

    rpc bgp-clearIpBgpAllVrf {
        description "";
        reference "";
        input  {
            leaf vrfName  {
                type cml_data_types:CML_STRING_T {
                    length "0..255";
                }

                mandatory true;
                description "vrf name";
            }
            leaf afi  {
                type cml_data_types:CML_AFI_TYPE_T;

                mandatory true;
                description "BGP 'afi' Types";
            }
            leaf safi  {
                type cml_data_types:CML_SAFI_TYPE_T;

                mandatory true;
                description "BGP 'safi' Types";
            }
            leaf clearType  {
                type cml_data_types:CML_CLEAR_TYPE_T;

                mandatory true;
                description "BGP 'clear' Types";
            }
            leaf clearSoft  {
                type cml_data_types:CML_CLEAR_SOFT_T;

                mandatory true;
                description "clear flag for peer soft, route flap dampening and table map";
            }
            leaf arg  {
                type cml_data_types:CML_IP_PREFIX_ADDR_T {
                    length "0..255";
                }

                mandatory true;
                description "input arguments (peer Address,prefix address, peer-group name, bgp As)";
            }
            leaf vrId  {
                type cml_data_types:CML_UINT32_T;

                mandatory true;
                description "";
            }
        }
    }

    rpc oambfd-bfd-snmp-restart {
        if-feature feature_list:HAVE_SNMP;
        description "";
        reference "";
    }

    rpc vrrp-snmp-restart-vrrp {
        if-feature feature_list:HAVE_SNMP;
        description "";
        reference "";
    }

    rpc vrrp-clear-vrrp-statistics {
        description "";
        reference "";
    }

    rpc vrrp-clear-vrrp-ipv4-statistics {
        description "";
        reference "";
        input  {
            leaf vrId  {
                type cml_data_types:CML_UINT32_T;

                mandatory true;
                description "";
            }
            leaf vrrpid  {
                type cml_data_types:CML_INT32_T {
                    range "1..255";
                }

                mandatory true;
                description "";
            }
            leaf ifName  {
                type cml_data_types:CML_STRING_T {
                    length "0..255";
                }

                mandatory true;
                description "";
            }
        }
    }

    rpc vrrp-clear-vrrp-ipv6-statistics {
        description "";
        reference "";
        input  {
            leaf vrId  {
                type cml_data_types:CML_UINT32_T;

                mandatory true;
                description "";
            }
            leaf vrrp6id  {
                type cml_data_types:CML_INT32_T {
                    range "1..255";
                }

                mandatory true;
                description "";
            }
            leaf ifName  {
                type cml_data_types:CML_STRING_T {
                    length "0..255";
                }

                mandatory true;
                description "";
            }
        }
    }

    rpc plist-clear-ip-prefix {
        description "";
        reference "";
        input  {
            leaf vrId  {
                type cml_data_types:CML_UINT32_T;

                mandatory true;
                description "";
            }
        }
    }

    rpc plist-clear-ip-prefix-by-name {
        description "";
        reference "";
        input  {
            leaf vrId  {
                type cml_data_types:CML_UINT32_T;

                mandatory true;
                description "";
            }
            leaf name  {
                type cml_data_types:CML_STRING_T {
                    length "0..255";
                }

                mandatory true;
                description "";
            }
        }
    }

    rpc plist-clear-ip-prefix-by-prefix {
        description "";
        reference "";
        input  {
            leaf vrId  {
                type cml_data_types:CML_UINT32_T;

                mandatory true;
                description "";
            }
            leaf name  {
                type cml_data_types:CML_STRING_T {
                    length "0..255";
                }

                mandatory true;
                description "";
            }
            leaf prefix  {
                type cml_data_types:CML_IPV4_ADDR_PREFIX_T;

                mandatory true;
                description "";
            }
        }
    }

    rpc plist-clear-ipv6-prefix {
        description "";
        reference "";
        input  {
            leaf vrId  {
                type cml_data_types:CML_UINT32_T;

                mandatory true;
                description "";
            }
        }
    }

    rpc plist-clear-ipv6-prefix-by-name {
        description "";
        reference "";
        input  {
            leaf vrId  {
                type cml_data_types:CML_UINT32_T;

                mandatory true;
                description "";
            }
            leaf name  {
                type cml_data_types:CML_STRING_T {
                    length "0..255";
                }

                mandatory true;
                description "";
            }
        }
    }

    rpc plist-clear-ipv6-prefix-by-prefix {
        description "";
        reference "";
        input  {
            leaf vrId  {
                type cml_data_types:CML_UINT32_T;

                mandatory true;
                description "";
            }
            leaf name  {
                type cml_data_types:CML_STRING_T {
                    length "0..255";
                }

                mandatory true;
                description "";
            }
            leaf prefix  {
                type cml_data_types:CML_IPV6_PREFIX_T;

                mandatory true;
                description "";
            }
        }
    }

    rpc isis-isis-restart {
        if-feature feature_list:HAVE_RESTART;
        description "";
        reference "";
        input  {
            leaf vrId  {
                type cml_data_types:CML_UINT32_T;

                mandatory true;
                description "";
            }
            leaf graceCMLSEPperiod  {
                type cml_data_types:CML_UINT16_T {
                    range "1..65535";
                }

                mandatory true;
                description "";
            }
        }
    }

    rpc isis-clear-is-neighbors {
        description "";
        reference "";
        input  {
            leaf vrId  {
                type cml_data_types:CML_UINT32_T;

                mandatory true;
                description "";
            }
            leaf SystemID  {
                type cml_data_types:CML_STRING_T {
                    length "0..255";
                }

                mandatory true;
                description "";
            }
        }
    }

    rpc isis-clear-neighbors {
        description "";
        reference "";
        input  {
            leaf vrId  {
                type cml_data_types:CML_UINT32_T;

                mandatory true;
                description "";
            }
        }
    }

    rpc isis-clear-ip-route {
        description "";
        reference "";
        input  {
            leaf vrId  {
                type cml_data_types:CML_UINT32_T;

                mandatory true;
                description "";
            }
            leaf isisInstanceTag  {
                type cml_data_types:CML_STRING_T {
                    length "0..255";
                }

                mandatory true;
                description "";
            }
            leaf ipv4route  {
                type cml_data_types:CML_ISIS_ROUTE_T;

                mandatory true;
                description "";
            }
        }
    }

    rpc isis-clear-ipv6-route {
        description "";
        reference "";
        input  {
            leaf vrId  {
                type cml_data_types:CML_UINT32_T;

                mandatory true;
                description "";
            }
            leaf isisInstanceTag  {
                type cml_data_types:CML_STRING_T {
                    length "0..255";
                }

                mandatory true;
                description "";
            }
            leaf ipv6route  {
                type cml_data_types:CML_ISIS_ROUTE_T;

                mandatory true;
                description "";
            }
        }
    }

    rpc isis-isis-proc-clear {
        description "";
        reference "";
        input  {
            leaf vrId  {
                type cml_data_types:CML_UINT32_T;

                mandatory true;
                description "";
            }
            leaf isisInstanceTag  {
                type cml_data_types:CML_STRING_T {
                    length "0..255";
                }

                mandatory true;
                description "";
            }
        }
    }

    rpc isis-isis-clear-counters {
        description "";
        reference "";
        input  {
            leaf vrId  {
                type cml_data_types:CML_UINT32_T;

                mandatory true;
                description "";
            }
        }
    }

    rpc isis-clear-interface-counters {
        description "";
        reference "";
        input  {
            leaf vrId  {
                type cml_data_types:CML_UINT32_T;

                mandatory true;
                description "";
            }
            leaf ifName  {
                type cml_data_types:CML_STRING_T {
                    length "0..255";
                }

                mandatory true;
                description "";
            }
        }
    }

    rpc isis-clear-adjacency-all {
        description "";
        reference "";
        input  {
            leaf vrId  {
                type cml_data_types:CML_UINT32_T;

                mandatory true;
                description "";
            }
            leaf adjall  {
                type cml_data_types:CML_BOOL_T;

                mandatory true;
                description "";
            }
            leaf adjvrfname  {
                type cml_data_types:CML_STRING_T {
                    length "0..255";
                }

                mandatory true;
                description "";
            }
        }
    }

    rpc isis-clear-adjacency-word-all {
        description "";
        reference "";
        input  {
            leaf vrId  {
                type cml_data_types:CML_UINT32_T;

                mandatory true;
                description "";
            }
            leaf tagname  {
                type cml_data_types:CML_STRING_T {
                    length "0..255";
                }

                mandatory true;
                description "";
            }
            leaf adjall  {
                type cml_data_types:CML_BOOL_T;

                mandatory true;
                description "";
            }
            leaf adjvrfname  {
                type cml_data_types:CML_STRING_T {
                    length "0..255";
                }

                mandatory true;
                description "";
            }
        }
    }

    rpc isis-clear-adjacency-word-ifname {
        description "";
        reference "";
        input  {
            leaf vrId  {
                type cml_data_types:CML_UINT32_T;

                mandatory true;
                description "";
            }
            leaf tagname  {
                type cml_data_types:CML_STRING_T {
                    length "0..255";
                }

                mandatory true;
                description "";
            }
            leaf tagifname  {
                type cml_data_types:CML_STRING_T {
                    length "0..255";
                }

                mandatory true;
                description "";
            }
            leaf adjvrfname  {
                type cml_data_types:CML_STRING_T {
                    length "0..255";
                }

                mandatory true;
                description "";
            }
        }
    }

    rpc isis-clear-adjacency-ifname {
        description "";
        reference "";
        input  {
            leaf vrId  {
                type cml_data_types:CML_UINT32_T;

                mandatory true;
                description "";
            }
            leaf adjifname  {
                type cml_data_types:CML_STRING_T {
                    length "0..255";
                }

                mandatory true;
                description "";
            }
            leaf adjvrfname  {
                type cml_data_types:CML_STRING_T {
                    length "0..255";
                }

                mandatory true;
                description "";
            }
        }
    }

    rpc isis-clear-adjacency-word-systemid {
        description "";
        reference "";
        input  {
            leaf vrId  {
                type cml_data_types:CML_UINT32_T;

                mandatory true;
                description "";
            }
            leaf tagname  {
                type cml_data_types:CML_STRING_T {
                    length "0..255";
                }

                mandatory true;
                description "";
            }
            leaf tagsystemid  {
                type cml_data_types:CML_ISIS_SYSTEMID_T {
                    length "0..255";
                }

                mandatory true;
                description "";
            }
            leaf tagvrfname  {
                type cml_data_types:CML_STRING_T {
                    length "0..255";
                }

                mandatory true;
                description "";
            }
        }
    }

    rpc isis-clear-adjacency-systemid {
        description "";
        reference "";
        input  {
            leaf vrId  {
                type cml_data_types:CML_UINT32_T;

                mandatory true;
                description "";
            }
            leaf adjsystemid  {
                type cml_data_types:CML_ISIS_SYSTEMID_T {
                    length "0..255";
                }

                mandatory true;
                description "";
            }
            leaf adjvrfname  {
                type cml_data_types:CML_STRING_T {
                    length "0..255";
                }

                mandatory true;
                description "";
            }
        }
    }

    rpc isis-snmp-restart-isis {
        if-feature feature_list:HAVE_SNMP;
        description "";
        reference "";
    }

    rpc pim-snmp-restart-pim {
        if-feature feature_list:HAVE_SNMP;
        description "";
        reference "";
    }

    rpc pim4-clear-ip-mroute {
        description "";
        reference "";
        input  {
            leaf vrId  {
                type cml_data_types:CML_UINT32_T;

                mandatory true;
                description "";
            }
            leaf vrfName  {
                type cml_data_types:CML_STRING_T {
                    length "0..255";
                }

                mandatory true;
                description "";
            }
            leaf allFlag  {
                type cml_data_types:CML_BOOL_T;

                mandatory true;
                description "";
            }
            leaf pimmode  {
                type cml_data_types:CML_PIM_MODE_TYPE_T;

                mandatory true;
                description "";
            }
        }
    }

    rpc pim4-clear-ip-mroute-xg {
        description "";
        reference "";
        input  {
            leaf vrId  {
                type cml_data_types:CML_UINT32_T;

                mandatory true;
                description "";
            }
            leaf vrfName  {
                type cml_data_types:CML_STRING_T {
                    length "0..255";
                }

                mandatory true;
                description "";
            }
            leaf mrouteXg  {
                type cml_data_types:CML_IPV4_ADDR_T;

                mandatory true;
                description "";
            }
        }
    }

    rpc pim4-clear-ip-mroute-sg {
        description "";
        reference "";
        input  {
            leaf vrId  {
                type cml_data_types:CML_UINT32_T;

                mandatory true;
                description "";
            }
            leaf vrfName  {
                type cml_data_types:CML_STRING_T {
                    length "0..255";
                }

                mandatory true;
                description "";
            }
            leaf mrouteGaddr  {
                type cml_data_types:CML_IPV4_ADDR_T;

                mandatory true;
                description "";
            }
            leaf mrouteSaddr  {
                type cml_data_types:CML_IPV4_ADDR_T;

                mandatory true;
                description "";
            }
            leaf pimgsmode  {
                type cml_data_types:CML_PIM_MODE_TYPE_T;

                mandatory true;
                description "";
            }
        }
    }

    rpc pim4-clear-ip-pim {
        if-feature feature_list:HAVE_PIM_SM;
        description "";
        reference "";
        input  {
            leaf vrId  {
                type cml_data_types:CML_UINT32_T;

                mandatory true;
                description "";
            }
            leaf vrfName  {
                type cml_data_types:CML_STRING_T {
                    length "0..255";
                }

                mandatory true;
                description "";
            }
            leaf allRp  {
                type cml_data_types:CML_BOOL_T;

                mandatory true;
                description "";
            }
        }
    }

    rpc pim4-clear-ip-msdp-peer {
        if-feature feature_list:HAVE_PIM_MSDP_API;
        description "";
        reference "";
        input  {
            leaf vrId  {
                type cml_data_types:CML_UINT32_T;

                mandatory true;
                description "";
            }
            leaf vrfName  {
                type cml_data_types:CML_STRING_T {
                    length "0..255";
                }

                mandatory true;
                description "";
            }
            leaf peerAddress  {
                type cml_data_types:CML_IPV4_ADDR_T;

                mandatory true;
                description "";
            }
        }
    }

    rpc pim4-clear-ip-msdp-sacache {
        if-feature feature_list:HAVE_PIM_MSDP_API;
        description "";
        reference "";
        input  {
            leaf vrId  {
                type cml_data_types:CML_UINT32_T;

                mandatory true;
                description "";
            }
            leaf vrfName  {
                type cml_data_types:CML_STRING_T {
                    length "0..255";
                }

                mandatory true;
                description "";
            }
            leaf saAddress  {
                type cml_data_types:CML_IPV4_ADDR_T;

                mandatory true;
                description "";
            }
        }
    }

    rpc vxlan-clear-nvo-id-vxlan-tunnels {
        if-feature feature_list:HAVE_VXLAN;
        description "";
        reference "";
        input  {
            leaf vrId  {
                type cml_data_types:CML_INT32_T;

                mandatory true;
                description "";
            }
        }
    }

    rpc vxlan-clear-nvo-id-access-port {
        if-feature feature_list:HAVE_VXLAN;
        description "";
        reference "";
        input  {
            leaf vrId  {
                type cml_data_types:CML_INT32_T;

                mandatory true;
                description "";
            }
            leaf ifName  {
                type cml_data_types:CML_STRING_T {
                    length "0..255";
                }

                mandatory true;
                description "";
            }
        }
    }

    rpc vxlan-clear-nvo-id-acess-port-vlan {
        if-feature feature_list:HAVE_VXLAN;
        description "";
        reference "";
        input  {
            leaf vrId  {
                type cml_data_types:CML_INT32_T;

                mandatory true;
                description "";
            }
            leaf ifName  {
                type cml_data_types:CML_STRING_T {
                    length "0..255";
                }

                mandatory true;
                description "";
            }
            leaf vlanId  {
                type cml_data_types:CML_UINT32_T;

                mandatory true;
                description "";
            }
            leaf innerVlanId  {
                type cml_data_types:CML_UINT32_T {
                    range "2..4094";
                }

                mandatory true;
                description "";
            }
        }
    }

    rpc vxlan-clear-nvo-id-access-all {
        if-feature feature_list:HAVE_VXLAN;
        description "";
        reference "";
        input  {
            leaf vrId  {
                type cml_data_types:CML_INT32_T;

                mandatory true;
                description "";
            }
            leaf clearAllCounter  {
                type cml_data_types:CML_BOOL_T;

                mandatory true;
                description "";
            }
        }
    }

    rpc vxlan-clear-nvo-id-network-all {
        if-feature feature_list:HAVE_VXLAN;
        description "";
        reference "";
        input  {
            leaf vrId  {
                type cml_data_types:CML_INT32_T;

                mandatory true;
                description "";
            }
            leaf clearNetworkAllCounter  {
                type cml_data_types:CML_BOOL_T;

                mandatory true;
                description "";
            }
        }
    }

    rpc vxlan-clear-nvo-id-network-port {
        if-feature feature_list:HAVE_VXLAN;
        description "";
        reference "";
        input  {
            leaf vrId  {
                type cml_data_types:CML_INT32_T;

                mandatory true;
                description "";
            }
            leaf destIpv4  {
                type cml_data_types:CML_STRING_T {
                    length "0..255";
                }

                mandatory true;
                description "";
            }
        }
    }

    rpc vxlan-clear-nvo-vxlan-mac-stale-entries {
        if-feature feature_list:HAVE_VXLAN;
        description "";
        reference "";
        input  {
            leaf vrId  {
                type cml_data_types:CML_INT32_T;

                mandatory true;
                description "";
            }
            leaf vnId  {
                type cml_data_types:CML_INT32_T {
                    range "1..16777215";
                }

                mandatory true;
                description "";
            }
        }
    }

    rpc snmp-clear-snmp-hostconfig {
        description "";
        reference "";
    }

    rpc radius-clear-radius-server-counters {
        description "";
        reference "";
        input  {
            leaf vrfName  {
                type cml_data_types:CML_STRING_T {
                    length "0..255";
                }

                mandatory true;
                description "";
            }
        }
    }

    rpc radius-clear-radius-server-name-counters {
        description "";
        reference "";
        input  {
            leaf hostname  {
                type cml_data_types:CML_HOSTPNAME_T {
                    length "0..255";
                }

                mandatory true;
                description "";
            }
            leaf vrfName  {
                type cml_data_types:CML_STRING_T {
                    length "0..255";
                }

                mandatory true;
                description "";
            }
        }
    }

    rpc tacacs-clear-tacacs-server-counters {
        description "";
        reference "";
        input  {
            leaf vrfName  {
                type cml_data_types:CML_STRING_T {
                    length "0..255";
                }

                mandatory true;
                description "";
            }
        }
    }

    rpc tacacs-clear-tacacs-server-name-counters {
        description "";
        reference "";
        input  {
            leaf hostname  {
                type cml_data_types:CML_HOSTPNAME_T {
                    length "0..255";
                }

                mandatory true;
                description "";
            }
            leaf vrfName  {
                type cml_data_types:CML_STRING_T {
                    length "0..255";
                }

                mandatory true;
                description "";
            }
        }
    }

    rpc usermgmt-user {
        if-feature feature_list:HAVE_USER_MGMT;
        description "";
        reference "";
        input  {
            leaf user  {
                type cml_data_types:CML_STRING_T {
                    length "0..255";
                }

                mandatory true;
                description "";
            }
        }
    }

    rpc ssh-lengthRSA {
        if-feature feature_list:HAVE_SSH_SERVER;
        description "";
        reference "";
        input  {
            leaf usernameRSA  {
                type cml_data_types:CML_STRING_T {
                    length "0..255";
                }

                mandatory true;
                description "";
            }
            leaf keyRSA  {
                type cml_data_types:CML_BOOL_T;

                mandatory true;
                description "";
            }
            leaf lengthRSA  {
                type cml_data_types:CML_UINT32_T {
                    range "768..4096";
                }

                mandatory true;
                description "";
            }
            leaf forceRSA  {
                type cml_data_types:CML_BOOL_T;

                mandatory true;
                description "";
            }
        }
    }

    rpc ssh-keyDSA {
        if-feature feature_list:HAVE_SSH_SERVER;
        description "";
        reference "";
        input  {
            leaf usernameDSA  {
                type cml_data_types:CML_STRING_T {
                    length "0..255";
                }

                mandatory true;
                description "";
            }
            leaf keyDSA  {
                type cml_data_types:CML_BOOL_T;

                mandatory true;
                description "";
            }
            leaf forceDSA  {
                type cml_data_types:CML_BOOL_T;

                mandatory true;
                description "";
            }
        }
    }

    rpc ssh-keyGenRSA {
        if-feature feature_list:HAVE_SSH_SERVER;
        description "";
        reference "";
        input  {
            leaf keyGenRSA  {
                type cml_data_types:CML_BOOL_T;

                mandatory true;
                description "";
            }
            leaf keyGenlengthRSA  {
                type cml_data_types:CML_UINT32_T {
                    range "768..4096";
                }

                mandatory true;
                description "";
            }
            leaf keyGenforceRSA  {
                type cml_data_types:CML_BOOL_T;

                mandatory true;
                description "";
            }
            leaf vrfName  {
                type cml_data_types:CML_STRING_T {
                    length "0..255";
                }

                mandatory true;
                description "";
            }
        }
    }

    rpc ssh-keyDelRSA {
        if-feature feature_list:HAVE_SSH_SERVER;
        description "";
        reference "";
        input  {
            leaf keyDelRSA  {
                type cml_data_types:CML_BOOL_T;

                mandatory true;
                description "";
            }
            leaf vrfName  {
                type cml_data_types:CML_STRING_T {
                    length "0..255";
                }

                mandatory true;
                description "";
            }
        }
    }

    rpc ssh-keyGenDSA {
        if-feature feature_list:HAVE_SSH_SERVER;
        description "";
        reference "";
        input  {
            leaf keyGenDSA  {
                type cml_data_types:CML_BOOL_T;

                mandatory true;
                description "";
            }
            leaf keyGenforceDSA  {
                type cml_data_types:CML_BOOL_T;

                mandatory true;
                description "";
            }
            leaf vrfName  {
                type cml_data_types:CML_STRING_T {
                    length "0..255";
                }

                mandatory true;
                description "";
            }
        }
    }

    rpc ssh-keyDelDSA {
        if-feature feature_list:HAVE_SSH_SERVER;
        description "";
        reference "";
        input  {
            leaf keyDelDSA  {
                type cml_data_types:CML_BOOL_T;

                mandatory true;
                description "";
            }
            leaf vrfName  {
                type cml_data_types:CML_STRING_T {
                    length "0..255";
                }

                mandatory true;
                description "";
            }
        }
    }

    rpc ssh-keyDelSSHkeys {
        if-feature feature_list:HAVE_SSH_SERVER;
        description "";
        reference "";
        input  {
            leaf keyDelSSHkeys  {
                type cml_data_types:CML_BOOL_T;

                mandatory true;
                description "";
            }
            leaf vrfName  {
                type cml_data_types:CML_STRING_T {
                    length "0..255";
                }

                mandatory true;
                description "";
            }
        }
    }

    rpc ssh-clearSSHhosts {
        if-feature feature_list:HAVE_SSH_SERVER;
        description "";
        reference "";
        input  {
            leaf clearSSHhosts  {
                type cml_data_types:CML_BOOL_T;

                mandatory true;
                description "";
            }
        }
    }

    rpc ntp-sync-retry {
        if-feature feature_list:HAVE_HOSTP_NTP;
        description "";
        reference "";
        input  {
            leaf vrfName  {
                type cml_data_types:CML_STRING_T {
                    length "0..255";
                }

                mandatory true;
                description "";
            }
        }
    }

    rpc ntp-clear {
        if-feature feature_list:HAVE_HOSTP_NTP;
        description "";
        reference "";
        input  {
            leaf statistics  {
                type cml_data_types:CML_CLEAR_NTP_STATISTICS_T;

                mandatory true;
                description "";
            }
        }
    }

    rpc aaa-lockout {
        if-feature feature_list:HAVE_HOSTPD;
        if-feature feature_list:HAVE_AAA;
        description "";
        reference "";
        input  {
            leaf username  {
                type cml_data_types:CML_STRING_T {
                    length "2..15";
                }

                mandatory true;
                description "";
            }
        }
    }

    rpc sflow-clearaccess-listlog-cache {
        if-feature feature_list:HAVE_CUSTOM1_ACL;
        description "";
        reference "";
    }

    rpc sflow-clearsflowstatistics {
        description "";
        reference "";
        input  {
            leaf interface  {
                type cml_data_types:CML_STRING_T {
                    length "0..255";
                }

                mandatory true;
                description "";
            }
        }
    }

    rpc libsyslog-cleardebuglogfile {
        description "";
        reference "";
    }

    rpc libsyslog-clearlogginglogfile {
        description "";
        reference "";
    }

    rpc license-licenseget {
        if-feature feature_list:HAVE_FLEXLM;
        description "";
        reference "";
        input  {
            leaf sourceCMLSEPinterface  {
                type cml_data_types:CML_STRING_T {
                    length "0..255";
                }

                mandatory true;
                description "";
            }
            leaf url  {
                type cml_data_types:CML_STRING_T {
                    length "0..255";
                }

                mandatory true;
                description "";
            }
        }
    }

    rpc license-licenserefresh {
        if-feature feature_list:HAVE_FLEXLM;
        description "";
        reference "";
        input  {
            leaf licenseCMLSEPfile  {
                type cml_data_types:CML_STRING_T {
                    length "0..255";
                }

                mandatory true;
                description "";
            }
        }
    }

    rpc license-getserver-ip {
        description "";
        reference "";
        input  {
            leaf serverIp  {
                type cml_data_types:CML_IP_ADDR_T {
                    length "0..255";
                }

                mandatory true;
                description "";
            }
            leaf vrfName  {
                type cml_data_types:CML_STRING_T {
                    length "0..255";
                }

                mandatory true;
                description "";
            }
            leaf portNo  {
                type cml_data_types:CML_UINT16_T;

                mandatory true;
                description "";
            }
        }
    }

    rpc license-licenserelease {
        description "";
        reference "";
    }

    rpc pserv-clearCores {
        if-feature feature_list:HAVE_PSERVD;
        if-feature feature_list:HAVE_ZEBOS_CORE_ANALYSER;
        description "";
        reference "";
        input  {
            leaf clearCore  {
                type cml_data_types:CML_STRING_T {
                    length "0..255";
                }

                mandatory true;
                description "";
            }
        }
    }

    rpc mrib4-snmp-restart-mrib {
        if-feature feature_list:HAVE_SNMP;
        description "";
        reference "";
    }

    rpc mrib4-mrib-bulking-start {
        if-feature feature_list:HAVE_ASYNC;
        description "";
        reference "";
    }

    rpc mrib4-mrib-bulking-stop {
        if-feature feature_list:HAVE_ASYNC;
        description "";
        reference "";
    }

    rpc mrib4-mrib-bulking-flush {
        if-feature feature_list:HAVE_ASYNC;
        description "";
        reference "";
    }

    rpc mrib4-clear-mrib-vrf-all {
        description "";
        reference "";
        input  {
            leaf vrId  {
                type cml_data_types:CML_UINT32_T;

                mandatory true;
                description "";
            }
            leaf vrfName  {
                type cml_data_types:CML_STRING_T {
                    length "0..255";
                }

                mandatory true;
                description "";
            }
            leaf allroute  {
                type cml_data_types:CML_BOOL_T;

                mandatory true;
                description "";
            }
        }
    }

    rpc mrib4-clear-mrib-grp {
        description "";
        reference "";
        input  {
            leaf vrId  {
                type cml_data_types:CML_UINT32_T;

                mandatory true;
                description "";
            }
            leaf vrfName  {
                type cml_data_types:CML_STRING_T {
                    length "0..255";
                }

                mandatory true;
                description "";
            }
            leaf grpAddr  {
                type cml_data_types:CML_IPV4_ADDR_T;

                mandatory true;
                description "";
            }
        }
    }

    rpc mrib4-clear-mrib-vrf-src-grp {
        description "";
        reference "";
        input  {
            leaf vrId  {
                type cml_data_types:CML_UINT32_T;

                mandatory true;
                description "";
            }
            leaf vrfName  {
                type cml_data_types:CML_STRING_T {
                    length "0..255";
                }

                mandatory true;
                description "";
            }
            leaf srcAddr  {
                type cml_data_types:CML_IPV4_ADDR_T;

                mandatory true;
                description "";
            }
            leaf grpAddr  {
                type cml_data_types:CML_IPV4_ADDR_T;

                mandatory true;
                description "";
            }
        }
    }

    rpc mrib4-clear-mrib-stats-all {
        description "";
        reference "";
        input  {
            leaf vrId  {
                type cml_data_types:CML_UINT32_T;

                mandatory true;
                description "";
            }
            leaf vrfName  {
                type cml_data_types:CML_STRING_T {
                    length "0..255";
                }

                mandatory true;
                description "";
            }
            leaf allroute  {
                type cml_data_types:CML_BOOL_T;

                mandatory true;
                description "";
            }
        }
    }

    rpc mrib4-clear-mrib-vrf-grp-stats {
        description "";
        reference "";
        input  {
            leaf vrId  {
                type cml_data_types:CML_UINT32_T;

                mandatory true;
                description "";
            }
            leaf vrfName  {
                type cml_data_types:CML_STRING_T {
                    length "0..255";
                }

                mandatory true;
                description "";
            }
            leaf grpAddr  {
                type cml_data_types:CML_IPV4_ADDR_T;

                mandatory true;
                description "";
            }
        }
    }

    rpc mrib4-clear-mrib-vrf-src-grp-stats {
        description "";
        reference "";
        input  {
            leaf vrId  {
                type cml_data_types:CML_UINT32_T;

                mandatory true;
                description "";
            }
            leaf vrfName  {
                type cml_data_types:CML_STRING_T {
                    length "0..255";
                }

                mandatory true;
                description "";
            }
            leaf srcAddr  {
                type cml_data_types:CML_IPV4_ADDR_T;

                mandatory true;
                description "";
            }
            leaf grpAddr  {
                type cml_data_types:CML_IPV4_ADDR_T;

                mandatory true;
                description "";
            }
        }
    }

    rpc igmp-mrib4-igmp-group-clear {
        description "";
        reference "";
        input  {
            leaf vrfName  {
                type cml_data_types:CML_STRING_T {
                    length "0..255";
                }

                mandatory true;
                description "";
            }
            leaf groupAddr  {
                type cml_data_types:CML_IPV4_ADDR_T;

                mandatory true;
                description "";
            }
            leaf ifName  {
                type cml_data_types:CML_STRING_T {
                    length "0..255";
                }

                mandatory true;
                description "";
            }
        }
    }

    rpc igmp-mrib4-igmp-interface-clear {
        description "";
        reference "";
        input  {
            leaf vrfName  {
                type cml_data_types:CML_STRING_T {
                    length "0..255";
                }

                mandatory true;
                description "";
            }
            leaf ifName  {
                type cml_data_types:CML_STRING_T {
                    length "0..255";
                }

                mandatory true;
                description "";
            }
        }
    }

    rpc igmp-mrib4-igmp-vrfName-clear {
        description "";
        reference "";
        input  {
            leaf vrfName  {
                type cml_data_types:CML_STRING_T {
                    length "0..255";
                }

                mandatory true;
                description "";
            }
        }
    }

    rpc igmp-mrib4-igmp-all-group-clear {
        description "";
        reference "";
        input  {
            leaf vrfName  {
                type cml_data_types:CML_STRING_T {
                    length "0..255";
                }

                mandatory true;
                description "";
            }
            leaf groupAddr  {
                type cml_data_types:CML_IPV4_ADDR_T;

                mandatory true;
                description "";
            }
        }
    }

    rpc igmp-mrib4-igmp-group-clear-all {
        description "";
        reference "";
        input  {
            leaf vrfName  {
                type cml_data_types:CML_STRING_T {
                    length "0..255";
                }

                mandatory true;
                description "";
            }
            leaf clearAll  {
                type cml_data_types:CML_EMPTY_T;

                mandatory true;
                description "";
            }
        }
    }

    rpc igmpsnooping-igmpsnooping-clear-interface-group {
        description "";
        reference "";
        input  {
            leaf groupAddr  {
                type cml_data_types:CML_IPV4_ADDR_T;

                mandatory true;
                description "";
            }
            leaf ifName  {
                type cml_data_types:CML_STRING_T {
                    length "0..255";
                }

                mandatory true;
                description "";
            }
        }
    }

    rpc igmpsnooping-igmpsnooping-clear-interface {
        description "";
        reference "";
        input  {
            leaf ifName  {
                type cml_data_types:CML_STRING_T {
                    length "0..255";
                }

                mandatory true;
                description "";
            }
        }
    }

    rpc igmpsnooping-igmpsnooping-clear-all {
        description "";
        reference "";
    }

    rpc igmpsnooping-igmpsnooping-clear {
        description "";
        reference "";
    }

    rpc igmpsnooping-igmpsnooping-clear-group {
        description "";
        reference "";
        input  {
            leaf groupAddr  {
                type cml_data_types:CML_IPV4_ADDR_T;

                mandatory true;
                description "";
            }
        }
    }

    rpc pbrport-clear-route-map {
        description "";
        reference "";
        input  {
            leaf vrId  {
                type cml_data_types:CML_UINT32_T;

                mandatory true;
                description "";
            }
            leaf pbrRouteMap  {
                type cml_data_types:CML_STRING_T {
                    length "0..255";
                }

                mandatory true;
                description "";
            }
        }
    }

    rpc hqos-clearStatics {
        description "";
        reference "";
        input  {
            leaf vrId  {
                type cml_data_types:CML_UINT32_T;

                mandatory true;
                description "";
            }
            leaf ifName  {
                type cml_data_types:CML_STRING_T {
                    length "0..255";
                }

                mandatory true;
                description "";
            }
            leaf cosStatValue  {
                type cml_data_types:CML_CLEAR_STAT_QOS_T;

                mandatory true;
                description "";
            }
        }
    }

    rpc cmm-clear-ddm-transceiver-alarm-all {
        description "";
        reference "";
    }

    rpc cmm-clear-ddm-transceiver-alarm {
        description "";
        reference "";
        input  {
            leaf vrId  {
                type cml_data_types:CML_UINT32_T;

                mandatory true;
                description "";
            }
            leaf ifName  {
                type cml_data_types:CML_STRING_T {
                    length "0..255";
                }

                mandatory true;
                description "";
            }
        }
    }

    rpc auth-snmp-restart {
        if-feature feature_list:HAVE_SNMP;
        description "";
        reference "";
    }

    rpc rip-rip-restart {
        if-feature feature_list:HAVE_RIP_GR_SUPPORT;
        if-feature feature_list:HAVE_RESTART;
        description "";
        reference "";
        input  {
            leaf vrId  {
                type cml_data_types:CML_UINT32_T;

                mandatory true;
                description "";
            }
            leaf gracePeriod  {
                type cml_data_types:CML_UINT32_T {
                    range "1..65535";
                }

                mandatory true;
                description "";
            }
        }
    }

    rpc rip-clear-ip-rip-route {
        description "";
        reference "";
        input  {
            leaf vrId  {
                type cml_data_types:CML_UINT32_T;

                mandatory true;
                description "";
            }
            leaf routeCMLSEPtype  {
                type cml_data_types:CML_RIP_ROUTE_T;

                mandatory true;
                description "";
            }
        }
    }

    rpc rip-clear-ip-rip-route-prefix {
        description "";
        reference "";
        input  {
            leaf vrId  {
                type cml_data_types:CML_UINT32_T;

                mandatory true;
                description "";
            }
            leaf routeCMLSEPtypeCMLSEPpre  {
                type cml_data_types:CML_IPV4_ADDR_PREFIX_T;

                mandatory true;
                description "";
            }
        }
    }

    rpc rip-clear-ip-rip-route-vrf-all {
        if-feature feature_list:HAVE_VRF_RIP;
        description "";
        reference "";
        input  {
            leaf vrId  {
                type cml_data_types:CML_UINT32_T;

                mandatory true;
                description "";
            }
            leaf vrfName  {
                type cml_data_types:CML_STRING_T {
                    length "0..255";
                }

                mandatory true;
                description "";
            }
        }
    }

    rpc rip-clear-ip-rip-route-vrf {
        if-feature feature_list:HAVE_VRF_RIP;
        description "";
        reference "";
        input  {
            leaf vrId  {
                type cml_data_types:CML_UINT32_T;

                mandatory true;
                description "";
            }
            leaf vrfName  {
                type cml_data_types:CML_STRING_T {
                    length "0..255";
                }

                mandatory true;
                description "";
            }
            leaf prefixStr  {
                type cml_data_types:CML_IPV4_ADDR_PREFIX_T;

                mandatory true;
                description "";
            }
        }
    }

    rpc rip-clear-ip-rip-stat-interf {
        description "";
        reference "";
        input  {
            leaf vrId  {
                type cml_data_types:CML_UINT32_T;

                mandatory true;
                description "";
            }
            leaf ifName  {
                type cml_data_types:CML_STRING_T {
                    length "0..255";
                }

                mandatory true;
                description "";
            }
        }
    }

    rpc rip-snmp-restart-rip {
        if-feature feature_list:HAVE_SNMP;
        description "";
        reference "";
    }

    rpc rip-clear-ipv4-rip-route-ip {
        if-feature feature_list:HAVE_VRF_RIP;
        description "";
        reference "";
        input  {
            leaf vrId  {
                type cml_data_types:CML_UINT32_T;

                mandatory true;
                description "";
            }
            leaf vrfName  {
                type cml_data_types:CML_STRING_T {
                    length "0..255";
                }

                mandatory true;
                description "";
            }
            leaf prefixStr  {
                type cml_data_types:CML_IPV4_ADDR_PREFIX_T;

                mandatory true;
                description "";
            }
        }
    }

    rpc rip-clear-ipv4-rip-route-all {
        if-feature feature_list:HAVE_VRF_RIP;
        description "";
        reference "";
        input  {
            leaf vrId  {
                type cml_data_types:CML_UINT32_T;

                mandatory true;
                description "";
            }
            leaf vrfName  {
                type cml_data_types:CML_STRING_T {
                    length "0..255";
                }

                mandatory true;
                description "";
            }
        }
    }

    rpc aclinterface-clear-access-list-counters {
        description "";
        reference "";
        input  {
            leaf vrId  {
                type cml_data_types:CML_UINT32_T;

                mandatory true;
                description "";
            }
        }
    }

    rpc aclinterface-clear-access-list-name-counters {
        description "";
        reference "";
        input  {
            leaf vrId  {
                type cml_data_types:CML_UINT32_T;

                mandatory true;
                description "";
            }
            leaf aclName  {
                type cml_data_types:CML_STRING_T {
                    length "0..255";
                }

                mandatory true;
                description "";
            }
        }
    }

    rpc aclinterface-clear-ip-access-list-counters {
        description "";
        reference "";
        input  {
            leaf vrId  {
                type cml_data_types:CML_UINT32_T;

                mandatory true;
                description "";
            }
        }
    }

    rpc aclinterface-clear-ip-access-list-name-counters {
        description "";
        reference "";
        input  {
            leaf vrId  {
                type cml_data_types:CML_UINT32_T;

                mandatory true;
                description "";
            }
            leaf aclName  {
                type cml_data_types:CML_STRING_T {
                    length "0..255";
                }

                mandatory true;
                description "";
            }
        }
    }

    rpc aclinterface-clear-ipv6-access-list-counters {
        description "";
        reference "";
        input  {
            leaf vrId  {
                type cml_data_types:CML_UINT32_T;

                mandatory true;
                description "";
            }
        }
    }

    rpc aclinterface-clear-ipv6-access-list-name-counters {
        description "";
        reference "";
        input  {
            leaf vrId  {
                type cml_data_types:CML_UINT32_T;

                mandatory true;
                description "";
            }
            leaf aclName  {
                type cml_data_types:CML_STRING_T {
                    length "0..255";
                }

                mandatory true;
                description "";
            }
        }
    }

    rpc aclinterface-clear-mac-access-list-counters {
        description "";
        reference "";
        input  {
            leaf vrId  {
                type cml_data_types:CML_UINT32_T;

                mandatory true;
                description "";
            }
        }
    }

    rpc aclinterface-clear-mac-access-list-name-counters {
        description "";
        reference "";
        input  {
            leaf vrId  {
                type cml_data_types:CML_UINT32_T;

                mandatory true;
                description "";
            }
            leaf aclName  {
                type cml_data_types:CML_STRING_T {
                    length "0..255";
                }

                mandatory true;
                description "";
            }
        }
    }

    rpc aclinterface-clear-arp-access-list-counters {
        description "";
        reference "";
        input  {
            leaf vrId  {
                type cml_data_types:CML_UINT32_T;

                mandatory true;
                description "";
            }
        }
    }

    rpc aclinterface-clear-arp-access-list-name-counters {
        description "";
        reference "";
        input  {
            leaf vrId  {
                type cml_data_types:CML_UINT32_T;

                mandatory true;
                description "";
            }
            leaf aclName  {
                type cml_data_types:CML_STRING_T {
                    length "0..255";
                }

                mandatory true;
                description "";
            }
        }
    }

    rpc ras-clear-hsl-ipc-stat-values {
        description "";
        reference "";
        input  {
            leaf startCMLSEPvalue  {
                type cml_data_types:CML_UINT16_T;

                mandatory true;
                description "";
            }
            leaf endCMLSEPvalue  {
                type cml_data_types:CML_UINT16_T;

                mandatory true;
                description "";
            }
        }
    }

    rpc ras-clear-hsl-ipc-stat {
        description "";
        reference "";
    }

    rpc ras-clear-hsl-mlag-mac-sync {
        if-feature feature_list:HAVE_MLAG;
        description "";
        reference "";
    }

    rpc ras-clear-hardware-discard-counters {
        description "";
        reference "";
    }

    rpc ras-clear-hsl-fdb-debug-counters {
        description "";
        reference "";
    }

    rpc ripng-clear-ipv6-rip-route {
        description "";
        reference "";
        input  {
            leaf vrId  {
                type cml_data_types:CML_UINT32_T;

                mandatory true;
                description "";
            }
            leaf routeCMLSEPtype  {
                type cml_data_types:CML_RIPNG_ROUTE_T;

                mandatory true;
                description "";
            }
        }
    }

    rpc ripng-clear-ipv6-rip-route-prefix {
        description "";
        reference "";
        input  {
            leaf vrId  {
                type cml_data_types:CML_UINT32_T;

                mandatory true;
                description "";
            }
            leaf routeCMLSEPtypeCMLSEPpre  {
                type cml_data_types:CML_IPV6_PREFIX_T;

                mandatory true;
                description "";
            }
        }
    }

    rpc ndd-cleararp {
        description "";
        reference "";
        input  {
            leaf vrId  {
                type cml_data_types:CML_UINT32_T;

                mandatory true;
                description "";
            }
            leaf ipAddr  {
                type cml_data_types:CML_IPV4_ADDR_T;

                mandatory true;
                description "";
            }
            leaf vrfName  {
                type cml_data_types:CML_VRF_NAME_T {
                    length "0..255";
                }

                mandatory true;
                description "";
            }
        }
    }

    rpc ndd-cleararpIfname {
        description "";
        reference "";
        input  {
            leaf vrId  {
                type cml_data_types:CML_UINT32_T;

                mandatory true;
                description "";
            }
            leaf ifName  {
                type cml_data_types:CML_STRING_T {
                    length "0..255";
                }

                mandatory true;
                description "";
            }
            leaf vrfName  {
                type cml_data_types:CML_VRF_NAME_T {
                    length "0..255";
                }

                mandatory true;
                description "";
            }
        }
    }

    rpc ndd-clearipv6neigbour {
        description "";
        reference "";
        input  {
            leaf vrId  {
                type cml_data_types:CML_UINT32_T;

                mandatory true;
                description "";
            }
            leaf ipv6Addr  {
                type cml_data_types:CML_IPV6_ADDR_T;

                mandatory true;
                description "";
            }
            leaf vrfName  {
                type cml_data_types:CML_VRF_NAME_T {
                    length "0..255";
                }

                mandatory true;
                description "";
            }
        }
    }

    rpc ndd-clearipv6neigbourifname {
        description "";
        reference "";
        input  {
            leaf vrId  {
                type cml_data_types:CML_UINT32_T;

                mandatory true;
                description "";
            }
            leaf ifName  {
                type cml_data_types:CML_STRING_T {
                    length "0..255";
                }

                mandatory true;
                description "";
            }
            leaf vrfName  {
                type cml_data_types:CML_VRF_NAME_T {
                    length "0..255";
                }

                mandatory true;
                description "";
            }
        }
    }

    rpc imi-clearUser {
        if-feature feature_list:HAVE_IMI;
        description "";
        reference "";
        input  {
            leaf vrId  {
                type cml_data_types:CML_UINT32_T;

                mandatory true;
                description "";
            }
            leaf clearUser  {
                type cml_data_types:CML_STRING_T {
                    length "1..28";
                }

                mandatory true;
                description "";
            }
        }
    }

    rpc imi-clearLine {
        if-feature feature_list:HAVE_IMI;
        description "";
        reference "";
        input  {
            leaf vrId  {
                type cml_data_types:CML_UINT32_T;

                mandatory true;
                description "";
            }
            leaf clearLine  {
                type cml_data_types:CML_STRING_T {
                    length "1..64";
                }

                mandatory true;
                description "";
            }
        }
    }

    rpc nat-clear {
        description "";
        reference "";
    }

    rpc erpsv2-clear-aps-statistics {
        description "";
        reference "";
        input  {
            leaf vrId  {
                type cml_data_types:CML_UINT32_T;

                mandatory true;
                description "";
            }
            leaf bridgeId  {
                type cml_data_types:CML_STRING_T {
                    length "0..255";
                }

                mandatory true;
                description "";
            }
            leaf instName  {
                type cml_data_types:CML_STRING_T {
                    length "0..255";
                }

                mandatory true;
                description "";
            }
        }
    }

    rpc erpsv2-switch-erp-instance {
        description "";
        reference "";
        input  {
            leaf vrId  {
                type cml_data_types:CML_UINT32_T;

                mandatory true;
                description "";
            }
            leaf bridgeId  {
                type cml_data_types:CML_STRING_T {
                    length "0..255";
                }

                mandatory true;
                description "";
            }
            leaf instName  {
                type cml_data_types:CML_STRING_T {
                    length "0..255";
                }

                mandatory true;
                description "Uniquely identifies ring instance.";
            }
            leaf operation  {
                type cml_data_types:ERPS_SWITCH_OPERATION_TYPE;

                mandatory true;
                description "G.8032 administrative operation types.";
            }
            leaf portId  {
                type cml_data_types:ERPS_PORT_ID_TYPE;

                mandatory true;
                description "Ring port to perform switch operation.";
            }
        }
    }

    rpc erpsv2-clear-ring-instance {
        description "";
        reference "";
        input  {
            leaf vrId  {
                type cml_data_types:CML_UINT32_T;

                mandatory true;
                description "";
            }
            leaf bridgeId  {
                type cml_data_types:CML_STRING_T {
                    length "0..255";
                }

                mandatory true;
                description "";
            }
            leaf instName  {
                type cml_data_types:CML_STRING_T {
                    length "0..255";
                }

                mandatory true;
                description "Uniquely identifies ring instance.";
            }
        }
    }

    rpc cfm-clear-ethernet-cfm-traceroute-cache {
        description "";
        reference "";
        input  {
            leaf bridgeId  {
                type cml_data_types:CML_STRING_T {
                    length "0..255";
                }

                mandatory true;
                description "";
            }
        }
    }

    rpc cfm-clear-ethernet-cfm-traceroute-cache-mpls {
        if-feature feature_list:HAVE_MPLS_VC;
        description "";
        reference "";
        input  {
            leaf bridgeType  {
                type cml_data_types:CFM_BRIDGE_TYPE;

                mandatory true;
                description "";
            }
        }
    }

    rpc cfm-clear-ethernet-cfm-maintenance-points-remote-by-domain-name {
        if-feature feature_list:HAVE_MPLS_VC;
        description "";
        reference "";
        input  {
            leaf bridgeType  {
                type cml_data_types:CFM_BRIDGE_TYPE;

                mandatory true;
                description "";
            }
            leaf domainName  {
                type cml_data_types:CML_STRING_T {
                    length "0..255";
                }

                mandatory true;
                description "";
            }
        }
    }

    rpc cfm-clear-ethernet-cfm-maintenance-points-remote-by-domain-name-bridge {
        description "";
        reference "";
        input  {
            leaf bridgeId  {
                type cml_data_types:CML_STRING_T {
                    length "0..255";
                }

                mandatory true;
                description "";
            }
            leaf domainName  {
                type cml_data_types:CML_STRING_T {
                    length "0..255";
                }

                mandatory true;
                description "";
            }
        }
    }

    rpc cfm-clear-stats-all {
        if-feature feature_list:CCM_HW_OFFLOAD;
        description "";
        reference "";
    }

    rpc cfm-clear-stats {
        if-feature feature_list:CCM_HW_OFFLOAD;
        description "";
        reference "";
        input  {
            leaf bridgeId  {
                type cml_data_types:CML_STRING_T {
                    length "0..255";
                }

                mandatory true;
                description "";
            }
            leaf domainName  {
                type cml_data_types:CML_STRING_T {
                    length "0..255";
                }

                mandatory true;
                description "";
            }
            leaf mepId  {
                type cml_data_types:CML_UINT16_T;

                mandatory true;
                description "";
            }
            leaf vlanId  {
                type cml_data_types:CML_UINT16_T;

                mandatory true;
                description "";
            }
        }
    }

    rpc cfm-cfm-snmp-restart {
        description "";
        reference "";
    }

    rpc cfm-abort-loss-measurement {
        if-feature feature_list:Y1731_HW_OFFLOAD;
        description "";
        reference "";
        input  {
            leaf bridgeId  {
                type cml_data_types:CML_STRING_T {
                    length "0..255";
                }

                mandatory true;
                description "";
            }
            leaf domainName  {
                type cml_data_types:CML_STRING_T {
                    length "0..255";
                }

                mandatory true;
                description "";
            }
            leaf vlanId  {
                type cml_data_types:CML_UINT32_T {
                    range "2..4094";
                }

                mandatory true;
                description "";
            }
            leaf mepId  {
                type cml_data_types:CML_UINT16_T;

                mandatory true;
                description "";
            }
        }
    }

    rpc cfm-clearhistory {
        if-feature feature_list:Y1731_HW_OFFLOAD;
        description "";
        reference "";
        input  {
            leaf bridgeId  {
                type cml_data_types:CML_STRING_T {
                    length "0..255";
                }

                mandatory true;
                description "";
            }
            leaf domainName  {
                type cml_data_types:CML_STRING_T {
                    length "0..255";
                }

                mandatory true;
                description "";
            }
            leaf vlanId  {
                type cml_data_types:CML_UINT16_T {
                    range "2..4094";
                }

                mandatory true;
                description "";
            }
            leaf mepId  {
                type cml_data_types:CML_UINT16_T;

                mandatory true;
                description "";
            }
        }
    }

    rpc cfm-cfm-lm-ondemand-start-immediate-stop-none {
        if-feature feature_list:Y1731_HW_OFFLOAD;
        description "";
        reference "";
        input  {
            leaf vrId  {
                type cml_data_types:CML_UINT32_T;

                mandatory true;
                description "";
            }
            leaf bridgeId  {
                type cml_data_types:CML_STRING_T {
                    length "0..255";
                }

                mandatory true;
                description "";
            }
            leaf mdName  {
                type cml_data_types:CML_STRING_T {
                    length "0..255";
                }

                mandatory true;
                description "";
            }
            leaf vlanId  {
                type cml_data_types:CML_UINT16_T {
                    range "2..4094";
                }

                mandatory true;
                description "";
            }
            leaf mepIdentifier  {
                type cml_data_types:CML_UINT16_T;

                mandatory true;
                description "";
            }
            leaf lmProfileName  {
                type cml_data_types:CML_STRING_T {
                    length "0..64";
                }

                mandatory true;
                description "";
            }
            leaf macAddress  {
                type cml_data_types:CML_RMEP_MAC_ADDR_T {
                    length "0..255";
                }

                mandatory true;
                description "";
            }
            leaf startType  {
                type cml_data_types:CML_STARTTIME_T;

                mandatory true;
                description "";
            }
            leaf stopType  {
                type cml_data_types:CML_STOPTIME_T;

                mandatory true;
                description "";
            }
            leaf repetitionPeriod  {
                type cml_data_types:CML_TIMETICKS_T {
                    range "6000..4294967295";
                }

                mandatory true;
                description "";
            }
        }
    }

    rpc cfm-cfm-lm-start-proactive {
        if-feature feature_list:Y1731_HW_OFFLOAD;
        description "";
        reference "";
        input  {
            leaf vrId  {
                type cml_data_types:CML_UINT32_T;

                mandatory true;
                description "";
            }
            leaf bridgeId  {
                type cml_data_types:CML_STRING_T {
                    length "0..255";
                }

                mandatory true;
                description "";
            }
            leaf mdName  {
                type cml_data_types:CML_STRING_T {
                    length "0..255";
                }

                mandatory true;
                description "";
            }
            leaf vlanId  {
                type cml_data_types:CML_UINT16_T {
                    range "2..4094";
                }

                mandatory true;
                description "";
            }
            leaf mepIdentifier  {
                type cml_data_types:CML_UINT16_T;

                mandatory true;
                description "";
            }
            leaf lmProfileName  {
                type cml_data_types:CML_STRING_T {
                    length "0..64";
                }

                mandatory true;
                description "";
            }
            leaf macAddress  {
                type cml_data_types:CML_RMEP_MAC_ADDR_T {
                    length "0..255";
                }

                mandatory true;
                description "";
            }
        }
    }

    rpc cfm-cfm-lm-ondemand-start-relative-stop-relative {
        if-feature feature_list:Y1731_HW_OFFLOAD;
        description "";
        reference "";
        input  {
            leaf vrId  {
                type cml_data_types:CML_UINT32_T;

                mandatory true;
                description "";
            }
            leaf bridgeId  {
                type cml_data_types:CML_STRING_T {
                    length "0..255";
                }

                mandatory true;
                description "";
            }
            leaf mdName  {
                type cml_data_types:CML_STRING_T {
                    length "0..255";
                }

                mandatory true;
                description "";
            }
            leaf vlanId  {
                type cml_data_types:CML_UINT16_T {
                    range "2..4094";
                }

                mandatory true;
                description "";
            }
            leaf mepIdentifier  {
                type cml_data_types:CML_UINT16_T;

                mandatory true;
                description "";
            }
            leaf lmProfileName  {
                type cml_data_types:CML_STRING_T {
                    length "0..64";
                }

                mandatory true;
                description "";
            }
            leaf macAddress  {
                type cml_data_types:CML_RMEP_MAC_ADDR_T {
                    length "0..255";
                }

                mandatory true;
                description "";
            }
            leaf startType  {
                type cml_data_types:CML_RELATIVE_T;

                mandatory true;
                description "";
            }
            leaf startTime  {
                type cml_data_types:CML_STRING_T {
                    length "0..255";
                }

                mandatory true;
                description "";
            }
            leaf stopType  {
                type cml_data_types:CML_RELATIVE_T;

                mandatory true;
                description "";
            }
            leaf stopTime  {
                type cml_data_types:CML_STRING_T {
                    length "0..255";
                }

                mandatory true;
                description "";
            }
            leaf repetitionPeriod  {
                type cml_data_types:CML_TIMETICKS_T {
                    range "6000..4294967295";
                }

                mandatory true;
                description "";
            }
        }
    }

    rpc cfm-cfm-lm-ondemand-start-relative-stop-none {
        if-feature feature_list:Y1731_HW_OFFLOAD;
        description "";
        reference "";
        input  {
            leaf vrId  {
                type cml_data_types:CML_UINT32_T;

                mandatory true;
                description "";
            }
            leaf bridgeId  {
                type cml_data_types:CML_STRING_T {
                    length "0..255";
                }

                mandatory true;
                description "";
            }
            leaf mdName  {
                type cml_data_types:CML_STRING_T {
                    length "0..255";
                }

                mandatory true;
                description "";
            }
            leaf vlanId  {
                type cml_data_types:CML_UINT16_T {
                    range "2..4094";
                }

                mandatory true;
                description "";
            }
            leaf mepIdentifier  {
                type cml_data_types:CML_UINT16_T;

                mandatory true;
                description "";
            }
            leaf lmProfileName  {
                type cml_data_types:CML_STRING_T {
                    length "0..64";
                }

                mandatory true;
                description "";
            }
            leaf macAddress  {
                type cml_data_types:CML_RMEP_MAC_ADDR_T {
                    length "0..255";
                }

                mandatory true;
                description "";
            }
            leaf startType  {
                type cml_data_types:CML_RELATIVE_T;

                mandatory true;
                description "";
            }
            leaf startTime  {
                type cml_data_types:CML_STRING_T {
                    length "0..255";
                }

                mandatory true;
                description "";
            }
            leaf stopType  {
                type cml_data_types:CML_STOPTIME_T;

                mandatory true;
                description "";
            }
            leaf repetitionPeriod  {
                type cml_data_types:CML_TIMETICKS_T {
                    range "6000..4294967295";
                }

                mandatory true;
                description "";
            }
        }
    }

    rpc cfm-cfm-lm-ondemand-start-relative-stop-absolute {
        if-feature feature_list:Y1731_HW_OFFLOAD;
        description "";
        reference "";
        input  {
            leaf vrId  {
                type cml_data_types:CML_UINT32_T;

                mandatory true;
                description "";
            }
            leaf bridgeId  {
                type cml_data_types:CML_STRING_T {
                    length "0..255";
                }

                mandatory true;
                description "";
            }
            leaf mdName  {
                type cml_data_types:CML_STRING_T {
                    length "0..255";
                }

                mandatory true;
                description "";
            }
            leaf vlanId  {
                type cml_data_types:CML_UINT16_T {
                    range "2..4094";
                }

                mandatory true;
                description "";
            }
            leaf mepIdentifier  {
                type cml_data_types:CML_UINT16_T;

                mandatory true;
                description "";
            }
            leaf lmProfileName  {
                type cml_data_types:CML_STRING_T {
                    length "0..64";
                }

                mandatory true;
                description "";
            }
            leaf macAddress  {
                type cml_data_types:CML_RMEP_MAC_ADDR_T {
                    length "0..255";
                }

                mandatory true;
                description "";
            }
            leaf startType  {
                type cml_data_types:CML_RELATIVE_T;

                mandatory true;
                description "";
            }
            leaf startTime  {
                type cml_data_types:CML_STRING_T {
                    length "0..255";
                }

                mandatory true;
                description "";
            }
            leaf stopType  {
                type cml_data_types:CML_ABSOLUTE_T;

                mandatory true;
                description "";
            }
            leaf stopTime  {
                type cml_data_types:CML_STRING_T {
                    length "0..255";
                }

                mandatory true;
                description "";
            }
            leaf endDay  {
                type cml_data_types:CML_STRING_T {
                    length "1..31";
                }

                mandatory true;
                description "";
            }
            leaf endMonth  {
                type cml_data_types:CML_STRING_T {
                    length "0..255";
                }

                mandatory true;
                description "";
            }
            leaf endYear  {
                type cml_data_types:CML_INT32_T {
                    range "1993..2035";
                }

                mandatory true;
                description "Year to stop";
            }
            leaf repetitionPeriod  {
                type cml_data_types:CML_TIMETICKS_T {
                    range "6000..4294967295";
                }

                mandatory true;
                description "";
            }
        }
    }

    rpc cfm-cfm-lm-ondemand-start-absolute-stop-absolute {
        if-feature feature_list:Y1731_HW_OFFLOAD;
        description "";
        reference "";
        input  {
            leaf vrId  {
                type cml_data_types:CML_UINT32_T;

                mandatory true;
                description "";
            }
            leaf bridgeId  {
                type cml_data_types:CML_STRING_T {
                    length "0..255";
                }

                mandatory true;
                description "";
            }
            leaf mdName  {
                type cml_data_types:CML_STRING_T {
                    length "0..255";
                }

                mandatory true;
                description "";
            }
            leaf vlanId  {
                type cml_data_types:CML_UINT16_T {
                    range "2..4094";
                }

                mandatory true;
                description "";
            }
            leaf mepIdentifier  {
                type cml_data_types:CML_UINT16_T;

                mandatory true;
                description "";
            }
            leaf lmProfileName  {
                type cml_data_types:CML_STRING_T {
                    length "0..64";
                }

                mandatory true;
                description "";
            }
            leaf macAddress  {
                type cml_data_types:CML_RMEP_MAC_ADDR_T {
                    length "0..255";
                }

                mandatory true;
                description "";
            }
            leaf startType  {
                type cml_data_types:CML_ABSOLUTE_T;

                mandatory true;
                description "";
            }
            leaf startTime  {
                type cml_data_types:CML_STRING_T {
                    length "0..255";
                }

                mandatory true;
                description "";
            }
            leaf startDay  {
                type cml_data_types:CML_STRING_T {
                    length "1..31";
                }

                mandatory true;
                description "";
            }
            leaf startMonth  {
                type cml_data_types:CML_STRING_T {
                    length "0..255";
                }

                mandatory true;
                description "";
            }
            leaf startYear  {
                type cml_data_types:CML_INT32_T {
                    range "1993..2035";
                }

                mandatory true;
                description "Year to start";
            }
            leaf stopType  {
                type cml_data_types:CML_ABSOLUTE_T;

                mandatory true;
                description "";
            }
            leaf stopTime  {
                type cml_data_types:CML_STRING_T {
                    length "0..255";
                }

                mandatory true;
                description "";
            }
            leaf endDay  {
                type cml_data_types:CML_STRING_T {
                    length "1..31";
                }

                mandatory true;
                description "";
            }
            leaf endMonth  {
                type cml_data_types:CML_STRING_T {
                    length "0..255";
                }

                mandatory true;
                description "";
            }
            leaf endYear  {
                type cml_data_types:CML_INT32_T {
                    range "1993..2035";
                }

                mandatory true;
                description "Year to stop";
            }
            leaf repetitionPeriod  {
                type cml_data_types:CML_TIMETICKS_T {
                    range "6000..4294967295";
                }

                mandatory true;
                description "";
            }
        }
    }

    rpc cfm-cfm-lm-ondemand-start-absolute-stop-relative {
        if-feature feature_list:Y1731_HW_OFFLOAD;
        description "";
        reference "";
        input  {
            leaf vrId  {
                type cml_data_types:CML_UINT32_T;

                mandatory true;
                description "";
            }
            leaf bridgeId  {
                type cml_data_types:CML_STRING_T {
                    length "0..255";
                }

                mandatory true;
                description "";
            }
            leaf mdName  {
                type cml_data_types:CML_STRING_T {
                    length "0..255";
                }

                mandatory true;
                description "";
            }
            leaf vlanId  {
                type cml_data_types:CML_UINT16_T {
                    range "2..4094";
                }

                mandatory true;
                description "";
            }
            leaf mepIdentifier  {
                type cml_data_types:CML_UINT16_T;

                mandatory true;
                description "";
            }
            leaf lmProfileName  {
                type cml_data_types:CML_STRING_T {
                    length "0..64";
                }

                mandatory true;
                description "";
            }
            leaf macAddress  {
                type cml_data_types:CML_RMEP_MAC_ADDR_T {
                    length "0..255";
                }

                mandatory true;
                description "";
            }
            leaf startType  {
                type cml_data_types:CML_ABSOLUTE_T;

                mandatory true;
                description "";
            }
            leaf startTime  {
                type cml_data_types:CML_STRING_T {
                    length "0..255";
                }

                mandatory true;
                description "";
            }
            leaf startDay  {
                type cml_data_types:CML_STRING_T {
                    length "1..31";
                }

                mandatory true;
                description "";
            }
            leaf startMonth  {
                type cml_data_types:CML_STRING_T {
                    length "0..255";
                }

                mandatory true;
                description "";
            }
            leaf startYear  {
                type cml_data_types:CML_INT32_T {
                    range "1993..2035";
                }

                mandatory true;
                description "Year to start";
            }
            leaf stopType  {
                type cml_data_types:CML_RELATIVE_T;

                mandatory true;
                description "";
            }
            leaf stopTime  {
                type cml_data_types:CML_STRING_T {
                    length "0..255";
                }

                mandatory true;
                description "";
            }
            leaf repetitionPeriod  {
                type cml_data_types:CML_TIMETICKS_T {
                    range "6000..4294967295";
                }

                mandatory true;
                description "";
            }
        }
    }

    rpc cfm-cfm-lm-ondemand-start-absolute-stop-none {
        if-feature feature_list:Y1731_HW_OFFLOAD;
        description "";
        reference "";
        input  {
            leaf vrId  {
                type cml_data_types:CML_UINT32_T;

                mandatory true;
                description "";
            }
            leaf bridgeId  {
                type cml_data_types:CML_STRING_T {
                    length "0..255";
                }

                mandatory true;
                description "";
            }
            leaf mdName  {
                type cml_data_types:CML_STRING_T {
                    length "0..255";
                }

                mandatory true;
                description "";
            }
            leaf vlanId  {
                type cml_data_types:CML_UINT16_T {
                    range "2..4094";
                }

                mandatory true;
                description "";
            }
            leaf mepIdentifier  {
                type cml_data_types:CML_UINT16_T;

                mandatory true;
                description "";
            }
            leaf lmProfileName  {
                type cml_data_types:CML_STRING_T {
                    length "0..64";
                }

                mandatory true;
                description "";
            }
            leaf macAddress  {
                type cml_data_types:CML_RMEP_MAC_ADDR_T {
                    length "0..255";
                }

                mandatory true;
                description "";
            }
            leaf startType  {
                type cml_data_types:CML_ABSOLUTE_T;

                mandatory true;
                description "";
            }
            leaf startTime  {
                type cml_data_types:CML_STRING_T {
                    length "0..255";
                }

                mandatory true;
                description "";
            }
            leaf startDay  {
                type cml_data_types:CML_STRING_T {
                    length "1..31";
                }

                mandatory true;
                description "";
            }
            leaf startMonth  {
                type cml_data_types:CML_STRING_T {
                    length "0..255";
                }

                mandatory true;
                description "";
            }
            leaf startYear  {
                type cml_data_types:CML_INT32_T {
                    range "1993..2035";
                }

                mandatory true;
                description "Year to start";
            }
            leaf stopType  {
                type cml_data_types:CML_STOPTIME_T;

                mandatory true;
                description "";
            }
            leaf repetitionPeriod  {
                type cml_data_types:CML_TIMETICKS_T {
                    range "6000..4294967295";
                }

                mandatory true;
                description "";
            }
        }
    }

    rpc cfm-cfm-lm-ondemand-start-immediate-stop-absolute {
        if-feature feature_list:Y1731_HW_OFFLOAD;
        description "";
        reference "";
        input  {
            leaf vrId  {
                type cml_data_types:CML_UINT32_T;

                mandatory true;
                description "";
            }
            leaf bridgeId  {
                type cml_data_types:CML_STRING_T {
                    length "0..255";
                }

                mandatory true;
                description "";
            }
            leaf mdName  {
                type cml_data_types:CML_STRING_T {
                    length "0..255";
                }

                mandatory true;
                description "";
            }
            leaf vlanId  {
                type cml_data_types:CML_UINT16_T {
                    range "2..4094";
                }

                mandatory true;
                description "";
            }
            leaf mepIdentifier  {
                type cml_data_types:CML_UINT16_T;

                mandatory true;
                description "";
            }
            leaf lmProfileName  {
                type cml_data_types:CML_STRING_T {
                    length "0..64";
                }

                mandatory true;
                description "";
            }
            leaf macAddress  {
                type cml_data_types:CML_RMEP_MAC_ADDR_T {
                    length "0..255";
                }

                mandatory true;
                description "";
            }
            leaf startType  {
                type cml_data_types:CML_STARTTIME_T;

                mandatory true;
                description "";
            }
            leaf stopType  {
                type cml_data_types:CML_ABSOLUTE_T;

                mandatory true;
                description "";
            }
            leaf stopTime  {
                type cml_data_types:CML_STRING_T {
                    length "0..255";
                }

                mandatory true;
                description "";
            }
            leaf endDay  {
                type cml_data_types:CML_STRING_T {
                    length "1..31";
                }

                mandatory true;
                description "";
            }
            leaf endMonth  {
                type cml_data_types:CML_STRING_T {
                    length "0..255";
                }

                mandatory true;
                description "";
            }
            leaf endYear  {
                type cml_data_types:CML_INT32_T {
                    range "1993..2035";
                }

                mandatory true;
                description "Year to stop";
            }
            leaf repetitionPeriod  {
                type cml_data_types:CML_TIMETICKS_T {
                    range "6000..4294967295";
                }

                mandatory true;
                description "";
            }
        }
    }

    rpc cfm-cfm-lm-ondemand-start-immediate-stop-relative {
        if-feature feature_list:Y1731_HW_OFFLOAD;
        description "";
        reference "";
        input  {
            leaf vrId  {
                type cml_data_types:CML_UINT32_T;

                mandatory true;
                description "";
            }
            leaf bridgeId  {
                type cml_data_types:CML_STRING_T {
                    length "0..255";
                }

                mandatory true;
                description "";
            }
            leaf mdName  {
                type cml_data_types:CML_STRING_T {
                    length "0..255";
                }

                mandatory true;
                description "";
            }
            leaf vlanId  {
                type cml_data_types:CML_UINT16_T {
                    range "2..4094";
                }

                mandatory true;
                description "";
            }
            leaf mepIdentifier  {
                type cml_data_types:CML_UINT16_T;

                mandatory true;
                description "";
            }
            leaf lmProfileName  {
                type cml_data_types:CML_STRING_T {
                    length "0..64";
                }

                mandatory true;
                description "";
            }
            leaf macAddress  {
                type cml_data_types:CML_RMEP_MAC_ADDR_T {
                    length "0..255";
                }

                mandatory true;
                description "";
            }
            leaf startType  {
                type cml_data_types:CML_STARTTIME_T;

                mandatory true;
                description "";
            }
            leaf stopType  {
                type cml_data_types:CML_RELATIVE_T;

                mandatory true;
                description "";
            }
            leaf stopTime  {
                type cml_data_types:CML_STRING_T {
                    length "0..255";
                }

                mandatory true;
                description "";
            }
            leaf repetitionPeriod  {
                type cml_data_types:CML_TIMETICKS_T {
                    range "6000..4294967295";
                }

                mandatory true;
                description "";
            }
        }
    }

    rpc cfm-abort-loss-measurement-mpls {
        if-feature feature_list:Y1731_HW_OFFLOAD;
        if-feature feature_list:HAVE_MPLS_VC;
        description "";
        reference "";
        input  {
            leaf vcName  {
                type cml_data_types:CML_STRING_T {
                    length "0..255";
                }

                mandatory true;
                description "Virtual Circuit";
            }
            leaf domainName  {
                type cml_data_types:CML_STRING_T {
                    length "0..255";
                }

                mandatory true;
                description "";
            }
            leaf mepId  {
                type cml_data_types:CML_UINT16_T;

                mandatory true;
                description "";
            }
        }
    }

    rpc cfm-clearhistory-mpls {
        if-feature feature_list:Y1731_HW_OFFLOAD;
        if-feature feature_list:HAVE_MPLS_VC;
        description "";
        reference "";
        input  {
            leaf vcName  {
                type cml_data_types:CML_STRING_T {
                    length "0..255";
                }

                mandatory true;
                description "Virtual Circuit";
            }
            leaf domainName  {
                type cml_data_types:CML_STRING_T {
                    length "0..255";
                }

                mandatory true;
                description "";
            }
            leaf mepId  {
                type cml_data_types:CML_UINT16_T;

                mandatory true;
                description "";
            }
        }
    }

    rpc cfm-cfm-lm-ondemand-start-immediate-stop-none-mpls {
        if-feature feature_list:Y1731_HW_OFFLOAD;
        if-feature feature_list:HAVE_MPLS_VC;
        description "";
        reference "";
        input  {
            leaf vrId  {
                type cml_data_types:CML_UINT32_T;

                mandatory true;
                description "";
            }
            leaf vcName  {
                type cml_data_types:CML_STRING_T {
                    length "0..255";
                }

                mandatory true;
                description "Virtual Circuit";
            }
            leaf mdName  {
                type cml_data_types:CML_STRING_T {
                    length "0..255";
                }

                mandatory true;
                description "";
            }
            leaf mepIdentifier  {
                type cml_data_types:CML_UINT16_T;

                mandatory true;
                description "";
            }
            leaf lmProfileName  {
                type cml_data_types:CML_STRING_T {
                    length "0..64";
                }

                mandatory true;
                description "";
            }
            leaf macAddress  {
                type cml_data_types:CML_RMEP_MAC_ADDR_T {
                    length "0..255";
                }

                mandatory true;
                description "";
            }
            leaf startType  {
                type cml_data_types:CML_STARTTIME_T;

                mandatory true;
                description "";
            }
            leaf stopType  {
                type cml_data_types:CML_STOPTIME_T;

                mandatory true;
                description "";
            }
            leaf repetitionPeriod  {
                type cml_data_types:CML_TIMETICKS_T {
                    range "6000..4294967295";
                }

                mandatory true;
                description "";
            }
        }
    }

    rpc cfm-cfm-lm-start-proactive-mpls {
        if-feature feature_list:Y1731_HW_OFFLOAD;
        if-feature feature_list:HAVE_MPLS_VC;
        description "";
        reference "";
        input  {
            leaf vrId  {
                type cml_data_types:CML_UINT32_T;

                mandatory true;
                description "";
            }
            leaf vcName  {
                type cml_data_types:CML_STRING_T {
                    length "0..255";
                }

                mandatory true;
                description "Virtual Circuit";
            }
            leaf mdName  {
                type cml_data_types:CML_STRING_T {
                    length "0..255";
                }

                mandatory true;
                description "";
            }
            leaf mepIdentifier  {
                type cml_data_types:CML_UINT16_T;

                mandatory true;
                description "";
            }
            leaf lmProfileName  {
                type cml_data_types:CML_STRING_T {
                    length "0..64";
                }

                mandatory true;
                description "";
            }
            leaf macAddress  {
                type cml_data_types:CML_RMEP_MAC_ADDR_T {
                    length "0..255";
                }

                mandatory true;
                description "";
            }
        }
    }

    rpc cfm-cfm-lm-ondemand-start-relative-stop-relative-mpls {
        if-feature feature_list:Y1731_HW_OFFLOAD;
        if-feature feature_list:HAVE_MPLS_VC;
        description "";
        reference "";
        input  {
            leaf vrId  {
                type cml_data_types:CML_UINT32_T;

                mandatory true;
                description "";
            }
            leaf vcName  {
                type cml_data_types:CML_STRING_T {
                    length "0..255";
                }

                mandatory true;
                description "Virtual Circuit";
            }
            leaf mdName  {
                type cml_data_types:CML_STRING_T {
                    length "0..255";
                }

                mandatory true;
                description "";
            }
            leaf mepIdentifier  {
                type cml_data_types:CML_UINT16_T;

                mandatory true;
                description "";
            }
            leaf lmProfileName  {
                type cml_data_types:CML_STRING_T {
                    length "0..64";
                }

                mandatory true;
                description "";
            }
            leaf macAddress  {
                type cml_data_types:CML_RMEP_MAC_ADDR_T {
                    length "0..255";
                }

                mandatory true;
                description "";
            }
            leaf startType  {
                type cml_data_types:CML_RELATIVE_T;

                mandatory true;
                description "";
            }
            leaf startTime  {
                type cml_data_types:CML_STRING_T {
                    length "0..255";
                }

                mandatory true;
                description "";
            }
            leaf stopType  {
                type cml_data_types:CML_RELATIVE_T;

                mandatory true;
                description "";
            }
            leaf stopTime  {
                type cml_data_types:CML_STRING_T {
                    length "0..255";
                }

                mandatory true;
                description "";
            }
            leaf repetitionPeriod  {
                type cml_data_types:CML_TIMETICKS_T {
                    range "6000..4294967295";
                }

                mandatory true;
                description "";
            }
        }
    }

    rpc cfm-cfm-lm-ondemand-start-relative-stop-none-mpls {
        if-feature feature_list:Y1731_HW_OFFLOAD;
        if-feature feature_list:HAVE_MPLS_VC;
        description "";
        reference "";
        input  {
            leaf vrId  {
                type cml_data_types:CML_UINT32_T;

                mandatory true;
                description "";
            }
            leaf vcName  {
                type cml_data_types:CML_STRING_T {
                    length "0..255";
                }

                mandatory true;
                description "Virtual Circuit";
            }
            leaf mdName  {
                type cml_data_types:CML_STRING_T {
                    length "0..255";
                }

                mandatory true;
                description "";
            }
            leaf mepIdentifier  {
                type cml_data_types:CML_UINT16_T;

                mandatory true;
                description "";
            }
            leaf lmProfileName  {
                type cml_data_types:CML_STRING_T {
                    length "0..64";
                }

                mandatory true;
                description "";
            }
            leaf macAddress  {
                type cml_data_types:CML_RMEP_MAC_ADDR_T {
                    length "0..255";
                }

                mandatory true;
                description "";
            }
            leaf startType  {
                type cml_data_types:CML_RELATIVE_T;

                mandatory true;
                description "";
            }
            leaf startTime  {
                type cml_data_types:CML_STRING_T {
                    length "0..255";
                }

                mandatory true;
                description "";
            }
            leaf stopType  {
                type cml_data_types:CML_STOPTIME_T;

                mandatory true;
                description "";
            }
            leaf repetitionPeriod  {
                type cml_data_types:CML_TIMETICKS_T {
                    range "6000..4294967295";
                }

                mandatory true;
                description "";
            }
        }
    }

    rpc cfm-cfm-lm-ondemand-start-relative-stop-absolute-mpls {
        if-feature feature_list:Y1731_HW_OFFLOAD;
        if-feature feature_list:HAVE_MPLS_VC;
        description "";
        reference "";
        input  {
            leaf vrId  {
                type cml_data_types:CML_UINT32_T;

                mandatory true;
                description "";
            }
            leaf vcName  {
                type cml_data_types:CML_STRING_T {
                    length "0..255";
                }

                mandatory true;
                description "Virtual Circuit";
            }
            leaf mdName  {
                type cml_data_types:CML_STRING_T {
                    length "0..255";
                }

                mandatory true;
                description "";
            }
            leaf mepIdentifier  {
                type cml_data_types:CML_UINT16_T;

                mandatory true;
                description "";
            }
            leaf lmProfileName  {
                type cml_data_types:CML_STRING_T {
                    length "0..64";
                }

                mandatory true;
                description "";
            }
            leaf macAddress  {
                type cml_data_types:CML_RMEP_MAC_ADDR_T {
                    length "0..255";
                }

                mandatory true;
                description "";
            }
            leaf startType  {
                type cml_data_types:CML_RELATIVE_T;

                mandatory true;
                description "";
            }
            leaf startTime  {
                type cml_data_types:CML_STRING_T {
                    length "0..255";
                }

                mandatory true;
                description "";
            }
            leaf stopType  {
                type cml_data_types:CML_ABSOLUTE_T;

                mandatory true;
                description "";
            }
            leaf stopTime  {
                type cml_data_types:CML_STRING_T {
                    length "0..255";
                }

                mandatory true;
                description "";
            }
            leaf endDay  {
                type cml_data_types:CML_STRING_T {
                    length "1..31";
                }

                mandatory true;
                description "";
            }
            leaf endMonth  {
                type cml_data_types:CML_STRING_T {
                    length "0..255";
                }

                mandatory true;
                description "";
            }
            leaf endYear  {
                type cml_data_types:CML_INT32_T {
                    range "1993..2035";
                }

                mandatory true;
                description "Year to stop";
            }
            leaf repetitionPeriod  {
                type cml_data_types:CML_TIMETICKS_T {
                    range "6000..4294967295";
                }

                mandatory true;
                description "";
            }
        }
    }

    rpc cfm-cfm-lm-ondemand-start-absolute-stop-absolute-mpls {
        if-feature feature_list:Y1731_HW_OFFLOAD;
        if-feature feature_list:HAVE_MPLS_VC;
        description "";
        reference "";
        input  {
            leaf vrId  {
                type cml_data_types:CML_UINT32_T;

                mandatory true;
                description "";
            }
            leaf vcName  {
                type cml_data_types:CML_STRING_T {
                    length "0..255";
                }

                mandatory true;
                description "Virtual Circuit";
            }
            leaf mdName  {
                type cml_data_types:CML_STRING_T {
                    length "0..255";
                }

                mandatory true;
                description "";
            }
            leaf mepIdentifier  {
                type cml_data_types:CML_UINT16_T;

                mandatory true;
                description "";
            }
            leaf lmProfileName  {
                type cml_data_types:CML_STRING_T {
                    length "0..64";
                }

                mandatory true;
                description "";
            }
            leaf macAddress  {
                type cml_data_types:CML_RMEP_MAC_ADDR_T {
                    length "0..255";
                }

                mandatory true;
                description "";
            }
            leaf startType  {
                type cml_data_types:CML_ABSOLUTE_T;

                mandatory true;
                description "";
            }
            leaf startTime  {
                type cml_data_types:CML_STRING_T {
                    length "0..255";
                }

                mandatory true;
                description "";
            }
            leaf startDay  {
                type cml_data_types:CML_STRING_T {
                    length "1..31";
                }

                mandatory true;
                description "";
            }
            leaf startMonth  {
                type cml_data_types:CML_STRING_T {
                    length "0..255";
                }

                mandatory true;
                description "";
            }
            leaf startYear  {
                type cml_data_types:CML_INT32_T {
                    range "1993..2035";
                }

                mandatory true;
                description "Year to start";
            }
            leaf stopType  {
                type cml_data_types:CML_ABSOLUTE_T;

                mandatory true;
                description "";
            }
            leaf stopTime  {
                type cml_data_types:CML_STRING_T {
                    length "0..255";
                }

                mandatory true;
                description "";
            }
            leaf endDay  {
                type cml_data_types:CML_STRING_T {
                    length "1..31";
                }

                mandatory true;
                description "";
            }
            leaf endMonth  {
                type cml_data_types:CML_STRING_T {
                    length "0..255";
                }

                mandatory true;
                description "";
            }
            leaf endYear  {
                type cml_data_types:CML_INT32_T {
                    range "1993..2035";
                }

                mandatory true;
                description "Year to stop";
            }
            leaf repetitionPeriod  {
                type cml_data_types:CML_TIMETICKS_T {
                    range "6000..4294967295";
                }

                mandatory true;
                description "";
            }
        }
    }

    rpc cfm-cfm-lm-ondemand-start-absolute-stop-relative-mpls {
        if-feature feature_list:Y1731_HW_OFFLOAD;
        if-feature feature_list:HAVE_MPLS_VC;
        description "";
        reference "";
        input  {
            leaf vrId  {
                type cml_data_types:CML_UINT32_T;

                mandatory true;
                description "";
            }
            leaf vcName  {
                type cml_data_types:CML_STRING_T {
                    length "0..255";
                }

                mandatory true;
                description "Virtual Circuit";
            }
            leaf mdName  {
                type cml_data_types:CML_STRING_T {
                    length "0..255";
                }

                mandatory true;
                description "";
            }
            leaf mepIdentifier  {
                type cml_data_types:CML_UINT16_T;

                mandatory true;
                description "";
            }
            leaf lmProfileName  {
                type cml_data_types:CML_STRING_T {
                    length "0..64";
                }

                mandatory true;
                description "";
            }
            leaf macAddress  {
                type cml_data_types:CML_RMEP_MAC_ADDR_T {
                    length "0..255";
                }

                mandatory true;
                description "";
            }
            leaf startType  {
                type cml_data_types:CML_ABSOLUTE_T;

                mandatory true;
                description "";
            }
            leaf startTime  {
                type cml_data_types:CML_STRING_T {
                    length "0..255";
                }

                mandatory true;
                description "";
            }
            leaf startDay  {
                type cml_data_types:CML_STRING_T {
                    length "1..31";
                }

                mandatory true;
                description "";
            }
            leaf startMonth  {
                type cml_data_types:CML_STRING_T {
                    length "0..255";
                }

                mandatory true;
                description "";
            }
            leaf startYear  {
                type cml_data_types:CML_INT32_T {
                    range "1993..2035";
                }

                mandatory true;
                description "Year to start";
            }
            leaf stopType  {
                type cml_data_types:CML_RELATIVE_T;

                mandatory true;
                description "";
            }
            leaf stopTime  {
                type cml_data_types:CML_STRING_T {
                    length "0..255";
                }

                mandatory true;
                description "";
            }
            leaf repetitionPeriod  {
                type cml_data_types:CML_TIMETICKS_T {
                    range "6000..4294967295";
                }

                mandatory true;
                description "";
            }
        }
    }

    rpc cfm-cfm-lm-ondemand-start-absolute-stop-none-mpls {
        if-feature feature_list:Y1731_HW_OFFLOAD;
        if-feature feature_list:HAVE_MPLS_VC;
        description "";
        reference "";
        input  {
            leaf vrId  {
                type cml_data_types:CML_UINT32_T;

                mandatory true;
                description "";
            }
            leaf vcName  {
                type cml_data_types:CML_STRING_T {
                    length "0..255";
                }

                mandatory true;
                description "Virtual Circuit";
            }
            leaf mdName  {
                type cml_data_types:CML_STRING_T {
                    length "0..255";
                }

                mandatory true;
                description "";
            }
            leaf mepIdentifier  {
                type cml_data_types:CML_UINT16_T;

                mandatory true;
                description "";
            }
            leaf lmProfileName  {
                type cml_data_types:CML_STRING_T {
                    length "0..64";
                }

                mandatory true;
                description "";
            }
            leaf macAddress  {
                type cml_data_types:CML_RMEP_MAC_ADDR_T {
                    length "0..255";
                }

                mandatory true;
                description "";
            }
            leaf startType  {
                type cml_data_types:CML_ABSOLUTE_T;

                mandatory true;
                description "";
            }
            leaf startTime  {
                type cml_data_types:CML_STRING_T {
                    length "0..255";
                }

                mandatory true;
                description "";
            }
            leaf startDay  {
                type cml_data_types:CML_STRING_T {
                    length "1..31";
                }

                mandatory true;
                description "";
            }
            leaf startMonth  {
                type cml_data_types:CML_STRING_T {
                    length "0..255";
                }

                mandatory true;
                description "";
            }
            leaf startYear  {
                type cml_data_types:CML_INT32_T {
                    range "1993..2035";
                }

                mandatory true;
                description "Year to start";
            }
            leaf stopType  {
                type cml_data_types:CML_STOPTIME_T;

                mandatory true;
                description "";
            }
            leaf repetitionPeriod  {
                type cml_data_types:CML_TIMETICKS_T {
                    range "6000..4294967295";
                }

                mandatory true;
                description "";
            }
        }
    }

    rpc cfm-cfm-lm-ondemand-start-immediate-stop-absolute-mpls {
        if-feature feature_list:Y1731_HW_OFFLOAD;
        if-feature feature_list:HAVE_MPLS_VC;
        description "";
        reference "";
        input  {
            leaf vrId  {
                type cml_data_types:CML_UINT32_T;

                mandatory true;
                description "";
            }
            leaf vcName  {
                type cml_data_types:CML_STRING_T {
                    length "0..255";
                }

                mandatory true;
                description "Virtual Circuit";
            }
            leaf mdName  {
                type cml_data_types:CML_STRING_T {
                    length "0..255";
                }

                mandatory true;
                description "";
            }
            leaf mepIdentifier  {
                type cml_data_types:CML_UINT16_T;

                mandatory true;
                description "";
            }
            leaf lmProfileName  {
                type cml_data_types:CML_STRING_T {
                    length "0..64";
                }

                mandatory true;
                description "";
            }
            leaf macAddress  {
                type cml_data_types:CML_RMEP_MAC_ADDR_T {
                    length "0..255";
                }

                mandatory true;
                description "";
            }
            leaf startType  {
                type cml_data_types:CML_STARTTIME_T;

                mandatory true;
                description "";
            }
            leaf stopType  {
                type cml_data_types:CML_ABSOLUTE_T;

                mandatory true;
                description "";
            }
            leaf stopTime  {
                type cml_data_types:CML_STRING_T {
                    length "0..255";
                }

                mandatory true;
                description "";
            }
            leaf endDay  {
                type cml_data_types:CML_STRING_T {
                    length "1..31";
                }

                mandatory true;
                description "";
            }
            leaf endMonth  {
                type cml_data_types:CML_STRING_T {
                    length "0..255";
                }

                mandatory true;
                description "";
            }
            leaf endYear  {
                type cml_data_types:CML_INT32_T {
                    range "1993..2035";
                }

                mandatory true;
                description "Year to stop";
            }
            leaf repetitionPeriod  {
                type cml_data_types:CML_TIMETICKS_T {
                    range "6000..4294967295";
                }

                mandatory true;
                description "";
            }
        }
    }

    rpc cfm-cfm-lm-ondemand-start-immediate-stop-relative-mpls {
        if-feature feature_list:Y1731_HW_OFFLOAD;
        if-feature feature_list:HAVE_MPLS_VC;
        description "";
        reference "";
        input  {
            leaf vrId  {
                type cml_data_types:CML_UINT32_T;

                mandatory true;
                description "";
            }
            leaf vcName  {
                type cml_data_types:CML_STRING_T {
                    length "0..255";
                }

                mandatory true;
                description "Virtual Circuit";
            }
            leaf mdName  {
                type cml_data_types:CML_STRING_T {
                    length "0..255";
                }

                mandatory true;
                description "";
            }
            leaf mepIdentifier  {
                type cml_data_types:CML_UINT16_T;

                mandatory true;
                description "";
            }
            leaf lmProfileName  {
                type cml_data_types:CML_STRING_T {
                    length "0..64";
                }

                mandatory true;
                description "";
            }
            leaf macAddress  {
                type cml_data_types:CML_RMEP_MAC_ADDR_T {
                    length "0..255";
                }

                mandatory true;
                description "";
            }
            leaf startType  {
                type cml_data_types:CML_STARTTIME_T;

                mandatory true;
                description "";
            }
            leaf stopType  {
                type cml_data_types:CML_RELATIVE_T;

                mandatory true;
                description "";
            }
            leaf stopTime  {
                type cml_data_types:CML_STRING_T {
                    length "0..255";
                }

                mandatory true;
                description "";
            }
            leaf repetitionPeriod  {
                type cml_data_types:CML_TIMETICKS_T {
                    range "6000..4294967295";
                }

                mandatory true;
                description "";
            }
        }
    }

    rpc cfm-cfm-dm-start-proactive {
        if-feature feature_list:Y1731_HW_OFFLOAD;
        description "";
        reference "";
        input  {
            leaf vrId  {
                type cml_data_types:CML_UINT32_T;

                mandatory true;
                description "This attribute is used to create a virtual router identifier for a virtual router";
            }
            leaf bridgeId  {
                type cml_data_types:CML_STRING_T {
                    length "0..255";
                }

                mandatory true;
                description "The bridge group name for which the MEP was associated";
            }
            leaf mdName  {
                type cml_data_types:CML_STRING_T {
                    length "0..255";
                }

                mandatory true;
                description "A unique identifier of a Maintenance Domain";
            }
            leaf vlanId  {
                type cml_data_types:CML_UINT16_T {
                    range "2..4094";
                }

                mandatory true;
                description "The Vlan on which this MEP was associated";
            }
            leaf mepIdentifier  {
                type cml_data_types:CML_UINT16_T;

                mandatory true;
                description "The MEP Id of the source MEP";
            }
            leaf dmProfileName  {
                type cml_data_types:CML_STRING_T {
                    length "0..64";
                }

                mandatory true;
                description "This attribute contains the profile name for the SOAM DM Session";
            }
            leaf rmepIdentifier  {
                type cml_data_types:CML_RMEP_TYPE_T {
                    length "0..255";
                }

                mandatory true;
                description "The remote MEP can be identified by either a MAC address or a MEP ID";
            }
        }
    }

    rpc cfm-cfm-dm-ondemand-start-immediate-stop-none {
        if-feature feature_list:Y1731_HW_OFFLOAD;
        description "";
        reference "";
        input  {
            leaf vrId  {
                type cml_data_types:CML_UINT32_T;

                mandatory true;
                description "This attribute is used to create a virtual router identifier for a virtual router";
            }
            leaf bridgeId  {
                type cml_data_types:CML_STRING_T {
                    length "0..255";
                }

                mandatory true;
                description "The bridge group name for which the MEP was associated";
            }
            leaf mdName  {
                type cml_data_types:CML_STRING_T {
                    length "0..255";
                }

                mandatory true;
                description "A unique identifier of a Maintenance Domain";
            }
            leaf vlanId  {
                type cml_data_types:CML_UINT16_T {
                    range "2..4094";
                }

                mandatory true;
                description "The Vlan on which this MEP was associated";
            }
            leaf mepIdentifier  {
                type cml_data_types:CML_UINT16_T;

                mandatory true;
                description "The MEP Id of the source MEP";
            }
            leaf dmProfileName  {
                type cml_data_types:CML_STRING_T {
                    length "0..64";
                }

                mandatory true;
                description "This attribute contains the profile name for the SOAM DM Session";
            }
            leaf rmepIdentifier  {
                type cml_data_types:CML_RMEP_TYPE_T {
                    length "0..255";
                }

                mandatory true;
                description "The remote MEP can be identified by either a MAC address or a MEP ID";
            }
            leaf startType  {
                type cml_data_types:CML_STARTTIME_T;

                mandatory true;
                description "Measurement session start time can be immediate, relative or absolute";
            }
            leaf stopType  {
                type cml_data_types:CML_STOPTIME_T;

                mandatory true;
                description "This attribute defines the session stop time";
            }
            leaf repetitionPeriod  {
                type cml_data_types:CML_TIMETICKS_T {
                    range "6000..4294967295";
                }

                mandatory true;
                description "This object specifies a configurable repetition time between Measurement Intervals in a Measurement session in hundredths of a second";
            }
        }
    }

    rpc cfm-cfm-dm-ondemand-start-relative-stop-relative {
        if-feature feature_list:Y1731_HW_OFFLOAD;
        description "";
        reference "";
        input  {
            leaf vrId  {
                type cml_data_types:CML_UINT32_T;

                mandatory true;
                description "This attribute is used to create a virtual router identifier for a virtual router";
            }
            leaf bridgeId  {
                type cml_data_types:CML_STRING_T {
                    length "0..255";
                }

                mandatory true;
                description "The bridge group name for which the MEP was associated";
            }
            leaf mdName  {
                type cml_data_types:CML_STRING_T {
                    length "0..255";
                }

                mandatory true;
                description "A unique identifier of a Maintenance Domain";
            }
            leaf vlanId  {
                type cml_data_types:CML_UINT16_T {
                    range "2..4094";
                }

                mandatory true;
                description "The Vlan on which this MEP was associated";
            }
            leaf mepIdentifier  {
                type cml_data_types:CML_UINT16_T;

                mandatory true;
                description "The MEP Id of the source MEP";
            }
            leaf dmProfileName  {
                type cml_data_types:CML_STRING_T {
                    length "0..64";
                }

                mandatory true;
                description "This attribute contains the profile name for the SOAM DM Session";
            }
            leaf rmepIdentifier  {
                type cml_data_types:CML_RMEP_TYPE_T {
                    length "0..255";
                }

                mandatory true;
                description "The remote MEP can be identified by either a MAC address or a MEP ID";
            }
            leaf startType  {
                type cml_data_types:CML_RELATIVE_T;

                mandatory true;
                description "Measurement session start time can be immediate, relative or absolute";
            }
            leaf startTime  {
                type cml_data_types:CML_STRING_T {
                    length "0..255";
                }

                mandatory true;
                description "The time that the current Measurement Interval started";
            }
            leaf stopType  {
                type cml_data_types:CML_RELATIVE_T;

                mandatory true;
                description "Measurement session stop time can be none, relative or absolute";
            }
            leaf stopTime  {
                type cml_data_types:CML_STRING_T {
                    length "0..255";
                }

                mandatory true;
                description "This attribute defines the session stop time";
            }
            leaf repetitionPeriod  {
                type cml_data_types:CML_TIMETICKS_T {
                    range "6000..4294967295";
                }

                mandatory true;
                description "This object specifies a configurable repetition time between Measurement Intervals in a Measurement session in hundredths of a second";
            }
        }
    }

    rpc cfm-cfm-dm-ondemand-start-relative-stop-none {
        if-feature feature_list:Y1731_HW_OFFLOAD;
        description "";
        reference "";
        input  {
            leaf vrId  {
                type cml_data_types:CML_UINT32_T;

                mandatory true;
                description "This attribute is used to create a virtual router identifier for a virtual router";
            }
            leaf bridgeId  {
                type cml_data_types:CML_STRING_T {
                    length "0..255";
                }

                mandatory true;
                description "The bridge group name for which the MEP was associated";
            }
            leaf mdName  {
                type cml_data_types:CML_STRING_T {
                    length "0..255";
                }

                mandatory true;
                description "A unique identifier of a Maintenance Domain";
            }
            leaf vlanId  {
                type cml_data_types:CML_UINT16_T {
                    range "2..4094";
                }

                mandatory true;
                description "The Vlan on which this MEP was associated";
            }
            leaf mepIdentifier  {
                type cml_data_types:CML_UINT16_T;

                mandatory true;
                description "The MEP Id of the source MEP";
            }
            leaf dmProfileName  {
                type cml_data_types:CML_STRING_T {
                    length "0..64";
                }

                mandatory true;
                description "This attribute contains the profile name for the SOAM DM Session";
            }
            leaf rmepIdentifier  {
                type cml_data_types:CML_RMEP_TYPE_T {
                    length "0..255";
                }

                mandatory true;
                description "The remote MEP can be identified by either a MAC address or a MEP ID";
            }
            leaf startType  {
                type cml_data_types:CML_RELATIVE_T;

                mandatory true;
                description "Measurement session start time can be immediate, relative or absolute";
            }
            leaf startTime  {
                type cml_data_types:CML_STRING_T {
                    length "0..255";
                }

                mandatory true;
                description "The time that the current Measurement Interval started";
            }
            leaf stopType  {
                type cml_data_types:CML_STOPTIME_T;

                mandatory true;
                description "Measurement session stop time can be none, relative or absolute";
            }
            leaf repetitionPeriod  {
                type cml_data_types:CML_TIMETICKS_T {
                    range "6000..4294967295";
                }

                mandatory true;
                description "This object specifies a configurable repetition time between Measurement Intervals in a Measurement session in hundredths of a second";
            }
        }
    }

    rpc cfm-cfm-dm-ondemand-start-relative-stop-absolute {
        if-feature feature_list:Y1731_HW_OFFLOAD;
        description "";
        reference "";
        input  {
            leaf vrId  {
                type cml_data_types:CML_UINT32_T;

                mandatory true;
                description "This attribute is used to create a virtual router identifier for a virtual router";
            }
            leaf bridgeId  {
                type cml_data_types:CML_STRING_T {
                    length "0..255";
                }

                mandatory true;
                description "The bridge group name for which the MEP was associated";
            }
            leaf mdName  {
                type cml_data_types:CML_STRING_T {
                    length "0..255";
                }

                mandatory true;
                description "A unique identifier of a Maintenance Domain";
            }
            leaf vlanId  {
                type cml_data_types:CML_UINT16_T {
                    range "2..4094";
                }

                mandatory true;
                description "The Vlan on which this MEP was associated";
            }
            leaf mepIdentifier  {
                type cml_data_types:CML_UINT16_T;

                mandatory true;
                description "The MEP Id of the source MEP";
            }
            leaf dmProfileName  {
                type cml_data_types:CML_STRING_T {
                    length "0..64";
                }

                mandatory true;
                description "This attribute contains the profile name for the SOAM DM Session";
            }
            leaf rmepIdentifier  {
                type cml_data_types:CML_RMEP_TYPE_T {
                    length "0..255";
                }

                mandatory true;
                description "The remote MEP can be identified by either a MAC address or a MEP ID";
            }
            leaf startType  {
                type cml_data_types:CML_RELATIVE_T;

                mandatory true;
                description "Measurement session start time can be immediate, relative or absolute";
            }
            leaf startTime  {
                type cml_data_types:CML_STRING_T {
                    length "0..255";
                }

                mandatory true;
                description "The time that the current Measurement Interval started";
            }
            leaf stopType  {
                type cml_data_types:CML_ABSOLUTE_T;

                mandatory true;
                description "Measurement session stop time can be none, relative or absolute";
            }
            leaf stopTime  {
                type cml_data_types:CML_STRING_T {
                    length "0..255";
                }

                mandatory true;
                description "This attribute defines the session stop time";
            }
            leaf eDay  {
                type cml_data_types:CML_UINT32_T {
                    range "1..31";
                }

                mandatory true;
                description "Day of the month";
            }
            leaf eMonth  {
                type cml_data_types:CML_STRING_T {
                    length "0..255";
                }

                mandatory true;
                description "Month of the year to stop (First three letters of the month)";
            }
            leaf eYear  {
                type cml_data_types:CML_INT32_T {
                    range "1993..2035";
                }

                mandatory true;
                description "Year to stop";
            }
            leaf repetitionPeriod  {
                type cml_data_types:CML_TIMETICKS_T {
                    range "6000..4294967295";
                }

                mandatory true;
                description "This object specifies a configurable repetition time between Measurement Intervals in a Measurement session in hundredths of a second";
            }
        }
    }

    rpc cfm-cfm-dm-ondemand-start-absolute-stop-absolute {
        if-feature feature_list:Y1731_HW_OFFLOAD;
        description "";
        reference "";
        input  {
            leaf vrId  {
                type cml_data_types:CML_UINT32_T;

                mandatory true;
                description "This attribute is used to create a virtual router identifier for a virtual router";
            }
            leaf bridgeId  {
                type cml_data_types:CML_STRING_T {
                    length "0..255";
                }

                mandatory true;
                description "The bridge group name for which the MEP was associated";
            }
            leaf mdName  {
                type cml_data_types:CML_STRING_T {
                    length "0..255";
                }

                mandatory true;
                description "A unique identifier of a Maintenance Domain";
            }
            leaf vlanId  {
                type cml_data_types:CML_UINT16_T {
                    range "2..4094";
                }

                mandatory true;
                description "The Vlan on which this MEP was associated";
            }
            leaf mepIdentifier  {
                type cml_data_types:CML_UINT16_T;

                mandatory true;
                description "The MEP Id of the source MEP";
            }
            leaf dmProfileName  {
                type cml_data_types:CML_STRING_T {
                    length "0..64";
                }

                mandatory true;
                description "This attribute contains the profile name for the SOAM DM Session";
            }
            leaf rmepIdentifier  {
                type cml_data_types:CML_RMEP_TYPE_T {
                    length "0..255";
                }

                mandatory true;
                description "The remote MEP can be identified by either a MAC address or a MEP ID";
            }
            leaf startType  {
                type cml_data_types:CML_ABSOLUTE_T;

                mandatory true;
                description "Measurement session start time can be immediate, relative or absolute";
            }
            leaf startTime  {
                type cml_data_types:CML_STRING_T {
                    length "0..255";
                }

                mandatory true;
                description "The time that the current Measurement Interval started";
            }
            leaf sDay  {
                type cml_data_types:CML_UINT8_T {
                    range "1..31";
                }

                mandatory true;
                description "Day of the month to start";
            }
            leaf sMonth  {
                type cml_data_types:CML_STRING_T {
                    length "0..255";
                }

                mandatory true;
                description "Month of the year to start (First three letters of the month)";
            }
            leaf sYear  {
                type cml_data_types:CML_INT32_T {
                    range "1993..2035";
                }

                mandatory true;
                description "Year to start";
            }
            leaf stopType  {
                type cml_data_types:CML_ABSOLUTE_T;

                mandatory true;
                description "Measurement session stop time can be none, relative or absolute";
            }
            leaf stopTime  {
                type cml_data_types:CML_STRING_T {
                    length "0..255";
                }

                mandatory true;
                description "This attribute defines the session stop time";
            }
            leaf eDay  {
                type cml_data_types:CML_UINT32_T {
                    range "1..31";
                }

                mandatory true;
                description "Day of the month";
            }
            leaf eMonth  {
                type cml_data_types:CML_STRING_T {
                    length "0..255";
                }

                mandatory true;
                description "Month of the year to stop (First three letters of the month)";
            }
            leaf eYear  {
                type cml_data_types:CML_INT32_T {
                    range "1993..2035";
                }

                mandatory true;
                description "Year to stop";
            }
            leaf repetitionPeriod  {
                type cml_data_types:CML_TIMETICKS_T {
                    range "6000..4294967295";
                }

                mandatory true;
                description "This object specifies a configurable repetition time between Measurement Intervals in a Measurement session in hundredths of a second";
            }
        }
    }

    rpc cfm-cfm-dm-ondemand-start-absolute-stop-relative {
        if-feature feature_list:Y1731_HW_OFFLOAD;
        description "";
        reference "";
        input  {
            leaf vrId  {
                type cml_data_types:CML_UINT32_T;

                mandatory true;
                description "This attribute is used to create a virtual router identifier for a virtual router";
            }
            leaf bridgeId  {
                type cml_data_types:CML_STRING_T {
                    length "0..255";
                }

                mandatory true;
                description "The bridge group name for which the MEP was associated";
            }
            leaf mdName  {
                type cml_data_types:CML_STRING_T {
                    length "0..255";
                }

                mandatory true;
                description "A unique identifier of a Maintenance Domain";
            }
            leaf vlanId  {
                type cml_data_types:CML_UINT16_T {
                    range "2..4094";
                }

                mandatory true;
                description "The Vlan on which this MEP was associated";
            }
            leaf mepIdentifier  {
                type cml_data_types:CML_UINT16_T;

                mandatory true;
                description "The MEP Id of the source MEP";
            }
            leaf dmProfileName  {
                type cml_data_types:CML_STRING_T {
                    length "0..64";
                }

                mandatory true;
                description "This attribute contains the profile name for the SOAM DM Session";
            }
            leaf rmepIdentifier  {
                type cml_data_types:CML_RMEP_TYPE_T {
                    length "0..255";
                }

                mandatory true;
                description "The remote MEP can be identified by either a MAC address or a MEP ID";
            }
            leaf startType  {
                type cml_data_types:CML_ABSOLUTE_T;

                mandatory true;
                description "Measurement session start time can be immediate, relative or absolute";
            }
            leaf startTime  {
                type cml_data_types:CML_STRING_T {
                    length "0..255";
                }

                mandatory true;
                description "The time that the current Measurement Interval started";
            }
            leaf sDay  {
                type cml_data_types:CML_UINT32_T {
                    range "1..31";
                }

                mandatory true;
                description "Day of the month to start";
            }
            leaf sMonth  {
                type cml_data_types:CML_STRING_T {
                    length "0..255";
                }

                mandatory true;
                description "Month of the year to start (First three letters of the month)";
            }
            leaf sYear  {
                type cml_data_types:CML_INT32_T {
                    range "1993..2035";
                }

                mandatory true;
                description "Year to start";
            }
            leaf stopType  {
                type cml_data_types:CML_RELATIVE_T;

                mandatory true;
                description "Measurement session stop time can be none, relative or absolute";
            }
            leaf stopTime  {
                type cml_data_types:CML_STRING_T {
                    length "0..255";
                }

                mandatory true;
                description "This attribute defines the session stop time";
            }
            leaf repetitionPeriod  {
                type cml_data_types:CML_TIMETICKS_T {
                    range "6000..4294967295";
                }

                mandatory true;
                description "This object specifies a configurable repetition time between Measurement Intervals in a Measurement session in hundredths of a second";
            }
        }
    }

    rpc cfm-cfm-dm-ondemand-start-absolute-stop-none {
        if-feature feature_list:Y1731_HW_OFFLOAD;
        description "";
        reference "";
        input  {
            leaf vrId  {
                type cml_data_types:CML_UINT32_T;

                mandatory true;
                description "This attribute is used to create a virtual router identifier for a virtual router";
            }
            leaf bridgeId  {
                type cml_data_types:CML_STRING_T {
                    length "0..255";
                }

                mandatory true;
                description "The bridge group name for which the MEP was associated";
            }
            leaf mdName  {
                type cml_data_types:CML_STRING_T {
                    length "0..255";
                }

                mandatory true;
                description "A unique identifier of a Maintenance Domain";
            }
            leaf vlanId  {
                type cml_data_types:CML_UINT16_T {
                    range "2..4094";
                }

                mandatory true;
                description "The Vlan on which this MEP was associated";
            }
            leaf mepIdentifier  {
                type cml_data_types:CML_UINT16_T;

                mandatory true;
                description "The MEP Id of the source MEP";
            }
            leaf dmProfileName  {
                type cml_data_types:CML_STRING_T {
                    length "0..64";
                }

                mandatory true;
                description "This attribute contains the profile name for the SOAM DM Session";
            }
            leaf rmepIdentifier  {
                type cml_data_types:CML_RMEP_TYPE_T {
                    length "0..255";
                }

                mandatory true;
                description "The remote MEP can be identified by either a MAC address or a MEP ID";
            }
            leaf startType  {
                type cml_data_types:CML_ABSOLUTE_T;

                mandatory true;
                description "Measurement session start time can be immediate, relative or absolute";
            }
            leaf startTime  {
                type cml_data_types:CML_STRING_T {
                    length "0..255";
                }

                mandatory true;
                description "The time that the current Measurement Interval started";
            }
            leaf sDay  {
                type cml_data_types:CML_UINT32_T {
                    range "1..31";
                }

                mandatory true;
                description "Day of the month to start";
            }
            leaf sMonth  {
                type cml_data_types:CML_STRING_T {
                    length "0..255";
                }

                mandatory true;
                description "Month of the year to start (First three letters of the month)";
            }
            leaf sYear  {
                type cml_data_types:CML_INT32_T {
                    range "1993..2035";
                }

                mandatory true;
                description "Year to start";
            }
            leaf stopType  {
                type cml_data_types:CML_STOPTIME_T;

                mandatory true;
                description "Measurement session stop time can be none, relative or absolute";
            }
            leaf repetitionPeriod  {
                type cml_data_types:CML_TIMETICKS_T {
                    range "6000..4294967295";
                }

                mandatory true;
                description "This object specifies a configurable repetition time between Measurement Intervals in a Measurement session in hundredths of a second";
            }
        }
    }

    rpc cfm-cfm-dm-ondemand-start-immediate-stop-absolute {
        if-feature feature_list:Y1731_HW_OFFLOAD;
        description "";
        reference "";
        input  {
            leaf vrId  {
                type cml_data_types:CML_UINT32_T;

                mandatory true;
                description "This attribute is used to create a virtual router identifier for a virtual router";
            }
            leaf bridgeId  {
                type cml_data_types:CML_STRING_T {
                    length "0..255";
                }

                mandatory true;
                description "The bridge group name for which the MEP was associated";
            }
            leaf mdName  {
                type cml_data_types:CML_STRING_T {
                    length "0..255";
                }

                mandatory true;
                description "A unique identifier of a Maintenance Domain";
            }
            leaf vlanId  {
                type cml_data_types:CML_UINT16_T {
                    range "2..4094";
                }

                mandatory true;
                description "The Vlan on which this MEP was associated";
            }
            leaf mepIdentifier  {
                type cml_data_types:CML_UINT16_T;

                mandatory true;
                description "The MEP Id of the source MEP";
            }
            leaf dmProfileName  {
                type cml_data_types:CML_STRING_T {
                    length "0..64";
                }

                mandatory true;
                description "This attribute contains the profile name for the SOAM DM Session";
            }
            leaf rmepIdentifier  {
                type cml_data_types:CML_RMEP_TYPE_T {
                    length "0..255";
                }

                mandatory true;
                description "The remote MEP can be identified by either a MAC address or a MEP ID";
            }
            leaf startType  {
                type cml_data_types:CML_STARTTIME_T;

                mandatory true;
                description "Measurement session start time can be immediate, relative or absolute";
            }
            leaf stopType  {
                type cml_data_types:CML_ABSOLUTE_T;

                mandatory true;
                description "Measurement session stop time can be none, relative or absolute";
            }
            leaf stopTime  {
                type cml_data_types:CML_STRING_T {
                    length "0..255";
                }

                mandatory true;
                description "This attribute defines the session stop time";
            }
            leaf eDay  {
                type cml_data_types:CML_UINT32_T {
                    range "1..31";
                }

                mandatory true;
                description "Day of the month";
            }
            leaf eMonth  {
                type cml_data_types:CML_STRING_T {
                    length "0..255";
                }

                mandatory true;
                description "Month of the year to stop (First three letters of the month)";
            }
            leaf eYear  {
                type cml_data_types:CML_INT32_T {
                    range "1993..2035";
                }

                mandatory true;
                description "Year to stop";
            }
            leaf repetitionPeriod  {
                type cml_data_types:CML_TIMETICKS_T {
                    range "6000..4294967295";
                }

                mandatory true;
                description "This object specifies a configurable repetition time between Measurement Intervals in a Measurement session in hundredths of a second";
            }
        }
    }

    rpc cfm-cfm-dm-ondemand-start-immediate-stop-relative {
        if-feature feature_list:Y1731_HW_OFFLOAD;
        description "";
        reference "";
        input  {
            leaf vrId  {
                type cml_data_types:CML_UINT32_T;

                mandatory true;
                description "This attribute is used to create a virtual router identifier for a virtual router";
            }
            leaf bridgeId  {
                type cml_data_types:CML_STRING_T {
                    length "0..255";
                }

                mandatory true;
                description "The bridge group name for which the MEP was associated";
            }
            leaf mdName  {
                type cml_data_types:CML_STRING_T {
                    length "0..255";
                }

                mandatory true;
                description "A unique identifier of a Maintenance Domain";
            }
            leaf vlanId  {
                type cml_data_types:CML_UINT16_T {
                    range "2..4094";
                }

                mandatory true;
                description "The Vlan on which this MEP was associated";
            }
            leaf mepIdentifier  {
                type cml_data_types:CML_UINT16_T;

                mandatory true;
                description "The MEP Id of the source MEP";
            }
            leaf dmProfileName  {
                type cml_data_types:CML_STRING_T {
                    length "0..64";
                }

                mandatory true;
                description "This attribute contains the profile name for the SOAM DM Session";
            }
            leaf rmepIdentifier  {
                type cml_data_types:CML_RMEP_TYPE_T {
                    length "0..255";
                }

                mandatory true;
                description "The remote MEP can be identified by either a MAC address or a MEP ID";
            }
            leaf startType  {
                type cml_data_types:CML_STARTTIME_T;

                mandatory true;
                description "Measurement session start time can be immediate, relative or absolute";
            }
            leaf stopType  {
                type cml_data_types:CML_RELATIVE_T;

                mandatory true;
                description "Measurement session stop time can be none, relative or absolute";
            }
            leaf stopTime  {
                type cml_data_types:CML_STRING_T {
                    length "0..255";
                }

                mandatory true;
                description "This attribute defines the session stop time";
            }
            leaf repetitionPeriod  {
                type cml_data_types:CML_TIMETICKS_T {
                    range "6000..4294967295";
                }

                mandatory true;
                description "This object specifies a configurable repetition time between Measurement Intervals in a Measurement session in hundredths of a second";
            }
        }
    }

    rpc cfm-cfm-dm-start-proactive-mpls {
        if-feature feature_list:Y1731_HW_OFFLOAD;
        if-feature feature_list:HAVE_MPLS_VC;
        description "";
        reference "";
        input  {
            leaf vrId  {
                type cml_data_types:CML_UINT32_T;

                mandatory true;
                description "This attribute is used to create a virtual router identifier for a virtual router";
            }
            leaf vcName  {
                type cml_data_types:CML_STRING_T {
                    length "0..255";
                }

                mandatory true;
                description "Virtual Circuit";
            }
            leaf mdName  {
                type cml_data_types:CML_STRING_T {
                    length "0..255";
                }

                mandatory true;
                description "A unique identifier of a Maintenance Domain";
            }
            leaf mepIdentifier  {
                type cml_data_types:CML_UINT16_T;

                mandatory true;
                description "The MEP Id of the source MEP";
            }
            leaf dmProfileName  {
                type cml_data_types:CML_STRING_T {
                    length "0..64";
                }

                mandatory true;
                description "This attribute contains the profile name for the SOAM DM Session";
            }
            leaf rmepIdentifier  {
                type cml_data_types:CML_RMEP_TYPE_T {
                    length "0..255";
                }

                mandatory true;
                description "The remote MEP can be identified by either a MAC address or a MEP ID";
            }
        }
    }

    rpc cfm-cfm-dm-ondemand-start-immediate-stop-none-mpls {
        if-feature feature_list:Y1731_HW_OFFLOAD;
        if-feature feature_list:HAVE_MPLS_VC;
        description "";
        reference "";
        input  {
            leaf vrId  {
                type cml_data_types:CML_UINT32_T;

                mandatory true;
                description "This attribute is used to create a virtual router identifier for a virtual router";
            }
            leaf vcName  {
                type cml_data_types:CML_STRING_T {
                    length "0..255";
                }

                mandatory true;
                description "Virtual Circuit";
            }
            leaf mdName  {
                type cml_data_types:CML_STRING_T {
                    length "0..255";
                }

                mandatory true;
                description "A unique identifier of a Maintenance Domain";
            }
            leaf mepIdentifier  {
                type cml_data_types:CML_UINT16_T;

                mandatory true;
                description "The MEP Id of the source MEP";
            }
            leaf dmProfileName  {
                type cml_data_types:CML_STRING_T {
                    length "0..64";
                }

                mandatory true;
                description "This attribute contains the profile name for the SOAM DM Session";
            }
            leaf rmepIdentifier  {
                type cml_data_types:CML_RMEP_TYPE_T {
                    length "0..255";
                }

                mandatory true;
                description "The remote MEP can be identified by either a MAC address or a MEP ID";
            }
            leaf startType  {
                type cml_data_types:CML_STARTTIME_T;

                mandatory true;
                description "Measurement session start time can be immediate, relative or absolute";
            }
            leaf stopType  {
                type cml_data_types:CML_STOPTIME_T;

                mandatory true;
                description "This attribute defines the session stop time";
            }
            leaf repetitionPeriod  {
                type cml_data_types:CML_TIMETICKS_T {
                    range "6000..4294967295";
                }

                mandatory true;
                description "This object specifies a configurable repetition time between Measurement Intervals in a Measurement session in hundredths of a second";
            }
        }
    }

    rpc cfm-cfm-dm-ondemand-start-relative-stop-relative-mpls {
        if-feature feature_list:Y1731_HW_OFFLOAD;
        if-feature feature_list:HAVE_MPLS_VC;
        description "";
        reference "";
        input  {
            leaf vrId  {
                type cml_data_types:CML_UINT32_T;

                mandatory true;
                description "This attribute is used to create a virtual router identifier for a virtual router";
            }
            leaf vcName  {
                type cml_data_types:CML_STRING_T {
                    length "0..255";
                }

                mandatory true;
                description "Virtual Circuit";
            }
            leaf mdName  {
                type cml_data_types:CML_STRING_T {
                    length "0..255";
                }

                mandatory true;
                description "A unique identifier of a Maintenance Domain";
            }
            leaf mepIdentifier  {
                type cml_data_types:CML_UINT16_T;

                mandatory true;
                description "The MEP Id of the source MEP";
            }
            leaf dmProfileName  {
                type cml_data_types:CML_STRING_T {
                    length "0..64";
                }

                mandatory true;
                description "This attribute contains the profile name for the SOAM DM Session";
            }
            leaf rmepIdentifier  {
                type cml_data_types:CML_RMEP_TYPE_T {
                    length "0..255";
                }

                mandatory true;
                description "The remote MEP can be identified by either a MAC address or a MEP ID";
            }
            leaf startType  {
                type cml_data_types:CML_RELATIVE_T;

                mandatory true;
                description "Measurement session start time can be immediate, relative or absolute";
            }
            leaf startTime  {
                type cml_data_types:CML_STRING_T {
                    length "0..255";
                }

                mandatory true;
                description "The time that the current Measurement Interval started";
            }
            leaf stopType  {
                type cml_data_types:CML_RELATIVE_T;

                mandatory true;
                description "Measurement session stop time can be none, relative or absolute";
            }
            leaf stopTime  {
                type cml_data_types:CML_STRING_T {
                    length "0..255";
                }

                mandatory true;
                description "This attribute defines the session stop time";
            }
            leaf repetitionPeriod  {
                type cml_data_types:CML_TIMETICKS_T {
                    range "6000..4294967295";
                }

                mandatory true;
                description "This object specifies a configurable repetition time between Measurement Intervals in a Measurement session in hundredths of a second";
            }
        }
    }

    rpc cfm-cfm-dm-ondemand-start-relative-stop-none-mpls {
        if-feature feature_list:Y1731_HW_OFFLOAD;
        if-feature feature_list:HAVE_MPLS_VC;
        description "";
        reference "";
        input  {
            leaf vrId  {
                type cml_data_types:CML_UINT32_T;

                mandatory true;
                description "This attribute is used to create a virtual router identifier for a virtual router";
            }
            leaf vcName  {
                type cml_data_types:CML_STRING_T {
                    length "0..255";
                }

                mandatory true;
                description "Virtual Circuit";
            }
            leaf mdName  {
                type cml_data_types:CML_STRING_T {
                    length "0..255";
                }

                mandatory true;
                description "A unique identifier of a Maintenance Domain";
            }
            leaf mepIdentifier  {
                type cml_data_types:CML_UINT16_T;

                mandatory true;
                description "The MEP Id of the source MEP";
            }
            leaf dmProfileName  {
                type cml_data_types:CML_STRING_T {
                    length "0..64";
                }

                mandatory true;
                description "This attribute contains the profile name for the SOAM DM Session";
            }
            leaf rmepIdentifier  {
                type cml_data_types:CML_RMEP_TYPE_T {
                    length "0..255";
                }

                mandatory true;
                description "The remote MEP can be identified by either a MAC address or a MEP ID";
            }
            leaf startType  {
                type cml_data_types:CML_RELATIVE_T;

                mandatory true;
                description "Measurement session start time can be immediate, relative or absolute";
            }
            leaf startTime  {
                type cml_data_types:CML_STRING_T {
                    length "0..255";
                }

                mandatory true;
                description "The time that the current Measurement Interval started";
            }
            leaf stopType  {
                type cml_data_types:CML_STOPTIME_T;

                mandatory true;
                description "Measurement session stop time can be none, relative or absolute";
            }
            leaf repetitionPeriod  {
                type cml_data_types:CML_TIMETICKS_T {
                    range "6000..4294967295";
                }

                mandatory true;
                description "This object specifies a configurable repetition time between Measurement Intervals in a Measurement session in hundredths of a second";
            }
        }
    }

    rpc cfm-cfm-dm-ondemand-start-relative-stop-absolute-mpls {
        if-feature feature_list:Y1731_HW_OFFLOAD;
        if-feature feature_list:HAVE_MPLS_VC;
        description "";
        reference "";
        input  {
            leaf vrId  {
                type cml_data_types:CML_UINT32_T;

                mandatory true;
                description "This attribute is used to create a virtual router identifier for a virtual router";
            }
            leaf vcName  {
                type cml_data_types:CML_STRING_T {
                    length "0..255";
                }

                mandatory true;
                description "Virtual Circuit";
            }
            leaf mdName  {
                type cml_data_types:CML_STRING_T {
                    length "0..255";
                }

                mandatory true;
                description "A unique identifier of a Maintenance Domain";
            }
            leaf mepIdentifier  {
                type cml_data_types:CML_UINT16_T;

                mandatory true;
                description "The MEP Id of the source MEP";
            }
            leaf dmProfileName  {
                type cml_data_types:CML_STRING_T {
                    length "0..64";
                }

                mandatory true;
                description "This attribute contains the profile name for the SOAM DM Session";
            }
            leaf rmepIdentifier  {
                type cml_data_types:CML_RMEP_TYPE_T {
                    length "0..255";
                }

                mandatory true;
                description "The remote MEP can be identified by either a MAC address or a MEP ID";
            }
            leaf startType  {
                type cml_data_types:CML_RELATIVE_T;

                mandatory true;
                description "Measurement session start time can be immediate, relative or absolute";
            }
            leaf startTime  {
                type cml_data_types:CML_STRING_T {
                    length "0..255";
                }

                mandatory true;
                description "The time that the current Measurement Interval started";
            }
            leaf stopType  {
                type cml_data_types:CML_ABSOLUTE_T;

                mandatory true;
                description "Measurement session stop time can be none, relative or absolute";
            }
            leaf stopTime  {
                type cml_data_types:CML_STRING_T {
                    length "0..255";
                }

                mandatory true;
                description "This attribute defines the session stop time";
            }
            leaf eDay  {
                type cml_data_types:CML_UINT32_T {
                    range "1..31";
                }

                mandatory true;
                description "Day of the month";
            }
            leaf eMonth  {
                type cml_data_types:CML_STRING_T {
                    length "0..255";
                }

                mandatory true;
                description "Month of the year to stop (First three letters of the month)";
            }
            leaf eYear  {
                type cml_data_types:CML_INT32_T {
                    range "1993..2035";
                }

                mandatory true;
                description "Year to stop";
            }
            leaf repetitionPeriod  {
                type cml_data_types:CML_TIMETICKS_T {
                    range "6000..4294967295";
                }

                mandatory true;
                description "This object specifies a configurable repetition time between Measurement Intervals in a Measurement session in hundredths of a second";
            }
        }
    }

    rpc cfm-cfm-dm-ondemand-start-absolute-stop-absolute-mpls {
        if-feature feature_list:Y1731_HW_OFFLOAD;
        if-feature feature_list:HAVE_MPLS_VC;
        description "";
        reference "";
        input  {
            leaf vrId  {
                type cml_data_types:CML_UINT32_T;

                mandatory true;
                description "This attribute is used to create a virtual router identifier for a virtual router";
            }
            leaf vcName  {
                type cml_data_types:CML_STRING_T {
                    length "0..255";
                }

                mandatory true;
                description "Virtual Circuit";
            }
            leaf mdName  {
                type cml_data_types:CML_STRING_T {
                    length "0..255";
                }

                mandatory true;
                description "A unique identifier of a Maintenance Domain";
            }
            leaf mepIdentifier  {
                type cml_data_types:CML_UINT16_T;

                mandatory true;
                description "The MEP Id of the source MEP";
            }
            leaf dmProfileName  {
                type cml_data_types:CML_STRING_T {
                    length "0..64";
                }

                mandatory true;
                description "This attribute contains the profile name for the SOAM DM Session";
            }
            leaf rmepIdentifier  {
                type cml_data_types:CML_RMEP_TYPE_T {
                    length "0..255";
                }

                mandatory true;
                description "The remote MEP can be identified by either a MAC address or a MEP ID";
            }
            leaf startType  {
                type cml_data_types:CML_ABSOLUTE_T;

                mandatory true;
                description "Measurement session start time can be immediate, relative or absolute";
            }
            leaf startTime  {
                type cml_data_types:CML_STRING_T {
                    length "0..255";
                }

                mandatory true;
                description "The time that the current Measurement Interval started";
            }
            leaf sDay  {
                type cml_data_types:CML_UINT8_T {
                    range "1..31";
                }

                mandatory true;
                description "Day of the month to start";
            }
            leaf sMonth  {
                type cml_data_types:CML_STRING_T {
                    length "0..255";
                }

                mandatory true;
                description "Month of the year to start (First three letters of the month)";
            }
            leaf sYear  {
                type cml_data_types:CML_INT32_T {
                    range "1993..2035";
                }

                mandatory true;
                description "Year to start";
            }
            leaf stopType  {
                type cml_data_types:CML_ABSOLUTE_T;

                mandatory true;
                description "Measurement session stop time can be none, relative or absolute";
            }
            leaf stopTime  {
                type cml_data_types:CML_STRING_T {
                    length "0..255";
                }

                mandatory true;
                description "This attribute defines the session stop time";
            }
            leaf eDay  {
                type cml_data_types:CML_UINT32_T {
                    range "1..31";
                }

                mandatory true;
                description "Day of the month";
            }
            leaf eMonth  {
                type cml_data_types:CML_STRING_T {
                    length "0..255";
                }

                mandatory true;
                description "Month of the year to stop (First three letters of the month)";
            }
            leaf eYear  {
                type cml_data_types:CML_INT32_T {
                    range "1993..2035";
                }

                mandatory true;
                description "Year to stop";
            }
            leaf repetitionPeriod  {
                type cml_data_types:CML_TIMETICKS_T {
                    range "6000..4294967295";
                }

                mandatory true;
                description "This object specifies a configurable repetition time between Measurement Intervals in a Measurement session in hundredths of a second";
            }
        }
    }

    rpc cfm-cfm-dm-ondemand-start-absolute-stop-relative-mpls {
        if-feature feature_list:Y1731_HW_OFFLOAD;
        if-feature feature_list:HAVE_MPLS_VC;
        description "";
        reference "";
        input  {
            leaf vrId  {
                type cml_data_types:CML_UINT32_T;

                mandatory true;
                description "This attribute is used to create a virtual router identifier for a virtual router";
            }
            leaf vcName  {
                type cml_data_types:CML_STRING_T {
                    length "0..255";
                }

                mandatory true;
                description "Virtual Circuit";
            }
            leaf mdName  {
                type cml_data_types:CML_STRING_T {
                    length "0..255";
                }

                mandatory true;
                description "A unique identifier of a Maintenance Domain";
            }
            leaf mepIdentifier  {
                type cml_data_types:CML_UINT16_T;

                mandatory true;
                description "The MEP Id of the source MEP";
            }
            leaf dmProfileName  {
                type cml_data_types:CML_STRING_T {
                    length "0..64";
                }

                mandatory true;
                description "This attribute contains the profile name for the SOAM DM Session";
            }
            leaf rmepIdentifier  {
                type cml_data_types:CML_RMEP_TYPE_T {
                    length "0..255";
                }

                mandatory true;
                description "The remote MEP can be identified by either a MAC address or a MEP ID";
            }
            leaf startType  {
                type cml_data_types:CML_ABSOLUTE_T;

                mandatory true;
                description "Measurement session start time can be immediate, relative or absolute";
            }
            leaf startTime  {
                type cml_data_types:CML_STRING_T {
                    length "0..255";
                }

                mandatory true;
                description "The time that the current Measurement Interval started";
            }
            leaf sDay  {
                type cml_data_types:CML_UINT32_T {
                    range "1..31";
                }

                mandatory true;
                description "Day of the month to start";
            }
            leaf sMonth  {
                type cml_data_types:CML_STRING_T {
                    length "0..255";
                }

                mandatory true;
                description "Month of the year to start (First three letters of the month)";
            }
            leaf sYear  {
                type cml_data_types:CML_INT32_T {
                    range "1993..2035";
                }

                mandatory true;
                description "Year to start";
            }
            leaf stopType  {
                type cml_data_types:CML_RELATIVE_T;

                mandatory true;
                description "Measurement session stop time can be none, relative or absolute";
            }
            leaf stopTime  {
                type cml_data_types:CML_STRING_T {
                    length "0..255";
                }

                mandatory true;
                description "This attribute defines the session stop time";
            }
            leaf repetitionPeriod  {
                type cml_data_types:CML_TIMETICKS_T {
                    range "6000..4294967295";
                }

                mandatory true;
                description "This object specifies a configurable repetition time between Measurement Intervals in a Measurement session in hundredths of a second";
            }
        }
    }

    rpc cfm-cfm-dm-ondemand-start-absolute-stop-none-mpls {
        if-feature feature_list:Y1731_HW_OFFLOAD;
        if-feature feature_list:HAVE_MPLS_VC;
        description "";
        reference "";
        input  {
            leaf vrId  {
                type cml_data_types:CML_UINT32_T;

                mandatory true;
                description "This attribute is used to create a virtual router identifier for a virtual router";
            }
            leaf vcName  {
                type cml_data_types:CML_STRING_T {
                    length "0..255";
                }

                mandatory true;
                description "Virtual Circuit";
            }
            leaf mdName  {
                type cml_data_types:CML_STRING_T {
                    length "0..255";
                }

                mandatory true;
                description "A unique identifier of a Maintenance Domain";
            }
            leaf mepIdentifier  {
                type cml_data_types:CML_UINT16_T;

                mandatory true;
                description "The MEP Id of the source MEP";
            }
            leaf dmProfileName  {
                type cml_data_types:CML_STRING_T {
                    length "0..64";
                }

                mandatory true;
                description "This attribute contains the profile name for the SOAM DM Session";
            }
            leaf rmepIdentifier  {
                type cml_data_types:CML_RMEP_TYPE_T {
                    length "0..255";
                }

                mandatory true;
                description "The remote MEP can be identified by either a MAC address or a MEP ID";
            }
            leaf startType  {
                type cml_data_types:CML_ABSOLUTE_T;

                mandatory true;
                description "Measurement session start time can be immediate, relative or absolute";
            }
            leaf startTime  {
                type cml_data_types:CML_STRING_T {
                    length "0..255";
                }

                mandatory true;
                description "The time that the current Measurement Interval started";
            }
            leaf sDay  {
                type cml_data_types:CML_UINT32_T {
                    range "1..31";
                }

                mandatory true;
                description "Day of the month to start";
            }
            leaf sMonth  {
                type cml_data_types:CML_STRING_T {
                    length "0..255";
                }

                mandatory true;
                description "Month of the year to start (First three letters of the month)";
            }
            leaf sYear  {
                type cml_data_types:CML_INT32_T {
                    range "1993..2035";
                }

                mandatory true;
                description "Year to start";
            }
            leaf stopType  {
                type cml_data_types:CML_STOPTIME_T;

                mandatory true;
                description "Measurement session stop time can be none, relative or absolute";
            }
            leaf repetitionPeriod  {
                type cml_data_types:CML_TIMETICKS_T {
                    range "6000..4294967295";
                }

                mandatory true;
                description "This object specifies a configurable repetition time between Measurement Intervals in a Measurement session in hundredths of a second";
            }
        }
    }

    rpc cfm-cfm-dm-ondemand-start-immediate-stop-absolute-mpls {
        if-feature feature_list:Y1731_HW_OFFLOAD;
        if-feature feature_list:HAVE_MPLS_VC;
        description "";
        reference "";
        input  {
            leaf vrId  {
                type cml_data_types:CML_UINT32_T;

                mandatory true;
                description "This attribute is used to create a virtual router identifier for a virtual router";
            }
            leaf vcName  {
                type cml_data_types:CML_STRING_T {
                    length "0..255";
                }

                mandatory true;
                description "Virtual Circuit";
            }
            leaf mdName  {
                type cml_data_types:CML_STRING_T {
                    length "0..255";
                }

                mandatory true;
                description "A unique identifier of a Maintenance Domain";
            }
            leaf mepIdentifier  {
                type cml_data_types:CML_UINT16_T;

                mandatory true;
                description "The MEP Id of the source MEP";
            }
            leaf dmProfileName  {
                type cml_data_types:CML_STRING_T {
                    length "0..64";
                }

                mandatory true;
                description "This attribute contains the profile name for the SOAM DM Session";
            }
            leaf rmepIdentifier  {
                type cml_data_types:CML_RMEP_TYPE_T {
                    length "0..255";
                }

                mandatory true;
                description "The remote MEP can be identified by either a MAC address or a MEP ID";
            }
            leaf startType  {
                type cml_data_types:CML_STARTTIME_T;

                mandatory true;
                description "Measurement session start time can be immediate, relative or absolute";
            }
            leaf stopType  {
                type cml_data_types:CML_ABSOLUTE_T;

                mandatory true;
                description "Measurement session stop time can be none, relative or absolute";
            }
            leaf stopTime  {
                type cml_data_types:CML_STRING_T {
                    length "0..255";
                }

                mandatory true;
                description "This attribute defines the session stop time";
            }
            leaf eDay  {
                type cml_data_types:CML_UINT32_T {
                    range "1..31";
                }

                mandatory true;
                description "Day of the month";
            }
            leaf eMonth  {
                type cml_data_types:CML_STRING_T {
                    length "0..255";
                }

                mandatory true;
                description "Month of the year to stop (First three letters of the month)";
            }
            leaf eYear  {
                type cml_data_types:CML_INT32_T {
                    range "1993..2035";
                }

                mandatory true;
                description "Year to stop";
            }
            leaf repetitionPeriod  {
                type cml_data_types:CML_TIMETICKS_T {
                    range "6000..4294967295";
                }

                mandatory true;
                description "This object specifies a configurable repetition time between Measurement Intervals in a Measurement session in hundredths of a second";
            }
        }
    }

    rpc cfm-cfm-dm-ondemand-start-immediate-stop-relative-mpls {
        if-feature feature_list:Y1731_HW_OFFLOAD;
        if-feature feature_list:HAVE_MPLS_VC;
        description "";
        reference "";
        input  {
            leaf vrId  {
                type cml_data_types:CML_UINT32_T;

                mandatory true;
                description "This attribute is used to create a virtual router identifier for a virtual router";
            }
            leaf vcName  {
                type cml_data_types:CML_STRING_T {
                    length "0..255";
                }

                mandatory true;
                description "Virtual Circuit";
            }
            leaf mdName  {
                type cml_data_types:CML_STRING_T {
                    length "0..255";
                }

                mandatory true;
                description "A unique identifier of a Maintenance Domain";
            }
            leaf mepIdentifier  {
                type cml_data_types:CML_UINT16_T;

                mandatory true;
                description "The MEP Id of the source MEP";
            }
            leaf dmProfileName  {
                type cml_data_types:CML_STRING_T {
                    length "0..64";
                }

                mandatory true;
                description "This attribute contains the profile name for the SOAM DM Session";
            }
            leaf rmepIdentifier  {
                type cml_data_types:CML_RMEP_TYPE_T {
                    length "0..255";
                }

                mandatory true;
                description "The remote MEP can be identified by either a MAC address or a MEP ID";
            }
            leaf startType  {
                type cml_data_types:CML_STARTTIME_T;

                mandatory true;
                description "Measurement session start time can be immediate, relative or absolute";
            }
            leaf stopType  {
                type cml_data_types:CML_RELATIVE_T;

                mandatory true;
                description "Measurement session stop time can be none, relative or absolute";
            }
            leaf stopTime  {
                type cml_data_types:CML_STRING_T {
                    length "0..255";
                }

                mandatory true;
                description "This attribute defines the session stop time";
            }
            leaf repetitionPeriod  {
                type cml_data_types:CML_TIMETICKS_T {
                    range "6000..4294967295";
                }

                mandatory true;
                description "This object specifies a configurable repetition time between Measurement Intervals in a Measurement session in hundredths of a second";
            }
        }
    }

    rpc cfm-abort-delay-measurement-mpls {
        if-feature feature_list:Y1731_HW_OFFLOAD;
        if-feature feature_list:HAVE_MPLS_VC;
        description "";
        reference "";
        input  {
            leaf vcName  {
                type cml_data_types:CML_STRING_T {
                    length "0..255";
                }

                mandatory true;
                description "Virtual Circuit";
            }
            leaf domainName  {
                type cml_data_types:CML_STRING_T {
                    length "0..255";
                }

                mandatory true;
                description "A unique identifier of a Maintenance Domain";
            }
            leaf mepId  {
                type cml_data_types:CML_UINT16_T;

                mandatory true;
                description "The MEP Id of the source MEP";
            }
        }
    }

    rpc cfm-abort-delay-measurement {
        if-feature feature_list:Y1731_HW_OFFLOAD;
        description "";
        reference "";
        input  {
            leaf bridgeId  {
                type cml_data_types:CML_STRING_T {
                    length "0..255";
                }

                mandatory true;
                description "The bridge group name for which the MEP was associated";
            }
            leaf domainName  {
                type cml_data_types:CML_STRING_T {
                    length "0..255";
                }

                mandatory true;
                description "A unique identifier of a Maintenance Domain";
            }
            leaf vlanId  {
                type cml_data_types:CML_UINT16_T {
                    range "2..4094";
                }

                mandatory true;
                description "The Vlan on which this MEP was associated";
            }
            leaf mepId  {
                type cml_data_types:CML_UINT16_T;

                mandatory true;
                description "The MEP Id of the source MEP";
            }
        }
    }

    rpc cfm-clear-dm-history-mpls {
        if-feature feature_list:Y1731_HW_OFFLOAD;
        if-feature feature_list:HAVE_MPLS_VC;
        description "";
        reference "";
        input  {
            leaf vcName  {
                type cml_data_types:CML_STRING_T {
                    length "0..255";
                }

                mandatory true;
                description "Virtual Circuit";
            }
            leaf domainName  {
                type cml_data_types:CML_STRING_T {
                    length "0..255";
                }

                mandatory true;
                description "A unique identifier of a Maintenance Domain";
            }
            leaf mepId  {
                type cml_data_types:CML_UINT16_T;

                mandatory true;
                description "The MEP Id of the source MEP";
            }
        }
    }

    rpc cfm-cleardmhistory {
        if-feature feature_list:Y1731_HW_OFFLOAD;
        description "";
        reference "";
        input  {
            leaf bridgeId  {
                type cml_data_types:CML_STRING_T {
                    length "0..255";
                }

                mandatory true;
                description "The bridge group name for which the MEP was associated";
            }
            leaf domainName  {
                type cml_data_types:CML_STRING_T {
                    length "0..255";
                }

                mandatory true;
                description "A unique identifier of a Maintenance Domain";
            }
            leaf vlanId  {
                type cml_data_types:CML_UINT16_T {
                    range "2..4094";
                }

                mandatory true;
                description "The Vlan on which this MEP was associated";
            }
            leaf mepId  {
                type cml_data_types:CML_UINT16_T;

                mandatory true;
                description "The MEP Id of the source MEP";
            }
        }
    }

    rpc ptp-clearPtpStats {
        if-feature feature_list:HAVE_PTP_HW_OFFLOAD;
        description "";
        reference "";
        input  {
            leaf ptpInstance  {
                type cml_data_types:CML_PTP_INSTANCE_T;

                mandatory true;
                description "";
            }
        }
    }

    rpc sysupdate-install {
        description "";
        reference "";
        input  {
            leaf installerName  {
                type cml_data_types:CML_STRING_T {
                    length "0..255";
                }

                mandatory true;
                description "";
            }
        }
    }

    rpc sysupdate-get {
        description "";
        reference "";
        input  {
            leaf sourceInterface  {
                type cml_data_types:CML_STRING_T {
                    length "0..255";
                }

                mandatory true;
                description "";
            }
            leaf url  {
                type cml_data_types:CML_STRING_T {
                    length "0..255";
                }

                mandatory true;
                description "";
            }
        }
    }

    rpc sysupdate-remove {
        description "";
        reference "";
        input  {
            leaf imageName  {
                type cml_data_types:CML_STRING_T {
                    length "0..255";
                }

                mandatory true;
                description "";
            }
        }
    }

    rpc sysupdate-cancel-download {
        description "";
        reference "";
    }

    notification force_unlock {

        description "Notify force unlck from netconf.";

        leaf message {
            type string;
            description " alarm message notification";
        }
    }

    notification system_shutdown_or_reload {

        description "Notify netconf about system shutdown or reload.";

        leaf message {
            type string;
            description " alarm message notification";
        }
    }

    notification config_sync_completion_status {

        description "Notify netconf about config sync being completed.";

        leaf message {
            type string;
            description " alarm message notification";
        }
    }

    notification interface-Errdis-Notif {

        description "The interfaceErrdisNotif is generated when an interface is error-disabled(errDisReason will have non-zero value) and when it recovers from errdisabled state (errDisReason will have '0'). Severity level is CRITICAL for interface going down and MINOR for interface moving to UP state when it recovers from errdisabled state..";

        leaf ifIndex {
            type string;
            description "A unique value, greater than zero, for each interface.It is recommended that values are assigned contiguously starting from 1.The value for each interface sub-layer must remain constant at least from one re-initialization of the entity's network management system to the next re-initialization.";
        }

        leaf vrId {
            type string;
            description "Virtual router id";
        }

        leaf errDisReason {
            type string;
            description "This object specifies the event that caused the interface to be error-disabled. If interface is error-disabled because of lag-mismatch, value of this object is 1. If interface is error-disabled because of stp-bpdu-guard, value of this object is 2. If interface is error-disabled because of link-flap, value of this object is 4.";
        }
    }

    notification agg-Min-Link {

        description "The aggMinLink is generated when a total Active (link-UP) LAG member link count becomes less than the configured min-link count. Severity level is CRITICAL for interface going down and INFO for interface moving to UP state..";

        leaf ifIndex {
            type string;
            description "A unique value, greater than zero, for each interface.It is recommended that values are assigned contiguously starting from 1.The value for each interface sub-layer must remain constant at least from one re-initialization of the entity's network management system to the next re-initialization.";
        }

        leaf vrId {
            type string;
            description "Virtual router id";
        }

        leaf aggDownMinLink {
            type string;
            description "aggDownMinLink Flag is set then Interface moved to Down state Min Links else move to Up state Min Links";
        }
    }

    notification interface-link-state-change-notification {

        description "A linkDown specifies that one of the communication links is about to enter the down state from some other state (but not from the notPresent state).  This other state is indicated by the included value of ifOperStatus. A linkUp trap signifies that one of communication links left the down state and transitioned into some other state (but not into the notPresent state).  This other state is indicated by the included value of ifOperStatus. Severity level is CRITICAL for link state Down and MINOR for link state Up..";

        leaf ifName {
            type string;
            description "The textual name of the interface. The value of this object should be the name of the interface as assigned by the local device and should be suitable for use in commands entered at the device's `console'. This might be a text name, such as `le0' or a simple port number, such as `1', depending on the interface naming syntax of the device. If several entries in the ifTable together represent a single interface as named by the device, then each will have the same value of ifName. Note that for an agent which responds to SNMP queries concerning an interface on some other (proxied) device, then the value of ifName for such an interface is the proxied device's local name for it. If there is no local name, or this object is otherwise not applicable, then this object contains a zero-length string.";
        }

        leaf vrId {
            type string;
            description "Virtual router id";
        }

        leaf ifOperStatus {
            type string;
            description "The current operational state of the interface.  The
            testing(3) state indicates that no operational packets can
            be passed.  If ifAdminStatus is down(2) then ifOperStatus
            should be down(2).  If ifAdminStatus is changed to up(1)
            then ifOperStatus should change to up(1) if the interface is
            ready to transmit and receive network traffic; it should
            change to dormant(5) if the interface is waiting for
            external actions (such as a serial line waiting for an
            incoming connection); it should remain in the down(2) state
            if and only if there is a fault that prevents it from going
            to the up(1) state; it should remain in the notPresent(6)
            state if the interface has missing (typically, hardware)
            components.";
        }
    }

    notification warning-TCAM-Util-Notif {

        description "The warningTCAMUtilNotif is generated         when number of entries in TCAM group crosses the warning threshold limit..";

        leaf groupId {
            type string;
            description "A unique number corresponding to each TCAM group.";
        }

        leaf groupName {
            type string;
            description "TCAM group name.";
        }

        leaf usedPercent {
            type string;
            description "Percentage of entries used in the TCAM group.
              Value of -1 means the field is not applicable.";
        }

        leaf freeEntries {
            type string;
            description "Count of free entries in the TCAM group.
              Value of -1 means the field is not applicable.";
        }
    }

    notification critical-TCAM-Util-Notif {

        description "The criticalTCAMUtilNotif is generated         when number of entries in TCAM group crosses the critical threshold limit..";

        leaf groupId {
            type string;
            description "A unique number corresponding to each TCAM group.";
        }

        leaf groupName {
            type string;
            description "TCAM group name.";
        }

        leaf usedPercent {
            type string;
            description "Percentage of entries used in the TCAM group.
              Value of -1 means the field is not applicable.";
        }

        leaf freeEntries {
            type string;
            description "Count of free entries in the TCAM group.
              Value of -1 means the field is not applicable.";
        }
    }

    notification topologyChange {

        description "A topologyChange trap is sent by a bridge when any of its configured ports transitions from the Learning state to the Forwarding state, or from the Forwarding state to the Blocking state..";

        leaf message {
            type string;
            description " alarm message notification";
        }
    }

    notification newRoot {

        description "The newRoot trap indicates that the sending agent has become the new root of the Spanning Tree..";

        leaf message {
            type string;
            description " alarm message notification";
        }
    }

    notification bgp-peer-state {

        description "bgp Peer State..";

        leaf peerAddr {
            type string;
            description "The peer address or Tag";
        }

        leaf bgpAs {
            type string;
            description "AS number";
        }

        leaf vrId {
            type string;
            description "Virtual router id";
        }

        leaf vrfName {
            type string;
            description "vrf name";
        }

        leaf bgpPeerState {
            type string;
            description "Bgp peer session state. If there is change in state of the session , notification will be published only if the current state or the previous state is in establised state ";
        }

        leaf peerAs {
            type string;
            description "Remote AS number <0-65535>>";
        }
    }

    notification bgp-maximum-prefix {

        description "Maximum prefix learned exceeded the limit for neighbor..";

        leaf peerAddr {
            type string;
            description "The peer address or Tag";
        }

        leaf bgpAs {
            type string;
            description "AS number";
        }

        leaf vrId {
            type string;
            description "Virtual router id";
        }

        leaf vrfName {
            type string;
            description "vrf name";
        }

        leaf maxPrefixes {
            type string;
            description "Maximum number of prefixes <1-4294967295>";
        }
    }

    notification vxlan-tunnel-status-change-notification {

        description "The nvoTunnelStatus trap is generated when there is any status change in Tunnel Severity level is CRITICAL for tunnel status going to Unresolved/Deleted status and MINOR for Resolved status..";

        leaf destIp {
            type string;
            description "Tunnel destination IP";
        }

        leaf vrId {
            type string;
            description "Virtual router id";
        }

        leaf tunnelStatus {
            type string;
            description "Status of tunnel";
        }
    }

    notification sflowReceiverTimeoutAlarmMsg {

        description "Notify alarm message.";

        leaf message {
            type string;
            description " alarm message notification";
        }
    }

    notification cmmSysPsDownNotification {

        description "The cmmSysPsDownNotification  event is generated when a protocol module down/hung/crashes.";

        leaf cmmSoftwareProcessID {
            type string;
            description "Each protocol module is uniquely identified with a number, also called as protocol module id";
        }

        leaf cmmSoftwareProcessName {
            type string;
            description "Protocol module name";
        }

        leaf cmmSoftwareProcessStartTime {
            type string;
            description "The starting time of a protocol module, given in date and time.";
        }

        leaf cmmSoftwareProcessLastRestartReason {
            type string;
            description "Reason for process to shutdown provided it was running.This value will be the signal description";
        }
    }

    notification cmmSysPsRestartNotification {

        description "The cmmSysPsRestartNotification  event is generated when a protocol module recovered from down/hung/crashes.";

        leaf cmmSoftwareProcessID {
            type string;
            description "Each protocol module is uniquely identified with a number, also called as protocol module id";
        }

        leaf cmmSoftwareProcessName {
            type string;
            description "Protocol module name";
        }

        leaf cmmSoftwareProcessStartTime {
            type string;
            description "The starting time of a protocol module, given in date and time.";
        }
    }

    notification cmmCpuLoad15MinCritical {

        description "notification to send information for 15min critical threshold and CPU Utilisation.";

        leaf cmmStackUnitIndex {
            type string;
            description "The unique index for this entry.Refer to the object cmmStackUnitIndexNext.";
        }

        leaf cmmStackUnitCpuLoad15Min {
            type string;
            description "CPU Load in percentage for last 15 minutes. '-1000.01' indicates unavailable.";
        }

        leaf cmmStackCpuLoad15minCriticalThreshold {
            type string;
            description "The CPU Critical Threshold percentage value for 15 min load. '-1000.01' indicates unavailable.";
        }
    }

    notification cmmCpuLoad5MinCritical {

        description "notification to send information for 5min critical threshold and CPU Utilisation.";

        leaf cmmStackUnitIndex {
            type string;
            description "The unique index for this entry.Refer to the object cmmStackUnitIndexNext.";
        }

        leaf cmmStackUnitCpuLoad5Min {
            type string;
            description "CPU Load in percentage for last 5 minutes. '-1000.01' indicates unavailable.";
        }

        leaf cmmStackCpuLoad5minCriticalThreshold {
            type string;
            description "The CPU Critical Threshold percentage value for 5 min load. '-1000.01' indicates unavailable.";
        }
    }

    notification cmmCpuLoad1MinAlert {

        description "notification to send information for 1min alert threshold and CPU Utilisation.";

        leaf cmmStackUnitIndex {
            type string;
            description "The unique index for this entry.Refer to the object cmmStackUnitIndexNext.";
        }

        leaf cmmStackUnitCpuLoad1Min {
            type string;
            description "CPU Load in percentage for last 1 minute. '-1000.01' indicates unavailable.";
        }

        leaf cmmStackCpuLoad1minAlertThreshold {
            type string;
            description "The CPU Alert Threshold percentage value for 1 min load. '-1000.01' indicates unavailable.";
        }
    }

    notification cmmCpuLoad1MinCritical {

        description "notification to send information for 1min critical threshold and CPU Utilisation.";

        leaf cmmStackUnitIndex {
            type string;
            description "The unique index for this entry.Refer to the object cmmStackUnitIndexNext.";
        }

        leaf cmmStackUnitCpuLoad1Min {
            type string;
            description "CPU Load in percentage for last 1 minute. '-1000.01' indicates unavailable.";
        }

        leaf cmmStackCpuLoad1minCriticalThreshold {
            type string;
            description "The CPU Critical Threshold percentage value for 1 min load. '-1000.01' indicates unavailable.";
        }
    }

    notification cmmCpuLoad1MinAlertRecovery {

        description "notification to send information for CPU usage recovered from Alert Condition.";

        leaf cmmStackUnitIndex {
            type string;
            description "The unique index for this entry.Refer to the object cmmStackUnitIndexNext.";
        }

        leaf cmmStackUnitCpuLoad1Min {
            type string;
            description "CPU Load in percentage for last 1 minute. '-1000.01' indicates unavailable.";
        }

        leaf cmmStackCpuLoad1minAlertThreshold {
            type string;
            description "The CPU Alert Threshold percentage value for 1 min load. '-1000.01' indicates unavailable.";
        }
    }

    notification cmmCpuLoad15MinCriticalRecovery {

        description "notification to send information for CPU usage recovered from 15 min Critical Condition.";

        leaf cmmStackUnitIndex {
            type string;
            description "The unique index for this entry.Refer to the object cmmStackUnitIndexNext.";
        }

        leaf cmmStackUnitCpuLoad15Min {
            type string;
            description "CPU Load in percentage for last 15 minutes. '-1000.01' indicates unavailable.";
        }

        leaf cmmStackCpuLoad15minCriticalThreshold {
            type string;
            description "The CPU Critical Threshold percentage value for 15 min load. '-1000.01' indicates unavailable.";
        }
    }

    notification cmmCpuLoad5MinCriticalRecovery {

        description "notification to send information for CPU usage recovered from 5 min Critical Condition.";

        leaf cmmStackUnitIndex {
            type string;
            description "The unique index for this entry.Refer to the object cmmStackUnitIndexNext.";
        }

        leaf cmmStackUnitCpuLoad5Min {
            type string;
            description "CPU Load in percentage for last 5 minutes. '-1000.01' indicates unavailable.";
        }

        leaf cmmStackCpuLoad5minCriticalThreshold {
            type string;
            description "The CPU Critical Threshold percentage value for 5 min load. '-1000.01' indicates unavailable.";
        }
    }

    notification cmmCpuLoad1MinCriticalRecovery {

        description "notification to send information for CPU usage recovered from 1 min Critical Condition.";

        leaf cmmStackUnitIndex {
            type string;
            description "The unique index for this entry.Refer to the object cmmStackUnitIndexNext.";
        }

        leaf cmmStackUnitCpuLoad1Min {
            type string;
            description "CPU Load in percentage for last 1 minute. '-1000.01' indicates unavailable.";
        }

        leaf cmmStackCpuLoad1minCriticalThreshold {
            type string;
            description "The CPU Critical Threshold percentage value for 1 min load. '-1000.01' indicates unavailable.";
        }
    }

    notification cmmCpuCoreUtilHighAlert {

        description "notification to send information for CPU utilization in alert condition..";

        leaf cmmStackUnitIndex {
            type string;
            description "The unique index for this entry.Refer to the object cmmStackUnitIndexNext.";
        }

        leaf cmmStackUnitCpuUtilization {
            type string;
            description "Total cpu usage in percentage. '-1000.01' indicates unavailable.";
        }

        leaf cmmStackUnitCpuUtilAlertThreshold {
            type string;
            description "The CPU utilization Alert Threshold %. '-1000.01' indicates unavailable.";
        }
    }

    notification cmmCpuCoreUtilHighCritical {

        description "notification to send information for CPU utilization in Critical condition..";

        leaf cmmStackUnitIndex {
            type string;
            description "The unique index for this entry.Refer to the object cmmStackUnitIndexNext.";
        }

        leaf cmmStackUnitCpuUtilization {
            type string;
            description "Total cpu usage in percentage. '-1000.01' indicates unavailable.";
        }

        leaf cmmStackUnitCpuUtilCriticalThreshold {
            type string;
            description "The CPU utilization Critical Threshold %. '-1000.01' indicates unavailable.";
        }
    }

    notification cmmCpuCoreUtilHighAlertRecovery {

        description "notification to send information for CPU utilization after alert recovery..";

        leaf cmmStackUnitIndex {
            type string;
            description "The unique index for this entry.Refer to the object cmmStackUnitIndexNext.";
        }

        leaf cmmStackUnitCpuUtilization {
            type string;
            description "Total cpu usage in percentage. '-1000.01' indicates unavailable.";
        }
    }

    notification cmmCpuCoreUtilHighCriticalRecovery {

        description "notification to send information for CPU utilization after Critical recovery..";

        leaf cmmStackUnitIndex {
            type string;
            description "The unique index for this entry.Refer to the object cmmStackUnitIndexNext.";
        }

        leaf cmmStackUnitCpuUtilization {
            type string;
            description "Total cpu usage in percentage. '-1000.01' indicates unavailable.";
        }
    }

    notification cmmRamUsageRisingAlert {

        description " notification to send when RAM usage exceeds Alert Threshold.";

        leaf cmmStackUnitIndex {
            type string;
            description "The unique index for this entry.Refer to the object cmmStackUnitIndexNext.";
        }

        leaf cmmSysRamUsedMem {
            type string;
            description "CPU RAM's Used memory available for utilisation in MBytes. '-100001' indicates unavailable.";
        }

        leaf cmmSysRamAlertThreshold {
            type string;
            description "RAM usage threshold % for Alert level. '-100001' indicates unavailable.";
        }
    }

    notification cmmRamUsageRisingCritical {

        description " notification to send when RAM usage exceeds Critical Threshold.";

        leaf cmmStackUnitIndex {
            type string;
            description "The unique index for this entry.Refer to the object cmmStackUnitIndexNext.";
        }

        leaf cmmSysRamUsedMem {
            type string;
            description "CPU RAM's Used memory available for utilisation in MBytes. '-100001' indicates unavailable.";
        }

        leaf cmmSysRamCriticalThreshold {
            type string;
            description "RAM usage threshold % for Critical level. '-100001' indicates unavailable.";
        }
    }

    notification cmmRamUsageAlertRecovery {

        description " notification to send when RAM usage recovers from Alert condition.";

        leaf cmmStackUnitIndex {
            type string;
            description "The unique index for this entry.Refer to the object cmmStackUnitIndexNext.";
        }

        leaf cmmSysRamUsedMem {
            type string;
            description "CPU RAM's Used memory available for utilisation in MBytes. '-100001' indicates unavailable.";
        }

        leaf cmmSysRamAlertThreshold {
            type string;
            description "RAM usage threshold % for Alert level. '-100001' indicates unavailable.";
        }
    }

    notification cmmRamUsageCriticalRecovery {

        description " notification to send when RAM usage recovers from Critical condition.";

        leaf cmmStackUnitIndex {
            type string;
            description "The unique index for this entry.Refer to the object cmmStackUnitIndexNext.";
        }

        leaf cmmSysRamUsedMem {
            type string;
            description "CPU RAM's Used memory available for utilisation in MBytes. '-100001' indicates unavailable.";
        }

        leaf cmmSysRamCriticalThreshold {
            type string;
            description "RAM usage threshold % for Critical level. '-100001' indicates unavailable.";
        }
    }

    notification cmmHardDiskUsageRisingAlert {

        description "notification to send when Hard Disk usage exceeds alert threshold..";

        leaf cmmStackUnitIndex {
            type string;
            description "The unique index for this entry.Refer to the object cmmStackUnitIndexNext.";
        }

        leaf cmmSysHarddiskUsedMem {
            type string;
            description "Used memory of the Hard disk. '-100001' indicates unavailable.";
        }

        leaf cmmSysHarddiskAlertThreshold {
            type string;
            description "Harddisk usage threshold %  for Alert Level. '-100001' indicates unavailable.";
        }

        leaf cmmSysMountPoint {
            type string;
            description "Path of the mounted filesystem";
        }
    }

    notification cmmHardDiskUsageRisingCritical {

        description "notification to send when Hard Disk usage exceeds critical threshold..";

        leaf cmmStackUnitIndex {
            type string;
            description "The unique index for this entry.Refer to the object cmmStackUnitIndexNext.";
        }

        leaf cmmSysHarddiskUsedMem {
            type string;
            description "Used memory of the Hard disk. '-100001' indicates unavailable.";
        }

        leaf cmmSysHarddiskCriticalThreshold {
            type string;
            description "Harddisk usage threshold %  for Critical Level. '-100001' indicates unavailable.";
        }

        leaf cmmSysMountPoint {
            type string;
            description "Path of the mounted filesystem";
        }
    }

    notification cmmHardDiskUsageAlertRecovery {

        description "notification to send when Hard Disk usage recovers under alert threshold..";

        leaf cmmStackUnitIndex {
            type string;
            description "The unique index for this entry.Refer to the object cmmStackUnitIndexNext.";
        }

        leaf cmmSysHarddiskUsedMem {
            type string;
            description "Used memory of the Hard disk. '-100001' indicates unavailable.";
        }

        leaf cmmSysHarddiskAlertThreshold {
            type string;
            description "Harddisk usage threshold %  for Alert Level. '-100001' indicates unavailable.";
        }

        leaf cmmSysMountPoint {
            type string;
            description "Path of the mounted filesystem";
        }
    }

    notification cmmHardDiskUsageCriticalRecovery {

        description "notification to send when Hard Disk usage recovers under critical threshold..";

        leaf cmmStackUnitIndex {
            type string;
            description "The unique index for this entry.Refer to the object cmmStackUnitIndexNext.";
        }

        leaf cmmSysHarddiskUsedMem {
            type string;
            description "Used memory of the Hard disk. '-100001' indicates unavailable.";
        }

        leaf cmmSysHarddiskCriticalThreshold {
            type string;
            description "Harddisk usage threshold %  for Critical Level. '-100001' indicates unavailable.";
        }

        leaf cmmSysMountPoint {
            type string;
            description "Path of the mounted filesystem";
        }
    }

    notification cmmTemperatureLowEmergency {

        description "notification sent when Temperature will be below lower threshold for sensor.";

        leaf cmmSysTemperatureSensorIndex {
            type string;
            description "Value represents Temperature Sensor Index";
        }

        leaf cmmStackUnitIndex {
            type string;
            description "The unique index for this entry.Refer to the object cmmStackUnitIndexNext.";
        }

        leaf cmmSysTemperatureValue {
            type string;
            description "Value represents Temperature Sensor value. '-1000.01' indicates unavailable.";
        }

        leaf cmmSysTempEmergencyThresholdMin {
            type string;
            description "Value represents Temperature Sensor Min Emergency threshold. '-1000.01' indicates unavailable.";
        }

        leaf cmmSysTempEmergencyThresholdMax {
            type string;
            description "Value represents Temperature Sensor Max Emergency threshold. '-1000.01' indicates unavailable.";
        }

        leaf cmmSysTemperatureSensorName {
            type string;
            description "Temperature Sensor Name. Blank indicates unavailable.";
        }
    }

    notification cmmTemperatureHighEmergency {

        description "notification sent when Temperature will be above threshold for sensor.";

        leaf cmmSysTemperatureSensorIndex {
            type string;
            description "Value represents Temperature Sensor Index";
        }

        leaf cmmStackUnitIndex {
            type string;
            description "The unique index for this entry.Refer to the object cmmStackUnitIndexNext.";
        }

        leaf cmmSysTemperatureValue {
            type string;
            description "Value represents Temperature Sensor value. '-1000.01' indicates unavailable.";
        }

        leaf cmmSysTempEmergencyThresholdMin {
            type string;
            description "Value represents Temperature Sensor Min Emergency threshold. '-1000.01' indicates unavailable.";
        }

        leaf cmmSysTempEmergencyThresholdMax {
            type string;
            description "Value represents Temperature Sensor Max Emergency threshold. '-1000.01' indicates unavailable.";
        }

        leaf cmmSysTemperatureSensorName {
            type string;
            description "Temperature Sensor Name. Blank indicates unavailable.";
        }
    }

    notification cmmTemperatureLowAlert {

        description "notification sent when Temperature is nearing low emergency condition for sensor.";

        leaf cmmSysTemperatureSensorIndex {
            type string;
            description "Value represents Temperature Sensor Index";
        }

        leaf cmmStackUnitIndex {
            type string;
            description "The unique index for this entry.Refer to the object cmmStackUnitIndexNext.";
        }

        leaf cmmSysTemperatureValue {
            type string;
            description "Value represents Temperature Sensor value. '-1000.01' indicates unavailable.";
        }

        leaf cmmSysTempAlertThresholdMin {
            type string;
            description "Value represents Temperature Sensor Min Alert threshold. '-1000.01' indicates unavailable.";
        }

        leaf cmmSysTempAlertThresholdMax {
            type string;
            description "Value represents Temperature Sensor Max Alert threshold. '-1000.01' indicates unavailable.";
        }

        leaf cmmSysTemperatureSensorName {
            type string;
            description "Temperature Sensor Name. Blank indicates unavailable.";
        }
    }

    notification cmmTemperatureHighAlert {

        description "notification sent when Temperature is nearing high emergency condition for sensor.";

        leaf cmmSysTemperatureSensorIndex {
            type string;
            description "Value represents Temperature Sensor Index";
        }

        leaf cmmStackUnitIndex {
            type string;
            description "The unique index for this entry.Refer to the object cmmStackUnitIndexNext.";
        }

        leaf cmmSysTemperatureValue {
            type string;
            description "Value represents Temperature Sensor value. '-1000.01' indicates unavailable.";
        }

        leaf cmmSysTempAlertThresholdMin {
            type string;
            description "Value represents Temperature Sensor Min Alert threshold. '-1000.01' indicates unavailable.";
        }

        leaf cmmSysTempAlertThresholdMax {
            type string;
            description "Value represents Temperature Sensor Max Alert threshold. '-1000.01' indicates unavailable.";
        }

        leaf cmmSysTemperatureSensorName {
            type string;
            description "Temperature Sensor Name. Blank indicates unavailable.";
        }
    }

    notification cmmTemperatureLowCritical {

        description "notification sent when Temperature has reached low critical condition for sensor.";

        leaf cmmSysTemperatureSensorIndex {
            type string;
            description "Value represents Temperature Sensor Index";
        }

        leaf cmmStackUnitIndex {
            type string;
            description "The unique index for this entry.Refer to the object cmmStackUnitIndexNext.";
        }

        leaf cmmSysTemperatureValue {
            type string;
            description "Value represents Temperature Sensor value. '-1000.01' indicates unavailable.";
        }

        leaf cmmSysTempCriticalThresholdMin {
            type string;
            description "Value represents Temperature Sensor Min Critical threshold. '-1000.01' indicates unavailable.";
        }

        leaf cmmSysTempCriticalThresholdMax {
            type string;
            description "Value represents Temperature Sensor Min Critical threshold. '-1000.01' indicates unavailable.";
        }

        leaf cmmSysTemperatureSensorName {
            type string;
            description "Temperature Sensor Name. Blank indicates unavailable.";
        }
    }

    notification cmmTemperatureHighCritical {

        description "notification sent when Temperature has reached high critical condition for sensor.";

        leaf cmmSysTemperatureSensorIndex {
            type string;
            description "Value represents Temperature Sensor Index";
        }

        leaf cmmStackUnitIndex {
            type string;
            description "The unique index for this entry.Refer to the object cmmStackUnitIndexNext.";
        }

        leaf cmmSysTemperatureValue {
            type string;
            description "Value represents Temperature Sensor value. '-1000.01' indicates unavailable.";
        }

        leaf cmmSysTempCriticalThresholdMin {
            type string;
            description "Value represents Temperature Sensor Min Critical threshold. '-1000.01' indicates unavailable.";
        }

        leaf cmmSysTempCriticalThresholdMax {
            type string;
            description "Value represents Temperature Sensor Min Critical threshold. '-1000.01' indicates unavailable.";
        }

        leaf cmmSysTemperatureSensorName {
            type string;
            description "Temperature Sensor Name. Blank indicates unavailable.";
        }
    }

    notification cmmTemperatureHighAlertRecovery {

        description "notification sent when Temperature is recovered to normal range from alert level high for sensor..";

        leaf cmmSysTemperatureSensorIndex {
            type string;
            description "Value represents Temperature Sensor Index";
        }

        leaf cmmStackUnitIndex {
            type string;
            description "The unique index for this entry.Refer to the object cmmStackUnitIndexNext.";
        }

        leaf cmmSysTemperatureValue {
            type string;
            description "Value represents Temperature Sensor value. '-1000.01' indicates unavailable.";
        }

        leaf cmmSysTempAlertThresholdMin {
            type string;
            description "Value represents Temperature Sensor Min Alert threshold. '-1000.01' indicates unavailable.";
        }

        leaf cmmSysTempAlertThresholdMax {
            type string;
            description "Value represents Temperature Sensor Max Alert threshold. '-1000.01' indicates unavailable.";
        }

        leaf cmmSysTemperatureSensorName {
            type string;
            description "Temperature Sensor Name. Blank indicates unavailable.";
        }
    }

    notification cmmTemperatureLowAlertRecovery {

        description "notification sent when Temperature is recovered to normal range from alert level low for sensor..";

        leaf cmmSysTemperatureSensorIndex {
            type string;
            description "Value represents Temperature Sensor Index";
        }

        leaf cmmStackUnitIndex {
            type string;
            description "The unique index for this entry.Refer to the object cmmStackUnitIndexNext.";
        }

        leaf cmmSysTemperatureValue {
            type string;
            description "Value represents Temperature Sensor value. '-1000.01' indicates unavailable.";
        }

        leaf cmmSysTempAlertThresholdMin {
            type string;
            description "Value represents Temperature Sensor Min Alert threshold. '-1000.01' indicates unavailable.";
        }

        leaf cmmSysTempAlertThresholdMax {
            type string;
            description "Value represents Temperature Sensor Max Alert threshold. '-1000.01' indicates unavailable.";
        }

        leaf cmmSysTemperatureSensorName {
            type string;
            description "Temperature Sensor Name. Blank indicates unavailable.";
        }
    }

    notification cmmTemperatureHighCriticalRecovery {

        description "notification sent when Temperature is recovered to normal range from critical level high for sensor..";

        leaf cmmSysTemperatureSensorIndex {
            type string;
            description "Value represents Temperature Sensor Index";
        }

        leaf cmmStackUnitIndex {
            type string;
            description "The unique index for this entry.Refer to the object cmmStackUnitIndexNext.";
        }

        leaf cmmSysTemperatureValue {
            type string;
            description "Value represents Temperature Sensor value. '-1000.01' indicates unavailable.";
        }

        leaf cmmSysTempCriticalThresholdMin {
            type string;
            description "Value represents Temperature Sensor Min Critical threshold. '-1000.01' indicates unavailable.";
        }

        leaf cmmSysTempCriticalThresholdMax {
            type string;
            description "Value represents Temperature Sensor Min Critical threshold. '-1000.01' indicates unavailable.";
        }

        leaf cmmSysTemperatureSensorName {
            type string;
            description "Temperature Sensor Name. Blank indicates unavailable.";
        }
    }

    notification cmmTemperatureLowCriticalRecovery {

        description "notification sent when Temperature is recovered to normal range from critical level low for sensor..";

        leaf cmmSysTemperatureSensorIndex {
            type string;
            description "Value represents Temperature Sensor Index";
        }

        leaf cmmStackUnitIndex {
            type string;
            description "The unique index for this entry.Refer to the object cmmStackUnitIndexNext.";
        }

        leaf cmmSysTemperatureValue {
            type string;
            description "Value represents Temperature Sensor value. '-1000.01' indicates unavailable.";
        }

        leaf cmmSysTempCriticalThresholdMin {
            type string;
            description "Value represents Temperature Sensor Min Critical threshold. '-1000.01' indicates unavailable.";
        }

        leaf cmmSysTempCriticalThresholdMax {
            type string;
            description "Value represents Temperature Sensor Min Critical threshold. '-1000.01' indicates unavailable.";
        }

        leaf cmmSysTemperatureSensorName {
            type string;
            description "Temperature Sensor Name. Blank indicates unavailable.";
        }
    }

    notification cmmPsuInsertedNotify {

        description "Set when Power supply unit is inserted.";

        leaf cmmSysPSUIndex {
            type string;
            description "The unique index of the power supply.";
        }

        leaf cmmStackUnitIndex {
            type string;
            description "The unique index for this entry.Refer to the object cmmStackUnitIndexNext.";
        }

        leaf cmmPsuSerialNumber {
            type string;
            description "PSU Date Code. Blank indicates unavailable.";
        }
    }

    notification cmmPsuRemovedAlert {

        description "Set when Power supply unit is Removed.";

        leaf cmmSysPSUIndex {
            type string;
            description "The unique index of the power supply.";
        }

        leaf cmmStackUnitIndex {
            type string;
            description "The unique index for this entry.Refer to the object cmmStackUnitIndexNext.";
        }

        leaf cmmPsuSerialNumber {
            type string;
            description "PSU Date Code. Blank indicates unavailable.";
        }
    }

    notification cmmPsuAcFailedAlert {

        description " Set when Power supply unit has no input power..";

        leaf cmmSysPSUIndex {
            type string;
            description "The unique index of the power supply.";
        }

        leaf cmmStackUnitIndex {
            type string;
            description "The unique index for this entry.Refer to the object cmmStackUnitIndexNext.";
        }
    }

    notification cmmPsuAcRecover {

        description " Set when Power supply unit input power is restored..";

        leaf cmmSysPSUIndex {
            type string;
            description "The unique index of the power supply.";
        }

        leaf cmmStackUnitIndex {
            type string;
            description "The unique index for this entry.Refer to the object cmmStackUnitIndexNext.";
        }
    }

    notification cmmPsu12vPgFailedAlert {

        description " Set when Power supply unit has no output power..";

        leaf cmmSysPSUIndex {
            type string;
            description "The unique index of the power supply.";
        }

        leaf cmmStackUnitIndex {
            type string;
            description "The unique index for this entry.Refer to the object cmmStackUnitIndexNext.";
        }
    }

    notification cmmPsu12vPgRecover {

        description " Set when Power supply unit output power is restored..";

        leaf cmmSysPSUIndex {
            type string;
            description "The unique index of the power supply.";
        }

        leaf cmmStackUnitIndex {
            type string;
            description "The unique index for this entry.Refer to the object cmmStackUnitIndexNext.";
        }
    }

    notification cmmFanTrayInsertedNotify {

        description "Set when fan tray is inserted.";

        leaf cmmFanTrayNumber {
            type string;
            description "Value represents the fan tray Number.";
        }

        leaf cmmStackUnitIndex {
            type string;
            description "The unique index for this entry.Refer to the object cmmStackUnitIndexNext.";
        }

        leaf cmmFanSerialNumber {
            type string;
            description "Fan Serial Number. Blank indicates unavailable.";
        }
    }

    notification cmmFanTrayRemovedAlert {

        description "Set when fan tray is Removed.";

        leaf cmmFanTrayNumber {
            type string;
            description "Value represents the fan tray Number.";
        }

        leaf cmmStackUnitIndex {
            type string;
            description "The unique index for this entry.Refer to the object cmmStackUnitIndexNext.";
        }

        leaf cmmFanSerialNumber {
            type string;
            description "Fan Serial Number. Blank indicates unavailable.";
        }
    }

    notification cmmFanTrayFaultyAlert {

        description "Set when Given Fan Tray is faulty.";

        leaf cmmFanTrayNumber {
            type string;
            description "Value represents the fan tray Number.";
        }

        leaf cmmStackUnitIndex {
            type string;
            description "The unique index for this entry.Refer to the object cmmStackUnitIndexNext.";
        }

        leaf cmmFanIndex {
            type string;
            description "Index of the fan per fantray.";
        }
    }

    notification cmmFanTrayRecovered {

        description "Set when Given Fan Tray is recovered.";

        leaf cmmFanTrayNumber {
            type string;
            description "Value represents the fan tray Number.";
        }

        leaf cmmStackUnitIndex {
            type string;
            description "The unique index for this entry.Refer to the object cmmStackUnitIndexNext.";
        }

        leaf cmmFanIndex {
            type string;
            description "Index of the fan per fantray.";
        }
    }

    notification cmmFanTrayStallAlert {

        description "Set when Given Fan Tray Stalled.";

        leaf cmmFanTrayNumber {
            type string;
            description "Value represents the fan tray Number.";
        }

        leaf cmmStackUnitIndex {
            type string;
            description "The unique index for this entry.Refer to the object cmmStackUnitIndexNext.";
        }

        leaf cmmFanIndex {
            type string;
            description "Index of the fan per fantray.";
        }
    }

    notification cmmFanTrayStallRecovered {

        description "Set when Given Fan Tray is recovered from stall.";

        leaf cmmFanTrayNumber {
            type string;
            description "Value represents the fan tray Number.";
        }

        leaf cmmStackUnitIndex {
            type string;
            description "The unique index for this entry.Refer to the object cmmStackUnitIndexNext.";
        }

        leaf cmmFanIndex {
            type string;
            description "Index of the fan per fantray.";
        }
    }

    notification cmmFanRPMMinAlert {

        description " Set when fan RPM set to its minimum value..";

        leaf cmmFanIndex {
            type string;
            description "Index of the fan per fantray.";
        }

        leaf cmmFanTrayNumber {
            type string;
            description "Value represents the fan tray Number.";
        }

        leaf cmmStackUnitIndex {
            type string;
            description "The unique index for this entry.Refer to the object cmmStackUnitIndexNext.";
        }

        leaf cmmFanRpmMin {
            type string;
            description "Value represents the minimum supported RPM of fan. '-100001' indicates unavailable.";
        }
    }

    notification cmmFanRPMMaxAlert {

        description " Set when fan RPM set to its maximum value..";

        leaf cmmFanIndex {
            type string;
            description "Index of the fan per fantray.";
        }

        leaf cmmFanTrayNumber {
            type string;
            description "Value represents the fan tray Number.";
        }

        leaf cmmStackUnitIndex {
            type string;
            description "The unique index for this entry.Refer to the object cmmStackUnitIndexNext.";
        }

        leaf cmmFanRpmMax {
            type string;
            description "Value represents the maximum supported RPM of fan. '-100001' indicates unavailable.";
        }
    }

    notification cmmTransCriticalTempHigh {

        description "Set when internal temperature exceeds high warning level.";

        leaf cmmTransIndex {
            type string;
            description "A unique index for each slot within the unit.";
        }

        leaf cmmStackUnitIndex {
            type string;
            description "The unique index for this entry.Refer to the object cmmStackUnitIndexNext.";
        }

        leaf cmmTransType {
            type string;
            description "Type of the transceiver SFP/QSFP.";
        }

        leaf cmmTransChannelIndex {
            type string;
            description "A unique value, greater than zero, for each channel in the transceiver within the unit.For SFP transceivers, only channel '1' is applicable.";
        }

        leaf cmmTransTemperature {
            type string;
            description "Internally measured temperature of the transceiver.This is common across channels for a transceiver. '-1000.01' indicates unavailable";
        }

        leaf cmmTransTempCriticalThresholdMin {
            type string;
            description "Min Alarm Threshold temperature of the transceiver.This is common across channels for a transceiver. '-1000.01' indicates unavailable.";
        }

        leaf cmmTransTempCriticalThresholdMax {
            type string;
            description "Max Alarm Threshold temperature of the transceiver.This is common across channels for a transceiver. '-1000.01' indicates unavailable.";
        }
    }

    notification cmmTransCriticalTempLow {

        description "Set when internal temperature is below low warning level.";

        leaf cmmTransIndex {
            type string;
            description "A unique index for each slot within the unit.";
        }

        leaf cmmStackUnitIndex {
            type string;
            description "The unique index for this entry.Refer to the object cmmStackUnitIndexNext.";
        }

        leaf cmmTransType {
            type string;
            description "Type of the transceiver SFP/QSFP.";
        }

        leaf cmmTransChannelIndex {
            type string;
            description "A unique value, greater than zero, for each channel in the transceiver within the unit.For SFP transceivers, only channel '1' is applicable.";
        }

        leaf cmmTransTemperature {
            type string;
            description "Internally measured temperature of the transceiver.This is common across channels for a transceiver. '-1000.01' indicates unavailable";
        }

        leaf cmmTransTempCriticalThresholdMin {
            type string;
            description "Min Alarm Threshold temperature of the transceiver.This is common across channels for a transceiver. '-1000.01' indicates unavailable.";
        }

        leaf cmmTransTempCriticalThresholdMax {
            type string;
            description "Max Alarm Threshold temperature of the transceiver.This is common across channels for a transceiver. '-1000.01' indicates unavailable.";
        }
    }

    notification cmmTransAlertTempHigh {

        description "Set when internal temperature of transceiver exceeds high Alert level..";

        leaf cmmTransIndex {
            type string;
            description "A unique index for each slot within the unit.";
        }

        leaf cmmStackUnitIndex {
            type string;
            description "The unique index for this entry.Refer to the object cmmStackUnitIndexNext.";
        }

        leaf cmmTransType {
            type string;
            description "Type of the transceiver SFP/QSFP.";
        }

        leaf cmmTransChannelIndex {
            type string;
            description "A unique value, greater than zero, for each channel in the transceiver within the unit.For SFP transceivers, only channel '1' is applicable.";
        }

        leaf cmmTransTemperature {
            type string;
            description "Internally measured temperature of the transceiver.This is common across channels for a transceiver. '-1000.01' indicates unavailable";
        }

        leaf cmmTransTempAlertThresholdMin {
            type string;
            description "Min Alert Threshold temperature of the transceiver.This is common across channels for a transceiver. '-1000.01' indicates unavailable.";
        }

        leaf cmmTransTempAlertThresholdMax {
            type string;
            description "Max Alert Threshold temperature of the transceiver.This is common across channels for a transceiver. '-1000.01' indicates unavailable.";
        }
    }

    notification cmmTransAlertTempLow {

        description "Set when internal temperature of transceiver falls below low Alert level..";

        leaf cmmTransIndex {
            type string;
            description "A unique index for each slot within the unit.";
        }

        leaf cmmStackUnitIndex {
            type string;
            description "The unique index for this entry.Refer to the object cmmStackUnitIndexNext.";
        }

        leaf cmmTransType {
            type string;
            description "Type of the transceiver SFP/QSFP.";
        }

        leaf cmmTransChannelIndex {
            type string;
            description "A unique value, greater than zero, for each channel in the transceiver within the unit.For SFP transceivers, only channel '1' is applicable.";
        }

        leaf cmmTransTemperature {
            type string;
            description "Internally measured temperature of the transceiver.This is common across channels for a transceiver. '-1000.01' indicates unavailable";
        }

        leaf cmmTransTempAlertThresholdMin {
            type string;
            description "Min Alert Threshold temperature of the transceiver.This is common across channels for a transceiver. '-1000.01' indicates unavailable.";
        }

        leaf cmmTransTempAlertThresholdMax {
            type string;
            description "Max Alert Threshold temperature of the transceiver.This is common across channels for a transceiver. '-1000.01' indicates unavailable.";
        }
    }

    notification cmmTransNotifyTransceiverTempRecovered {

        description "Set when temperature of transceiver is recovered from temperature fault.";

        leaf cmmTransIndex {
            type string;
            description "A unique index for each slot within the unit.";
        }

        leaf cmmStackUnitIndex {
            type string;
            description "The unique index for this entry.Refer to the object cmmStackUnitIndexNext.";
        }

        leaf cmmTransType {
            type string;
            description "Type of the transceiver SFP/QSFP.";
        }

        leaf cmmTransChannelIndex {
            type string;
            description "A unique value, greater than zero, for each channel in the transceiver within the unit.For SFP transceivers, only channel '1' is applicable.";
        }

        leaf cmmTransTemperature {
            type string;
            description "Internally measured temperature of the transceiver.This is common across channels for a transceiver. '-1000.01' indicates unavailable";
        }
    }

    notification cmmTransCriticalVoltageHigh {

        description "Set when internal supply voltage of transceiver exceeds high alarm level..";

        leaf cmmTransIndex {
            type string;
            description "A unique index for each slot within the unit.";
        }

        leaf cmmStackUnitIndex {
            type string;
            description "The unique index for this entry.Refer to the object cmmStackUnitIndexNext.";
        }

        leaf cmmTransType {
            type string;
            description "Type of the transceiver SFP/QSFP.";
        }

        leaf cmmTransChannelIndex {
            type string;
            description "A unique value, greater than zero, for each channel in the transceiver within the unit.For SFP transceivers, only channel '1' is applicable.";
        }

        leaf cmmTransVoltage {
            type string;
            description "Internally measured supply voltage of the transceiver.This is common across channels for a transceiver. '-100.001' indicates unavailable.";
        }

        leaf cmmTransVoltCriticalThresholdMin {
            type string;
            description "Min Alarm Threshold voltage of the transceiver.This is common across channels for a transceiver. '-100.001' indicates unavailable.";
        }

        leaf cmmTransVoltCriticalThresholdMax {
            type string;
            description "Max Alarm Threshold voltage of the transceiver.This is common across channels for a transceiver. '-100.001' indicates unavailable.";
        }
    }

    notification cmmTransCriticalVoltageLow {

        description "Set when internal supply voltage of transceiver is below low alarm level..";

        leaf cmmTransIndex {
            type string;
            description "A unique index for each slot within the unit.";
        }

        leaf cmmStackUnitIndex {
            type string;
            description "The unique index for this entry.Refer to the object cmmStackUnitIndexNext.";
        }

        leaf cmmTransType {
            type string;
            description "Type of the transceiver SFP/QSFP.";
        }

        leaf cmmTransChannelIndex {
            type string;
            description "A unique value, greater than zero, for each channel in the transceiver within the unit.For SFP transceivers, only channel '1' is applicable.";
        }

        leaf cmmTransVoltage {
            type string;
            description "Internally measured supply voltage of the transceiver.This is common across channels for a transceiver. '-100.001' indicates unavailable.";
        }

        leaf cmmTransVoltCriticalThresholdMin {
            type string;
            description "Min Alarm Threshold voltage of the transceiver.This is common across channels for a transceiver. '-100.001' indicates unavailable.";
        }

        leaf cmmTransVoltCriticalThresholdMax {
            type string;
            description "Max Alarm Threshold voltage of the transceiver.This is common across channels for a transceiver. '-100.001' indicates unavailable.";
        }
    }

    notification cmmTransAlertVoltageHigh {

        description " Set when internal supply voltage of transceiver exceeds high Alert level..";

        leaf cmmTransIndex {
            type string;
            description "A unique index for each slot within the unit.";
        }

        leaf cmmStackUnitIndex {
            type string;
            description "The unique index for this entry.Refer to the object cmmStackUnitIndexNext.";
        }

        leaf cmmTransType {
            type string;
            description "Type of the transceiver SFP/QSFP.";
        }

        leaf cmmTransChannelIndex {
            type string;
            description "A unique value, greater than zero, for each channel in the transceiver within the unit.For SFP transceivers, only channel '1' is applicable.";
        }

        leaf cmmTransVoltage {
            type string;
            description "Internally measured supply voltage of the transceiver.This is common across channels for a transceiver. '-100.001' indicates unavailable.";
        }

        leaf cmmTransVoltAlertThresholdMin {
            type string;
            description "Min Alert Threshold voltage of the transceiver.This is common across channels for a transceiver. '-100.001' indicates unavailable.";
        }

        leaf cmmTransVoltAlertThresholdMax {
            type string;
            description "Max Alert Threshold voltage of the transceiver.This is common across channels for a transceiver. '-100.001' indicates unavailable.";
        }
    }

    notification cmmTransAlertVoltageLow {

        description " Set when internal supply voltage of transceiver is below low Alert level...";

        leaf cmmTransIndex {
            type string;
            description "A unique index for each slot within the unit.";
        }

        leaf cmmStackUnitIndex {
            type string;
            description "The unique index for this entry.Refer to the object cmmStackUnitIndexNext.";
        }

        leaf cmmTransType {
            type string;
            description "Type of the transceiver SFP/QSFP.";
        }

        leaf cmmTransChannelIndex {
            type string;
            description "A unique value, greater than zero, for each channel in the transceiver within the unit.For SFP transceivers, only channel '1' is applicable.";
        }

        leaf cmmTransVoltage {
            type string;
            description "Internally measured supply voltage of the transceiver.This is common across channels for a transceiver. '-100.001' indicates unavailable.";
        }

        leaf cmmTransVoltAlertThresholdMin {
            type string;
            description "Min Alert Threshold voltage of the transceiver.This is common across channels for a transceiver. '-100.001' indicates unavailable.";
        }

        leaf cmmTransVoltAlertThresholdMax {
            type string;
            description "Max Alert Threshold voltage of the transceiver.This is common across channels for a transceiver. '-100.001' indicates unavailable.";
        }
    }

    notification cmmTransNotifyTransceiverVoltRecovered {

        description " Set when Trasceiver is recovered from voltage fault..";

        leaf cmmTransIndex {
            type string;
            description "A unique index for each slot within the unit.";
        }

        leaf cmmStackUnitIndex {
            type string;
            description "The unique index for this entry.Refer to the object cmmStackUnitIndexNext.";
        }

        leaf cmmTransType {
            type string;
            description "Type of the transceiver SFP/QSFP.";
        }

        leaf cmmTransChannelIndex {
            type string;
            description "A unique value, greater than zero, for each channel in the transceiver within the unit.For SFP transceivers, only channel '1' is applicable.";
        }

        leaf cmmTransVoltage {
            type string;
            description "Internally measured supply voltage of the transceiver.This is common across channels for a transceiver. '-100.001' indicates unavailable.";
        }
    }

    notification cmmTransCriticalBiasHigh {

        description "Set when TX Bias current of transceiver exceeds high alarm level..";

        leaf cmmTransIndex {
            type string;
            description "A unique index for each slot within the unit.";
        }

        leaf cmmStackUnitIndex {
            type string;
            description "The unique index for this entry.Refer to the object cmmStackUnitIndexNext.";
        }

        leaf cmmTransType {
            type string;
            description "Type of the transceiver SFP/QSFP.";
        }

        leaf cmmTransChannelIndex {
            type string;
            description "A unique value, greater than zero, for each channel in the transceiver within the unit.For SFP transceivers, only channel '1' is applicable.";
        }

        leaf cmmTransLaserBiasCurrent {
            type string;
            description "Internally measured TX Bias Current in Channel of transceiver. '-100.001' indicates unavailable.";
        }

        leaf cmmTransLaserBiasCurrCriticalThresholdMin {
            type string;
            description "Min Alarm Threshold of Laser Bias Current per channel. '-100.001' indicates unavailable.";
        }

        leaf cmmTransLaserBiasCurrCriticalThresholdMax {
            type string;
            description "Max Alarm Threshold of Laser Bias Current per channel. '-100.001' indicates unavailable.";
        }
    }

    notification cmmTransCriticalBiasLow {

        description "Set when TX Bias current of transceiver is below low alarm level..";

        leaf cmmTransIndex {
            type string;
            description "A unique index for each slot within the unit.";
        }

        leaf cmmStackUnitIndex {
            type string;
            description "The unique index for this entry.Refer to the object cmmStackUnitIndexNext.";
        }

        leaf cmmTransType {
            type string;
            description "Type of the transceiver SFP/QSFP.";
        }

        leaf cmmTransChannelIndex {
            type string;
            description "A unique value, greater than zero, for each channel in the transceiver within the unit.For SFP transceivers, only channel '1' is applicable.";
        }

        leaf cmmTransLaserBiasCurrent {
            type string;
            description "Internally measured TX Bias Current in Channel of transceiver. '-100.001' indicates unavailable.";
        }

        leaf cmmTransLaserBiasCurrCriticalThresholdMin {
            type string;
            description "Min Alarm Threshold of Laser Bias Current per channel. '-100.001' indicates unavailable.";
        }

        leaf cmmTransLaserBiasCurrCriticalThresholdMax {
            type string;
            description "Max Alarm Threshold of Laser Bias Current per channel. '-100.001' indicates unavailable.";
        }
    }

    notification cmmTransAlertBiasHigh {

        description "Set when TX Bias current of transceiver exceeds high alert level..";

        leaf cmmTransIndex {
            type string;
            description "A unique index for each slot within the unit.";
        }

        leaf cmmStackUnitIndex {
            type string;
            description "The unique index for this entry.Refer to the object cmmStackUnitIndexNext.";
        }

        leaf cmmTransType {
            type string;
            description "Type of the transceiver SFP/QSFP.";
        }

        leaf cmmTransChannelIndex {
            type string;
            description "A unique value, greater than zero, for each channel in the transceiver within the unit.For SFP transceivers, only channel '1' is applicable.";
        }

        leaf cmmTransLaserBiasCurrent {
            type string;
            description "Internally measured TX Bias Current in Channel of transceiver. '-100.001' indicates unavailable.";
        }

        leaf cmmTransLaserBiasCurrAlertThresholdMin {
            type string;
            description "Min Alert Threshold of Laser Bias Current per channel. '-100.001' indicates unavailable.";
        }

        leaf cmmTransLaserBiasCurrAlertThresholdMax {
            type string;
            description "Max Alert Threshold of Laser Bias Current per channel. '-100.001' indicates unavailable.";
        }
    }

    notification cmmTransAlertBiasLow {

        description "Set when TX Bias current of transceiver is below low alert level..";

        leaf cmmTransIndex {
            type string;
            description "A unique index for each slot within the unit.";
        }

        leaf cmmStackUnitIndex {
            type string;
            description "The unique index for this entry.Refer to the object cmmStackUnitIndexNext.";
        }

        leaf cmmTransType {
            type string;
            description "Type of the transceiver SFP/QSFP.";
        }

        leaf cmmTransChannelIndex {
            type string;
            description "A unique value, greater than zero, for each channel in the transceiver within the unit.For SFP transceivers, only channel '1' is applicable.";
        }

        leaf cmmTransLaserBiasCurrent {
            type string;
            description "Internally measured TX Bias Current in Channel of transceiver. '-100.001' indicates unavailable.";
        }

        leaf cmmTransLaserBiasCurrAlertThresholdMin {
            type string;
            description "Min Alert Threshold of Laser Bias Current per channel. '-100.001' indicates unavailable.";
        }

        leaf cmmTransLaserBiasCurrAlertThresholdMax {
            type string;
            description "Max Alert Threshold of Laser Bias Current per channel. '-100.001' indicates unavailable.";
        }
    }

    notification cmmTransNotifyTransceiverBiasRecovered {

        description "Set when TX Bias current of transceiver is recovered to normal..";

        leaf cmmTransIndex {
            type string;
            description "A unique index for each slot within the unit.";
        }

        leaf cmmStackUnitIndex {
            type string;
            description "The unique index for this entry.Refer to the object cmmStackUnitIndexNext.";
        }

        leaf cmmTransType {
            type string;
            description "Type of the transceiver SFP/QSFP.";
        }

        leaf cmmTransChannelIndex {
            type string;
            description "A unique value, greater than zero, for each channel in the transceiver within the unit.For SFP transceivers, only channel '1' is applicable.";
        }

        leaf cmmTransLaserBiasCurrent {
            type string;
            description "Internally measured TX Bias Current in Channel of transceiver. '-100.001' indicates unavailable.";
        }
    }

    notification cmmTransCriticalRxPowerHigh {

        description "Set when Received Power of transceiver exceeds high alarm level..";

        leaf cmmTransIndex {
            type string;
            description "A unique index for each slot within the unit.";
        }

        leaf cmmStackUnitIndex {
            type string;
            description "The unique index for this entry.Refer to the object cmmStackUnitIndexNext.";
        }

        leaf cmmTransType {
            type string;
            description "Type of the transceiver SFP/QSFP.";
        }

        leaf cmmTransChannelIndex {
            type string;
            description "A unique value, greater than zero, for each channel in the transceiver within the unit.For SFP transceivers, only channel '1' is applicable.";
        }

        leaf cmmTransRxPower {
            type string;
            description "Measured RX input power in Channel of transceiver.'-100' value represents no power. '-100.001' indicates unavailable.";
        }

        leaf cmmTransRxPowerCriticalThresholdMin {
            type string;
            description "Min Alarm Threshold value of Rx Input Power per channel.'-100' value represents no power. '-100.001' indicates unavailable.";
        }

        leaf cmmTransRxPowerCriticalThresholdMax {
            type string;
            description "Max Alarm Threshold value of Rx Input Power per channel.'-100' value represents no power. '-100.001' indicates unavailable.";
        }
    }

    notification cmmTransCriticalRxPowerlow {

        description "Set when Received Power of transceiver is below low alarm level..";

        leaf cmmTransIndex {
            type string;
            description "A unique index for each slot within the unit.";
        }

        leaf cmmStackUnitIndex {
            type string;
            description "The unique index for this entry.Refer to the object cmmStackUnitIndexNext.";
        }

        leaf cmmTransType {
            type string;
            description "Type of the transceiver SFP/QSFP.";
        }

        leaf cmmTransChannelIndex {
            type string;
            description "A unique value, greater than zero, for each channel in the transceiver within the unit.For SFP transceivers, only channel '1' is applicable.";
        }

        leaf cmmTransRxPower {
            type string;
            description "Measured RX input power in Channel of transceiver.'-100' value represents no power. '-100.001' indicates unavailable.";
        }

        leaf cmmTransRxPowerCriticalThresholdMin {
            type string;
            description "Min Alarm Threshold value of Rx Input Power per channel.'-100' value represents no power. '-100.001' indicates unavailable.";
        }

        leaf cmmTransRxPowerCriticalThresholdMax {
            type string;
            description "Max Alarm Threshold value of Rx Input Power per channel.'-100' value represents no power. '-100.001' indicates unavailable.";
        }
    }

    notification cmmTransAlertRxPowerHigh {

        description "Set when Received Power of transceiver exceeds high alert level..";

        leaf cmmTransIndex {
            type string;
            description "A unique index for each slot within the unit.";
        }

        leaf cmmStackUnitIndex {
            type string;
            description "The unique index for this entry.Refer to the object cmmStackUnitIndexNext.";
        }

        leaf cmmTransType {
            type string;
            description "Type of the transceiver SFP/QSFP.";
        }

        leaf cmmTransChannelIndex {
            type string;
            description "A unique value, greater than zero, for each channel in the transceiver within the unit.For SFP transceivers, only channel '1' is applicable.";
        }

        leaf cmmTransRxPower {
            type string;
            description "Measured RX input power in Channel of transceiver.'-100' value represents no power. '-100.001' indicates unavailable.";
        }

        leaf cmmTransRxPowerAlertThresholdMin {
            type string;
            description "Min Alert Threshold value of Rx Input Power per channel.'-100' value represents no power. '-100.001' indicates unavailable.";
        }

        leaf cmmTransRxPowerAlertThresholdMax {
            type string;
            description "Max Alert Threshold value of Rx Input Power per channel.'-100' value represents no power. '-100.001' indicates unavailable.";
        }
    }

    notification cmmTransAlertRxPowerLow {

        description "Set when Received Power of transceiver is below low alert level..";

        leaf cmmTransIndex {
            type string;
            description "A unique index for each slot within the unit.";
        }

        leaf cmmStackUnitIndex {
            type string;
            description "The unique index for this entry.Refer to the object cmmStackUnitIndexNext.";
        }

        leaf cmmTransType {
            type string;
            description "Type of the transceiver SFP/QSFP.";
        }

        leaf cmmTransChannelIndex {
            type string;
            description "A unique value, greater than zero, for each channel in the transceiver within the unit.For SFP transceivers, only channel '1' is applicable.";
        }

        leaf cmmTransRxPower {
            type string;
            description "Measured RX input power in Channel of transceiver.'-100' value represents no power. '-100.001' indicates unavailable.";
        }

        leaf cmmTransRxPowerAlertThresholdMin {
            type string;
            description "Min Alert Threshold value of Rx Input Power per channel.'-100' value represents no power. '-100.001' indicates unavailable.";
        }

        leaf cmmTransRxPowerAlertThresholdMax {
            type string;
            description "Max Alert Threshold value of Rx Input Power per channel.'-100' value represents no power. '-100.001' indicates unavailable.";
        }
    }

    notification cmmTransNotifyTransceiverRxPowRecovered {

        description "Set when Received Power of transceiver is recovered to normal..";

        leaf cmmTransIndex {
            type string;
            description "A unique index for each slot within the unit.";
        }

        leaf cmmStackUnitIndex {
            type string;
            description "The unique index for this entry.Refer to the object cmmStackUnitIndexNext.";
        }

        leaf cmmTransType {
            type string;
            description "Type of the transceiver SFP/QSFP.";
        }

        leaf cmmTransChannelIndex {
            type string;
            description "A unique value, greater than zero, for each channel in the transceiver within the unit.For SFP transceivers, only channel '1' is applicable.";
        }

        leaf cmmTransRxPower {
            type string;
            description "Measured RX input power in Channel of transceiver.'-100' value represents no power. '-100.001' indicates unavailable.";
        }
    }

    notification cmmTransCriticalTxPowerHigh {

        description "Set when Transferred Power of transceiver exceeds high alarm level..";

        leaf cmmTransIndex {
            type string;
            description "A unique index for each slot within the unit.";
        }

        leaf cmmStackUnitIndex {
            type string;
            description "The unique index for this entry.Refer to the object cmmStackUnitIndexNext.";
        }

        leaf cmmTransType {
            type string;
            description "Type of the transceiver SFP/QSFP.";
        }

        leaf cmmTransChannelIndex {
            type string;
            description "A unique value, greater than zero, for each channel in the transceiver within the unit.For SFP transceivers, only channel '1' is applicable.";
        }

        leaf cmmTransTxPower {
            type string;
            description "Measured TX output power in Channel of transceiver.'-100' value represents no power. '-100.001' indicates unavailable.";
        }

        leaf cmmTransTxPowerCriticalThresholdMin {
            type string;
            description "Min Alarm Threshold of TxOutput Power per channel.'-100' value represents no power. '-100.001' indicates unavailable.";
        }

        leaf cmmTransTxPowerCriticalThresholdMax {
            type string;
            description "Max Alarm Threshold of TxOutput Power per channel.'-100' value represents no power. '-100.001' indicates unavailable.";
        }
    }

    notification cmmTransCriticalTxPowerLow {

        description "Set when Transferred Power of transceiver is below low alarm level..";

        leaf cmmTransIndex {
            type string;
            description "A unique index for each slot within the unit.";
        }

        leaf cmmStackUnitIndex {
            type string;
            description "The unique index for this entry.Refer to the object cmmStackUnitIndexNext.";
        }

        leaf cmmTransType {
            type string;
            description "Type of the transceiver SFP/QSFP.";
        }

        leaf cmmTransChannelIndex {
            type string;
            description "A unique value, greater than zero, for each channel in the transceiver within the unit.For SFP transceivers, only channel '1' is applicable.";
        }

        leaf cmmTransTxPower {
            type string;
            description "Measured TX output power in Channel of transceiver.'-100' value represents no power. '-100.001' indicates unavailable.";
        }

        leaf cmmTransTxPowerCriticalThresholdMin {
            type string;
            description "Min Alarm Threshold of TxOutput Power per channel.'-100' value represents no power. '-100.001' indicates unavailable.";
        }

        leaf cmmTransTxPowerCriticalThresholdMax {
            type string;
            description "Max Alarm Threshold of TxOutput Power per channel.'-100' value represents no power. '-100.001' indicates unavailable.";
        }
    }

    notification cmmTransAlertTxPowerHigh {

        description "Set when Transferred Power of transceiver exceeds high alert level..";

        leaf cmmTransIndex {
            type string;
            description "A unique index for each slot within the unit.";
        }

        leaf cmmStackUnitIndex {
            type string;
            description "The unique index for this entry.Refer to the object cmmStackUnitIndexNext.";
        }

        leaf cmmTransType {
            type string;
            description "Type of the transceiver SFP/QSFP.";
        }

        leaf cmmTransChannelIndex {
            type string;
            description "A unique value, greater than zero, for each channel in the transceiver within the unit.For SFP transceivers, only channel '1' is applicable.";
        }

        leaf cmmTransTxPower {
            type string;
            description "Measured TX output power in Channel of transceiver.'-100' value represents no power. '-100.001' indicates unavailable.";
        }

        leaf cmmTransTxPowerAlertThresholdMin {
            type string;
            description "Min Alert Threshold of TxOutput Power per channel.'-100' value represents no power. '-100.001' indicates unavailable.";
        }

        leaf cmmTransTxPowerAlertThresholdMax {
            type string;
            description "Max Alert Threshold of TxOutput Power per channel.'-100' value represents no power. '-100.001' indicates unavailable.";
        }
    }

    notification cmmTransAlertTxPowerLow {

        description "Set when Transferred Power of transceiver is below low alert level..";

        leaf cmmTransIndex {
            type string;
            description "A unique index for each slot within the unit.";
        }

        leaf cmmStackUnitIndex {
            type string;
            description "The unique index for this entry.Refer to the object cmmStackUnitIndexNext.";
        }

        leaf cmmTransType {
            type string;
            description "Type of the transceiver SFP/QSFP.";
        }

        leaf cmmTransChannelIndex {
            type string;
            description "A unique value, greater than zero, for each channel in the transceiver within the unit.For SFP transceivers, only channel '1' is applicable.";
        }

        leaf cmmTransTxPower {
            type string;
            description "Measured TX output power in Channel of transceiver.'-100' value represents no power. '-100.001' indicates unavailable.";
        }

        leaf cmmTransTxPowerAlertThresholdMin {
            type string;
            description "Min Alert Threshold of TxOutput Power per channel.'-100' value represents no power. '-100.001' indicates unavailable.";
        }

        leaf cmmTransTxPowerAlertThresholdMax {
            type string;
            description "Max Alert Threshold of TxOutput Power per channel.'-100' value represents no power. '-100.001' indicates unavailable.";
        }
    }

    notification cmmTransNotifyTransceiverTxPowRecovered {

        description "Set when Transferred Power of transceiver is recovered to normal..";

        leaf cmmTransIndex {
            type string;
            description "A unique index for each slot within the unit.";
        }

        leaf cmmStackUnitIndex {
            type string;
            description "The unique index for this entry.Refer to the object cmmStackUnitIndexNext.";
        }

        leaf cmmTransType {
            type string;
            description "Type of the transceiver SFP/QSFP.";
        }

        leaf cmmTransChannelIndex {
            type string;
            description "A unique value, greater than zero, for each channel in the transceiver within the unit.For SFP transceivers, only channel '1' is applicable.";
        }

        leaf cmmTransTxPower {
            type string;
            description "Measured TX output power in Channel of transceiver.'-100' value represents no power. '-100.001' indicates unavailable.";
        }
    }

    notification cmmTransNotifyTransceiverInserted {

        description " Set when Trasceiver is inserted..";

        leaf cmmTransIndex {
            type string;
            description "A unique index for each slot within the unit.";
        }

        leaf cmmStackUnitIndex {
            type string;
            description "The unique index for this entry.Refer to the object cmmStackUnitIndexNext.";
        }

        leaf cmmTransType {
            type string;
            description "Type of the transceiver SFP/QSFP.";
        }

        leaf cmmTransVendorName {
            type string;
            description "Transceiver vendor name. Blank indicates unavailable.";
        }

        leaf cmmTransVendorSerialNumber {
            type string;
            description "Serial number provided by vendor. Blank indicates unavailable.";
        }

        leaf cmmTransconnectortype {
            type string;
            description "Connector type for the transceiver.";
        }
    }

    notification cmmTransAlertTransceiverRemoved {

        description " Set when Trasceiver is removed..";

        leaf cmmTransIndex {
            type string;
            description "A unique index for each slot within the unit.";
        }

        leaf cmmStackUnitIndex {
            type string;
            description "The unique index for this entry.Refer to the object cmmStackUnitIndexNext.";
        }

        leaf cmmTransType {
            type string;
            description "Type of the transceiver SFP/QSFP.";
        }

        leaf cmmTransVendorName {
            type string;
            description "Transceiver vendor name. Blank indicates unavailable.";
        }

        leaf cmmTransVendorSerialNumber {
            type string;
            description "Serial number provided by vendor. Blank indicates unavailable.";
        }

        leaf cmmTransconnectortype {
            type string;
            description "Connector type for the transceiver.";
        }
    }

    notification cmmTransAlertFaultyTransceiverInserted {

        description " Set when Faulty Trasceiver is inserted..";

        leaf cmmTransIndex {
            type string;
            description "A unique index for each slot within the unit.";
        }

        leaf cmmStackUnitIndex {
            type string;
            description "The unique index for this entry.Refer to the object cmmStackUnitIndexNext.";
        }

        leaf cmmTransType {
            type string;
            description "Type of the transceiver SFP/QSFP.";
        }
    }

    notification cmmAlertIncompatibleTransceiverPresence {

        description "Set when Incompatible Trasceiver is Present..";

        leaf cmmTransIndex {
            type string;
            description "A unique index for each slot within the unit.";
        }

        leaf cmmStackUnitIndex {
            type string;
            description "The unique index for this entry.Refer to the object cmmStackUnitIndexNext.";
        }
    }

    notification cmmNotifyIncompatibleTransceiverRemoved {

        description "Set when Incompatible Trasceiver is Removed..";

        leaf cmmTransIndex {
            type string;
            description "A unique index for each slot within the unit.";
        }

        leaf cmmStackUnitIndex {
            type string;
            description "The unique index for this entry.Refer to the object cmmStackUnitIndexNext.";
        }
    }

    notification g8032-state-change-notification {

        description "This notification indicates state change of the instance per the G.8032 state machine.";

        leaf instName {
            type string;
            description "ERPS instance identifier";
        }

        leaf bridgeId {
            type string;
            description "";
        }

        leaf vrId {
            type string;
            description "Virtual router id";
        }

        leaf currentState {
            type string;
            description "The current state of the ERPS instance";
        }

        leaf prevState {
            type string;
            description "The previous state of the ERPS instance";
        }
    }

    notification cfm_oam_capture_fault_info {

        description "Notify alarm message.";

        leaf mepIdentifier {
            type string;
            description "Integer that is unique among all the MEPs in the same MA. Other definition is: a small integer, unique over a given Maintenance Association, identifying a specific Maintenance association End Point";
        }

        leaf maName {
            type string;
            description "The value union for the Maintenance Association Name. The type must correspond to the configuration name-type according to the";
        }

        leaf mdName {
            type string;
            description "A unique identifier of a Maintenance Domain";
        }

        leaf bridgeId {
            type string;
            description "";
        }

        leaf vrId {
            type string;
            description "Virtual router id";
        }

        leaf highestPriorityDefectFound {
            type string;
            description "Value indicating the highest-priority defect that has been present since the MEP Fault Notification Generator state machine           was last in the FNG_RESET state The non-existence of this leaf represents that no defect has been present since the last FNG_RESET state";
        }
    }

    notification cpuQueueFull {

        description "notification to send information when CPU queue is full..";

        leaf queueId {
            type string;
            description "cpuqueueId is a unique number representing each queue in CPU";
        }

        leaf queueName {
            type string;
            description "Queue Name corresponding to the QueueId.";
        }

        leaf ratePercent {
            type string;
            description "Percentage of control packets transmitted in the CPU queue.
            Value of -1 indicates rate percentage is not applicable.";
        }

        leaf txPktRate {
            type string;
            description "The number of Tx Pkts transmitted from the corresponding CPU queue.";
        }

        leaf lastIncrementCnt {
            type string;
            description "The number of Last Dropped Pkts in the corresponding CPU queue.
            This is Updated at every 5sec interval.";
        }

        leaf lastIncrementTime {
            type string;
            description "Last increment time of Tx Dropped Packets in CPU Queue.
             This is Updated at every 5sec interval.";
        }
    }

    notification cpuQueueHigh {

        description "notification to send information when CPU queue is high crossing threshold of 90%..";

        leaf queueId {
            type string;
            description "cpuqueueId is a unique number representing each queue in CPU";
        }

        leaf queueName {
            type string;
            description "Queue Name corresponding to the QueueId.";
        }

        leaf ratePercent {
            type string;
            description "Percentage of control packets transmitted in the CPU queue.
            Value of -1 indicates rate percentage is not applicable.";
        }

        leaf txPktRate {
            type string;
            description "The number of Tx Pkts transmitted from the corresponding CPU queue.";
        }
    }

    notification cpuQueueRecovery {

        description "notification to send information when CPU queue is recovered from full/high..";

        leaf queueId {
            type string;
            description "cpuqueueId is a unique number representing each queue in CPU";
        }

        leaf queueName {
            type string;
            description "Queue Name corresponding to the QueueId.";
        }

        leaf ratePercent {
            type string;
            description "Percentage of control packets transmitted in the CPU queue.
            Value of -1 indicates rate percentage is not applicable.";
        }
    }

    notification cpuCRCErrorPkts {

        description "notification to send information for CRC error packets received on the cpu interface..";

        leaf badCrc {
            type string;
            description "Last increment time of Bad CRC packets.
             This is Updated at every 5sec interval.";
        }
    }

    notification cpuUndersizeErrorPkts {

        description "notification to send information for undersize error packets received on the cpu interface..";

        leaf undersizePkts {
            type string;
            description "Last inbound packets discarded whose size are less than
             64 octets (which exclude framing bits, but include the FCS)
             and have a good FCS value.
             This is Updated at every 5sec interval.";
        }
    }

    notification cpuOversizeErrorPkts {

        description "notification to send information for oversize error packets received on the cpu interface..";

        leaf mtuExceed {
            type string;
            description "Rx Oversize Packets";
        }
    }

    notification cpuFragementErrorPkts {

        description "notification to send information for fragment error packets received on the cpu interface..";

        leaf fragmentsPkts {
            type string;
            description "Last inbound packets discarded whose size are less than
             64 octets (which exclude framing bits, but include the FCS)
             and have a bad FCS value.
             This is Updated at every 5sec interval.";
        }
    }

    notification cpuJabberErrorPkts {

        description "notification to send information for jabber error packets received on the cpu interface..";

        leaf jabberPkts {
            type string;
            description "Last inbound packets whose size are more than maximum
            transmission unit size (which excludes framing bits, but include
            FCS) and have a bad FCS value.
            This is Updated at every 5sec interval.";
        }
    }

    notification ifCRCErrorPkts {

        description "notification to send information for CRC error packets received on the interface..";

        leaf ifName {
            type string;
            description "The textual name of the interface. The value of this object should be the name of the interface as assigned by the local device and should be suitable for use in commands entered at the device's `console'. This might be a text name, such as `le0' or a simple port number, such as `1', depending on the interface naming syntax of the device. If several entries in the ifTable together represent a single interface as named by the device, then each will have the same value of ifName. Note that for an agent which responds to SNMP queries concerning an interface on some other (proxied) device, then the value of ifName for such an interface is the proxied device's local name for it. If there is no local name, or this object is otherwise not applicable, then this object contains a zero-length string.";
        }

        leaf vrId {
            type string;
            description "Virtual router id";
        }

        leaf badCrc {
            type string;
            description "Last increment time of Bad CRC packets.
             This is Updated at every 5sec interval.";
        }
    }

    notification ifUndersizeErrorPkts {

        description "notification to send information for undersize error packets received on the interface..";

        leaf ifName {
            type string;
            description "The textual name of the interface. The value of this object should be the name of the interface as assigned by the local device and should be suitable for use in commands entered at the device's `console'. This might be a text name, such as `le0' or a simple port number, such as `1', depending on the interface naming syntax of the device. If several entries in the ifTable together represent a single interface as named by the device, then each will have the same value of ifName. Note that for an agent which responds to SNMP queries concerning an interface on some other (proxied) device, then the value of ifName for such an interface is the proxied device's local name for it. If there is no local name, or this object is otherwise not applicable, then this object contains a zero-length string.";
        }

        leaf vrId {
            type string;
            description "Virtual router id";
        }

        leaf undersizePkts {
            type string;
            description "Last inbound packets discarded whose size are less than
             64 octets (which exclude framing bits, but include the FCS)
             and have a good FCS value.
             This is Updated at every 5sec interval.";
        }
    }

    notification ifOversizeErrorPkts {

        description "notification to send information for oversize error packets received on the interface..";

        leaf ifName {
            type string;
            description "The textual name of the interface. The value of this object should be the name of the interface as assigned by the local device and should be suitable for use in commands entered at the device's `console'. This might be a text name, such as `le0' or a simple port number, such as `1', depending on the interface naming syntax of the device. If several entries in the ifTable together represent a single interface as named by the device, then each will have the same value of ifName. Note that for an agent which responds to SNMP queries concerning an interface on some other (proxied) device, then the value of ifName for such an interface is the proxied device's local name for it. If there is no local name, or this object is otherwise not applicable, then this object contains a zero-length string.";
        }

        leaf vrId {
            type string;
            description "Virtual router id";
        }

        leaf mtuExceed {
            type string;
            description "Rx Oversize Packets";
        }
    }

    notification ifFragementErrorPkts {

        description "notification to send information for fragment error packets received on the interface..";

        leaf ifName {
            type string;
            description "The textual name of the interface. The value of this object should be the name of the interface as assigned by the local device and should be suitable for use in commands entered at the device's `console'. This might be a text name, such as `le0' or a simple port number, such as `1', depending on the interface naming syntax of the device. If several entries in the ifTable together represent a single interface as named by the device, then each will have the same value of ifName. Note that for an agent which responds to SNMP queries concerning an interface on some other (proxied) device, then the value of ifName for such an interface is the proxied device's local name for it. If there is no local name, or this object is otherwise not applicable, then this object contains a zero-length string.";
        }

        leaf vrId {
            type string;
            description "Virtual router id";
        }

        leaf fragmentsPkts {
            type string;
            description "Last inbound packets discarded whose size are less than
             64 octets (which exclude framing bits, but include the FCS)
             and have a bad FCS value.
             This is Updated at every 5sec interval.";
        }
    }

    notification ifJabberErrorPkts {

        description "notification to send information for jabber error packets received on the interface..";

        leaf ifName {
            type string;
            description "The textual name of the interface. The value of this object should be the name of the interface as assigned by the local device and should be suitable for use in commands entered at the device's `console'. This might be a text name, such as `le0' or a simple port number, such as `1', depending on the interface naming syntax of the device. If several entries in the ifTable together represent a single interface as named by the device, then each will have the same value of ifName. Note that for an agent which responds to SNMP queries concerning an interface on some other (proxied) device, then the value of ifName for such an interface is the proxied device's local name for it. If there is no local name, or this object is otherwise not applicable, then this object contains a zero-length string.";
        }

        leaf vrId {
            type string;
            description "Virtual router id";
        }

        leaf jabberPkts {
            type string;
            description "Last inbound packets whose size are more than maximum
            transmission unit size (which excludes framing bits, but include
            FCS) and have a bad FCS value.
            This is Updated at every 5sec interval.";
        }
    }

    notification SysUpdateInstallation {

        description "This system update event is generated when the software installation starts and ends..";

        leaf message {
            type string;
            description " alarm message notification";
        }
    }

    notification SysUpdateDownloadStatus {

        description "Notification sent on download operation completion, on success with INFO severity/on failure with MAJOR severity..";

        leaf message {
            type string;
            description " alarm message notification";
        }
    }

}
