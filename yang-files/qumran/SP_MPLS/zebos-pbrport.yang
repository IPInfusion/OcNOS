/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-pbrport.yang
*
*/

submodule zebos-pbrport {

    belongs-to  zebos { prefix zebos; }

    import cml_data_types {
        prefix cml_data_types;
    }

    include zebos-interface;
    organization
        "IP Infusion Inc.";

    contact
        "Address: 3965 Freedom Circle, Suite 200, Santa Clara, CA 95054
         Phone: +1 408-400-1900
         E-mail: support@ipinfusion.com
         Web: http://www.ipinfusion.com/";

    description
        "Layer-3 pbr configurations";


    revision "2018-06-21" {
        description " Initial Version.";
        reference "";
    }



    grouping pbrEnable-grouping {
    description
        "pbrEnable";
        list pbrEnable {
            key "Pbr";
            description
                "pbrEnable";
            leaf Pbr  {
                type  cml_data_types:CML_BOOL_T;
                description "";
            } // END of Pbr definition.


        } // End of pbrEnable-list
    } // END of pbrEnable-grouping definition.


    grouping pbrInterface-grouping {
    description
        "PBR interface related operations";
        list pbrInterface {
            key "ifName";
            description
                "PBR interface related operations";
            leaf ifName  {
                type  cml_data_types:CML_STRING_T {
                    length "0..255";
                }
                description "";
            } // END of ifName definition.


            leaf vrId  {
                type  cml_data_types:CML_UINT32_T;
                default "0";
                description "";
            } // END of vrId definition.


            leaf RouteMap  {
                type  cml_data_types:CML_STRING_T {
                    length "0..255";
                }
                description "";
            } // END of RouteMap definition.


            leaf RouteMapv6  {
                type  cml_data_types:CML_STRING_T {
                    length "0..255";
                }
                description "";
            } // END of RouteMapv6 definition.


        } // End of pbrInterface-list
    } // END of pbrInterface-grouping definition.


}
