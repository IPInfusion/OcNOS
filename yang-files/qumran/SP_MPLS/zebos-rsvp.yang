/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-rsvp.yang
*
*/

submodule zebos-rsvp {

    belongs-to  zebos { prefix zebos; }

    import cml_data_types {
        prefix cml_data_types;
    }

    import feature_list {
        prefix feature_list;
    }

    include zebos-interface;
    organization
        "IP Infusion Inc.";

    contact
        "Address: 3965 Freedom Circle, Suite 200, Santa Clara, CA 95054
         Phone: +1 408-400-1900
         E-mail: support@ipinfusion.com
         Web: http://www.ipinfusion.com/";

    description
        "Resource Reservation Protocol";


    revision "2018-06-21" {
        description " Initial Version.";
        reference "";
    }



    grouping datalink-grouping {
    description
        "datalink";
        list datalink {
            if-feature feature_list:HAVE_GMPLS;
            key "dlName";
            config false;
            description
                "datalink";
            leaf dlName  {
                type  cml_data_types:CML_STRING_T {
                    length "0..255";
                }
                description "";
            } // END of dlName definition.


            leaf dlDescription  {
                type  cml_data_types:CML_STRING_T {
                    length "0..255";
                }
                description "";
            } // END of dlDescription definition.


            leaf dlGifIndex  {
                type  cml_data_types:CML_INT32_T;
                description "";
            } // END of dlGifIndex definition.


            leaf lLinkid  {
                type  cml_data_types:CML_STRING_T {
                    length "0..255";
                }
                description "";
            } // END of lLinkid definition.


            leaf rLinkid  {
                type  cml_data_types:CML_STRING_T {
                    length "0..255";
                }
                description "";
            } // END of rLinkid definition.


            leaf ifpName  {
                type  cml_data_types:CML_STRING_T {
                    length "0..255";
                }
                description "";
            } // END of ifpName definition.


            leaf teLinkName  {
                type  cml_data_types:CML_STRING_T {
                    length "0..255";
                }
                description "";
            } // END of teLinkName definition.


            container rsvpDatalinkInterface {
                config false;
                description
                    "rsvpDatalinkInterface";
                leaf rsvpStatusFlag  {
                    type  cml_data_types:CML_STRING_T {
                        length "0..255";
                    }
                    description "";
                } // END of rsvpStatusFlag definition.


                leaf labelSpaceStatusFlag  {
                    type  cml_data_types:CML_STRING_T {
                        length "0..255";
                    }
                    description "";
                } // END of labelSpaceStatusFlag definition.


                leaf rsvpdlifIfIndex  {
                    type  cml_data_types:CML_UINT32_T;
                    description "";
                } // END of rsvpdlifIfIndex definition.


                leaf rsvpdlifLabelSpace  {
                    type  cml_data_types:CML_UINT16_T;
                    description "";
                } // END of rsvpdlifLabelSpace definition.


                leaf rsvpdlifMinLabelVal  {
                    type  cml_data_types:CML_UINT32_T;
                    description "";
                } // END of rsvpdlifMinLabelVal definition.


                leaf rsvpdlifMaxLabelVal  {
                    type  cml_data_types:CML_UINT32_T;
                    description "";
                } // END of rsvpdlifMaxLabelVal definition.


            } // END of rsvpDatalinkInterface-container definition.
        } // End of datalink-list
    } // END of datalink-grouping definition.


    grouping rsvpInterface-grouping {
    description
        "RSVP interface related operations";
        list rsvpInterface {
            key "ifName";
            description
                "RSVP interface related operations";
            leaf ifName  {
                type  cml_data_types:CML_STRING_T {
                    length "0..255";
                }
                description "";
            } // END of ifName definition.


            leaf vrId  {
                type  cml_data_types:CML_INT32_T;
                description "";
            } // END of vrId definition.


            uses rsvpInterfaceGrouping;
        } // End of rsvpInterface-list
    } // END of rsvpInterface-grouping definition.
    grouping rsvpTrunk {
        description
            "rsvpTrunk";
        leaf trunkId  {
            type  cml_data_types:CML_UINT16_T;
            config false;
            description "";
        } // END of trunkId definition.


        leaf description  {
            type  cml_data_types:CML_STRING_T {
                length "0..255";
            }
            config false;
            description "";
        } // END of description definition.


        leaf egress  {
            type  cml_data_types:CML_STRING_T {
                length "0..255";
            }
            config false;
            description "";
        } // END of egress definition.


        leaf sessionStyle  {
            type  cml_data_types:CML_STRING_T {
                length "0..255";
            }
            config false;
            description "";
        } // END of sessionStyle definition.


        leaf sessionInLabel  {
            type  cml_data_types:CML_STRING_T {
                length "0..255";
            }
            config false;
            description "";
        } // END of sessionInLabel definition.


        leaf sessionOutLabel  {
            type  cml_data_types:CML_STRING_T {
                length "0..255";
            }
            config false;
            description "";
        } // END of sessionOutLabel definition.


        leaf dsType  {
            type  cml_data_types:CML_STRING_T {
                length "0..255";
            }
            config false;
            description "";
        } // END of dsType definition.


        leaf extTunnelId  {
            type  cml_data_types:CML_STRING_T {
                length "0..255";
            }
            default "NULL";
            description "";
        } // END of extTunnelId definition.


        leaf ingress  {
            type  cml_data_types:CML_STRING_T {
                length "0..255";
            }
            config false;
            description "";
        } // END of ingress definition.


        leaf techType  {
            type  cml_data_types:CML_UINT8_T;
            description "";
        } // END of techType definition.


        leaf trunkType  {
            type  cml_data_types:CML_UINT8_T;
            config false;
            description "";
        } // END of trunkType definition.


        leaf config  {
            type  cml_data_types:CML_UINT32_T;
            config false;
            description "";
        } // END of config definition.


        leaf flags  {
            type  cml_data_types:CML_UINT8_T;
            config false;
            description "";
        } // END of flags definition.


        leaf family  {
            type  cml_data_types:CML_RSVP_TRUNK_ADDRFAMILY_T;
            mandatory true;
            description "";
        } // END of family definition.


        leaf updateType  {
            type  cml_data_types:CML_UINT8_T;
            config false;
            description "";
        } // END of updateType definition.


        leaf bypassTrunk  {
            if-feature feature_list:HAVE_MPLS_FRR;
            type  cml_data_types:CML_BOOL_T;
            config false;
            description "";
        } // END of bypassTrunk definition.


        leaf bypassCurrentBandwidth  {
            if-feature feature_list:HAVE_MPLS_FRR;
            type  cml_data_types:CML_INT32_T;
            config false;
            description "";
        } // END of bypassCurrentBandwidth definition.


        leaf upStamp  {
            type  cml_data_types:CML_UINT32_T;
            config false;
            description "";
        } // END of upStamp definition.


        leaf lastUpStamp  {
            type  cml_data_types:CML_UINT32_T;
            config false;
            description "";
        } // END of lastUpStamp definition.


        leaf configMetric  {
            type  cml_data_types:CML_UINT32_T;
            config false;
            description "";
        } // END of configMetric definition.


        leaf gmplsFlags  {
            type  cml_data_types:CML_UINT8_T;
            config false;
            description "";
        } // END of gmplsFlags definition.


        leaf tesiState  {
            type  cml_data_types:CML_UINT8_T;
            config false;
            description "";
        } // END of tesiState definition.


        leaf p2mpId  {
            type  cml_data_types:CML_UINT32_T;
            config false;
            description "";
        } // END of p2mpId definition.


        leaf activeSessionType  {
            type  cml_data_types:CML_UINT8_T;
            config false;
            description "";
        } // END of activeSessionType definition.



        list mainSessionList {
            key "sessionRole";
            config false;
            description
                "mainSessionList";
            leaf sessionRole  {
                type  cml_data_types:CML_STRING_T {
                    length "0..255";
                }
                description "";
            } // END of sessionRole definition.


            uses rsvpSession;
        } // End of mainSessionList-list

        list mbbSessionList {
            key "sessionRole";
            config false;
            description
                "mbbSessionList";
            leaf sessionRole  {
                type  cml_data_types:CML_STRING_T {
                    length "0..255";
                }
                description "";
            } // END of sessionRole definition.


            uses rsvpSession;
        } // End of mbbSessionList-list

        list detourSessionList {
            key "sessionRole";
            config false;
            description
                "detourSessionList";
            leaf sessionRole  {
                type  cml_data_types:CML_STRING_T {
                    length "0..255";
                }
                description "";
            } // END of sessionRole definition.


            uses rsvpSession;
        } // End of detourSessionList-list

        list rsvpMappedRoute4 {
            key "dst";
            config false;
            description
                "rsvpMappedRoute4";
            leaf sessionLspId  {
                type  cml_data_types:CML_UINT16_T;
                description "";
            } // END of sessionLspId definition.


            leaf dscpIn  {
                type  cml_data_types:CML_UINT8_T;
                description "";
            } // END of dscpIn definition.


            leaf prefixlen  {
                type  cml_data_types:CML_UINT8_T;
                description "";
            } // END of prefixlen definition.


            leaf family  {
                type  cml_data_types:CML_UINT8_T;
                description "";
            } // END of family definition.


            leaf trunkId  {
                type  cml_data_types:CML_UINT16_T;
                description "";
            } // END of trunkId definition.


            leaf dst  {
                type  cml_data_types:CML_STRING_T {
                    length "0..255";
                }
                description "";
            } // END of dst definition.


        } // End of rsvpMappedRoute4-list

        list rsvpMappedRoute6 {
            key "dst";
            config false;
            description
                "rsvpMappedRoute6";
            leaf sessionLspId  {
                type  cml_data_types:CML_UINT16_T;
                description "";
            } // END of sessionLspId definition.


            leaf dscpIn  {
                type  cml_data_types:CML_UINT8_T;
                description "";
            } // END of dscpIn definition.


            leaf prefixlen  {
                type  cml_data_types:CML_UINT8_T;
                description "";
            } // END of prefixlen definition.


            leaf family  {
                type  cml_data_types:CML_UINT8_T;
                description "";
            } // END of family definition.


            leaf trunkId  {
                type  cml_data_types:CML_UINT16_T;
                description "";
            } // END of trunkId definition.


            leaf dst  {
                type  cml_data_types:CML_STRING_T {
                    length "0..255";
                }
                description "";
            } // END of dst definition.


        } // End of rsvpMappedRoute6-list
        container rsvpSessLabelSet {
            config false;
            description
                "rsvpSessLabelSet";
            leaf actionType  {
                type  cml_data_types:CML_UINT8_T;
                description "";
            } // END of actionType definition.


            leaf startLabelRange  {
                type  cml_data_types:CML_UINT32_T;
                description "";
            } // END of startLabelRange definition.


            leaf endLabelRange  {
                type  cml_data_types:CML_UINT32_T;
                description "";
            } // END of endLabelRange definition.


        } // END of rsvpSessLabelSet-container definition.
        container gmplsAttr {
            config false;
            description
                "gmplsAttr";
            leaf direction  {
                type  cml_data_types:CML_UINT8_T;
                description "";
            } // END of direction definition.


            leaf encodingType  {
                type  cml_data_types:CML_UINT16_T;
                description "";
            } // END of encodingType definition.


            leaf switchingCapability  {
                type  cml_data_types:CML_UINT16_T;
                description "the switching cap";
            } // END of switchingCapability definition.


            leaf gpId  {
                type  cml_data_types:CML_UINT16_T;
                description "";
            } // END of gpId definition.


        } // END of gmplsAttr-container definition.
        container pceAttr {
            if-feature feature_list:HAVE_PCE;
            config false;
            description
                "pceAttr";
            leaf objectiveFunc  {
                type  cml_data_types:CML_UINT8_T;
                description "";
            } // END of objectiveFunc definition.


            leaf objMetricType  {
                type  cml_data_types:CML_UINT8_T;
                description "";
            } // END of objMetricType definition.


            leaf-list metValue  {
                type  cml_data_types:CML_UINT32_T;
                description "";
            } // END of metValue definition.


        } // END of pceAttr-container definition.
    } // END of rsvpTrunk definition.
    grouping p2mpSession {
        description
            "p2mpSession";
        leaf sessionType  {
            type  cml_data_types:CML_UINT8_T;
            description "";
        } // END of sessionType definition.


        leaf sessionRole  {
            type  cml_data_types:CML_STRING_T {
                length "0..255";
            }
            description "";
        } // END of sessionRole definition.


        leaf ingress  {
            type  cml_data_types:CML_STRING_T {
                length "0..255";
            }
            description "";
        } // END of ingress definition.


        leaf isInterface  {
            type  cml_data_types:CML_UINT32_T;
            description "";
        } // END of isInterface definition.


        leaf adminState  {
            type  cml_data_types:CML_UINT32_T;
            description "";
        } // END of adminState definition.


        leaf rowStatus  {
            type  cml_data_types:CML_UINT32_T;
            description "";
        } // END of rowStatus definition.


        leaf upTime  {
            type  cml_data_types:CML_UINT32_T;
            description "";
        } // END of upTime definition.


        leaf lastUpStamp  {
            type  cml_data_types:CML_UINT32_T;
            description "";
        } // END of lastUpStamp definition.


        leaf first  {
            type  cml_data_types:CML_UINT8_T;
            description "";
        } // END of first definition.


        leaf upStamp  {
            type  cml_data_types:CML_UINT32_T;
            description "";
        } // END of upStamp definition.


        leaf stateChangeCount  {
            type  cml_data_types:CML_UINT32_T;
            description "";
        } // END of stateChangeCount definition.


        leaf type  {
            type  cml_data_types:CML_UINT8_T;
            description "";
        } // END of type definition.


        leaf p2mpRole  {
            type  cml_data_types:CML_UINT8_T;
            description "";
        } // END of p2mpRole definition.


        leaf s2lCnt  {
            type  cml_data_types:CML_UINT16_T;
            description "";
        } // END of s2lCnt definition.


        leaf actvS2lCnt  {
            type  cml_data_types:CML_UINT16_T;
            description "";
        } // END of actvS2lCnt definition.


        leaf mbbSyncPending  {
            type  cml_data_types:CML_UINT16_T;
            description "";
        } // END of mbbSyncPending definition.


        leaf flags  {
            type  cml_data_types:CML_UINT32_T;
            description "";
        } // END of flags definition.


        leaf config  {
            type  cml_data_types:CML_UINT8_T;
            description "";
        } // END of config definition.


        leaf protection  {
            if-feature feature_list:HAVE_MPLS_FRR;
            type  cml_data_types:CML_UINT8_T;
            description "";
        } // END of protection definition.


        leaf backupMode  {
            if-feature feature_list:HAVE_MPLS_FRR;
            type  cml_data_types:CML_UINT8_T;
            description "";
        } // END of backupMode definition.


        leaf frrConfig  {
            if-feature feature_list:HAVE_MPLS_FRR;
            type  cml_data_types:CML_UINT16_T;
            description "";
        } // END of frrConfig definition.



        list adminGroupList {
            if-feature feature_list:HAVE_TE;
            key "adminGroupName";
            config false;
            description
                "adminGroupList";
            leaf type  {
                type  cml_data_types:CML_UINT8_T;
                description "";
            } // END of type definition.


            leaf adminGroupName  {
                type  cml_data_types:CML_STRING_T {
                    length "0..255";
                }
                description "";
            } // END of adminGroupName definition.


            leaf val  {
                type  cml_data_types:CML_UINT32_T;
                description "";
            } // END of val definition.


        } // End of adminGroupList-list

        list frrAdminGroupList {
            if-feature feature_list:HAVE_MPLS_FRR;
            key "name";
            config false;
            description
                "frrAdminGroupList";
            leaf type  {
                type  cml_data_types:CML_UINT8_T;
                description "";
            } // END of type definition.


            leaf name  {
                type  cml_data_types:CML_STRING_T {
                    length "0..255";
                }
                description "";
            } // END of name definition.


            leaf val  {
                type  cml_data_types:CML_UINT32_T;
                description "";
            } // END of val definition.


        } // End of frrAdminGroupList-list
        container p2mpSessConfig {
            config false;
            description
                "p2mpSessConfig";
            leaf includeAny  {
                type  cml_data_types:CML_UINT32_T;
                description "";
            } // END of includeAny definition.


            leaf excludeAny  {
                type  cml_data_types:CML_UINT32_T;
                description "";
            } // END of excludeAny definition.


            leaf includeAll  {
                type  cml_data_types:CML_UINT32_T;
                description "";
            } // END of includeAll definition.


            leaf bandwidth  {
                type  cml_data_types:CML_INT32_T;
                description "";
            } // END of bandwidth definition.


            leaf retryCount  {
                type  cml_data_types:CML_UINT16_T;
                description "";
            } // END of retryCount definition.


            leaf retryInterval  {
                type  cml_data_types:CML_UINT16_T;
                description "";
            } // END of retryInterval definition.


            leaf ctName  {
                if-feature feature_list:HAVE_DSTE;
                type  cml_data_types:CML_STRING_T {
                    length "0..255";
                }
                description "";
            } // END of ctName definition.


            leaf ctNum  {
                if-feature feature_list:HAVE_DSTE;
                type  cml_data_types:CML_UINT8_T;
                description "";
            } // END of ctNum definition.


            leaf traffic  {
                type  cml_data_types:CML_UINT8_T;
                description "";
            } // END of traffic definition.


            leaf hopLimit  {
                type  cml_data_types:CML_UINT8_T;
                description "";
            } // END of hopLimit definition.


            leaf setupPriority  {
                type  cml_data_types:CML_UINT8_T;
                description "";
            } // END of setupPriority definition.


            leaf holdPriority  {
                type  cml_data_types:CML_UINT8_T;
                description "";
            } // END of holdPriority definition.


        } // END of p2mpSessConfig-container definition.
        container p2mpSessFrrConfig {
            if-feature feature_list:HAVE_MPLS_FRR;
            config false;
            description
                "p2mpSessFrrConfig";
            leaf sPriority  {
                type  cml_data_types:CML_UINT8_T;
                description "";
            } // END of sPriority definition.


            leaf hPriority  {
                type  cml_data_types:CML_UINT8_T;
                description "";
            } // END of hPriority definition.


            leaf hopLimit  {
                type  cml_data_types:CML_UINT8_T;
                description "";
            } // END of hopLimit definition.


            leaf flags  {
                type  cml_data_types:CML_UINT8_T;
                description "";
            } // END of flags definition.


            leaf bandwidth  {
                type  cml_data_types:CML_INT32_T;
                description "";
            } // END of bandwidth definition.


            leaf includeAny  {
                type  cml_data_types:CML_UINT32_T;
                description "";
            } // END of includeAny definition.


            leaf excludeAny  {
                type  cml_data_types:CML_UINT32_T;
                description "";
            } // END of excludeAny definition.


            leaf includeAll  {
                type  cml_data_types:CML_UINT32_T;
                description "";
            } // END of includeAll definition.


        } // END of p2mpSessFrrConfig-container definition.
    } // END of p2mpSession definition.
    grouping rsvpSession {
        description
            "rsvpSession";
        leaf lspId  {
            type  cml_data_types:CML_UINT16_T;
            description "";
        } // END of lspId definition.


        leaf sessionType  {
            type  cml_data_types:CML_UINT8_T;
            description "";
        } // END of sessionType definition.


        leaf ingress  {
            type  cml_data_types:CML_STRING_T {
                length "0..255";
            }
            description "";
        } // END of ingress definition.


        leaf isInterface  {
            type  cml_data_types:CML_UINT32_T;
            description "";
        } // END of isInterface definition.


        leaf adminState  {
            type  cml_data_types:CML_UINT32_T;
            description "";
        } // END of adminState definition.


        leaf rowStatus  {
            type  cml_data_types:CML_UINT32_T;
            description "";
        } // END of rowStatus definition.


        leaf upTime  {
            type  cml_data_types:CML_UINT32_T;
            description "";
        } // END of upTime definition.


        leaf lastUpStamp  {
            type  cml_data_types:CML_UINT32_T;
            description "";
        } // END of lastUpStamp definition.


        leaf first  {
            type  cml_data_types:CML_UINT8_T;
            description "";
        } // END of first definition.


        leaf upStamp  {
            type  cml_data_types:CML_UINT32_T;
            description "";
        } // END of upStamp definition.


        leaf stateChangeCount  {
            type  cml_data_types:CML_UINT32_T;
            description "";
        } // END of stateChangeCount definition.


        leaf type  {
            type  cml_data_types:CML_UINT8_T;
            description "";
        } // END of type definition.


        leaf cspfMetric  {
            type  cml_data_types:CML_UINT16_T;
            description "";
        } // END of cspfMetric definition.


        leaf lspName  {
            type  cml_data_types:CML_STRING_T {
                length "0..255";
            }
            description "";
        } // END of lspName definition.


        leaf retryCountNum  {
            type  cml_data_types:CML_UINT16_T;
            description "";
        } // END of retryCountNum definition.


        leaf retryCount  {
            type  cml_data_types:CML_UINT16_T;
            description "";
        } // END of retryCount definition.


        leaf retryInterval  {
            type  cml_data_types:CML_UINT16_T;
            description "";
        } // END of retryInterval definition.


        leaf cspfRetryCount  {
            type  cml_data_types:CML_UINT16_T;
            description "";
        } // END of cspfRetryCount definition.


        leaf cspfRetryCountInterval  {
            type  cml_data_types:CML_UINT16_T;
            description "";
        } // END of cspfRetryCountInterval definition.


        leaf excludePathCount  {
            if-feature feature_list:HAVE_MPLS_FRR;
            type  cml_data_types:CML_UINT8_T;
            description "";
        } // END of excludePathCount definition.


        leaf errNode  {
            type  cml_data_types:CML_STRING_T {
                length "0..255";
            }
            description "";
        } // END of errNode definition.


        leaf errCode  {
            type  cml_data_types:CML_UINT32_T;
            description "";
        } // END of errCode definition.


        leaf errVal  {
            type  cml_data_types:CML_UINT32_T;
            description "";
        } // END of errVal definition.


        leaf pathChangeCount  {
            type  cml_data_types:CML_UINT32_T;
            description "";
        } // END of pathChangeCount definition.


        leaf hopLimit  {
            type  cml_data_types:CML_UINT8_T;
            description "";
        } // END of hopLimit definition.


        leaf errFlag  {
            type  cml_data_types:CML_UINT8_T;
            description "";
        } // END of errFlag definition.


        leaf traffic  {
            type  cml_data_types:CML_UINT8_T;
            description "";
        } // END of traffic definition.


        leaf flags  {
            type  cml_data_types:CML_UINT32_T;
            description "";
        } // END of flags definition.


        leaf flags2  {
            type  cml_data_types:CML_UINT32_T;
            description "";
        } // END of flags2 definition.


        leaf config  {
            type  cml_data_types:CML_UINT32_T;
            description "";
        } // END of config definition.


        leaf nexthopAddr  {
            type  cml_data_types:CML_STRING_T {
                length "0..255";
            }
            description "";
        } // END of nexthopAddr definition.


        leaf protection  {
            if-feature feature_list:HAVE_MPLS_FRR;
            type  cml_data_types:CML_UINT32_T;
            description "";
        } // END of protection definition.


        leaf frrOriginIngress  {
            if-feature feature_list:HAVE_MPLS_FRR;
            type  cml_data_types:CML_STRING_T {
                length "0..255";
            }
            description "";
        } // END of frrOriginIngress definition.


        leaf backupMode  {
            if-feature feature_list:HAVE_MPLS_FRR;
            type  cml_data_types:CML_UINT8_T;
            description "";
        } // END of backupMode definition.


        leaf mergeCount  {
            if-feature feature_list:HAVE_MPLS_FRR;
            type  cml_data_types:CML_UINT32_T;
            description "";
        } // END of mergeCount definition.


        leaf frrConfig  {
            if-feature feature_list:HAVE_MPLS_FRR;
            type  cml_data_types:CML_UINT32_T;
            description "";
        } // END of frrConfig definition.


        leaf frrFlags  {
            if-feature feature_list:HAVE_MPLS_FRR;
            type  cml_data_types:CML_UINT32_T;
            description "";
        } // END of frrFlags definition.


        leaf mpRtrId  {
            if-feature feature_list:HAVE_MPLS_FRR;
            type  cml_data_types:CML_UINT32_T;
            description "";
        } // END of mpRtrId definition.


        leaf numMpIpaddr  {
            if-feature feature_list:HAVE_MPLS_FRR;
            type  cml_data_types:CML_UINT32_T;
            description "";
        } // END of numMpIpaddr definition.


        leaf numTrIpaddr  {
            if-feature feature_list:HAVE_MPLS_FRR;
            type  cml_data_types:CML_UINT32_T;
            description "";
        } // END of numTrIpaddr definition.


        leaf mpLabel  {
            if-feature feature_list:HAVE_MPLS_FRR;
            type  cml_data_types:CML_UINT32_T;
            description "";
        } // END of mpLabel definition.


        leaf bwCurrent  {
            if-feature feature_list:HAVE_MPLS_FRR;
            type  cml_data_types:CML_UINT32_T;
            description "";
        } // END of bwCurrent definition.


        leaf protCurr  {
            if-feature feature_list:HAVE_MPLS_FRR;
            type  cml_data_types:CML_UINT32_T;
            description "";
        } // END of protCurr definition.


        leaf satisfied  {
            if-feature feature_list:HAVE_MPLS_FRR;
            type  cml_data_types:CML_UINT32_T;
            description "";
        } // END of satisfied definition.


        leaf txBytes  {
            if-feature feature_list:HAVE_MPLS_FWD;
            type  cml_data_types:CML_UINT32_T;
            description "";
        } // END of txBytes definition.


        leaf txPkts  {
            if-feature feature_list:HAVE_MPLS_FWD;
            type  cml_data_types:CML_UINT32_T;
            description "";
        } // END of txPkts definition.


        leaf errorPkts  {
            if-feature feature_list:HAVE_MPLS_FWD;
            type  cml_data_types:CML_UINT32_T;
            description "";
        } // END of errorPkts definition.


        leaf hcPkts  {
            if-feature feature_list:HAVE_MPLS_FWD;
            type  cml_data_types:CML_UINT32_T;
            description "";
        } // END of hcPkts definition.


        leaf hcBytes  {
            if-feature feature_list:HAVE_MPLS_FWD;
            type  cml_data_types:CML_UINT32_T;
            description "";
        } // END of hcBytes definition.


        leaf sessionState  {
            type  cml_data_types:CML_UINT32_T;
            description "";
        } // END of sessionState definition.


        leaf subGrpOrigId  {
            type  cml_data_types:CML_STRING_T {
                length "0..255";
            }
            description "";
        } // END of subGrpOrigId definition.


        leaf egress  {
            type  cml_data_types:CML_STRING_T {
                length "0..255";
            }
            description "";
        } // END of egress definition.


        leaf s2lMbbRole  {
            type  cml_data_types:CML_UINT8_T;
            description "";
        } // END of s2lMbbRole definition.



        list adminGroupList {
            key "adminGroupName";
            config false;
            description
                "adminGroupList";
            leaf type  {
                type  cml_data_types:CML_UINT8_T;
                description "";
            } // END of type definition.


            leaf adminGroupName  {
                type  cml_data_types:CML_STRING_T {
                    length "0..255";
                }
                description "";
            } // END of adminGroupName definition.


            leaf val  {
                type  cml_data_types:CML_UINT32_T;
                description "";
            } // END of val definition.


        } // End of adminGroupList-list

        list frrAdminGroupList {
            if-feature feature_list:HAVE_MPLS_FRR;
            key "name";
            config false;
            description
                "frrAdminGroupList";
            leaf type  {
                type  cml_data_types:CML_UINT8_T;
                description "";
            } // END of type definition.


            leaf name  {
                type  cml_data_types:CML_STRING_T {
                    length "0..255";
                }
                description "";
            } // END of name definition.


            leaf val  {
                type  cml_data_types:CML_UINT32_T;
                description "";
            } // END of val definition.


        } // End of frrAdminGroupList-list
        container psb {
            config false;
            description
                "psb";
            leaf pname  {
                type  cml_data_types:CML_STRING_T {
                    length "0..255";
                }
                description "";
            } // END of pname definition.


            leaf ipTtl  {
                type  cml_data_types:CML_UINT32_T;
                description "";
            } // END of ipTtl definition.


            leaf refreshLen  {
                type  cml_data_types:CML_UINT16_T;
                description "";
            } // END of refreshLen definition.


            leaf pathRefresh  {
                type  cml_data_types:CML_UINT16_T;
                description "";
            } // END of pathRefresh definition.


            leaf pathLifetime  {
                type  cml_data_types:CML_UINT32_T;
                description "";
            } // END of pathLifetime definition.


            leaf refreshBuf  {
                type  cml_data_types:CML_STRING_T {
                    length "0..255";
                }
                description "";
            } // END of refreshBuf definition.


            leaf refreshStatus  {
                type  cml_data_types:CML_UINT32_T;
                description "";
            } // END of refreshStatus definition.


            leaf ctName  {
                type  cml_data_types:CML_STRING_T {
                    length "0..255";
                }
                description "";
            } // END of ctName definition.


            leaf ctNum  {
                type  cml_data_types:CML_UINT8_T;
                description "";
            } // END of ctNum definition.


            leaf msgId  {
                type  cml_data_types:CML_UINT32_T;
                description "";
            } // END of msgId definition.


            leaf-list epoch  {
                type  cml_data_types:CML_UINT8_T;
                description "";
            } // END of epoch definition.


            leaf rcvdMsgId  {
                type  cml_data_types:CML_UINT32_T;
                description "";
            } // END of rcvdMsgId definition.


            leaf-list rcvdEpoch  {
                type  cml_data_types:CML_UINT8_T;
                description "";
            } // END of rcvdEpoch definition.


            leaf psbFlags  {
                type  cml_data_types:CML_UINT8_T;
                description "";
            } // END of psbFlags definition.


            container eroList {
                config false;
                description
                    "eroList";
                uses rsvpPathEroRuntimeGrouping;
            } // END of eroList-container definition.
            container rcvdEroList {
                config false;
                description
                    "rcvdEroList";
                uses rsvpPathEroRuntimeGrouping;
            } // END of rcvdEroList-container definition.
            container rroDown {
                config false;
                description
                    "rroDown";
                uses rsvpPathRroGrouping;
            } // END of rroDown-container definition.
            container phop {
                config false;
                description
                    "phop";
                leaf address  {
                    type  cml_data_types:CML_STRING_T {
                        length "0..255";
                    }
                    description "";
                } // END of address definition.


                leaf phopIfindex  {
                    type  cml_data_types:CML_UINT32_T;
                    description "";
                } // END of phopIfindex definition.


            } // END of phop-container definition.
            container diffserv {
                config false;
                description
                    "diffserv";
                container elsp {
                    config false;
                    description
                        "elsp";
                    leaf mapNb  {
                        type  cml_data_types:CML_UINT32_T;
                        description "";
                    } // END of mapNb definition.



                    list mapEntry {
                        key "id";
                        config false;
                        description
                            "mapEntry";
                        leaf id  {
                            type  cml_data_types:CML_UINT32_T;
                            description "";
                        } // END of id definition.


                        leaf exp  {
                            type  cml_data_types:CML_UINT16_T;
                            description "";
                        } // END of exp definition.


                        leaf phbid  {
                            type  cml_data_types:CML_UINT16_T;
                            description "";
                        } // END of phbid definition.


                    } // End of mapEntry-list
                } // END of elsp-container definition.
                container llsp {
                    config false;
                    description
                        "llsp";
                    leaf psc  {
                        type  cml_data_types:CML_UINT32_T;
                        description "";
                    } // END of psc definition.


                } // END of llsp-container definition.
            } // END of diffserv-container definition.
            container frr {
                config false;
                description
                    "frr";
                leaf count  {
                    type  cml_data_types:CML_UINT16_T;
                    description "";
                } // END of count definition.


                leaf frrIfIndex  {
                    type  cml_data_types:CML_UINT32_T;
                    description "";
                } // END of frrIfIndex definition.


                leaf sPriority  {
                    type  cml_data_types:CML_UINT8_T;
                    description "";
                } // END of sPriority definition.


                leaf hPriority  {
                    type  cml_data_types:CML_UINT8_T;
                    description "";
                } // END of hPriority definition.


                leaf hopLimit  {
                    type  cml_data_types:CML_UINT8_T;
                    description "";
                } // END of hopLimit definition.


                leaf flags  {
                    type  cml_data_types:CML_UINT8_T;
                    description "";
                } // END of flags definition.


                leaf bandwidth  {
                    type  cml_data_types:CML_INT32_T;
                    description "";
                } // END of bandwidth definition.


                leaf includeAny  {
                    type  cml_data_types:CML_UINT32_T;
                    description "";
                } // END of includeAny definition.


                leaf excludeAny  {
                    type  cml_data_types:CML_UINT32_T;
                    description "";
                } // END of excludeAny definition.


                leaf includeAll  {
                    type  cml_data_types:CML_UINT32_T;
                    description "";
                } // END of includeAll definition.


            } // END of frr-container definition.
            container detour {
                config false;
                description
                    "detour";
                leaf count  {
                    type  cml_data_types:CML_UINT16_T;
                    description "";
                } // END of count definition.


                container avoidNode {
                    config false;
                    description
                        "avoidNode";
                    leaf plrId  {
                        type  cml_data_types:CML_STRING_T {
                            length "0..255";
                        }
                        description "";
                    } // END of plrId definition.


                    leaf avoidnodeId  {
                        type  cml_data_types:CML_STRING_T {
                            length "0..255";
                        }
                        description "";
                    } // END of avoidnodeId definition.


                } // END of avoidNode-container definition.
            } // END of detour-container definition.
            container psbLabel {
                config false;
                description
                    "psbLabel";
                leaf fec  {
                    type  cml_data_types:CML_STRING_T {
                        length "0..255";
                    }
                    description "";
                } // END of fec definition.


                leaf labelSpace  {
                    type  cml_data_types:CML_UINT16_T;
                    description "";
                } // END of labelSpace definition.


                leaf installFlag  {
                    type  cml_data_types:CML_UINT8_T;
                    description "";
                } // END of installFlag definition.


                leaf lspDirection  {
                    type  cml_data_types:CML_UINT8_T;
                    description "";
                } // END of lspDirection definition.


            } // END of psbLabel-container definition.
            uses sessionAttrGrouping;
        } // END of psb-container definition.
        container rsb {
            config false;
            description
                "rsb";
            leaf rsvpIfUp  {
                type  cml_data_types:CML_STRING_T {
                    length "0..255";
                }
                description "";
            } // END of rsvpIfUp definition.


            leaf resvRefresh  {
                type  cml_data_types:CML_UINT16_T;
                description "";
            } // END of resvRefresh definition.


            leaf resvLifetime  {
                type  cml_data_types:CML_UINT32_T;
                description "";
            } // END of resvLifetime definition.


            leaf rsbMsgId  {
                type  cml_data_types:CML_UINT32_T;
                description "";
            } // END of rsbMsgId definition.


            leaf rsbEpoch  {
                type  cml_data_types:CML_STRING_T {
                    length "0..255";
                }
                description "";
            } // END of rsbEpoch definition.


            leaf rsbRcvdMsgId  {
                type  cml_data_types:CML_UINT32_T;
                description "";
            } // END of rsbRcvdMsgId definition.


            leaf rsbFlags  {
                type  cml_data_types:CML_UINT8_T;
                description "";
            } // END of rsbFlags definition.


            container rroUp {
                config false;
                description
                    "rroUp";
                uses rsvpPathRroGrouping;
            } // END of rroUp-container definition.
            container nhop {
                config false;
                description
                    "nhop";
                leaf address  {
                    type  cml_data_types:CML_STRING_T {
                        length "0..255";
                    }
                    description "";
                } // END of address definition.


                leaf hopIfindex  {
                    type  cml_data_types:CML_UINT32_T;
                    description "";
                } // END of hopIfindex definition.


            } // END of nhop-container definition.
            container rsbLabel {
                config false;
                description
                    "rsbLabel";
                leaf fec  {
                    type  cml_data_types:CML_STRING_T {
                        length "0..255";
                    }
                    description "";
                } // END of fec definition.


                leaf labelSpace  {
                    type  cml_data_types:CML_UINT16_T;
                    description "";
                } // END of labelSpace definition.


                leaf installFlag  {
                    type  cml_data_types:CML_UINT8_T;
                    description "";
                } // END of installFlag definition.


                leaf lspDirection  {
                    type  cml_data_types:CML_UINT8_T;
                    description "";
                } // END of lspDirection definition.


            } // END of rsbLabel-container definition.
            uses labelObjGrouping;
        } // END of rsb-container definition.
        container dsInfo {
            config false;
            description
                "dsInfo";
            leaf lspType  {
                type  cml_data_types:CML_UINT8_T;
                description "";
            } // END of lspType definition.


            leaf-list dscpExpMap  {
                type  cml_data_types:CML_UINT8_T;
                description "";
            } // END of dscpExpMap definition.


            leaf dscp  {
                type  cml_data_types:CML_UINT8_T;
                description "";
            } // END of dscp definition.


            leaf afSet  {
                type  cml_data_types:CML_UINT8_T;
                description "";
            } // END of afSet definition.


        } // END of dsInfo-container definition.
        container excludePath {
            if-feature feature_list:HAVE_MPLS_FRR;
            config false;
            description
                "excludePath";
            leaf excludePathType  {
                type  cml_data_types:CML_UINT8_T;
                description "";
            } // END of excludePathType definition.


            leaf excludePathAddrType  {
                type  cml_data_types:CML_UINT8_T;
                description "";
            } // END of excludePathAddrType definition.


            leaf unnumbereIfId  {
                type  cml_data_types:CML_UINT32_T;
                description "";
            } // END of unnumbereIfId definition.


            leaf unnumbereRouterId  {
                type  cml_data_types:CML_STRING_T {
                    length "0..255";
                }
                description "";
            } // END of unnumbereRouterId definition.


        } // END of excludePath-container definition.
        container mpIpAddr {
            if-feature feature_list:HAVE_MPLS_FRR;
            config false;
            description
                "mpIpAddr";
            leaf addressType  {
                type  cml_data_types:CML_UINT8_T;
                description "";
            } // END of addressType definition.


            leaf addr  {
                type  cml_data_types:CML_STRING_T {
                    length "0..255";
                }
                description "";
            } // END of addr definition.


            leaf ifId  {
                type  cml_data_types:CML_UINT32_T;
                description "";
            } // END of ifId definition.


        } // END of mpIpAddr-container definition.
        container rsvpSessGmplsAttr {
            config false;
            description
                "rsvpSessGmplsAttr";
            leaf bwReverse  {
                type  cml_data_types:CML_INT32_T;
                description "";
            } // END of bwReverse definition.


            leaf linkProtection  {
                type  cml_data_types:CML_UINT8_T;
                description "";
            } // END of linkProtection definition.


            leaf flags  {
                type  cml_data_types:CML_UINT8_T;
                description "";
            } // END of flags definition.


            leaf-list sharedLinkGroup  {
                type  cml_data_types:CML_STRING_T {
                    length "0..255";
                }
                description "";
            } // END of sharedLinkGroup definition.


            container forwardDir {
                config false;
                description
                    "forwardDir";
                leaf entryType  {
                    type  cml_data_types:CML_UINT8_T;
                    description "";
                } // END of entryType definition.


                leaf pkt  {
                    type  cml_data_types:CML_UINT32_T;
                    description "";
                } // END of pkt definition.


                leaf gifndex  {
                    type  cml_data_types:CML_UINT32_T;
                    description "";
                } // END of gifndex definition.


                leaf tslot  {
                    type  cml_data_types:CML_UINT32_T;
                    description "";
                } // END of tslot definition.


                leaf bvid  {
                    type  cml_data_types:CML_UINT16_T;
                    description "";
                } // END of bvid definition.


                leaf-list bmac  {
                    type  cml_data_types:CML_UINT8_T;
                    description "";
                } // END of bmac definition.


            } // END of forwardDir-container definition.
            container reverseDir {
                config false;
                description
                    "reverseDir";
                leaf entryType  {
                    type  cml_data_types:CML_UINT8_T;
                    description "";
                } // END of entryType definition.


                leaf pkt  {
                    type  cml_data_types:CML_UINT32_T;
                    description "";
                } // END of pkt definition.


                leaf gifndex  {
                    type  cml_data_types:CML_UINT32_T;
                    description "";
                } // END of gifndex definition.


                leaf tslot  {
                    type  cml_data_types:CML_UINT32_T;
                    description "";
                } // END of tslot definition.


                leaf bvid  {
                    type  cml_data_types:CML_UINT16_T;
                    description "";
                } // END of bvid definition.


                leaf-list bmac  {
                    type  cml_data_types:CML_UINT8_T;
                    description "";
                } // END of bmac definition.


            } // END of reverseDir-container definition.
        } // END of rsvpSessGmplsAttr-container definition.
        container p2mpNextHopNode {
            config false;
            description
                "p2mpNextHopNode";
            leaf iifIx  {
                type  cml_data_types:CML_UINT32_T;
                description "";
            } // END of iifIx definition.


            leaf inlabel  {
                type  cml_data_types:CML_UINT32_T;
                description "";
            } // END of inlabel definition.


            leaf oifIx  {
                type  cml_data_types:CML_UINT32_T;
                description "";
            } // END of oifIx definition.


            leaf nhAddr  {
                type  cml_data_types:CML_STRING_T {
                    length "0..255";
                }
                description "";
            } // END of nhAddr definition.


            leaf outLabel  {
                type  cml_data_types:CML_UINT32_T;
                description "";
            } // END of outLabel definition.


            leaf state  {
                type  cml_data_types:CML_UINT32_T;
                description "";
            } // END of state definition.



            list s21Sess {
                key "lspId";
                config false;
                description
                    "s21Sess";
                leaf lspId  {
                    type  cml_data_types:CML_UINT32_T;
                    description "";
                } // END of lspId definition.


                leaf egress  {
                    type  cml_data_types:CML_STRING_T {
                        length "0..255";
                    }
                    description "";
                } // END of egress definition.


                leaf sessionRole  {
                    type  cml_data_types:CML_UINT8_T;
                    description "";
                } // END of sessionRole definition.


            } // End of s21Sess-list
            container retData {
                config false;
                description
                    "retData";
                container ftnRetData {
                    config false;
                    description
                        "ftnRetData";
                    leaf flags  {
                        type  cml_data_types:CML_UINT16_T;
                        description "";
                    } // END of flags definition.


                    leaf id  {
                        type  cml_data_types:CML_UINT32_T;
                        description "";
                    } // END of id definition.


                    leaf ftnIx  {
                        type  cml_data_types:CML_UINT32_T;
                        description "";
                    } // END of ftnIx definition.


                    leaf nhAddr  {
                        type  cml_data_types:CML_STRING_T {
                            length "0..255";
                        }
                        description "";
                    } // END of nhAddr definition.


                    leaf xcIx  {
                        type  cml_data_types:CML_UINT32_T;
                        description "";
                    } // END of xcIx definition.


                    leaf nhlfeIx  {
                        type  cml_data_types:CML_UINT32_T;
                        description "";
                    } // END of nhlfeIx definition.


                    leaf nhInfoNum  {
                        type  cml_data_types:CML_UINT32_T;
                        description "";
                    } // END of nhInfoNum definition.


                } // END of ftnRetData-container definition.
                container ilmGenRetData {
                    config false;
                    description
                        "ilmGenRetData";
                    leaf flags  {
                        type  cml_data_types:CML_UINT16_T;
                        description "";
                    } // END of flags definition.


                    leaf id  {
                        type  cml_data_types:CML_UINT32_T;
                        description "";
                    } // END of id definition.


                    leaf iifIx  {
                        type  cml_data_types:CML_UINT32_T;
                        description "";
                    } // END of iifIx definition.


                    leaf ilmIx  {
                        type  cml_data_types:CML_UINT32_T;
                        description "";
                    } // END of ilmIx definition.


                    leaf nhAddr  {
                        type  cml_data_types:CML_STRING_T {
                            length "0..255";
                        }
                        description "";
                    } // END of nhAddr definition.


                    leaf xcIx  {
                        type  cml_data_types:CML_UINT32_T;
                        description "";
                    } // END of xcIx definition.


                    leaf nhlfeIx  {
                        type  cml_data_types:CML_UINT32_T;
                        description "";
                    } // END of nhlfeIx definition.


                    leaf nhInfoNum  {
                        type  cml_data_types:CML_UINT32_T;
                        description "";
                    } // END of nhInfoNum definition.


                } // END of ilmGenRetData-container definition.
            } // END of retData-container definition.
        } // END of p2mpNextHopNode-container definition.
        uses qosResourceGrouping;
    } // END of rsvpSession definition.
    grouping rsvpPathEroRuntimeGrouping {
        description
            "rsvpPathEroRuntimeGrouping";
        leaf hopCount  {
            type  cml_data_types:CML_UINT16_T;
            description "";
        } // END of hopCount definition.


        leaf explicitLabelIinfo  {
            type  cml_data_types:CML_UINT8_T;
            description "";
        } // END of explicitLabelIinfo definition.


        leaf isStrict  {
            type  cml_data_types:CML_UINT8_T;
            description "";
        } // END of isStrict definition.


        leaf rowStatus  {
            type  cml_data_types:CML_UINT32_T;
            description "";
        } // END of rowStatus definition.


        leaf stType  {
            type  cml_data_types:CML_UINT32_T;
            description "";
        } // END of stType definition.


        leaf type  {
            type  cml_data_types:CML_UINT8_T;
            description "";
        } // END of type definition.


        leaf pathComp  {
            type  cml_data_types:CML_UINT32_T;
            description "";
        } // END of pathComp definition.



        list unnumbered {
            key "unnumberedAddrRun";
            config false;
            description
                "unnumbered";
            leaf unnumberedAddrRun  {
                type  cml_data_types:CML_STRING_T {
                    length "0..255";
                }
                description "";
            } // END of unnumberedAddrRun definition.



            list linkaddr {
                key "linkAddressRun";
                config false;
                description
                    "linkaddr";
                leaf linkAddressRun  {
                    type  cml_data_types:CML_STRING_T {
                        length "0..255";
                    }
                    description "";
                } // END of linkAddressRun definition.


            } // End of linkaddr-list
        } // End of unnumbered-list
        container explicitLabelForward {
            config false;
            description
                "explicitLabelForward";
            leaf gmplsEntryType  {
                type  cml_data_types:CML_UINT8_T;
                description "";
            } // END of gmplsEntryType definition.


            leaf pkt  {
                type  cml_data_types:CML_UINT32_T;
                description "";
            } // END of pkt definition.


            container tdm {
                config false;
                description
                    "tdm";
                leaf gifndex  {
                    type  cml_data_types:CML_UINT32_T;
                    description "";
                } // END of gifndex definition.


                leaf tslot  {
                    type  cml_data_types:CML_UINT32_T;
                    description "";
                } // END of tslot definition.


            } // END of tdm-container definition.
            container pbb {
                config false;
                description
                    "pbb";
                leaf bvid  {
                    type  cml_data_types:CML_UINT16_T;
                    description "";
                } // END of bvid definition.


                leaf-list bmac  {
                    type  cml_data_types:CML_UINT8_T;
                    description "";
                } // END of bmac definition.


            } // END of pbb-container definition.
        } // END of explicitLabelForward-container definition.
        container explicitLabelRev {
            config false;
            description
                "explicitLabelRev";
            leaf gmplsEntryType  {
                type  cml_data_types:CML_UINT8_T;
                description "";
            } // END of gmplsEntryType definition.


            leaf pkt  {
                type  cml_data_types:CML_UINT32_T;
                description "";
            } // END of pkt definition.


            container tdm {
                config false;
                description
                    "tdm";
                leaf gifndex  {
                    type  cml_data_types:CML_UINT32_T;
                    description "";
                } // END of gifndex definition.


                leaf tslot  {
                    type  cml_data_types:CML_UINT32_T;
                    description "";
                } // END of tslot definition.


            } // END of tdm-container definition.
            container pbb {
                config false;
                description
                    "pbb";
                leaf bvid  {
                    type  cml_data_types:CML_UINT16_T;
                    description "";
                } // END of bvid definition.


                leaf-list bmac  {
                    type  cml_data_types:CML_UINT8_T;
                    description "";
                } // END of bmac definition.


            } // END of pbb-container definition.
        } // END of explicitLabelRev-container definition.
    } // END of rsvpPathEroRuntimeGrouping definition.
    grouping rsvpPathRroGrouping {
        description
            "rsvpPathRroGrouping";
        leaf pathRroLength  {
            type  cml_data_types:CML_UINT16_T;
            config false;
            description "";
        } // END of pathRroLength definition.


        leaf pathRroVal  {
            type  cml_data_types:CML_STRING_T {
                length "0..255";
            }
            config false;
            description "";
        } // END of pathRroVal definition.


    } // END of rsvpPathRroGrouping definition.
    grouping rsvpInterfaceGrouping {
        description
            "rsvpInterfaceGrouping";
        leaf ipv4Address  {
            type  cml_data_types:CML_STRING_T {
                length "0..255";
            }
            config false;
            description "";
        } // END of ipv4Address definition.


        leaf ipv6Address  {
            type  cml_data_types:CML_STRING_T {
                length "0..255";
            }
            config false;
            description "";
        } // END of ipv6Address definition.


        leaf ifConfig  {
            type  cml_data_types:CML_UINT16_T;
            config false;
            description "";
        } // END of ifConfig definition.


        leaf refreshReductionConfig  {
            type  cml_data_types:CML_BOOL_T;
            description "";
        } // END of refreshReductionConfig definition.


        leaf messageAckConfig  {
            type  cml_data_types:CML_BOOL_T;
            description "";
        } // END of messageAckConfig definition.


        leaf IANAHelloConfig  {
            type  cml_data_types:CML_BOOL_T;
            description "";
        } // END of IANAHelloConfig definition.


        leaf helloReceiptConfig  {
            type  cml_data_types:CML_BOOL_T;
            description "";
        } // END of helloReceiptConfig definition.


        leaf ifRefreshTime  {
            type  cml_data_types:CML_UINT16_T {
                 range "1..65535";
            }
            description "";
        } // END of ifRefreshTime definition.


        leaf interfaceType  {
            type  cml_data_types:CML_STRING_T {
                length "0..255";
            }
            config false;
            description "";
        } // END of interfaceType definition.


        leaf rsvpStatus  {
            type  cml_data_types:CML_STRING_T {
                length "0..255";
            }
            config false;
            description "";
        } // END of rsvpStatus definition.


        leaf ctrlAdjStatus  {
            type  cml_data_types:CML_STRING_T {
                length "0..255";
            }
            config false;
            description "";
        } // END of ctrlAdjStatus definition.


        leaf ifRefreshReductionFlag  {
            type  cml_data_types:CML_STRING_T {
                length "0..255";
            }
            config false;
            description "";
        } // END of ifRefreshReductionFlag definition.


        leaf ifMsgAcknowledgementFlag  {
            type  cml_data_types:CML_STRING_T {
                length "0..255";
            }
            config false;
            description "";
        } // END of ifMsgAcknowledgementFlag definition.


        leaf keepMultipler  {
            type  cml_data_types:CML_UINT8_T {
                 range "1..255";
            }
            default "3";
            description "";
        } // END of keepMultipler definition.


        leaf bundleBufSize  {
            type  cml_data_types:CML_UINT16_T;
            config false;
            description "";
        } // END of bundleBufSize definition.


        leaf ifHelloInterval  {
            type  cml_data_types:CML_UINT16_T {
                 range "1..65535";
            }
            description "";
        } // END of ifHelloInterval definition.


        leaf ifHelloTimeout  {
            type  cml_data_types:CML_UINT16_T {
                 range "1..65535";
            }
            description "";
        } // END of ifHelloTimeout definition.


        leaf enableRsvpFlag  {
            type  cml_data_types:CML_BOOL_T;
            description "the Control Adj structure";
        } // END of enableRsvpFlag definition.


        leaf ifFlags  {
            type  cml_data_types:CML_UINT8_T;
            config false;
            description "";
        } // END of ifFlags definition.


        leaf epoch  {
            type  cml_data_types:CML_UINT8_T;
            config false;
            description "";
        } // END of epoch definition.


        leaf bypassName  {
            if-feature feature_list:HAVE_MPLS_FRR;
            type  cml_data_types:CML_STRING_T {
                length "0..255";
            }
            config false;
            description "";
        } // END of bypassName definition.


        leaf msgId  {
            type  cml_data_types:CML_UINT32_T;
            config false;
            description "";
        } // END of msgId definition.


        leaf maxMsgId  {
            type  cml_data_types:CML_UINT32_T;
            config false;
            description "";
        } // END of maxMsgId definition.


        leaf ifAckWaitTimeout  {
            type  cml_data_types:CML_UINT16_T {
                 range "1..65535";
            }
            description "";
        } // END of ifAckWaitTimeout definition.


        leaf ackWaitInterval  {
            type  cml_data_types:CML_UINT16_T;
            config false;
            description "";
        } // END of ackWaitInterval definition.


        leaf type  {
            type  cml_data_types:CML_UINT8_T;
            config false;
            description "";
        } // END of type definition.


        container rsvpDataLinkInterface {
            config false;
            description
                "rsvpDataLinkInterface";
            leaf flags  {
                type  cml_data_types:CML_UINT8_T;
                description "";
            } // END of flags definition.


            leaf dLIfIndex  {
                type  cml_data_types:CML_UINT32_T;
                description "";
            } // END of dLIfIndex definition.


            container labelSpaceData {
                config false;
                description
                    "labelSpaceData";
                leaf status  {
                    type  cml_data_types:CML_UINT8_T;
                    description "";
                } // END of status definition.


                leaf labelSpace  {
                    type  cml_data_types:CML_UINT16_T;
                    description "";
                } // END of labelSpace definition.


                leaf minLabelValue  {
                    type  cml_data_types:CML_UINT32_T;
                    description "";
                } // END of minLabelValue definition.


                leaf maxLabelValue  {
                    type  cml_data_types:CML_UINT32_T;
                    description "";
                } // END of maxLabelValue definition.



                list labelRangeData {
                    key "labelPoolRangeMax";
                    config false;
                    description
                        "labelRangeData";
                    leaf labelPoolRangeMax  {
                        type  cml_data_types:CML_UINT32_T;
                        description "";
                    } // END of labelPoolRangeMax definition.


                    leaf fromLabel  {
                        type  cml_data_types:CML_UINT32_T;
                        description "";
                    } // END of fromLabel definition.


                    leaf toLabel  {
                        type  cml_data_types:CML_UINT32_T;
                        description "";
                    } // END of toLabel definition.


                } // End of labelRangeData-list
            } // END of labelSpaceData-container definition.
        } // END of rsvpDataLinkInterface-container definition.
        container rsvpControlAdjUseCc {
            config false;
            description
                "rsvpControlAdjUseCc";
            leaf ccName  {
                type  cml_data_types:CML_STRING_T {
                    length "0..255";
                }
                description "";
            } // END of ccName definition.


            leaf ccgifindex  {
                type  cml_data_types:CML_UINT32_T;
                description "";
            } // END of ccgifindex definition.


            leaf ccid  {
                type  cml_data_types:CML_UINT32_T;
                description "";
            } // END of ccid definition.


            leaf bifindex  {
                type  cml_data_types:CML_UINT32_T;
                description "";
            } // END of bifindex definition.


            leaf lAddr  {
                type  cml_data_types:CML_STRING_T {
                    length "0..255";
                }
                description "";
            } // END of lAddr definition.


            leaf rAddr  {
                type  cml_data_types:CML_STRING_T {
                    length "0..255";
                }
                description "";
            } // END of rAddr definition.


        } // END of rsvpControlAdjUseCc-container definition.
    } // END of rsvpInterfaceGrouping definition.
    grouping labelObjGrouping {
        description
            "labelObjGrouping";

        list labelObj {
            key "techType";
            config false;
            description
                "labelObj";
            leaf techType  {
                type  cml_data_types:CML_UINT8_T;
                description "";
            } // END of techType definition.


            leaf length  {
                type  cml_data_types:CML_UINT32_T;
                description "";
            } // END of length definition.


        } // End of labelObj-list
    } // END of labelObjGrouping definition.
    grouping sessionAttrGrouping {
        description
            "sessionAttrGrouping";
        container sessionAttr {
            config false;
            description
                "sessionAttr";
            leaf cType  {
                type  cml_data_types:CML_UINT8_T;
                description "";
            } // END of cType definition.


            leaf excludeAny  {
                type  cml_data_types:CML_UINT32_T;
                description "";
            } // END of excludeAny definition.


            leaf includeAny  {
                type  cml_data_types:CML_UINT32_T;
                description "";
            } // END of includeAny definition.


            leaf includeAll  {
                type  cml_data_types:CML_UINT32_T;
                description "";
            } // END of includeAll definition.


            leaf setupPriority  {
                type  cml_data_types:CML_UINT8_T;
                description "";
            } // END of setupPriority definition.


            leaf holdPriority  {
                type  cml_data_types:CML_UINT8_T;
                description "";
            } // END of holdPriority definition.


            leaf localProtectionInUseFlags  {
                type  cml_data_types:CML_UINT8_T;
                description "";
            } // END of localProtectionInUseFlags definition.


            leaf flags  {
                type  cml_data_types:CML_UINT8_T;
                description "";
            } // END of flags definition.


            leaf nameLen  {
                type  cml_data_types:CML_UINT8_T;
                description "";
            } // END of nameLen definition.


            leaf sessionName  {
                type  cml_data_types:CML_STRING_T {
                    length "0..255";
                }
                description "";
            } // END of sessionName definition.


        } // END of sessionAttr-container definition.
    } // END of sessionAttrGrouping definition.
    grouping qosResourceGrouping {
        description
            "qosResourceGrouping";
        container qosResource {
            config false;
            description
                "qosResource";
            leaf resourceId  {
                type  cml_data_types:CML_UINT32_T;
                description "";
            } // END of resourceId definition.


            leaf protocolId  {
                type  cml_data_types:CML_UINT8_T;
                description "";
            } // END of protocolId definition.


            leaf id  {
                type  cml_data_types:CML_UINT32_T;
                description "";
            } // END of id definition.


            leaf flags  {
                type  cml_data_types:CML_UINT16_T;
                description "";
            } // END of flags definition.


            leaf setupPriority  {
                type  cml_data_types:CML_UINT8_T;
                description "";
            } // END of setupPriority definition.


            leaf holdPriority  {
                type  cml_data_types:CML_UINT8_T;
                description "";
            } // END of holdPriority definition.


            leaf qosRefCount  {
                type  cml_data_types:CML_UINT32_T;
                description "";
            } // END of qosRefCount definition.


            leaf ctNum  {
                type  cml_data_types:CML_UINT8_T;
                description "";
            } // END of ctNum definition.


        } // END of qosResource-container definition.
    } // END of qosResourceGrouping definition.

    grouping  rsvpMaster-grouping {
    description
        "rsvp Master configurations";
    container rsvpMaster {
        description
            "rsvp Master configurations";
        leaf confDebugFlag  {
            type  cml_data_types:CML_RSVP_DEBUG_T;
            description "";
        } // END of confDebugFlag definition.


        leaf termDebugFlag  {
            type  cml_data_types:CML_RSVP_DEBUG_T;
            description "";
        } // END of termDebugFlag definition.


        leaf notification  {
            if-feature feature_list:HAVE_SNMP;
            type  cml_data_types:CML_ENABLE_DISABLE_T;
            description "";
        } // END of notification definition.


        leaf notificationMaxrate  {
            type  cml_data_types:CML_UINT32_T;
            config false;
            description "";
        } // END of notificationMaxrate definition.


        leaf notifyResendTime  {
            type  cml_data_types:CML_UINT16_T;
            config false;
            description "";
        } // END of notifyResendTime definition.


        leaf supportedDSCPClassName  {
            type  cml_data_types:CML_STRING_T {
                length "0..255";
            }
            config false;
            description "";
        } // END of supportedDSCPClassName definition.


        leaf supportedDscpBits  {
            type  cml_data_types:CML_STRING_T {
                length "0..255";
            }
            config false;
            description "";
        } // END of supportedDscpBits definition.


        leaf classExpMappingName  {
            type  cml_data_types:CML_STRING_T {
                length "0..255";
            }
            config false;
            description "";
        } // END of classExpMappingName definition.


        leaf classExpMappingBits  {
            type  cml_data_types:CML_STRING_T {
                length "0..255";
            }
            config false;
            description "";
        } // END of classExpMappingBits definition.


        leaf classExpMapExpValue  {
            type  cml_data_types:CML_UINT8_T;
            config false;
            description "";
        } // END of classExpMapExpValue definition.



        list adminGroup {
            key "adminGroupName";
            config false;
            description
                "adminGroup";
            leaf adminGroupName  {
                type  cml_data_types:CML_STRING_T {
                    length "0..255";
                }
                description "";
            } // END of adminGroupName definition.


            leaf val  {
                type  cml_data_types:CML_UINT32_T;
                description "";
            } // END of val definition.


        } // End of adminGroup-list

        list dsteData {
            if-feature feature_list:HAVE_DSTE;
            key "ctNum";
            config false;
            description
                "dsteData";
            leaf ctName  {
                type  cml_data_types:CML_STRING_T {
                    length "0..255";
                }
                description "";
            } // END of ctName definition.


            leaf ctNum  {
                type  cml_data_types:CML_UINT8_T;
                description "";
            } // END of ctNum definition.


            leaf tePriority  {
                type  cml_data_types:CML_UINT8_T;
                description "";
            } // END of tePriority definition.


        } // End of dsteData-list
        container rsvpInstance {
            presence "yes";
            description
                "rsvpInstance";
            leaf rsvpInstance  {
                type  cml_data_types:CML_RSVP_INSTANCE_T;
                mandatory true;
                description "rsvp Instance";
            } // END of rsvpInstance definition.


            leaf bundleSendConfig  {
                type  cml_data_types:CML_BOOL_T;
                description "";
            } // END of bundleSendConfig definition.


            leaf cspfStatus  {
                if-feature feature_list:HAVE_CSPF;
                type  cml_data_types:CML_RSVP_CSPF_STATUS_T;
                description "";
            } // END of cspfStatus definition.


            leaf explicitNull  {
                type  cml_data_types:CML_BOOL_T;
                description "";
            } // END of explicitNull definition.


            leaf gracefulRestartConfig  {
                if-feature feature_list:HAVE_RSVP_GRST;
                type  cml_data_types:CML_RSVP_RESTART_STATUS_T;
                description "";
            } // END of gracefulRestartConfig definition.


            leaf helloReciptConfig  {
                type  cml_data_types:CML_BOOL_T;
                description "";
            } // END of helloReciptConfig definition.


            leaf localProtection  {
                type  cml_data_types:CML_BOOL_T;
                description "";
            } // END of localProtection definition.


            leaf messageAck  {
                type  cml_data_types:CML_BOOL_T;
                description "";
            } // END of messageAck definition.


            leaf rsvpPhp  {
                type  cml_data_types:CML_RSVP_PHP_T;
                description "";
            } // END of rsvpPhp definition.


            leaf rsvpElc  {
                type  cml_data_types:CML_BOOL_T;
                description "";
            } // END of rsvpElc definition.


            leaf preemptionType  {
                type  cml_data_types:CML_RSVP_PREEMP_T;
                default "less-lsp-preempted";
                description "";
            } // END of preemptionType definition.


            leaf bypassLspAddrQueryInterval  {
                if-feature feature_list:HAVE_MPLS_FRR;
                type  cml_data_types:CML_UINT8_T {
                     range "10..60";
                }
                default "60";
                description "";
            } // END of bypassLspAddrQueryInterval definition.


            leaf gmplsNotification  {
                type  cml_data_types:CML_BOOL_T;
                description "";
            } // END of gmplsNotification definition.


            leaf overRideDiffServ  {
                if-feature feature_list:HAVE_DIFFSERV;
                type  cml_data_types:CML_BOOL_T;
                description "";
            } // END of overRideDiffServ definition.


            leaf preProgSuggLabel  {
                type  cml_data_types:CML_BOOL_T;
                description "the suggected label option";
            } // END of preProgSuggLabel definition.


            leaf refreshReduction  {
                type  cml_data_types:CML_BOOL_T;
                description "";
            } // END of refreshReduction definition.


            leaf refreshResvParsing  {
                type  cml_data_types:CML_REFRESH_RESV_PARSING_T;
                description "";
            } // END of refreshResvParsing definition.


            leaf refreshPathParsing  {
                type  cml_data_types:CML_REFRESH_PATH_PARSING_T;
                description "";
            } // END of refreshPathParsing definition.


            leaf detourIden  {
                if-feature feature_list:HAVE_MPLS_FRR;
                type  cml_data_types:CML_RSVP_DETOUR_IDEN_T;
                default "path";
                description "";
            } // END of detourIden definition.


            leaf ctrlPktId  {
                type  cml_data_types:CML_UINT32_T;
                config false;
                description "";
            } // END of ctrlPktId definition.


            leaf ipId  {
                type  cml_data_types:CML_UINT32_T;
                config false;
                description "";
            } // END of ipId definition.


            leaf rsvpVersion  {
                type  cml_data_types:CML_UINT16_T;
                config false;
                description "";
            } // END of rsvpVersion definition.


            leaf refreshTime  {
                type  cml_data_types:CML_UINT16_T {
                     range "1..65535";
                }
                default "30";
                description "";
            } // END of refreshTime definition.


            leaf-list forceSwitchover  {
                type  cml_data_types:CML_STRING_T {
                    length "0..255";
                }
                description "";
            } // END of forceSwitchover definition.


            leaf-list forceReopt  {
                type  cml_data_types:CML_STRING_T {
                    length "0..255";
                }
                description "";
            } // END of forceReopt definition.


            leaf egressStyle  {
                type  cml_data_types:CML_UINT8_T;
                config false;
                description "";
            } // END of egressStyle definition.


            leaf egressTraffic  {
                type  cml_data_types:CML_UINT8_T;
                config false;
                description "";
            } // END of egressTraffic definition.


            leaf helloInterval  {
                type  cml_data_types:CML_INT32_T {
                     range "1..65535";
                }
                default "2";
                description "";
            } // END of helloInterval definition.


            leaf helloTimeout  {
                type  cml_data_types:CML_INT32_T {
                     range "1..65535";
                }
                default "7";
                description "";
            } // END of helloTimeout definition.


            leaf ackWaitTimeout  {
                type  cml_data_types:CML_UINT32_T {
                     range "1..65535";
                }
                default "10";
                description "";
            } // END of ackWaitTimeout definition.


            leaf cspfLSPReopTime  {
                type  cml_data_types:CML_UINT32_T {
                     range "5..240";
                }
                default "5";
                description "";
            } // END of cspfLSPReopTime definition.


            leaf ingress  {
                type  cml_data_types:CML_IPV4_ADDR_T;
                description "";
            } // END of ingress definition.


            leaf ingress6  {
                type  cml_data_types:CML_IPV6_ADDR_T;
                description "";
            } // END of ingress6 definition.


            leaf keepMultiplier  {
                type  cml_data_types:CML_INT32_T {
                     range "1..255";
                }
                default "3";
                description "";
            } // END of keepMultiplier definition.


            leaf loopDetection  {
                type  cml_data_types:CML_LOOP_DETECTION_T;
                description "";
            } // END of loopDetection definition.


            leaf flags  {
                type  cml_data_types:CML_UINT32_T;
                config false;
                description "";
            } // END of flags definition.


            leaf grstSetRecovery  {
                type  cml_data_types:CML_UINT8_T;
                config false;
                description "";
            } // END of grstSetRecovery definition.


            leaf dsteEnable  {
                type  cml_data_types:CML_BOOL_T;
                config false;
                description "";
            } // END of dsteEnable definition.


            leaf pathSend  {
                type  cml_data_types:CML_UINT32_T;
                config false;
                description "";
            } // END of pathSend definition.


            leaf pathRecv  {
                type  cml_data_types:CML_UINT32_T;
                config false;
                description "";
            } // END of pathRecv definition.


            leaf perrSend  {
                type  cml_data_types:CML_UINT32_T;
                config false;
                description "";
            } // END of perrSend definition.


            leaf perrRecv  {
                type  cml_data_types:CML_UINT32_T;
                config false;
                description "";
            } // END of perrRecv definition.


            leaf ptearSend  {
                type  cml_data_types:CML_UINT32_T;
                config false;
                description "";
            } // END of ptearSend definition.


            leaf ptearRecv  {
                type  cml_data_types:CML_UINT32_T;
                config false;
                description "";
            } // END of ptearRecv definition.


            leaf resvFFsend  {
                type  cml_data_types:CML_UINT32_T;
                config false;
                description "";
            } // END of resvFFsend definition.


            leaf resvFFrecv  {
                type  cml_data_types:CML_UINT32_T;
                config false;
                description "";
            } // END of resvFFrecv definition.


            leaf resvWFsend  {
                type  cml_data_types:CML_UINT32_T;
                config false;
                description "";
            } // END of resvWFsend definition.


            leaf resvWFrecv  {
                type  cml_data_types:CML_UINT32_T;
                config false;
                description "";
            } // END of resvWFrecv definition.


            leaf resvSEsend  {
                type  cml_data_types:CML_UINT32_T;
                config false;
                description "";
            } // END of resvSEsend definition.


            leaf resvSErecv  {
                type  cml_data_types:CML_UINT32_T;
                config false;
                description "";
            } // END of resvSErecv definition.


            leaf rerrSend  {
                type  cml_data_types:CML_UINT32_T;
                config false;
                description "";
            } // END of rerrSend definition.


            leaf rerrRecv  {
                type  cml_data_types:CML_UINT32_T;
                config false;
                description "";
            } // END of rerrRecv definition.


            leaf rtearSend  {
                type  cml_data_types:CML_UINT32_T;
                config false;
                description "";
            } // END of rtearSend definition.


            leaf rtearRecv  {
                type  cml_data_types:CML_UINT32_T;
                config false;
                description "";
            } // END of rtearRecv definition.


            leaf rconfSend  {
                type  cml_data_types:CML_UINT32_T;
                config false;
                description "";
            } // END of rconfSend definition.


            leaf rconfRecv  {
                type  cml_data_types:CML_UINT32_T;
                config false;
                description "";
            } // END of rconfRecv definition.


            leaf helloSend  {
                type  cml_data_types:CML_UINT32_T;
                config false;
                description "";
            } // END of helloSend definition.


            leaf helloRecv  {
                type  cml_data_types:CML_UINT32_T;
                config false;
                description "";
            } // END of helloRecv definition.


            leaf bundleSend  {
                type  cml_data_types:CML_UINT32_T;
                config false;
                description "";
            } // END of bundleSend definition.


            leaf bundleRecv  {
                type  cml_data_types:CML_UINT32_T;
                config false;
                description "";
            } // END of bundleRecv definition.


            leaf ackSend  {
                type  cml_data_types:CML_UINT32_T;
                config false;
                description "";
            } // END of ackSend definition.


            leaf ackRecv  {
                type  cml_data_types:CML_UINT32_T;
                config false;
                description "";
            } // END of ackRecv definition.


            leaf srefreshSend  {
                type  cml_data_types:CML_UINT32_T;
                config false;
                description "";
            } // END of srefreshSend definition.


            leaf srefreshRecv  {
                type  cml_data_types:CML_UINT32_T;
                config false;
                description "";
            } // END of srefreshRecv definition.


            leaf notifySend  {
                type  cml_data_types:CML_UINT32_T;
                config false;
                description "";
            } // END of notifySend definition.


            leaf notifyRecv  {
                type  cml_data_types:CML_UINT32_T;
                config false;
                description "";
            } // END of notifyRecv definition.


            leaf tRecoveryTimeval  {
                type  cml_data_types:CML_STRING_T {
                    length "0..255";
                }
                config false;
                description "";
            } // END of tRecoveryTimeval definition.


            leaf grstRestart  {
                if-feature feature_list:HAVE_RSVP_GRST;
                type  cml_data_types:CML_UINT32_T {
                     range "1..4294967295";
                }
                default "18000";
                description "";
            } // END of grstRestart definition.


            leaf grstRecovery  {
                if-feature feature_list:HAVE_RSVP_GRST;
                type  cml_data_types:CML_UINT32_T {
                     range "1..4294967295";
                }
                default "36000";
                description "";
            } // END of grstRecovery definition.


            leaf routerId  {
                type  cml_data_types:CML_STRING_T {
                    length "0..255";
                }
                config false;
                description "";
            } // END of routerId definition.


            leaf revertTimer  {
                type  cml_data_types:CML_UINT32_T {
                     range "1..65535";
                }
                default "60";
                description "";
            } // END of revertTimer definition.



            list rsvpPath {
                if-feature feature_list:NOT_HAVE_MPLS_TUNNEL;
                key "pathName";
                description
                    "rsvpPath";
                leaf id  {
                    type  cml_data_types:CML_UINT16_T;
                    config false;
                    description "";
                } // END of id definition.


                leaf pathName  {
                    type  cml_data_types:CML_STRING_T {
                        length "0..255";
                    }
                    description "";
                } // END of pathName definition.


                leaf pathHopCount  {
                    type  cml_data_types:CML_UINT16_T;
                    config false;
                    description "";
                } // END of pathHopCount definition.


                leaf flags  {
                    type  cml_data_types:CML_UINT32_T;
                    config false;
                    description "";
                } // END of flags definition.


                leaf pathType  {
                    type  cml_data_types:CML_RSVP_PATH_TYPE_T;
                    mandatory true;
                    description "";
                } // END of pathType definition.


                leaf pathComp  {
                    type  cml_data_types:CML_UINT32_T;
                    config false;
                    description "";
                } // END of pathComp definition.


                container rsvpPathEro {
                    description
                        "rsvpPathEro";
                    leaf dummy  {
                        type  cml_data_types:CML_UINT16_T;
                        description "";
                    } // END of dummy definition.



                    list rsvpMplsPathHop {
                        key "hopAddr";
                        description
                            "rsvpMplsPathHop";
                        leaf pathHopType  {
                            type  cml_data_types:CML_RSVP_PATH_STATUS_T;
                            mandatory true;
                            description "";
                        } // END of pathHopType definition.


                        leaf hopAddr  {
                            type  cml_data_types:CML_IP_ADDR_T {
                                length "0..255";
                            }
                            description "";
                        } // END of hopAddr definition.


                        leaf hopPrefixlen  {
                            type  cml_data_types:CML_UINT8_T;
                            config false;
                            description "";
                        } // END of hopPrefixlen definition.


                        leaf hopAddrtype  {
                            type  cml_data_types:CML_UINT8_T;
                            config false;
                            description "";
                        } // END of hopAddrtype definition.


                        leaf hopAsNum  {
                            type  cml_data_types:CML_UINT8_T;
                            config false;
                            description "";
                        } // END of hopAsNum definition.


                        leaf hopRowstatus  {
                            type  cml_data_types:CML_UINT32_T;
                            config false;
                            description "";
                        } // END of hopRowstatus definition.


                        leaf hopStType  {
                            type  cml_data_types:CML_UINT32_T;
                            config false;
                            description "";
                        } // END of hopStType definition.


                        leaf hopInclude  {
                            type  cml_data_types:CML_BOOL_T;
                            config false;
                            description "";
                        } // END of hopInclude definition.


                    } // End of rsvpMplsPathHop-list

                    list rsvpGmplsPathStrictHop {
                        key "strictHopAddr";
                        description
                            "rsvpGmplsPathStrictHop";
                        leaf strictHopAddr  {
                            type  cml_data_types:CML_IPV4_ADDR_T;
                            description "Is hop strict or loose";
                        } // END of strictHopAddr definition.


                    } // End of rsvpGmplsPathStrictHop-list

                    list rsvpGmplsPathUnnumberedHop {
                        key "unnumberedAddr";
                        description
                            "rsvpGmplsPathUnnumberedHop";
                        leaf unnumberedAddr  {
                            type  cml_data_types:CML_IPV4_ADDR_T;
                            description "";
                        } // END of unnumberedAddr definition.



                        list linkAddr {
                            key "linkId";
                            description
                                "linkAddr";
                            leaf linkId  {
                                type  cml_data_types:CML_IPV4_ADDR_T;
                                description "";
                            } // END of linkId definition.


                        } // End of linkAddr-list
                    } // End of rsvpGmplsPathUnnumberedHop-list
                } // END of rsvpPathEro-container definition.
            } // End of rsvpPath-list

            list rsvpNeighbor {
                key "neighAddr";
                description
                    "rsvpNeighbor";
                leaf neighAddr  {
                    type  cml_data_types:CML_IP_ADDR_T {
                        length "0..255";
                    }
                    description "";
                } // END of neighAddr definition.


                leaf sessionListCount  {
                    type  cml_data_types:CML_UINT32_T;
                    config false;
                    description "";
                } // END of sessionListCount definition.


                leaf refreshReductionFlag  {
                    type  cml_data_types:CML_STRING_T {
                        length "0..255";
                    }
                    config false;
                    description "";
                } // END of refreshReductionFlag definition.


                leaf neighborUpCount  {
                    type  cml_data_types:CML_UINT32_T;
                    config false;
                    description "";
                } // END of neighborUpCount definition.


                leaf neighborDownCount  {
                    type  cml_data_types:CML_UINT32_T;
                    config false;
                    description "";
                } // END of neighborDownCount definition.


                leaf ifName  {
                    type  cml_data_types:CML_STRING_T {
                        length "0..255";
                    }
                    config false;
                    description "";
                } // END of ifName definition.


                leaf srcDistance  {
                    type  cml_data_types:CML_UINT32_T;
                    config false;
                    description "";
                } // END of srcDistance definition.


                leaf dstDistance  {
                    type  cml_data_types:CML_UINT32_T;
                    config false;
                    description "";
                } // END of dstDistance definition.


                leaf neighborState  {
                    type  cml_data_types:CML_UINT8_T;
                    config false;
                    description "";
                } // END of neighborState definition.


                leaf grstState  {
                    type  cml_data_types:CML_UINT8_T;
                    config false;
                    description "";
                } // END of grstState definition.


                leaf neighborFlags  {
                    type  cml_data_types:CML_UINT8_T;
                    config false;
                    description "";
                } // END of neighborFlags definition.


                leaf neighborConfig  {
                    type  cml_data_types:CML_STRING_T {
                        length "0..255";
                    }
                    config false;
                    description "";
                } // END of neighborConfig definition.


                leaf TsrefreshTimeval  {
                    type  cml_data_types:CML_STRING_T {
                        length "0..255";
                    }
                    config false;
                    description "";
                } // END of TsrefreshTimeval definition.


                leaf maxAckPacket  {
                    type  cml_data_types:CML_UINT8_T;
                    config false;
                    description "";
                } // END of maxAckPacket definition.


                leaf usedAckBytes  {
                    type  cml_data_types:CML_UINT8_T;
                    config false;
                    description "";
                } // END of usedAckBytes definition.


                leaf maxBundlePacket  {
                    type  cml_data_types:CML_UINT8_T;
                    config false;
                    description "";
                } // END of maxBundlePacket definition.


                leaf usedBundleBytes  {
                    type  cml_data_types:CML_UINT8_T;
                    config false;
                    description "";
                } // END of usedBundleBytes definition.


                leaf bypassFtnIx  {
                    type  cml_data_types:CML_UINT32_T;
                    config false;
                    description "";
                } // END of bypassFtnIx definition.


                leaf bypassNhlfeIx  {
                    type  cml_data_types:CML_UINT32_T;
                    config false;
                    description "";
                } // END of bypassNhlfeIx definition.


                leaf resatrtTime  {
                    if-feature feature_list:HAVE_RSVP_GRST;
                    type  cml_data_types:CML_UINT32_T;
                    config false;
                    description "";
                } // END of resatrtTime definition.


                leaf recoveryTime  {
                    if-feature feature_list:HAVE_RSVP_GRST;
                    type  cml_data_types:CML_UINT32_T;
                    config false;
                    description "";
                } // END of recoveryTime definition.


                leaf tRestartTimeval  {
                    if-feature feature_list:HAVE_RSVP_GRST;
                    type  cml_data_types:CML_UINT32_T;
                    config false;
                    description "";
                } // END of tRestartTimeval definition.


                leaf tRecoveryTimeval  {
                    if-feature feature_list:HAVE_RSVP_GRST;
                    type  cml_data_types:CML_UINT32_T;
                    config false;
                    description "";
                } // END of tRecoveryTimeval definition.



                list sessionList {
                    key "lspId";
                    config false;
                    description
                        "sessionList";
                    leaf lspId  {
                        type  cml_data_types:CML_UINT16_T;
                        description "";
                    } // END of lspId definition.


                    leaf trunkId  {
                        type  cml_data_types:CML_UINT16_T;
                        description "";
                    } // END of trunkId definition.


                    leaf sessionIngress  {
                        type  cml_data_types:CML_STRING_T {
                            length "0..255";
                        }
                        description "";
                    } // END of sessionIngress definition.


                    leaf sessionEgress  {
                        type  cml_data_types:CML_STRING_T {
                            length "0..255";
                        }
                        description "";
                    } // END of sessionEgress definition.


                    leaf sessionType  {
                        type  cml_data_types:CML_STRING_T {
                            length "0..255";
                        }
                        description "";
                    } // END of sessionType definition.


                } // End of sessionList-list
            } // End of rsvpNeighbor-list

            list srefreshTable {
                key "srefreshAddr";
                config false;
                description
                    "srefreshTable";
                leaf srefreshAddr  {
                    type  cml_data_types:CML_STRING_T {
                        length "0..255";
                    }
                    description "";
                } // END of srefreshAddr definition.


                leaf lspId  {
                    type  cml_data_types:CML_UINT16_T;
                    description "";
                } // END of lspId definition.


                leaf msgId  {
                    type  cml_data_types:CML_UINT32_T;
                    description "";
                } // END of msgId definition.


                leaf trunkId  {
                    type  cml_data_types:CML_UINT16_T;
                    description "";
                } // END of trunkId definition.


                leaf srefreshIngress  {
                    type  cml_data_types:CML_STRING_T {
                        length "0..255";
                    }
                    description "";
                } // END of srefreshIngress definition.


                leaf srefreshEgress  {
                    type  cml_data_types:CML_STRING_T {
                        length "0..255";
                    }
                    description "";
                } // END of srefreshEgress definition.


            } // End of srefreshTable-list

            list localAddr4 {
                key "ifName";
                config false;
                description
                    "localAddr4";
                leaf ifName  {
                    type  cml_data_types:CML_STRING_T {
                        length "0..255";
                    }
                    description "";
                } // END of ifName definition.


                leaf ipv4Family  {
                    type  cml_data_types:CML_STRING_T {
                        length "0..255";
                    }
                    description "";
                } // END of ipv4Family definition.


                leaf addr4  {
                    type  cml_data_types:CML_STRING_T {
                        length "0..255";
                    }
                    description "";
                } // END of addr4 definition.


            } // End of localAddr4-list

            list localAddr6 {
                key "ifName";
                config false;
                description
                    "localAddr6";
                leaf ifName  {
                    type  cml_data_types:CML_STRING_T {
                        length "0..255";
                    }
                    description "";
                } // END of ifName definition.


                leaf ipv6Family  {
                    type  cml_data_types:CML_STRING_T {
                        length "0..255";
                    }
                    description "";
                } // END of ipv6Family definition.


                leaf addr6  {
                    type  cml_data_types:CML_STRING_T {
                        length "0..255";
                    }
                    description "";
                } // END of addr6 definition.


            } // End of localAddr6-list

            list rsvpNexthop {
                key "nexthopPrefix";
                config false;
                description
                    "rsvpNexthop";
                leaf nexthopPrefix  {
                    type  cml_data_types:CML_STRING_T {
                        length "0..255";
                    }
                    description "";
                } // END of nexthopPrefix definition.


                leaf flags  {
                    type  cml_data_types:CML_UINT8_T;
                    description "";
                } // END of flags definition.


                leaf refcount  {
                    type  cml_data_types:CML_UINT32_T;
                    description "";
                } // END of refcount definition.


                container nexthop {
                    config false;
                    description
                        "nexthop";
                    leaf gatewayAddr  {
                        type  cml_data_types:CML_STRING_T {
                            length "0..255";
                        }
                        description "";
                    } // END of gatewayAddr definition.


                    leaf nextHopIfname  {
                        type  cml_data_types:CML_STRING_T {
                            length "0..255";
                        }
                        description "";
                    } // END of nextHopIfname definition.


                } // END of nexthop-container definition.
            } // End of rsvpNexthop-list

            list rsvpMappedRoute4 {
                key "dst";
                config false;
                description
                    "rsvpMappedRoute4";
                leaf sessionLspId  {
                    type  cml_data_types:CML_UINT16_T;
                    description "";
                } // END of sessionLspId definition.


                leaf dscpIn  {
                    type  cml_data_types:CML_STRING_T {
                        length "0..255";
                    }
                    description "";
                } // END of dscpIn definition.


                leaf prefixlen  {
                    type  cml_data_types:CML_UINT8_T;
                    description "";
                } // END of prefixlen definition.


                leaf family  {
                    type  cml_data_types:CML_UINT8_T;
                    description "";
                } // END of family definition.


                leaf trunkId  {
                    type  cml_data_types:CML_UINT16_T;
                    description "";
                } // END of trunkId definition.


                leaf dst  {
                    type  cml_data_types:CML_STRING_T {
                        length "0..255";
                    }
                    description "";
                } // END of dst definition.


            } // End of rsvpMappedRoute4-list

            list rsvpMappedRoute6 {
                key "dst";
                config false;
                description
                    "rsvpMappedRoute6";
                leaf sessionLspId  {
                    type  cml_data_types:CML_UINT16_T;
                    description "";
                } // END of sessionLspId definition.


                leaf dscpIn  {
                    type  cml_data_types:CML_STRING_T {
                        length "0..255";
                    }
                    description "";
                } // END of dscpIn definition.


                leaf prefixlen  {
                    type  cml_data_types:CML_UINT8_T;
                    description "";
                } // END of prefixlen definition.


                leaf family  {
                    type  cml_data_types:CML_UINT8_T;
                    description "";
                } // END of family definition.


                leaf trunkId  {
                    type  cml_data_types:CML_UINT16_T;
                    description "";
                } // END of trunkId definition.


                leaf dst  {
                    type  cml_data_types:CML_STRING_T {
                        length "0..255";
                    }
                    description "";
                } // END of dst definition.


            } // End of rsvpMappedRoute6-list
            container rsvpTableHolder {
                description
                    "rsvpTableHolder";
                leaf dummy  {
                    type  cml_data_types:CML_UINT16_T;
                    description "";
                } // END of dummy definition.


                leaf total  {
                    type  cml_data_types:CML_INT32_T;
                    config false;
                    description "";
                } // END of total definition.


                leaf up  {
                    type  cml_data_types:CML_INT32_T;
                    config false;
                    description "";
                } // END of up definition.


                leaf cIngress  {
                    type  cml_data_types:CML_INT32_T;
                    config false;
                    description "";
                } // END of cIngress definition.


                leaf cIngressUp  {
                    type  cml_data_types:CML_INT32_T;
                    config false;
                    description "";
                } // END of cIngressUp definition.


                leaf cTransit  {
                    type  cml_data_types:CML_INT32_T;
                    config false;
                    description "";
                } // END of cTransit definition.


                leaf cTransitUp  {
                    type  cml_data_types:CML_INT32_T;
                    config false;
                    description "";
                } // END of cTransitUp definition.


                leaf cEgress  {
                    type  cml_data_types:CML_INT32_T;
                    config false;
                    description "";
                } // END of cEgress definition.


                leaf cEgressUp  {
                    type  cml_data_types:CML_INT32_T;
                    config false;
                    description "";
                } // END of cEgressUp definition.



                list bypassTrunk {
                    if-feature feature_list:HAVE_MPLS_FRR;
                    key "bypassName";
                    description
                        "bypassTrunk";
                    leaf bypassName  {
                        type  cml_data_types:CML_STRING_T {
                            length "0..255";
                        }
                        description "";
                    } // END of bypassName definition.


                    leaf ingress  {
                        type  cml_data_types:CML_STRING_T {
                            length "0..255";
                        }
                        description "";
                    } // END of ingress definition.


                    leaf egress  {
                        type  cml_data_types:CML_STRING_T {
                            length "0..255";
                        }
                        description "";
                    } // END of egress definition.


                    leaf extTunnleId  {
                        type  cml_data_types:CML_STRING_T {
                            length "0..255";
                        }
                        description "";
                    } // END of extTunnleId definition.


                    leaf updateType  {
                        type  cml_data_types:CML_RSVP_UPDATE_TYPE_T;
                        default "make-before-break";
                        description "";
                    } // END of updateType definition.


                    leaf bypassBackupBwType  {
                        type  cml_data_types:CML_RSVP_BACKUP_BW_TYPE;
                        default "best-effort";
                        description "";
                    } // END of bypassBackupBwType definition.


                    container session {
                        description
                            "session";
                        leaf hopLimit  {
                            type  cml_data_types:CML_UINT16_T {
                                 range "1..255";
                            }
                            default "255";
                            description "";
                        } // END of hopLimit definition.


                        leaf traffic  {
                            type  cml_data_types:CML_RSVP_TRAFFIC_TYPE_T;
                            default "controlled-load";
                            description "";
                        } // END of traffic definition.


                        leaf retryCount  {
                            type  cml_data_types:CML_UINT16_T {
                                 range "1..65535";
                            }
                            description "";
                        } // END of retryCount definition.


                        leaf retryInterval  {
                            type  cml_data_types:CML_UINT16_T {
                                 range "1..600";
                            }
                            default "30";
                            description "";
                        } // END of retryInterval definition.


                        leaf recordConfig  {
                            type  cml_data_types:CML_RSVP_RECORD_T;
                            description "";
                        } // END of recordConfig definition.


                        leaf reuseRouteRec  {
                            type  cml_data_types:CML_BOOL_T;
                            description "";
                        } // END of reuseRouteRec definition.


                        leaf cspfRetryCount  {
                            if-feature feature_list:HAVE_CSPF;
                            type  cml_data_types:CML_UINT16_T {
                                 range "1..65535";
                            }
                            description "";
                        } // END of cspfRetryCount definition.


                        leaf cspfRetryInterval  {
                            if-feature feature_list:HAVE_CSPF;
                            type  cml_data_types:CML_UINT16_T {
                                 range "1..600";
                            }
                            default "30";
                            description "";
                        } // END of cspfRetryInterval definition.


                        container excludePathAddr {
                            description
                                "excludePathAddr";
                            leaf excludePathAddr  {
                                type  cml_data_types:CML_STRING_T {
                                    length "0..255";
                                }
                                description "";
                            } // END of excludePathAddr definition.


                            leaf excludePathType  {
                                type  cml_data_types:CML_RSVP_EXCLUDE_PATH_TYPE_T;
                                description "";
                            } // END of excludePathType definition.


                        } // END of excludePathAddr-container definition.
                        container psb {
                            description
                                "psb";
                            leaf path  {
                                type  cml_data_types:CML_STRING_T {
                                    length "0..255";
                                }
                                description "";
                            } // END of path definition.


                            leaf bandwidth  {
                                if-feature feature_list:HAVE_TE;
                                type  cml_data_types:CML_STRING_T {
                                    length "0..255";
                                }
                                description "";
                            } // END of bandwidth definition.


                            container sessionAttr {
                                description
                                    "sessionAttr";
                                leaf holdPriority  {
                                    type  cml_data_types:CML_UINT8_T {
                                         range "0..7";
                                    }
                                    default "0";
                                    description "";
                                } // END of holdPriority definition.


                                leaf setupPriority  {
                                    type  cml_data_types:CML_UINT8_T {
                                         range "0..7";
                                    }
                                    default "7";
                                    description "";
                                } // END of setupPriority definition.


                                leaf filterFlag  {
                                    type  cml_data_types:CML_RSVP_FILTER_TYPE_T;
                                    default "default";
                                    description "";
                                } // END of filterFlag definition.


                                leaf labelRecord  {
                                    type  cml_data_types:CML_BOOL_T;
                                    description "";
                                } // END of labelRecord definition.


                            } // END of sessionAttr-container definition.
                        } // END of psb-container definition.
                        container dsInfo {
                            if-feature feature_list:HAVE_DIFFSERV;
                            description
                                "dsInfo";
                            leaf llspClass  {
                                type  cml_data_types:CML_STRING_T {
                                    length "0..255";
                                }
                                description "";
                            } // END of llspClass definition.



                            list dscpExpMap {
                                key "expVal";
                                description
                                    "dscpExpMap";
                                leaf className  {
                                    type  cml_data_types:CML_STRING_T {
                                        length "0..255";
                                    }
                                    description "";
                                } // END of className definition.


                                leaf expVal  {
                                    type  cml_data_types:CML_INT32_T {
                                         range "0..7";
                                    }
                                    description "";
                                } // END of expVal definition.


                            } // End of dscpExpMap-list
                            container elspClass {
                                description
                                    "elspClass";
                                leaf elspSignal  {
                                    type  cml_data_types:CML_BOOL_T;
                                    description "";
                                } // END of elspSignal definition.


                                leaf elspSignalClass1  {
                                    type  cml_data_types:CML_STRING_T {
                                        length "0..255";
                                    }
                                    description "";
                                } // END of elspSignalClass1 definition.


                                leaf elspSignalClass2  {
                                    type  cml_data_types:CML_STRING_T {
                                        length "0..255";
                                    }
                                    description "";
                                } // END of elspSignalClass2 definition.


                                leaf elspSignalClass3  {
                                    type  cml_data_types:CML_STRING_T {
                                        length "0..255";
                                    }
                                    description "";
                                } // END of elspSignalClass3 definition.


                                leaf elspSignalClass4  {
                                    type  cml_data_types:CML_STRING_T {
                                        length "0..255";
                                    }
                                    description "";
                                } // END of elspSignalClass4 definition.


                                leaf elspSignalClass5  {
                                    type  cml_data_types:CML_STRING_T {
                                        length "0..255";
                                    }
                                    description "";
                                } // END of elspSignalClass5 definition.


                                leaf elspSignalClass6  {
                                    type  cml_data_types:CML_STRING_T {
                                        length "0..255";
                                    }
                                    description "";
                                } // END of elspSignalClass6 definition.


                                leaf elspSignalClass7  {
                                    type  cml_data_types:CML_STRING_T {
                                        length "0..255";
                                    }
                                    description "";
                                } // END of elspSignalClass7 definition.


                            } // END of elspClass-container definition.
                        } // END of dsInfo-container definition.
                    } // END of session-container definition.
                } // End of bypassTrunk-list

                list ingressTrunk {
                    key "trunkName";
                    description
                        "ingressTrunk";
                    leaf trunkName  {
                        type  cml_data_types:CML_STRING_T {
                            length "0..255";
                        }
                        description "";
                    } // END of trunkName definition.


                    leaf trunkFamily  {
                        type  cml_data_types:CML_RSVP_TRUNK_FAMILY_T;
                        mandatory true;
                        description "";
                    } // END of trunkFamily definition.


                    leaf ingress  {
                        type  cml_data_types:CML_IP_ADDR_T {
                            length "0..255";
                        }
                        description "";
                    } // END of ingress definition.


                    leaf egress  {
                        type  cml_data_types:CML_IP_ADDR_T {
                            length "0..255";
                        }
                        description "";
                    } // END of egress definition.


                    leaf extTunnleId  {
                        type  cml_data_types:CML_IP_ADDR_T {
                            length "0..255";
                        }
                        description "";
                    } // END of extTunnleId definition.


                    leaf switchingCapability  {
                        type  cml_data_types:CML_RSVP_CAPABILITY_TYPE_T;
                        default "psc-1";
                        description "";
                    } // END of switchingCapability definition.


                    leaf direction  {
                        type  cml_data_types:CML_RSVP_DIRECTION_TYPE_T;
                        default "unidirectional";
                        description "";
                    } // END of direction definition.


                    leaf ecmpgroup  {
                        if-feature feature_list:HAVE_MPLS_ECMP;
                        type  cml_data_types:CML_STRING_T {
                            length "0..255";
                        }
                        description "";
                    } // END of ecmpgroup definition.


                    leaf igpShortcut  {
                        type  cml_data_types:CML_RSVP_IGP_T;
                        description "";
                    } // END of igpShortcut definition.


                    leaf gpId  {
                        type  cml_data_types:CML_RSVP_GPID_TYPE_T;
                        description "";
                    } // END of gpId definition.


                    leaf updateType  {
                        type  cml_data_types:CML_RSVP_UPDATE_TYPE_T;
                        default "make-before-break";
                        description "";
                    } // END of updateType definition.


                    leaf absoluteMetric  {
                        type  cml_data_types:CML_UINT32_T {
                             range "1..65535";
                        }
                        description "";
                    } // END of absoluteMetric definition.


                    leaf relativeMetric  {
                        type  cml_data_types:CML_INT32_T {
                             range "-65535..0 | 1..65535";
                        }
                        description "";
                    } // END of relativeMetric definition.


                    leaf revertTimer  {
                        type  cml_data_types:CML_UINT32_T {
                             range "1..65535";
                        }
                        default "60";
                        description "";
                    } // END of revertTimer definition.


                    leaf reoptimize  {
                        type  cml_data_types:CML_BOOL_T;
                        description "";
                    } // END of reoptimize definition.



                    list mappedRouteListprefix4 {
                        key "mapRouteDstIpv4";
                        description
                            "Rsvp map-route operation";
                        leaf mapRouteDstIpv4  {
                            type  cml_data_types:CML_IPV4_PREFIX_T;
                            description "";
                        } // END of mapRouteDstIpv4 definition.


                    } // End of mappedRouteListprefix4-list

                    list mappedRouteList4 {
                        key "dstIpv4";
                        description
                            "mappedRouteList4";
                        leaf dstIpv4  {
                            type  cml_data_types:CML_IPV4_PREFIX_T;
                            description "";
                        } // END of dstIpv4 definition.


                        leaf-list className  {
                            if-feature feature_list:HAVE_DIFFSERV;
                            type  cml_data_types:CML_STRING_T {
                                length "0..255";
                            }
                            description "";
                        } // END of className definition.


                    } // End of mappedRouteList4-list

                    list mappedRouteList6 {
                        if-feature feature_list:HAVE_IPV6;
                        key "dstIpv6";
                        description
                            "mappedRouteList6";
                        leaf dstIpv6  {
                            type  cml_data_types:CML_IPV6_PREFIX_T;
                            description "";
                        } // END of dstIpv6 definition.


                        leaf-list className  {
                            if-feature feature_list:HAVE_DIFFSERV;
                            type  cml_data_types:CML_STRING_T {
                                length "0..255";
                            }
                            description "";
                        } // END of className definition.


                    } // End of mappedRouteList6-list
                    container gmplsLabelSet {
                        if-feature feature_list:HAVE_GMPLS;
                        description
                            "gmplsLabelSet";
                        leaf actionType  {
                            type  cml_data_types:CML_BOOL_T;
                            description "";
                        } // END of actionType definition.


                        leaf startLblRange  {
                            type  cml_data_types:CML_INT32_T {
                                 range "16..1048575";
                            }
                            description "";
                        } // END of startLblRange definition.


                        leaf endLblRange  {
                            type  cml_data_types:CML_INT32_T {
                                 range "16..1048575";
                            }
                            description "";
                        } // END of endLblRange definition.


                    } // END of gmplsLabelSet-container definition.
                    container session {
                        description
                            "session";
                        leaf frrProtection  {
                            if-feature feature_list:HAVE_MPLS_FRR;
                            type  cml_data_types:CML_RSVP_FRR_PROTECTION_T;
                            description "";
                        } // END of frrProtection definition.


                        leaf frrConfigNodeProtection  {
                            if-feature feature_list:HAVE_MPLS_FRR;
                            type  cml_data_types:CML_BOOL_T;
                            description "";
                        } // END of frrConfigNodeProtection definition.



                        list sessionList {
                            key "sessionType";
                            description
                                "sessionList";
                            leaf sessionType  {
                                type  cml_data_types:CML_RSVP_SESS_TYEP_T;
                                description "";
                            } // END of sessionType definition.


                            leaf cspf  {
                                if-feature feature_list:HAVE_CSPF;
                                type  cml_data_types:CML_RSVP_CSPF_STATUS_T;
                                description "";
                            } // END of cspf definition.


                            leaf hopLimit  {
                                type  cml_data_types:CML_UINT16_T {
                                     range "1..255";
                                }
                                default "255";
                                description "";
                            } // END of hopLimit definition.


                            leaf traffic  {
                                type  cml_data_types:CML_RSVP_TRAFFIC_TYPE_T;
                                default "controlled-load";
                                description "";
                            } // END of traffic definition.


                            leaf retryCount  {
                                type  cml_data_types:CML_UINT16_T {
                                     range "1..65535";
                                }
                                description "";
                            } // END of retryCount definition.


                            leaf retryInterval  {
                                type  cml_data_types:CML_UINT16_T {
                                     range "1..600";
                                }
                                default "30";
                                description "";
                            } // END of retryInterval definition.


                            leaf recordConfig  {
                                type  cml_data_types:CML_RSVP_RECORD_T;
                                description "";
                            } // END of recordConfig definition.


                            leaf affinityConfig  {
                                if-feature feature_list:HAVE_TE;
                                type  cml_data_types:CML_RSVP_AFFINITY_T;
                                description "";
                            } // END of affinityConfig definition.


                            leaf elspPreconfig  {
                                if-feature feature_list:HAVE_SWFWDR;
                                if-feature feature_list:HAVE_DIFFSERV;
                                type  cml_data_types:CML_BOOL_T;
                                description "";
                            } // END of elspPreconfig definition.


                            leaf localProtection  {
                                type  cml_data_types:CML_BOOL_T;
                                description "";
                            } // END of localProtection definition.


                            leaf reuseRouteRec  {
                                type  cml_data_types:CML_BOOL_T;
                                description "";
                            } // END of reuseRouteRec definition.


                            leaf cspfRetryCount  {
                                if-feature feature_list:HAVE_CSPF;
                                type  cml_data_types:CML_UINT16_T {
                                     range "1..65535";
                                }
                                description "";
                            } // END of cspfRetryCount definition.


                            leaf cspfRetryInterval  {
                                if-feature feature_list:HAVE_CSPF;
                                type  cml_data_types:CML_UINT16_T {
                                     range "1..600";
                                }
                                default "30";
                                description "";
                            } // END of cspfRetryInterval definition.



                            list adminGroup {
                                if-feature feature_list:HAVE_TE;
                                key "adminGrpName";
                                description
                                    "adminGroup";
                                leaf adminGrpName  {
                                    type  cml_data_types:CML_STRING_T {
                                        length "0..255";
                                    }
                                    description "";
                                } // END of adminGrpName definition.


                                leaf adminType  {
                                    type  cml_data_types:CML_RSVP_ADMIN_TYPE_T;
                                    description "";
                                } // END of adminType definition.


                            } // End of adminGroup-list
                            container psb {
                                description
                                    "psb";
                                leaf path  {
                                    type  cml_data_types:CML_STRING_T {
                                        length "0..255";
                                    }
                                    description "";
                                } // END of path definition.


                                leaf classTypeName  {
                                    if-feature feature_list:HAVE_DSTE;
                                    type  cml_data_types:CML_STRING_T {
                                        length "0..255";
                                    }
                                    description "";
                                } // END of classTypeName definition.


                                leaf bandwidth  {
                                    if-feature feature_list:HAVE_TE;
                                    type  cml_data_types:CML_STRING_T {
                                        length "0..255";
                                    }
                                    description "";
                                } // END of bandwidth definition.


                                container sessionAttr {
                                    description
                                        "sessionAttr";
                                    leaf setupPriority  {
                                        type  cml_data_types:CML_UINT8_T {
                                             range "0..7";
                                        }
                                        default "7";
                                        description "";
                                    } // END of setupPriority definition.


                                    leaf holdPriority  {
                                        type  cml_data_types:CML_UINT8_T {
                                             range "0..7";
                                        }
                                        default "0";
                                        description "";
                                    } // END of holdPriority definition.


                                    leaf filterFlag  {
                                        type  cml_data_types:CML_RSVP_FILTER_TYPE_T;
                                        default "default";
                                        description "";
                                    } // END of filterFlag definition.


                                    leaf labelRecord  {
                                        type  cml_data_types:CML_BOOL_T;
                                        description "";
                                    } // END of labelRecord definition.


                                } // END of sessionAttr-container definition.
                            } // END of psb-container definition.
                            container gmplsAttr {
                                if-feature feature_list:HAVE_GMPLS;
                                description
                                    "gmplsAttr";
                                leaf linkProtection  {
                                    type  cml_data_types:CML_RSVP_PROTECTION_TYPE_T;
                                    default "unprotected";
                                    description "";
                                } // END of linkProtection definition.


                                container explicitFwd {
                                    description
                                        "explicitFwd";
                                    leaf fwdLabelVal  {
                                        type  cml_data_types:CML_UINT32_T {
                                             range "16..1048575";
                                        }
                                        description "";
                                    } // END of fwdLabelVal definition.


                                    leaf expDirection  {
                                        type  cml_data_types:CML_RSVP_EXPLICIT_FWD_DIR_T;
                                        description "";
                                    } // END of expDirection definition.


                                } // END of explicitFwd-container definition.
                                container explicitFRev {
                                    description
                                        "explicitFRev";
                                    leaf revLabelVal  {
                                        type  cml_data_types:CML_UINT32_T {
                                             range "16..1048575";
                                        }
                                        description "";
                                    } // END of revLabelVal definition.


                                    leaf expDirection  {
                                        type  cml_data_types:CML_RSVP_EXPLICIT_REV_DIR_T;
                                        description "";
                                    } // END of expDirection definition.


                                } // END of explicitFRev-container definition.
                            } // END of gmplsAttr-container definition.
                            container dsInfo {
                                if-feature feature_list:HAVE_DIFFSERV;
                                description
                                    "dsInfo";
                                leaf llspClass  {
                                    if-feature feature_list:NOT_HAVE_CUSTOM2_QOS;
                                    type  cml_data_types:CML_STRING_T {
                                        length "0..255";
                                    }
                                    description "";
                                } // END of llspClass definition.



                                list dscpExpMap {
                                    key "expVal";
                                    description
                                        "dscpExpMap";
                                    leaf className  {
                                        type  cml_data_types:CML_STRING_T {
                                            length "0..255";
                                        }
                                        description "";
                                    } // END of className definition.


                                    leaf expVal  {
                                        type  cml_data_types:CML_INT32_T {
                                             range "0..7";
                                        }
                                        description "";
                                    } // END of expVal definition.


                                } // End of dscpExpMap-list
                                container elspClass {
                                    description
                                        "elspClass";
                                    leaf elspSignal  {
                                        type  cml_data_types:CML_BOOL_T;
                                        description "";
                                    } // END of elspSignal definition.


                                    leaf elspSignalClass1  {
                                        type  cml_data_types:CML_STRING_T {
                                            length "0..255";
                                        }
                                        description "";
                                    } // END of elspSignalClass1 definition.


                                    leaf elspSignalClass2  {
                                        type  cml_data_types:CML_STRING_T {
                                            length "0..255";
                                        }
                                        description "";
                                    } // END of elspSignalClass2 definition.


                                    leaf elspSignalClass3  {
                                        type  cml_data_types:CML_STRING_T {
                                            length "0..255";
                                        }
                                        description "";
                                    } // END of elspSignalClass3 definition.


                                    leaf elspSignalClass4  {
                                        type  cml_data_types:CML_STRING_T {
                                            length "0..255";
                                        }
                                        description "";
                                    } // END of elspSignalClass4 definition.


                                    leaf elspSignalClass5  {
                                        type  cml_data_types:CML_STRING_T {
                                            length "0..255";
                                        }
                                        description "";
                                    } // END of elspSignalClass5 definition.


                                    leaf elspSignalClass6  {
                                        type  cml_data_types:CML_STRING_T {
                                            length "0..255";
                                        }
                                        description "";
                                    } // END of elspSignalClass6 definition.


                                    leaf elspSignalClass7  {
                                        type  cml_data_types:CML_STRING_T {
                                            length "0..255";
                                        }
                                        description "";
                                    } // END of elspSignalClass7 definition.


                                } // END of elspClass-container definition.
                            } // END of dsInfo-container definition.
                        } // End of sessionList-list

                        list frrAdminGroup {
                            if-feature feature_list:HAVE_MPLS_FRR;
                            key "frrAdminGroupName";
                            description
                                "frrAdminGroup";
                            leaf frrAdminGroupName  {
                                type  cml_data_types:CML_STRING_T {
                                    length "0..255";
                                }
                                description "";
                            } // END of frrAdminGroupName definition.


                            leaf frrAttributeType  {
                                type  cml_data_types:CML_RSVP_FRR_ADMIN_TYPE_T;
                                description "";
                            } // END of frrAttributeType definition.


                        } // End of frrAdminGroup-list
                        container frr {
                            if-feature feature_list:HAVE_MPLS_FRR;
                            description
                                "frr";
                            leaf frrSetupPriority  {
                                type  cml_data_types:CML_UINT32_T {
                                     range "0..7";
                                }
                                default "7";
                                description "";
                            } // END of frrSetupPriority definition.


                            leaf frrHoldPriority  {
                                type  cml_data_types:CML_UINT32_T {
                                     range "0..7";
                                }
                                default "0";
                                description "";
                            } // END of frrHoldPriority definition.


                            leaf frrHopLimit  {
                                type  cml_data_types:CML_UINT32_T {
                                     range "1..255";
                                }
                                default "64";
                                description "";
                            } // END of frrHopLimit definition.


                            leaf frrBandwidth  {
                                type  cml_data_types:CML_STRING_T {
                                    length "0..255";
                                }
                                description "";
                            } // END of frrBandwidth definition.


                        } // END of frr-container definition.
                    } // END of session-container definition.
                } // End of ingressTrunk-list

                list tTable4 {
                    key "trunkName";
                    config false;
                    description
                        "tTable4";
                    leaf trunkName  {
                        type  cml_data_types:CML_STRING_T {
                            length "0..255";
                        }
                        description "";
                    } // END of trunkName definition.


                    uses rsvpTrunk;
                } // End of tTable4-list

                list tTable6 {
                    key "trunkName";
                    config false;
                    description
                        "tTable6";
                    leaf trunkName  {
                        type  cml_data_types:CML_STRING_T {
                            length "0..255";
                        }
                        description "";
                    } // END of trunkName definition.


                    uses rsvpTrunk;
                } // End of tTable6-list
            } // END of rsvpTableHolder-container definition.
        } // END of rsvpInstance-container definition.
    } // END of rsvpMaster-container definition.
    } // END of rsvpMaster-container definition.


}
