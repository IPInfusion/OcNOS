/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-if-ethernet.yang
*
*/

module ipi-if-ethernet {

    namespace   "http://www.ipinfusion.com/yang/ocnos/ipi-if-ethernet";

    prefix "ipi-if-ethernet";

    import ietf-yang-types {
        prefix yang;
    }

    import cml-data-types {
        prefix cml-data-types;
    }

    import ipi-if-types {
        prefix ipi-if-types;
    }

    import ipi-interface {
        prefix ipi-interface;
    }

    import feature-list {
        prefix feature-list;
    }

    organization
        "IP Infusion Inc.";

    contact
        "Address: 3965 Freedom Circle, Suite 200, Santa Clara, CA 95054
         Phone: +1 408-400-1900
         E-mail: support@ipinfusion.com
         Web: http://www.ipinfusion.com/";

    description
        "Model for managing Ethernet interfaces -- augments the OpenConfig model for interface configuration and state.";


    revision "2018-06-21" {
        description " Initial Version.";
        reference " Openconfig Yang model : https://github.com/openconfig/public/blob/master/release/models/interfaces/openconfig-if-ethernet.yang.";
    }

    grouping ethernet-interface-config {
        description
            "Configuration items for Ethernet interfaces";
        leaf duplex-mode  {
            type  ipi-if-types:IF_DUPLEX_T;
            description "Use this attribute to set the duplex mode for each interface
           When auto-negotiate is TRUE, this optionally sets the
           duplex mode that will be advertised to the peer.  If
           unspecified, the interface should negotiate the duplex mode
           directly (typically full-duplex).  When auto-negotiate is
           FALSE, this sets the duplex mode on the interface directly.
        ";
        } // END of duplex-mode definition.

        leaf mac-address  {
            if-feature feature-list:NOT_HAVE_DUNE;
            type  cml-data-types:CML_MAC_ADDR_T {
                length "1..20";
            }
            description "Use this attribute to set the mac address for an interface.
            If not specified, the corresponding operational state leaf is
            expected to show the system-assigned MAC address.";
        } // END of mac-address definition.

        leaf port-speed  {
            type  ipi-if-types:IF_INTERFACE_SPEED_T;
            description "When auto-negotiate is TRUE, this optionally sets the
            port-speed mode that will be advertised to the peer for
            negotiation.  If unspecified, it is expected that the
            interface will select the highest speed available based on
            negotiation.  When auto-negotiate is set to FALSE, sets the
            link speed to a fixed value -- supported values are defined
            by ETHERNET_SPEED identities.
        ";
        } // END of port-speed definition.

    } // END of ethernet-interface-config definition.
    grouping flow-control-config {
        description
            "Grouping for Flow control Configuration data for ethernet interfaces";
        leaf enable-rcv  {
            type  ipi-if-types:IF_FLOWCTRL_T;
            default "off";
            description "This attribute is used to show flow control on receive";
        } // END of enable-rcv definition.

        leaf enable-snd  {
            type  ipi-if-types:IF_FLOWCTRL_T;
            default "off";
            description "This attribute is used to show flow control on send";
        } // END of enable-snd definition.

    } // END of flow-control-config definition.
    grouping flow-control-state {
        description
            "Grouping for Flow control State variables for Ethernet interfaces";
        leaf rcv-oper-status  {
            type  ipi-if-types:IF_FLOWCTRL_T;
            config false;
            description "This attribute is used to show Operations status of Flow control on receive";
        } // END of rcv-oper-status definition.

        leaf snd-oper-status  {
            type  ipi-if-types:IF_FLOWCTRL_T;
            config false;
            description "This attribute is used to show Operations status of Flow control on send";
        } // END of snd-oper-status definition.

    } // END of flow-control-state definition.
    grouping ethernet-in-frames-size-dist {
        description
            "Grouping for defining the size distribution of the frames received";
        container in-distribution {
            config false;
            description
                "In distribution interface counters";
            leaf in-frames-64-octets  {
                if-feature feature-list:HAVE_BROADCOM;
                if-feature feature-list:HAVE_HAL;
                if-feature feature-list:NOT_HAVE_SWFWDR;
                type  yang:counter64;
                description "Number of packets (including bad packets) received that
            were 64 bytes in length (excluding framing bits but including FCS bytes).
            ";
            } // END of in-frames-64-octets definition.

            leaf in-frames-65-127-octets  {
                if-feature feature-list:HAVE_BROADCOM;
                if-feature feature-list:HAVE_HAL;
                if-feature feature-list:NOT_HAVE_SWFWDR;
                type  yang:counter64;
                description "Number of good and bad packets received that were
            between 65 and 127 bytes in length (excluding framing bits but including FCS bytes).
          ";
            } // END of in-frames-65-127-octets definition.

            leaf in-frames-128-255-octets  {
                if-feature feature-list:HAVE_BROADCOM;
                if-feature feature-list:HAVE_HAL;
                if-feature feature-list:NOT_HAVE_SWFWDR;
                type  yang:counter64;
                description "Number of good and bad packets received that were
            between 128 and 255 bytes in length inclusive
            (excluding framing bits but including FCS bytes).
          ";
            } // END of in-frames-128-255-octets definition.

            leaf in-frames-256-511-octets  {
                if-feature feature-list:HAVE_BROADCOM;
                if-feature feature-list:HAVE_HAL;
                if-feature feature-list:NOT_HAVE_SWFWDR;
                type  yang:counter64;
                description "Number of good and bad packets received that were
            between 256 and 511 bytes in length inclusive
            (excluding framing bits but including FCS bytes).
          ";
            } // END of in-frames-256-511-octets definition.

            leaf in-frames-512-1023-octets  {
                if-feature feature-list:HAVE_BROADCOM;
                if-feature feature-list:HAVE_HAL;
                if-feature feature-list:NOT_HAVE_SWFWDR;
                type  yang:counter64;
                description "Number of good and bad packets received that were
            between 512 and 1023 bytes in length inclusive
            (excluding framing bits but including FCS bytes).
          ";
            } // END of in-frames-512-1023-octets definition.

            leaf in-frames-1024-1518-octets  {
                if-feature feature-list:HAVE_BROADCOM;
                if-feature feature-list:HAVE_HAL;
                if-feature feature-list:NOT_HAVE_SWFWDR;
                type  yang:counter64;
                description "Number of good and bad packets received that were
            between 1024 and 1518 bytes in length inclusive
            (excluding framing bits but including FCS bytes).
          ";
            } // END of in-frames-1024-1518-octets definition.

            leaf in-frames-1519-2047-octets  {
                if-feature feature-list:HAVE_BROADCOM;
                if-feature feature-list:HAVE_HAL;
                if-feature feature-list:NOT_HAVE_SWFWDR;
                type  yang:counter64;
                description "Number of good and bad packets received that were
            between 1519 and 2047 bytes in length inclusive
           (excluding framing bits but including FCS bytes).
          ";
            } // END of in-frames-1519-2047-octets definition.

            leaf in-frames-2048-4095-octets  {
                if-feature feature-list:HAVE_BROADCOM;
                if-feature feature-list:HAVE_HAL;
                if-feature feature-list:NOT_HAVE_SWFWDR;
                type  yang:counter64;
                description "Number of good and bad packets received that were
            between 2048 and 4095 bytes in length inclusive
            (excluding framing bits but including FCS bytes).
          ";
            } // END of in-frames-2048-4095-octets definition.

            leaf in-frames-4096-9216-octets  {
                if-feature feature-list:HAVE_BROADCOM;
                if-feature feature-list:HAVE_HAL;
                if-feature feature-list:NOT_HAVE_SWFWDR;
                type  yang:counter64;
                description "Number of good and bad packets received that were
            between 4096 and 9216 bytes in length inclusive
            (excluding framing bits but including FCS bytes).
          ";
            } // END of in-frames-4096-9216-octets definition.

        } // END of in-distribution-container definition.
    } // END of ethernet-in-frames-size-dist definition.
    grouping ethernet-out-frames-size-dist {
        description
            "Grouping for defining the size distribution of the frames sent";
        container out-distribution {
            config false;
            description
                "Out distribution interface counters";
            leaf out-frames-64-octets  {
                if-feature feature-list:HAVE_BROADCOM;
                if-feature feature-list:HAVE_HAL;
                if-feature feature-list:NOT_HAVE_SWFWDR;
                type  yang:counter64;
                description "Number of packets (including bad packets) sent that
            were 64 bytes in length (excluding framing bits but including FCS bytes).
            ";
            } // END of out-frames-64-octets definition.

            leaf out-frames-65-127-octets  {
                if-feature feature-list:HAVE_BROADCOM;
                if-feature feature-list:HAVE_HAL;
                if-feature feature-list:NOT_HAVE_SWFWDR;
                type  yang:counter64;
                description "Number of good and bad packets sent that were
            between 65 and 127 bytes in length (excluding framing bits but including FCS bytes).
          ";
            } // END of out-frames-65-127-octets definition.

            leaf out-frames-128-255-octets  {
                if-feature feature-list:HAVE_BROADCOM;
                if-feature feature-list:HAVE_HAL;
                if-feature feature-list:NOT_HAVE_SWFWDR;
                type  yang:counter64;
                description "Number of good and bad packets sent that were
            between 128 and 255 bytes in length inclusive
            (excluding framing bits but including FCS bytes).
          ";
            } // END of out-frames-128-255-octets definition.

            leaf out-frames-256-511-octets  {
                if-feature feature-list:HAVE_BROADCOM;
                if-feature feature-list:HAVE_HAL;
                if-feature feature-list:NOT_HAVE_SWFWDR;
                type  yang:counter64;
                description "Number of good and bad packets sent that were
            between 256 and 511 bytes in length inclusive
            (excluding framing bits but including FCS bytes).
          ";
            } // END of out-frames-256-511-octets definition.

            leaf out-frames-512-1023-octets  {
                if-feature feature-list:HAVE_BROADCOM;
                if-feature feature-list:HAVE_HAL;
                if-feature feature-list:NOT_HAVE_SWFWDR;
                type  yang:counter64;
                description "Number of good and bad packets sent that were
            between 512 and 1023 bytes in length inclusive
            (excluding framing bits but including FCS bytes).
          ";
            } // END of out-frames-512-1023-octets definition.

            leaf out-frames-1024-1518-octets  {
                if-feature feature-list:HAVE_BROADCOM;
                if-feature feature-list:HAVE_HAL;
                if-feature feature-list:NOT_HAVE_SWFWDR;
                type  yang:counter64;
                description "Number of good and bad packets sent that were
            between 1024 and 1518 bytes in length inclusive
            (excluding framing bits but including FCS bytes).
          ";
            } // END of out-frames-1024-1518-octets definition.

            leaf out-frames-1519-2047-octets  {
                if-feature feature-list:HAVE_BROADCOM;
                if-feature feature-list:HAVE_HAL;
                if-feature feature-list:NOT_HAVE_SWFWDR;
                type  yang:counter64;
                description "Number of good and bad packets sent that were
            between 1519 and 2047 bytes in length inclusive
           (excluding framing bits but including FCS bytes).
          ";
            } // END of out-frames-1519-2047-octets definition.

            leaf out-frames-2048-4095-octets  {
                if-feature feature-list:HAVE_BROADCOM;
                if-feature feature-list:HAVE_HAL;
                if-feature feature-list:NOT_HAVE_SWFWDR;
                type  yang:counter64;
                description "Number of good and bad packets sent that were
            between 2048 and 4095 bytes in length inclusive
            (excluding framing bits but including FCS bytes).
          ";
            } // END of out-frames-2048-4095-octets definition.

            leaf out-frames-4096-9216-octets  {
                if-feature feature-list:HAVE_BROADCOM;
                if-feature feature-list:HAVE_HAL;
                if-feature feature-list:NOT_HAVE_SWFWDR;
                type  yang:counter64;
                description "Number of good and bad packets sent that were
            between 4096 and 9216 bytes in length inclusive
            (excluding framing bits but including FCS bytes).
          ";
            } // END of out-frames-4096-9216-octets definition.

        } // END of out-distribution-container definition.
    } // END of ethernet-out-frames-size-dist definition.
    grouping ethernet-interface-state-counters {
        description
            "Ethernet-specific counters and statistics";
        leaf in-mac-control-frames  {
            if-feature feature-list:HAVE_BROADCOM;
            if-feature feature-list:HAVE_HAL;
            if-feature feature-list:NOT_HAVE_SWFWDR;
            type  yang:counter64;
            config false;
            description "MAC layer control frames received on the interface";
        } // END of in-mac-control-frames definition.

        leaf in-mac-pause-frames  {
            type  yang:counter64;
            config false;
            description "MAC layer PAUSE frames received on the interface";
        } // END of in-mac-pause-frames definition.

        leaf in-undersize-frames  {
            if-feature feature-list:HAVE_BROADCOM;
            if-feature feature-list:HAVE_HAL;
            if-feature feature-list:NOT_HAVE_SWFWDR;
            type  yang:counter64;
            config false;
            description "The total number of frames received that were
          less than 64 octets long (excluding framing bits,
          but including FCS octets) and were otherwisewell formed.
        ";
        } // END of in-undersize-frames definition.

        leaf in-oversize-frames  {
            if-feature feature-list:HAVE_BROADCOM;
            if-feature feature-list:HAVE_HAL;
            if-feature feature-list:NOT_HAVE_SWFWDR;
            type  yang:counter64;
            config false;
            description "The total number of frames received that were
          longer than 1518 octets (excluding framing bits,
          but including FCS octets) and were otherwise well formed.
        ";
        } // END of in-oversize-frames definition.

        leaf in-fragment-frames  {
            if-feature feature-list:HAVE_BROADCOM;
            if-feature feature-list:HAVE_HAL;
            if-feature feature-list:NOT_HAVE_SWFWDR;
            type  yang:counter64;
            config false;
            description "The total number of frames received that were less than
          64 octets in length (excluding framing bits but including
          FCS octets) and had either a bad Frame Check Sequence
          (FCS) with an integral number of octets (FCS Error) or a
          bad FCS with a non-integral number of octets (Alignment Error).
        ";
        } // END of in-fragment-frames definition.

        leaf in-jabber-frames  {
            if-feature feature-list:HAVE_BROADCOM;
            if-feature feature-list:HAVE_HAL;
            if-feature feature-list:NOT_HAVE_SWFWDR;
            type  yang:counter64;
            config false;
            description "Number of jabber frames received on the
          interface.  Jabber frames are typically defined as oversize
          frames which also have a bad CRC.  Implementations may use
          slightly different definitions of what constitutes a jabber
          frame.  Often indicative of a NIC hardware problem.
        ";
        } // END of in-jabber-frames definition.

        leaf in-crc-errors  {
            if-feature feature-list:HAVE_BROADCOM;
            if-feature feature-list:HAVE_HAL;
            if-feature feature-list:NOT_HAVE_SWFWDR;
            type  yang:counter64;
            config false;
            description "The total number of frames received that
          had a length (excluding framing bits, but including FCS octets) of between 64 and 1518
          octets, inclusive, but had either a bad Frame Check Sequence (FCS) with an integral
          number of octets (FCS Error) or a bad FCS with a non-integral number of octets (Alignment Error)
        ";
        } // END of in-crc-errors definition.

        leaf out-mac-control-frames  {
            if-feature feature-list:HAVE_BROADCOM;
            if-feature feature-list:HAVE_HAL;
            if-feature feature-list:NOT_HAVE_SWFWDR;
            type  yang:counter64;
            config false;
            description "MAC layer control frames sent on the interface";
        } // END of out-mac-control-frames definition.

        leaf out-mac-pause-frames  {
            type  yang:counter64;
            config false;
            description "MAC layer PAUSE frames sent on the interface";
        } // END of out-mac-pause-frames definition.

    } // END of ethernet-interface-state-counters definition.
    grouping ethernet-interface-state {
        description
            "Grouping for defining Ethernet-specific operational state";
        leaf hw-mac-address  {
            type  cml-data-types:CML_MAC_ADDR_T;
            config false;
            description "Represenets the 'burned-in',  or system-assigned, MAC
          address for the Ethernet interface.
        ";
        } // END of hw-mac-address definition.

        leaf negotiated-duplex-mode  {
            type  ipi-if-types:IF_DUPLEX_T;
            config false;
            description "When auto-negotiate is set to TRUE, and the interface has
          completed auto-negotiation with the remote peer, this value
          shows the duplex mode that has been negotiated.
        ";
        } // END of negotiated-duplex-mode definition.

        leaf negotiated-port-speed  {
            type  ipi-if-types:IF_INTERFACE_SPEED_T;
            config false;
            description "When auto-negotiate is set to TRUE, and the interface has
          completed auto-negotiation with the remote peer, this value
          shows the speed that has been negotiated.
        ";
        } // END of negotiated-port-speed definition.

        container counters {
            config false;
            description
                "Ethernet interface counters";
            uses ethernet-interface-state-counters;
            uses ethernet-in-frames-size-dist;
            uses ethernet-out-frames-size-dist;
        } // END of counters-container definition.
    } // END of ethernet-interface-state definition.

    grouping  ethernet-grouping {
    description
        "Top-level container for ethernet configuration";
    container ethernet {
        description
            "Top-level container for ethernet configuration";
        container config {
            description
                "Configuration data for ethernet interfaces";
            uses ethernet-interface-config;
        } // END of config-container definition.
        container state {
            config false;
            description
                "State variables for Ethernet interfaces";
            uses ethernet-interface-config;
            uses ethernet-interface-state;
        } // END of state-container definition.
        container flow-control {
            description
                "Flow control container for ethernet configuration";
            container config {
                description
                    "Flow control Configuration data for ethernet interfaces";
                uses flow-control-config;
            } // END of config-container definition.
            container state {
                config false;
                description
                    "Flow control State variables for Ethernet interfaces";
                uses flow-control-config;
                uses flow-control-state;
            } // END of state-container definition.
        } // END of flow-control-container definition.
    } // END of ethernet-container definition.
    } // END of ethernet-grouping definition.

    augment /ipi-interface:interfaces/ipi-interface:interface {
        description
            "Top-level container for ethernet configuration";
        uses ethernet-grouping;
    }


}
