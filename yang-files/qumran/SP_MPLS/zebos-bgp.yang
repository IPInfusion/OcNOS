/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-bgp.yang
*
*/

submodule zebos-bgp {

    belongs-to  zebos { prefix zebos; }

    import cml_data_types {
        prefix cml_data_types;
    }

    import ietf-inet-types {
        prefix inet;
    }

    import feature_list {
        prefix feature_list;
    }

    organization
        "IP Infusion Inc.";

    contact
        "Address: 3965 Freedom Circle, Suite 200, Santa Clara, CA 95054
         Phone: +1 408-400-1900
         E-mail: support@ipinfusion.com
         Web: http://www.ipinfusion.com/";

    description
        "";


    revision "2018-06-21" {
        description " Initial Version.";
        reference "";
    }



    typedef  CML_BGP_MD5_T {
        type enumeration {
            enum 0 {
                value 1;
                description "Unencrypted password (key)";
            }
        }
        description "";
        reference "";
    }

    grouping bgp-grouping {
    description
        "bgp";
        list bgp {
            key "bgpAs";
            description
                "bgp";
            leaf bgpAs  {
                type  cml_data_types:CML_UINT32_T {
                     range "1..4294967295";
                }
                description "AS number";
            } // END of bgpAs definition.



            list view {
                key "view";
                description
                    "view";
                leaf view  {
                    type  cml_data_types:CML_STRING_T {
                        length "0..255";
                    }
                    description "view name";
                } // END of view definition.


            } // End of view-list
            container bgpStats {
                config false;
                description
                    "This describes bgp Statistics";
                leaf bgpNeighborSntRcvMsgs  {
                    type  cml_data_types:CML_STRING_T {
                        length "0..255";
                    }
                    description "Neighbor aggregated statistics sent/recived messages";
                } // END of bgpNeighborSntRcvMsgs definition.


                leaf bgpNeighborSntRcvBytes  {
                    type  cml_data_types:CML_STRING_T {
                        length "0..255";
                    }
                    description "Neighbor aggregated statistics sent/recived bytes";
                } // END of bgpNeighborSntRcvBytes definition.


                leaf bgpNeighborSntRcvOpens  {
                    type  cml_data_types:CML_STRING_T {
                        length "0..255";
                    }
                    description "Neighbor aggregated statistics sent/recived opens";
                } // END of bgpNeighborSntRcvOpens definition.


                leaf bgpNeighborSntRcvUpdates  {
                    type  cml_data_types:CML_STRING_T {
                        length "0..255";
                    }
                    description "Neighbor aggregated statistics sent/recived Updates";
                } // END of bgpNeighborSntRcvUpdates definition.


                leaf bgpNeighborSntRcvKeepalive  {
                    type  cml_data_types:CML_STRING_T {
                        length "0..255";
                    }
                    description "Neighbor aggregated statistics sent/recived keepalives";
                } // END of bgpNeighborSntRcvKeepalive definition.


                leaf bgpNeighborSntRcvNotif  {
                    type  cml_data_types:CML_STRING_T {
                        length "0..255";
                    }
                    description "Neighbor aggregated statistics sent/recived Notifications";
                } // END of bgpNeighborSntRcvNotif definition.


                leaf bgpNeighborSntRcvRoutRf  {
                    type  cml_data_types:CML_STRING_T {
                        length "0..255";
                    }
                    description "Neighbor aggregated statistics sent/recived route-refresh";
                } // END of bgpNeighborSntRcvRoutRf definition.


                leaf bgpNeighborSntRcvCap  {
                    type  cml_data_types:CML_STRING_T {
                        length "0..255";
                    }
                    description "Neighbor aggregated statistics sent/recived Capabilities";
                } // END of bgpNeighborSntRcvCap definition.


                leaf bgpActiveOpen  {
                    type  cml_data_types:CML_UINT16_T;
                    description "Active Open attempts";
                } // END of bgpActiveOpen definition.


                leaf bgpPassiveOpen  {
                    type  cml_data_types:CML_UINT16_T;
                    description "Passive Open attempts ";
                } // END of bgpPassiveOpen definition.


                leaf bgpIoOpenLoops  {
                    type  cml_data_types:CML_UINT16_T;
                    description "BGP I/O Open loops ";
                } // END of bgpIoOpenLoops definition.


                leaf bgpIoOpenCalls  {
                    type  cml_data_types:CML_UINT16_T;
                    description "BGP I/O Open calls";
                } // END of bgpIoOpenCalls definition.


                leaf bgpOpenIoRcvCalls  {
                    type  cml_data_types:CML_UINT16_T;
                    description "BGP I/O Open recv calls";
                } // END of bgpOpenIoRcvCalls definition.


                leaf bgpIoSendCalls  {
                    type  cml_data_types:CML_UINT16_T;
                    description "BGP I/O Send calls";
                } // END of bgpIoSendCalls definition.


                leaf bgpIoRecvCalls  {
                    type  cml_data_types:CML_UINT16_T;
                    description "BGP I/O Recv calls";
                } // END of bgpIoRecvCalls definition.


                leaf bgpIoWriteCalls  {
                    type  cml_data_types:CML_UINT16_T;
                    description "BGP I/O Write calls";
                } // END of bgpIoWriteCalls definition.


                leaf bgpIoWriteLoops  {
                    type  cml_data_types:CML_UINT16_T;
                    description "BGP I/O Write loops";
                } // END of bgpIoWriteLoops definition.


                leaf bgpIoWrloopYield  {
                    type  cml_data_types:CML_UINT16_T;
                    description "BGP I/O Write loop yields";
                } // END of bgpIoWrloopYield definition.


                leaf bgpIoReadloopCall  {
                    type  cml_data_types:CML_UINT16_T;
                    description "BGP I/O Read calls";
                } // END of bgpIoReadloopCall definition.


                leaf bgpIoReadloops  {
                    type  cml_data_types:CML_UINT16_T;
                    description "BGP I/O Read loops";
                } // END of bgpIoReadloops definition.


                leaf bgpIoReadloopYield  {
                    type  cml_data_types:CML_UINT16_T;
                    description "BGP I/O Read loop yields";
                } // END of bgpIoReadloopYield definition.


                leaf bgpIoProcNlriYld  {
                    type  cml_data_types:CML_UINT16_T;
                    description "BGP I/O process nlri yields";
                } // END of bgpIoProcNlriYld definition.


                leaf bgpIoProcWithdrawYld  {
                    type  cml_data_types:CML_UINT16_T;
                    description "BGP I/O process withdraw yields";
                } // END of bgpIoProcWithdrawYld definition.


                leaf bgpReadTimeExceed  {
                    type  cml_data_types:CML_UINT16_T;
                    description "BGP Read time exceeded";
                } // END of bgpReadTimeExceed definition.


                leaf bgpUpdateSndPending  {
                    type  cml_data_types:CML_UINT16_T;
                    description "BGP Update send pending";
                } // END of bgpUpdateSndPending definition.


                leaf bgpUpdateBufferNA  {
                    type  cml_data_types:CML_UINT16_T;
                    description "BGP Update buffer not available";
                } // END of bgpUpdateBufferNA definition.


                leaf bgpUpdateWalkSuspend  {
                    type  cml_data_types:CML_UINT16_T;
                    description "BGP Update walk suspended";
                } // END of bgpUpdateWalkSuspend definition.


                leaf bgpYldInUpdate  {
                    type  cml_data_types:CML_UINT16_T;
                    description "BGP Yielded in updates";
                } // END of bgpYldInUpdate definition.


                leaf bgpYldInPack  {
                    type  cml_data_types:CML_UINT16_T;
                    description "BGP Yielded in packing";
                } // END of bgpYldInPack definition.


                leaf bgpNoSendPeerBuf  {
                    type  cml_data_types:CML_UINT16_T;
                    description "BGP No sendbuf for peer";
                } // END of bgpNoSendPeerBuf definition.


                leaf bgpNoWdrwPeerBuf  {
                    type  cml_data_types:CML_UINT16_T;
                    description "BGP No withdraw buf for peer";
                } // END of bgpNoWdrwPeerBuf definition.


                leaf bgpYldInUpPeerLoop  {
                    type  cml_data_types:CML_UINT16_T;
                    description "BGP Yields in update peer loop";
                } // END of bgpYldInUpPeerLoop definition.


                leaf bgpNoUpPenRNobuf  {
                    type  cml_data_types:CML_UINT16_T;
                    description "No updates pending or no buffers";
                } // END of bgpNoUpPenRNobuf definition.


                leaf bgpNoDataToWr  {
                    type  cml_data_types:CML_UINT16_T;
                    description "No data to write";
                } // END of bgpNoDataToWr definition.


                leaf bgpMsgQRcvErr  {
                    type  cml_data_types:CML_UINT16_T;
                    description "Msg queue recv errors";
                } // END of bgpMsgQRcvErr definition.


                leaf bgpSocCreateAccClose  {
                    type  cml_data_types:CML_STRING_T {
                        length "0..255";
                    }
                    description "Sockets create/accept/close";
                } // END of bgpSocCreateAccClose definition.


                leaf bgpSocCreateRtrOrFail  {
                    type  cml_data_types:CML_STRING_T {
                        length "0..255";
                    }
                    description "Sockets create retries/failures";
                } // END of bgpSocCreateRtrOrFail definition.


                leaf bgpSocFdCloseSess  {
                    type  cml_data_types:CML_UINT32_T;
                    description "Socket fd-close session";
                } // END of bgpSocFdCloseSess definition.


                leaf bgpMemPoolAdvCnt  {
                    type  cml_data_types:CML_UINT32_T;
                    description "MemPool count- Advertise";
                } // END of bgpMemPoolAdvCnt definition.


                leaf bgpMemPoolAdvTime  {
                    type  cml_data_types:CML_STRING_T {
                        length "0..255";
                    }
                    description "MemPool time in microsec - Advertise";
                } // END of bgpMemPoolAdvTime definition.


                leaf bgpMemPoolAdvSlotSect  {
                    type  cml_data_types:CML_STRING_T {
                        length "0..255";
                    }
                    description "MemPool slot sector count - Advertise";
                } // END of bgpMemPoolAdvSlotSect definition.


                leaf bgpMemPoolAdvTotalCnt  {
                    type  cml_data_types:CML_UINT32_T;
                    description "MemPool total count - Advertise";
                } // END of bgpMemPoolAdvTotalCnt definition.


                leaf bgpMemPoolAdvTotalBlkSize  {
                    type  cml_data_types:CML_UINT32_T;
                    description "MemPool Total block size - Advertise";
                } // END of bgpMemPoolAdvTotalBlkSize definition.


                leaf bgpMemPoolAdvBlkSize  {
                    type  cml_data_types:CML_UINT32_T;
                    description "MemPool Adjusted block size - Advertise";
                } // END of bgpMemPoolAdvBlkSize definition.


                leaf bgpMemPoolAdjCnt  {
                    type  cml_data_types:CML_UINT32_T;
                    description "MemPool count- Adjout";
                } // END of bgpMemPoolAdjCnt definition.


                leaf bgpMemPoolAdjTime  {
                    type  cml_data_types:CML_STRING_T {
                        length "0..255";
                    }
                    description "MemPool time in microsec - Adjout";
                } // END of bgpMemPoolAdjTime definition.


                leaf bgpMemPoolAdjSlotSect  {
                    type  cml_data_types:CML_STRING_T {
                        length "0..255";
                    }
                    description "MemPool slot sector count - Adjout";
                } // END of bgpMemPoolAdjSlotSect definition.


                leaf bgpMemPoolAdjTotalCnt  {
                    type  cml_data_types:CML_UINT32_T;
                    description "MemPool total count - Adjout";
                } // END of bgpMemPoolAdjTotalCnt definition.


                leaf bgpMemPoolAdjTotalBlkSize  {
                    type  cml_data_types:CML_UINT32_T;
                    description "MemPool Total block size - Adjout";
                } // END of bgpMemPoolAdjTotalBlkSize definition.


                leaf bgpMemPoolAdjBlkSize  {
                    type  cml_data_types:CML_UINT32_T;
                    description "MemPool Adjusted block size - Adjout";
                } // END of bgpMemPoolAdjBlkSize definition.


            } // END of bgpStats-container definition.
            uses bgpAttrs;
        } // End of bgp-list
    } // END of bgp-grouping definition.
    grouping bgpAttrs {
        description
            "bgpAttrs";
        leaf bgpVersion  {
            type  cml_data_types:CML_INT32_T;
            config false;
            description "BGP version";
        } // END of bgpVersion definition.


        leaf bgpTableVersion  {
            type  cml_data_types:CML_INT32_T;
            config false;
            description "BGP table version";
        } // END of bgpTableVersion definition.


        leaf ntwkPrefixCount  {
            type  cml_data_types:CML_INT32_T;
            config false;
            description "Network prefix count";
        } // END of ntwkPrefixCount definition.


        leaf nhtConfigured  {
            type  cml_data_types:CML_BOOL_T;
            config false;
            description "Configured NHT";
        } // END of nhtConfigured definition.


        leaf nhtDlyTime  {
            type  cml_data_types:CML_INT32_T;
            config false;
            description "NHT Delay time-interval";
        } // END of nhtDlyTime definition.


        leaf nhtRcvMsgCnt  {
            type  cml_data_types:CML_STRING_T {
                length "0..255";
            }
            config false;
            description "Recvd Msg count from RIB/NSM";
        } // END of nhtRcvMsgCnt definition.


        leaf nhtIpv4Cnt  {
            type  cml_data_types:CML_INT32_T;
            config false;
            description "Total number of IPV4 nexthops";
        } // END of nhtIpv4Cnt definition.


        leaf nhtIpv6Cnt  {
            type  cml_data_types:CML_INT32_T;
            config false;
            description "Total number of IPV6 nexthops";
        } // END of nhtIpv6Cnt definition.


        leaf nhtDlyTimeRemain  {
            type  cml_data_types:CML_INT32_T;
            config false;
            description "NHT delay-timer remaining seconds";
        } // END of nhtDlyTimeRemain definition.


        leaf routerIpAddr  {
            type  cml_data_types:CML_IPV4_ADDR_T;
            description "router-id";
        } // END of routerIpAddr definition.


        leaf routerRunIpAddr  {
            type  cml_data_types:CML_STRING_T {
                length "0..255";
            }
            config false;
            description "router-id";
        } // END of routerRunIpAddr definition.


        leaf clusterId  {
            type  cml_data_types:CML_CLUSTER_ID_T {
                length "0..255";
            }
            description "BGP route reflector cluster ID";
        } // END of clusterId definition.


        leaf confedId  {
            type  cml_data_types:CML_INT32_T {
                 range "1..65535";
            }
            description "Confederation ID <1-65535>";
        } // END of confedId definition.


        leaf keepAlive  {
            type  cml_data_types:CML_UINT16_T {
                 range "0..65535";
            }
            default "30";
            description "BGP keepalive time 0|<3-65535>";
        } // END of keepAlive definition.


        leaf holdTime  {
            type  cml_data_types:CML_UINT16_T {
                 range "0..65535";
            }
            default "90";
            description "BGP holdtime 0|<1-21845>";
        } // END of holdTime definition.


        leaf localPref  {
            type  cml_data_types:CML_UINT32_T {
                 range "0..4294967295";
            }
            default "100";
            description "BGP default local preference <0-4294967295> ,default value is 100";
        } // END of localPref definition.


        leaf setGshutCapable  {
            type  cml_data_types:CML_BOOL_T;
            description "bgp g-shut capable";
        } // END of setGshutCapable definition.


        leaf setGshut  {
            type  cml_data_types:CML_BOOL_T;
            description "bgp g-shut";
        } // END of setGshut definition.


        leaf gshutLocalPref  {
            type  cml_data_types:CML_UINT32_T {
                 range "0..4294967295";
            }
            default "0";
            description "bgp g-shut local preference";
        } // END of gshutLocalPref definition.


        leaf setInboundRouteFilter  {
            if-feature feature_list:HAVE_VRF;
            type  cml_data_types:CML_BOOL_T;
            description "bgp inbound route-filter";
        } // END of setInboundRouteFilter definition.


        leaf setLogNbrChanges  {
            type  cml_data_types:CML_BOOL_T;
            description "bgp log-neighbor changes";
        } // END of setLogNbrChanges definition.


        leaf scanInterval  {
            type  cml_data_types:CML_UINT32_T {
                 range "0..60";
            }
            default "60";
            description "Scan interval (sec) [Default:60; Disable:0]";
        } // END of scanInterval definition.


        leaf distance  {
            type  cml_data_types:CML_UINT8_T {
                 range "1..255";
            }
            description "bgp distance <1-255>";
        } // END of distance definition.


        leaf distanceSrcIp  {
            type  cml_data_types:CML_IPV4_PREFIX_T;
            description "bgp distance source ip";
        } // END of distanceSrcIp definition.


        leaf distanceACLName  {
            type  cml_data_types:CML_STRING_T {
                length "0..255";
            }
            description "Access list name";
        } // END of distanceACLName definition.


        leaf restartTime  {
            if-feature feature_list:HAVE_RESTART;
            type  cml_data_types:CML_UINT32_T {
                 range "1..3600";
            }
            default "90";
            description "Max time needed for Neighbor(s) to restart <1-3600>";
        } // END of restartTime definition.


        leaf stalepathTime  {
            if-feature feature_list:HAVE_RESTART;
            type  cml_data_types:CML_UINT32_T {
                 range "1..3600";
            }
            default "360";
            description "Max time to retain stale paths from restarting Neighbor(s) <1-3600>";
        } // END of stalepathTime definition.


        leaf deferTime  {
            if-feature feature_list:HAVE_RESTART;
            type  cml_data_types:CML_UINT32_T {
                 range "1..3600";
            }
            default "120";
            description "Max time to defer initial route-selection <1-3600>";
        } // END of deferTime definition.


        leaf bestpathDontCompareOriginator  {
            type  cml_data_types:CML_BOOL_T;
            description "Don't Compare originator-id";
        } // END of bestpathDontCompareOriginator definition.


        leaf noBestpathTieBreak  {
            type  cml_data_types:CML_BOOL_T;
            default true;
            description "tie break on age";
        } // END of noBestpathTieBreak definition.


        leaf noIpv4Unicast  {
            type  cml_data_types:CML_BOOL_T;
            default true;
            description "ipv4-unicast for a peer";
        } // END of noIpv4Unicast definition.


        leaf deterministicMed  {
            type  cml_data_types:CML_BOOL_T;
            description "deterministic med";
        } // END of deterministicMed definition.


        leaf compareMed  {
            type  cml_data_types:CML_BOOL_T;
            description "always compare med";
        } // END of compareMed definition.


        leaf bestpathAspath  {
            type  cml_data_types:CML_BOOL_T;
            description "as-path ignore";
        } // END of bestpathAspath definition.


        leaf bestpathCompareConfed  {
            type  cml_data_types:CML_BOOL_T;
            description "compare confed aspath";
        } // END of bestpathCompareConfed definition.


        leaf bestpathCompareRouterId  {
            type  cml_data_types:CML_BOOL_T;
            description "compare router-id";
        } // END of bestpathCompareRouterId definition.


        leaf enforceFirst  {
            type  cml_data_types:CML_BOOL_T;
            description "enforce first as";
        } // END of enforceFirst definition.


        leaf noExternalFailover  {
            type  cml_data_types:CML_BOOL_T;
            default true;
            description "fast external failover";
        } // END of noExternalFailover definition.


        leaf allocateLabelAll  {
            if-feature feature_list:HAVE_BGP_LU;
            type  cml_data_types:CML_BOOL_T;
            description "allocate-label all";
        } // END of allocateLabelAll definition.


        leaf RouteMapName  {
            if-feature feature_list:HAVE_BGP_LU;
            type  cml_data_types:CML_STRING_T {
                length "0..255";
            }
            description "route-map name";
        } // END of RouteMapName definition.


        leaf ebgpMaxPath  {
            type  cml_data_types:CML_INT32_T {
                 range "2..64";
            }
            default "2";
            description "max-paths <2-64>";
        } // END of ebgpMaxPath definition.


        leaf ibgpMaxPath  {
            type  cml_data_types:CML_INT32_T {
                 range "2..64";
            }
            default "2";
            description "max-paths <2-64>";
        } // END of ibgpMaxPath definition.


        leaf autoSummary  {
            type  cml_data_types:CML_BOOL_T;
            description "auto summary enable/disable";
        } // END of autoSummary definition.


        leaf setSyncFlag  {
            type  cml_data_types:CML_BOOL_T;
            description "synchronization enable/disable";
        } // END of setSyncFlag definition.


        leaf setNwSyncFlag  {
            type  cml_data_types:CML_BOOL_T;
            description "network synchronization enable/disable";
        } // END of setNwSyncFlag definition.


        leaf localAsCount  {
            type  cml_data_types:CML_UINT8_T {
                 range "2..64";
            }
            description "as local count";
        } // END of localAsCount definition.


        leaf grstSet  {
            if-feature feature_list:HAVE_RESTART;
            type  cml_data_types:CML_BOOL_T;
            description "graceful restart";
        } // END of grstSet definition.


        leaf noSetClientReflect  {
            type  cml_data_types:CML_BOOL_T;
            default true;
            description "client-client reflection";
        } // END of noSetClientReflect definition.


        leaf rfdMaxPenaltyCeil  {
            type  cml_data_types:CML_INT32_T;
            default "0";
            config false;
            description "dampening penalty ceil";
        } // END of rfdMaxPenaltyCeil definition.


        leaf rfdMinPenaltyFloor  {
            type  cml_data_types:CML_INT32_T;
            default "0";
            config false;
            description "dampening penalty floor";
        } // END of rfdMinPenaltyFloor definition.


        leaf medType  {
            type  cml_data_types:CML_BGP_MED_TYPE_T;
            description "MED in confederation paths";
        } // END of medType definition.


        leaf gracefulReset  {
            type  cml_data_types:CML_BOOL_T;
            description "graceful-reset";
        } // END of gracefulReset definition.


        leaf distanceEbgp  {
            type  cml_data_types:CML_UINT8_T {
                 range "1..255";
            }
            default "20";
            description "Distance for routes external to the AS <1-255>";
        } // END of distanceEbgp definition.


        leaf distanceIbgp  {
            type  cml_data_types:CML_UINT8_T {
                 range "1..255";
            }
            default "200";
            description "Distance for routes internal to the AS <1-255>";
        } // END of distanceIbgp definition.


        leaf distanceLocal  {
            type  cml_data_types:CML_UINT8_T {
                 range "1..255";
            }
            default "200";
            description "Distance for local routes <1-255>";
        } // END of distanceLocal definition.


        leaf multipathRelax  {
            type  cml_data_types:CML_BOOL_T;
            description "Relax as-path in selecting a route";
        } // END of multipathRelax definition.


        leaf tableMap  {
            if-feature feature_list:HAVE_BGP_TABLE_MAP;
            type  cml_data_types:CML_STRING_T {
                length "0..255";
            }
            description "table map name";
        } // END of tableMap definition.


        leaf tableMapFilter  {
            if-feature feature_list:HAVE_BGP_TABLE_MAP;
            type  cml_data_types:CML_BOOL_T;
            description "filter name";
        } // END of tableMapFilter definition.


        leaf SetAddPathFlag  {
            if-feature feature_list:HAVE_BGP_PIC_CORE_EDGE;
            type  cml_data_types:CML_BOOL_T;
            description "additional-paths flag";
        } // END of SetAddPathFlag definition.


        leaf SetAddPathFrrFlag  {
            if-feature feature_list:HAVE_BGP_PIC_CORE_EDGE;
            type  cml_data_types:CML_BOOL_T;
            description "";
        } // END of SetAddPathFrrFlag definition.


        leaf additionalPaths  {
            if-feature feature_list:HAVE_BGP_ADD_PATH;
            type  cml_data_types:BGP_ADDITIONAL_PATH_TYPE_T;
            description "additional-paths";
        } // END of additionalPaths definition.


        leaf addPathSelectAll  {
            if-feature feature_list:HAVE_BGP_ADD_PATH;
            type  cml_data_types:CML_BOOL_T;
            description "additional-paths all";
        } // END of addPathSelectAll definition.


        leaf bestCount  {
            if-feature feature_list:HAVE_BGP_ADD_PATH;
            type  cml_data_types:CML_UINT8_T {
                 range "2..3";
            }
            description "best <2-3>";
        } // END of bestCount definition.



        list bgpConfed {
            key "peerConfedId";
            description
                "bgpConfed";
            leaf peerConfedId  {
                type  cml_data_types:CML_INT32_T {
                     range "1..65535";
                }
                description "Peer confederation ID <1-65535>";
            } // END of peerConfedId definition.


        } // End of bgpConfed-list

        list bgpNetworkList {
            key "localAddr";
            description
                "bgpNetworkList";
            leaf localAddr  {
                type  cml_data_types:CML_BGP_NETWORK_T {
                    length "0..255";
                }
                description "network address";
            } // END of localAddr definition.


            leaf networkRmapName  {
                type  cml_data_types:CML_STRING_T {
                    length "0..255";
                }
                description "route-map name";
            } // END of networkRmapName definition.


            leaf backdoor  {
                type  cml_data_types:CML_BOOL_T;
                default false;
                description "backdoor";
            } // END of backdoor definition.


            uses nwRunTimeAttr;
        } // End of bgpNetworkList-list

        list bgpAggregateAddrList {
            key "aggregateAddr";
            description
                "bgpAggregateAddrList";
            leaf aggregateAddr  {
                type  cml_data_types:CML_IPV4_PREFIX_T;
                description "aggregate-prefix";
            } // END of aggregateAddr definition.


            leaf aggregateAsSet  {
                type  cml_data_types:CML_BOOL_T;
                default true;
                description "as-set path";
            } // END of aggregateAsSet definition.


            leaf aggregateSummOnly  {
                type  cml_data_types:CML_BOOL_T;
                default true;
                description "summary-only path";
            } // END of aggregateSummOnly definition.


        } // End of bgpAggregateAddrList-list

        list bgpRedistList {
            key "redistType";
            description
                "bgpRedistList";
            leaf redistType  {
                type  cml_data_types:CML_BGP_REDISTRIBUTE_TYPE_T;
                description "redistribute type";
            } // END of redistType definition.


            leaf redistRmapName  {
                type  cml_data_types:CML_STRING_T {
                    length "0..255";
                }
                description "";
            } // END of redistRmapName definition.


        } // End of bgpRedistList-list

        list bgpRedistOspfNo {
            key "redistOspfNo";
            description
                "bgpRedistOspfNo";
            leaf redistOspfNo  {
                type  cml_data_types:CML_UINT32_T {
                     range "0..65535";
                }
                description "";
            } // END of redistOspfNo definition.


            leaf redistOspfRmap  {
                type  cml_data_types:CML_STRING_T {
                    length "0..255";
                }
                description "";
            } // END of redistOspfRmap definition.


        } // End of bgpRedistOspfNo-list

        list bgpPeerGroup {
            key "peerGroupTag";
            description
                "bgpPeerGroup";
            leaf peerGroupTag  {
                type  cml_data_types:CML_STRING_T {
                    length "0..255";
                }
                description "";
            } // END of peerGroupTag definition.


            leaf peerGroupRange  {
                type  cml_data_types:CML_STRING_T {
                    length "0..255";
                }
                description "";
            } // END of peerGroupRange definition.


            leaf groupLimit  {
                type  cml_data_types:CML_UINT8_T {
                     range "1..200";
                }
                description "";
            } // END of groupLimit definition.



            list OptionalASList {
                key "optionalAS";
                description
                    "OptionalASList";
                leaf optionalAS  {
                    type  cml_data_types:CML_UINT32_T {
                         range "1..4294967295";
                    }
                    description "Optional AS number";
                } // END of optionalAS definition.


            } // End of OptionalASList-list
            uses peerAndPeerGroupAttrs;
        } // End of bgpPeerGroup-list

        list bgpAddressFamily {
            key "afi";
            description
                "bgpAddressFamily";
            leaf afi  {
                type  cml_data_types:CML_AFI_TYPE_T;
                description "";
            } // END of afi definition.



            list bgpSubAddressFamily {
                key "safi";
                description
                    "bgpSubAddressFamily";
                leaf safi  {
                    type  cml_data_types:CML_SAFI_TYPE_T;
                    description "";
                } // END of safi definition.


                leaf SetAddPathFrrFlagAf  {
                    if-feature feature_list:HAVE_BGP_PIC_CORE_EDGE;
                    type  cml_data_types:CML_BOOL_T;
                    description "";
                } // END of SetAddPathFrrFlagAf definition.


                leaf additionalPathsAf  {
                    if-feature feature_list:HAVE_BGP_ADD_PATH;
                    type  cml_data_types:BGP_ADDITIONAL_PATH_TYPE_T;
                    description "additional-paths";
                } // END of additionalPathsAf definition.


                leaf addPathSelectAllAf  {
                    if-feature feature_list:HAVE_BGP_ADD_PATH;
                    type  cml_data_types:CML_BOOL_T;
                    description "additional-paths all";
                } // END of addPathSelectAllAf definition.


                leaf bestCountAf  {
                    if-feature feature_list:HAVE_BGP_ADD_PATH;
                    type  cml_data_types:CML_UINT8_T {
                         range "2..3";
                    }
                    description "best <2-3>";
                } // END of bestCountAf definition.


                leaf noSetClientReflectAf  {
                    type  cml_data_types:CML_BOOL_T;
                    description "client-client reflection";
                } // END of noSetClientReflectAf definition.



                list bgpAddressFamilyAggregateAddrList {
                    key "aggregateAddrAf";
                    description
                        "bgpAddressFamilyAggregateAddrList";
                    leaf aggregateAddrAf  {
                        type  cml_data_types:CML_IPV6_PREFIX_T;
                        description "aggregate-prefix";
                    } // END of aggregateAddrAf definition.


                    leaf aggregateAsSetAf  {
                        type  cml_data_types:CML_BOOL_T;
                        description "as-set path";
                    } // END of aggregateAsSetAf definition.


                    leaf aggregateSummOnlyAf  {
                        type  cml_data_types:CML_BOOL_T;
                        description "summary-only path";
                    } // END of aggregateSummOnlyAf definition.


                } // End of bgpAddressFamilyAggregateAddrList-list
                uses bgpAfAttrs;
                uses networkAfAttrs;
            } // End of bgpSubAddressFamily-list
        } // End of bgpAddressFamily-list

        list vrfAddressFamily {
            key "afi";
            description
                "vrfAddressFamily";
            leaf afi  {
                type  cml_data_types:CML_VRF_AFI_TYPE_T;
                description "";
            } // END of afi definition.



            list vrfSubAddressFamily {
                key "safi";
                description
                    "vrfSubAddressFamily";
                leaf safi  {
                    type  cml_data_types:CML_VRF_SAFI_TYPE_T;
                    description "";
                } // END of safi definition.



                list afVrfObj {
                    key "vrfName";
                    description
                        "afVrfObj";
                    leaf vrfName  {
                        type  cml_data_types:CML_STRING_T {
                            length "0..255";
                        }
                        description "";
                    } // END of vrfName definition.


                    leaf setGshutAf  {
                        type  cml_data_types:CML_BOOL_T;
                        description "bgp g-shut";
                    } // END of setGshutAf definition.


                    leaf setGshutCapableAf  {
                        type  cml_data_types:CML_BOOL_T;
                        description "bgp g-shut-capable";
                    } // END of setGshutCapableAf definition.


                    leaf gshutLocalPrefAf  {
                        type  cml_data_types:CML_UINT32_T {
                             range "0..4294967295";
                        }
                        default "0";
                        description "bgp g-shut-local-preference";
                    } // END of gshutLocalPrefAf definition.


                    leaf confedIdAf  {
                        type  cml_data_types:CML_INT32_T {
                             range "1..65535";
                        }
                        description "Confederation ID <1-65535>";
                    } // END of confedIdAf definition.



                    list bgpConfed {
                        key "peerConfedIdAf";
                        description
                            "bgpConfed";
                        leaf peerConfedIdAf  {
                            type  cml_data_types:CML_INT32_T {
                                 range "1..65535";
                            }
                            description "Confederation ID <1-65535>";
                        } // END of peerConfedIdAf definition.


                    } // End of bgpConfed-list

                    list vrfPeer {
                        key "peerAddr";
                        description
                            "vrfPeer";
                        leaf peerAddr  {
                            type  cml_data_types:CML_HOSTNAME_T {
                                length "0..255";
                            }
                            description "The peer address or Tag";
                        } // END of peerAddr definition.


                        leaf peerAsAf  {
                            type  cml_data_types:CML_UINT32_T {
                                 range "1..4294967295";
                            }
                            description "Remote AS number <0-65535>>";
                        } // END of peerAsAf definition.


                        leaf sourceIdAf  {
                            type  cml_data_types:CML_STRING_T {
                                length "0..255";
                            }
                            default "NULL";
                            description "";
                        } // END of sourceIdAf definition.


                        leaf peerLocalAsAf  {
                            type  cml_data_types:CML_UINT32_T {
                                 range "1..4294967295";
                            }
                            description "";
                        } // END of peerLocalAsAf definition.


                        leaf bgpVersionAf  {
                            type  cml_data_types:CML_UINT8_T;
                            default "4";
                            description "BGP Version";
                        } // END of bgpVersionAf definition.


                        leaf peerConnectIntervalAf  {
                            type  cml_data_types:CML_UINT32_T {
                                 range "1..65535";
                            }
                            default "1";
                            description "Connect timer value <1-65535>";
                        } // END of peerConnectIntervalAf definition.


                        leaf peerKeepAliveAf  {
                            type  cml_data_types:CML_UINT16_T {
                                 range "0..65535";
                            }
                            default "30";
                            description "BGP keepalive time 0|<3-65535>";
                        } // END of peerKeepAliveAf definition.


                        leaf peerHoldTimeAf  {
                            type  cml_data_types:CML_UINT16_T {
                                 range "0..65535";
                            }
                            default "90";
                            description "holdtime BGP holdtime 0|<1-21845>";
                        } // END of peerHoldTimeAf definition.


                        leaf enforceMultihopAf  {
                            type  cml_data_types:CML_BOOL_T;
                            description "";
                        } // END of enforceMultihopAf definition.


                        leaf peerShutdownAf  {
                            type  cml_data_types:CML_BOOL_T;
                            description "";
                        } // END of peerShutdownAf definition.


                        leaf peerGroupStrAf  {
                            type  cml_data_types:CML_BOOL_T;
                            description "";
                        } // END of peerGroupStrAf definition.


                        leaf peerGroupRangeAf  {
                            type  cml_data_types:CML_STRING_T {
                                length "0..255";
                            }
                            description "";
                        } // END of peerGroupRangeAf definition.


                        leaf groupLimitAf  {
                            type  cml_data_types:CML_UINT8_T {
                                 range "1..200";
                            }
                            description "";
                        } // END of groupLimitAf definition.


                        leaf transportConnectionPassiveAf  {
                            type  cml_data_types:CML_BOOL_T;
                            description "";
                        } // END of transportConnectionPassiveAf definition.


                        leaf maxHopCountAf  {
                            type  cml_data_types:CML_UINT8_T {
                                 range "1..255";
                            }
                            default "255";
                            description "";
                        } // END of maxHopCountAf definition.


                        leaf timeToLiveAf  {
                            type  cml_data_types:CML_BOOL_T;
                            description "";
                        } // END of timeToLiveAf definition.


                        leaf dontCapabilityNegotiateAf  {
                            type  cml_data_types:CML_BOOL_T;
                            description "";
                        } // END of dontCapabilityNegotiateAf definition.


                        leaf connRetryIntervalAf  {
                            type  cml_data_types:CML_INT32_T {
                                 range "1..65535";
                            }
                            default "120";
                            description "Connect timer value >1-65535;<";
                        } // END of connRetryIntervalAf definition.


                        leaf dynamicCapabilityAf  {
                            type  cml_data_types:CML_BOOL_T;
                            description "";
                        } // END of dynamicCapabilityAf definition.


                        leaf peerRaIntervalAf  {
                            type  cml_data_types:CML_UINT32_T {
                                 range "0..65535";
                            }
                            default "0";
                            description "Minimum route advertisement interval <0-65535>";
                        } // END of peerRaIntervalAf definition.


                        leaf peerAsorigIntervalAf  {
                            type  cml_data_types:CML_UINT32_T {
                                 range "1..65535";
                            }
                            default "1";
                            description "Time interval <1-65535>";
                        } // END of peerAsorigIntervalAf definition.


                        leaf neighborAsOverrideAf  {
                            type  cml_data_types:CML_BOOL_T;
                            description "";
                        } // END of neighborAsOverrideAf definition.


                        leaf peerIfNameAf  {
                            if-feature feature_list:HAVE_VRF;
                            type  cml_data_types:CML_STRING_T {
                                length "0..255";
                            }
                            description "Interface name";
                        } // END of peerIfNameAf definition.


                        leaf peerDescAf  {
                            type  cml_data_types:CML_LINE_T {
                                length "0..255";
                            }
                            description "";
                        } // END of peerDescAf definition.


                        leaf peerRestartTimeAf  {
                            if-feature feature_list:HAVE_RESTART;
                            if-feature feature_list:HAVE_VRF;
                            type  cml_data_types:CML_UINT32_T {
                                 range "1..3600";
                            }
                            description "restart time";
                        } // END of peerRestartTimeAf definition.


                        leaf siteOriginIdAf  {
                            if-feature feature_list:HAVE_VRF;
                            type  cml_data_types:CML_STRING_T {
                                length "0..255";
                            }
                            description "";
                        } // END of siteOriginIdAf definition.


                        leaf setGracefulShutAf  {
                            type  cml_data_types:CML_BOOL_T;
                            description "";
                        } // END of setGracefulShutAf definition.


                        leaf gshutTimerAf  {
                            type  cml_data_types:CML_UINT32_T {
                                 range "10..65535";
                            }
                            description "";
                        } // END of gshutTimerAf definition.



                        list OptionalASAfList {
                            key "optionalASAf";
                            description
                                "OptionalASAfList";
                            leaf optionalASAf  {
                                type  cml_data_types:CML_UINT32_T {
                                     range "1..4294967295";
                                }
                                description "Optional AS number <0-65535>>";
                            } // END of optionalASAf definition.


                        } // End of OptionalASAfList-list
                        container bgpPasswordAf {
                            description
                                "Configure password for the neighbor in addressfamily";
                            leaf passwordAf  {
                                if-feature feature_list:HAVE_TCP_MD5SIG;
                                type  cml_data_types:CML_STRING_T {
                                    length "0..255";
                                }
                                description "";
                            } // END of passwordAf definition.


                            leaf authKeyEncryptionAddrAf  {
                                type  CML_BGP_MD5_T;
                                description "";
                            } // END of authKeyEncryptionAddrAf definition.


                        } // END of bgpPasswordAf-container definition.
                        uses peerVrfAttrs;
                        uses peerRuntimeAttr;
                        uses peerAdjOutRouteAttrs;
                        uses peerAdjInRouteAttrs;
                    } // End of vrfPeer-list
                    uses bgpAfAttrs;
                    uses networkAfAttrs;
                } // End of afVrfObj-list
            } // End of vrfSubAddressFamily-list
        } // End of vrfAddressFamily-list

        list bgpPeer {
            key "peerAddr";
            description
                "bgpPeer";
            leaf peerAddr  {
                type  cml_data_types:CML_HOSTNAME_T {
                    length "0..255";
                }
                description "The peer address or Tag";
            } // END of peerAddr definition.


            leaf peerAs  {
                type  cml_data_types:CML_UINT32_T {
                     range "1..4294967295";
                }
                description "Remote AS number <0-65535>>";
            } // END of peerAs definition.


            leaf vrfName  {
                type  cml_data_types:CML_STRING_T {
                    length "0..255";
                }
                config false;
                description "vrf name";
            } // END of vrfName definition.


            leaf bgpPeerState  {
                type  cml_data_types:CML_BGP_PEER_STATUS_T;
                description "Bgp peer session state. If there is change in state of the session , notification will be published only if the current state or the previous state is in establised state ";
            } // END of bgpPeerState definition.


            leaf peerAdditionalPaths  {
                if-feature feature_list:HAVE_BGP_ADD_PATH;
                type  cml_data_types:BGP_PEER_ADDITIONAL_PATH_TYPE_T;
                description "";
            } // END of peerAdditionalPaths definition.


            leaf peerAddPathSelectAll  {
                if-feature feature_list:HAVE_BGP_ADD_PATH;
                type  cml_data_types:CML_BOOL_T;
                description "";
            } // END of peerAddPathSelectAll definition.


            leaf peerBestCount  {
                if-feature feature_list:HAVE_BGP_ADD_PATH;
                type  cml_data_types:CML_UINT8_T {
                     range "2..3";
                }
                description "";
            } // END of peerBestCount definition.


            leaf setGracefulShut  {
                type  cml_data_types:CML_BOOL_T;
                description "";
            } // END of setGracefulShut definition.


            leaf bgpPeerBfd  {
                type  cml_data_types:CML_BOOL_T;
                description "";
            } // END of bgpPeerBfd definition.


            leaf peerBfdMh  {
                type  cml_data_types:CML_BOOL_T;
                description "";
            } // END of peerBfdMh definition.


            leaf gshutTimer  {
                type  cml_data_types:CML_UINT32_T {
                     range "10..65535";
                }
                description "";
            } // END of gshutTimer definition.


            leaf peerRestartTime  {
                if-feature feature_list:HAVE_RESTART;
                type  cml_data_types:CML_UINT32_T {
                     range "1..3600";
                }
                description "restart time";
            } // END of peerRestartTime definition.


            leaf peerLocalAs  {
                type  cml_data_types:CML_UINT32_T {
                     range "1..4294967295";
                }
                description "";
            } // END of peerLocalAs definition.


            leaf neighborAttrUnchanged  {
                type  cml_data_types:CML_ATTRIBUTE_UNCHANGED_TYPE_T;
                description "";
            } // END of neighborAttrUnchanged definition.


            leaf neighborCapabilityGrst  {
                if-feature feature_list:HAVE_RESTART;
                type  cml_data_types:CML_BOOL_T;
                description "";
            } // END of neighborCapabilityGrst definition.


            leaf peerRemovePvtAs  {
                type  cml_data_types:CML_BOOL_T;
                description "";
            } // END of peerRemovePvtAs definition.


            leaf sendCommunity  {
                type  cml_data_types:CML_BOOL_T;
                description "";
            } // END of sendCommunity definition.


            leaf sendCommunityType  {
                type  cml_data_types:CML_BGP_SEND_COMMU_TYPE_T;
                description "";
            } // END of sendCommunityType definition.


            leaf neighborRouteServerClient  {
                type  cml_data_types:CML_BOOL_T;
                description "";
            } // END of neighborRouteServerClient definition.


            leaf peerRouteReflector  {
                type  cml_data_types:CML_BOOL_T;
                description "";
            } // END of peerRouteReflector definition.


            leaf peerAdminFlag  {
                type  cml_data_types:CML_INT32_T;
                description "";
            } // END of peerAdminFlag definition.


            leaf connRetryInterval  {
                type  cml_data_types:CML_INT32_T {
                     range "1..65535";
                }
                default "120";
                description "";
            } // END of connRetryInterval definition.


            leaf peerDesc  {
                type  cml_data_types:CML_LINE_T {
                    length "0..255";
                }
                description "";
            } // END of peerDesc definition.


            leaf transparentAs  {
                type  cml_data_types:CML_BOOL_T;
                description "";
            } // END of transparentAs definition.


            leaf transparentNexthop  {
                type  cml_data_types:CML_BOOL_T;
                description "";
            } // END of transparentNexthop definition.


            leaf timeToLive  {
                type  cml_data_types:CML_BOOL_T;
                description "";
            } // END of timeToLive definition.


            leaf maxHopCount  {
                type  cml_data_types:CML_UINT8_T {
                     range "1..255";
                }
                default "255";
                description "";
            } // END of maxHopCount definition.


            leaf peerConnectInterval  {
                type  cml_data_types:CML_UINT32_T {
                     range "1..65535";
                }
                default "1";
                description "Connect timer value <1-65535>";
            } // END of peerConnectInterval definition.


            leaf peerAsorigInterval  {
                type  cml_data_types:CML_UINT32_T {
                     range "1..65535";
                }
                default "1";
                description "Time interval <1-65535>";
            } // END of peerAsorigInterval definition.


            leaf peerRaInterval  {
                type  cml_data_types:CML_UINT32_T {
                     range "0..65535";
                }
                default "0";
                description "Minimum route advertisement interval <0-65535>";
            } // END of peerRaInterval definition.


            leaf dynamicCapability  {
                type  cml_data_types:CML_BOOL_T;
                description "";
            } // END of dynamicCapability definition.


            leaf collideEstablished  {
                type  cml_data_types:CML_BOOL_T;
                description "";
            } // END of collideEstablished definition.


            leaf sourceId  {
                type  cml_data_types:CML_STRING_T {
                    length "0..255";
                }
                default "NULL";
                description "";
            } // END of sourceId definition.


            leaf enforceMultihop  {
                type  cml_data_types:CML_BOOL_T;
                description "";
            } // END of enforceMultihop definition.


            leaf neighborOverrideCapability  {
                type  cml_data_types:CML_BOOL_T;
                description "";
            } // END of neighborOverrideCapability definition.


            leaf neighborStrictCapability  {
                type  cml_data_types:CML_BOOL_T;
                description "";
            } // END of neighborStrictCapability definition.


            leaf disallowHoldtimer  {
                type  cml_data_types:CML_BOOL_T;
                description "";
            } // END of disallowHoldtimer definition.


            leaf dontCapabilityNegotiate  {
                type  cml_data_types:CML_BOOL_T;
                description "";
            } // END of dontCapabilityNegotiate definition.


            leaf transportConnectionPassive  {
                type  cml_data_types:CML_BOOL_T;
                description "";
            } // END of transportConnectionPassive definition.


            leaf peerShutdown  {
                type  cml_data_types:CML_BOOL_T;
                description "";
            } // END of peerShutdown definition.


            leaf bgpPort  {
                type  cml_data_types:CML_UINT16_T {
                     range "0..65535";
                }
                default "179";
                description "tcp port number <0-65535>";
            } // END of bgpPort definition.


            leaf bgpVersion  {
                type  cml_data_types:CML_UINT8_T;
                default "4";
                description "BGP Version";
            } // END of bgpVersion definition.


            leaf peerIfName  {
                type  cml_data_types:CML_STRING_T {
                    length "0..255";
                }
                description "Interface name";
            } // END of peerIfName definition.


            leaf softReconfigInbound  {
                type  cml_data_types:CML_BOOL_T;
                description "";
            } // END of softReconfigInbound definition.


            leaf weight  {
                type  cml_data_types:CML_UINT16_T {
                     range "0..65535";
                }
                default "0";
                description "Weight for routes <0-65535>";
            } // END of weight definition.


            leaf maxPrefixes  {
                type  cml_data_types:CML_UINT32_T {
                     range "1..4294967295";
                }
                description "Maximum number of prefixes <1-4294967295>";
            } // END of maxPrefixes definition.


            leaf stopUpdate  {
                type  cml_data_types:CML_BOOL_T;
                description "";
            } // END of stopUpdate definition.


            leaf maxPrefixeWarning  {
                type  cml_data_types:CML_BOOL_T;
                description "Throw warning if exceeds threshold-value Yes/No flag";
            } // END of maxPrefixeWarning definition.


            leaf threshold  {
                type  cml_data_types:CML_UINT8_T {
                     range "1..100";
                }
                default "75";
                description "Threshold-value in percent <1-100>";
            } // END of threshold definition.


            leaf warning  {
                type  cml_data_types:CML_BOOL_T;
                description "Throw warning if exceeds threshold-value Yes/No flag";
            } // END of warning definition.


            leaf allowAsNum  {
                type  cml_data_types:CML_UINT32_T {
                     range "1..10";
                }
                default "3";
                description "Allow AS number <1-10>";
            } // END of allowAsNum definition.


            leaf peerGroupTag  {
                type  cml_data_types:CML_STRING_T {
                    length "0..255";
                }
                description "BGP peer group name";
            } // END of peerGroupTag definition.


            leaf peerActivate  {
                type  cml_data_types:CML_BOOL_T;
                description "Activate/Deactivate neighbor";
            } // END of peerActivate definition.


            leaf unSuppressAclInfo  {
                type  cml_data_types:CML_STRING_T {
                    length "0..255";
                }
                description "unsuppress map name";
            } // END of unSuppressAclInfo definition.


            leaf peerRmapOriName  {
                type  cml_data_types:CML_STRING_T {
                    length "0..255";
                }
                description "Route-map name";
            } // END of peerRmapOriName definition.


            leaf defaultPeerRmapName  {
                type  cml_data_types:CML_BOOL_T;
                description "";
            } // END of defaultPeerRmapName definition.


            leaf orfPrefixOpt  {
                type  cml_data_types:CML_BGP_ORF_PREFIX_TYPE_T;
                description "";
            } // END of orfPrefixOpt definition.


            leaf peerKeepAlive  {
                type  cml_data_types:CML_UINT16_T {
                     range "0..65535";
                }
                default "30";
                description "BGP keepalive time 0|<3-65535>";
            } // END of peerKeepAlive definition.


            leaf peerHoldTime  {
                type  cml_data_types:CML_UINT16_T {
                     range "0..65535";
                }
                default "90";
                description "holdtime BGP holdtime 0|<1-21845>";
            } // END of peerHoldTime definition.


            leaf nextHopSelf  {
                type  cml_data_types:CML_BOOL_T;
                description "";
            } // END of nextHopSelf definition.



            list bgpDlistFilter {
                key "distributeListDirection";
                description
                    "bgpDlistFilter";
                leaf aclInfo  {
                    type  cml_data_types:CML_STRING_T {
                        length "0..255";
                    }
                    mandatory true;
                    description "Access-list numbe";
                } // END of aclInfo definition.


                leaf distributeListDirection  {
                    type  cml_data_types:CML_BGP_DISTRIBUTE_LIST_ACTION_T;
                    description "Direction of the filter (0=FILTER_IN |1=FILTER_OUT)";
                } // END of distributeListDirection definition.


            } // End of bgpDlistFilter-list

            list bgpPlistFilter {
                key "prefixListDirection";
                description
                    "bgpPlistFilter";
                leaf prefixListAclInfo  {
                    type  cml_data_types:CML_STRING_T {
                        length "0..255";
                    }
                    mandatory true;
                    description "Access-list number";
                } // END of prefixListAclInfo definition.


                leaf prefixListDirection  {
                    type  cml_data_types:CML_BGP_DISTRIBUTE_LIST_ACTION_T;
                    description "Direction of the filter (0=FILTER_IN |1=FILTER_OUT)";
                } // END of prefixListDirection definition.


            } // End of bgpPlistFilter-list

            list bgpAslistFilter {
                key "asListDirection";
                description
                    "bgpAslistFilter";
                leaf asListAclInfo  {
                    type  cml_data_types:CML_STRING_T {
                        length "0..255";
                    }
                    mandatory true;
                    description "Access-list number";
                } // END of asListAclInfo definition.


                leaf asListDirection  {
                    type  cml_data_types:CML_BGP_DISTRIBUTE_LIST_ACTION_T;
                    description "Direction of the filter (0=FILTER_IN |1=FILTER_OUT)";
                } // END of asListDirection definition.


            } // End of bgpAslistFilter-list

            list bgpRmapFilter {
                key "peerRmapDirection";
                description
                    "bgpRmapFilter";
                leaf peerRmapName  {
                    type  cml_data_types:CML_STRING_T {
                        length "0..255";
                    }
                    mandatory true;
                    description "route map";
                } // END of peerRmapName definition.


                leaf peerRmapDirection  {
                    type  cml_data_types:CML_BGP_DISTRIBUTE_LIST_ACTION_T;
                    description "Direction of the filter (0=FILTER_IN |1=FILTER_OUT)";
                } // END of peerRmapDirection definition.


            } // End of bgpRmapFilter-list

            list bgpPeerAddressFamily {
                key "afi";
                description
                    "bgpPeerAddressFamily";
                leaf afi  {
                    type  cml_data_types:CML_AFI_TYPE_T;
                    description "";
                } // END of afi definition.



                list bgpPeerSubAddressFamily {
                    key "safi";
                    description
                        "bgpPeerSubAddressFamily";
                    leaf safi  {
                        type  cml_data_types:CML_SAFI_TYPE_T;
                        description "";
                    } // END of safi definition.


                    leaf peerAdditionalPathsAf  {
                        if-feature feature_list:HAVE_BGP_ADD_PATH;
                        type  cml_data_types:BGP_PEER_ADDITIONAL_PATH_TYPE_T;
                        description "";
                    } // END of peerAdditionalPathsAf definition.


                    leaf peerAddPathSelectAllAf  {
                        if-feature feature_list:HAVE_BGP_ADD_PATH;
                        type  cml_data_types:CML_BOOL_T;
                        description "";
                    } // END of peerAddPathSelectAllAf definition.


                    leaf peerBestCountAf  {
                        if-feature feature_list:HAVE_BGP_ADD_PATH;
                        type  cml_data_types:CML_UINT8_T {
                             range "2..3";
                        }
                        description "";
                    } // END of peerBestCountAf definition.


                    leaf neighborRouteServerClientAf  {
                        type  cml_data_types:CML_BOOL_T;
                        description "";
                    } // END of neighborRouteServerClientAf definition.


                    leaf nextHopSelfAf  {
                        type  cml_data_types:CML_BOOL_T;
                        description "";
                    } // END of nextHopSelfAf definition.


                    uses peerVrfAttrs;
                    uses peerRuntimeAttr;
                    uses peerAdjInRouteAttrs;
                    uses peerAdjOutRouteAttrs;
                } // End of bgpPeerSubAddressFamily-list
            } // End of bgpPeerAddressFamily-list
            uses peerAndPeerGroupAttrs;
            uses peerRuntimeAttr;
            uses peerAdjOutRouteAttrs;
            uses peerAdjInRouteAttrs;
        } // End of bgpPeer-list
        container bgpRfdCbCfgParam {
            description
                "BGP Route Flap Dampening User Configurable Parameters";
            leaf halfLife  {
                type  cml_data_types:CML_UINT32_T {
                     range "1..45";
                }
                default "15";
                description "half life";
            } // END of halfLife definition.


            leaf reusePenalty  {
                type  cml_data_types:CML_UINT32_T {
                     range "1..20000";
                }
                default "750";
                description "reuse Penalty <1-20000>";
            } // END of reusePenalty definition.


            leaf suppressPenalty  {
                type  cml_data_types:CML_UINT32_T {
                     range "1..20000";
                }
                default "2000";
                description "suppress penalty <1-20000>";
            } // END of suppressPenalty definition.


            leaf maxSuppress  {
                type  cml_data_types:CML_UINT32_T {
                     range "1..255";
                }
                default "60";
                description "max suppress <1-255>";
            } // END of maxSuppress definition.


            leaf unreachHalfLife  {
                type  cml_data_types:CML_UINT32_T {
                     range "1..45";
                }
                default "15";
                description "unreachable half life <1-45>";
            } // END of unreachHalfLife definition.


            leaf dampeningRmapName  {
                type  cml_data_types:CML_STRING_T {
                    length "0..255";
                }
                default "NULL";
                description "dampening route-map name";
            } // END of dampeningRmapName definition.


        } // END of bgpRfdCbCfgParam-container definition.
    } // END of bgpAttrs definition.
    grouping peerAndPeerGroupAttrs {
        description
            "peerAndPeerGroupAttrs";
        container bgpPassword {
            description
                "Configure password for the neighbor";
            leaf password  {
                if-feature feature_list:HAVE_TCP_MD5SIG;
                type  cml_data_types:CML_STRING_T {
                    length "0..255";
                }
                default "NULL";
                description "";
            } // END of password definition.


            leaf authKeyEncryptionAddr  {
                type  CML_BGP_MD5_T;
                description "";
            } // END of authKeyEncryptionAddr definition.


        } // END of bgpPassword-container definition.
    } // END of peerAndPeerGroupAttrs definition.
    grouping bgpAfAttrs {
        description
            "bgpAfAttrs";
        leaf autoSummaryAf  {
            type  cml_data_types:CML_BOOL_T;
            description "auto summary enable/disable";
        } // END of autoSummaryAf definition.


        leaf SetAddPathFlagAf  {
            if-feature feature_list:HAVE_BGP_PIC_CORE_EDGE;
            type  cml_data_types:CML_BOOL_T;
            description "additional-paths flag";
        } // END of SetAddPathFlagAf definition.


        leaf setNwSyncFlagAf  {
            type  cml_data_types:CML_BOOL_T;
            description "network synchronization enable/disable";
        } // END of setNwSyncFlagAf definition.


        leaf tableMapAf  {
            if-feature feature_list:HAVE_BGP_TABLE_MAP;
            type  cml_data_types:CML_STRING_T {
                length "0..255";
            }
            description "table map name";
        } // END of tableMapAf definition.


        leaf tableMapFilterAf  {
            if-feature feature_list:HAVE_BGP_TABLE_MAP;
            type  cml_data_types:CML_BOOL_T;
            description "";
        } // END of tableMapFilterAf definition.


        leaf distanceEbgpAf  {
            type  cml_data_types:CML_UINT8_T {
                 range "1..255";
            }
            default "20";
            description "Distance for routes external to the AS <1-255>";
        } // END of distanceEbgpAf definition.


        leaf distanceIbgpAf  {
            type  cml_data_types:CML_UINT8_T {
                 range "1..255";
            }
            default "200";
            description "Distance for routes internal to the AS <1-255>";
        } // END of distanceIbgpAf definition.


        leaf distanceLocalAf  {
            type  cml_data_types:CML_UINT8_T {
                 range "1..255";
            }
            default "200";
            description "Distance for local routes <1-255>";
        } // END of distanceLocalAf definition.


        leaf setSyncFlagAf  {
            type  cml_data_types:CML_BOOL_T;
            description "synchronization enable/disable";
        } // END of setSyncFlagAf definition.


        leaf ebgpMaxPathAf  {
            type  cml_data_types:CML_INT32_T {
                 range "2..64";
            }
            default "2";
            description "max-paths <2-64>";
        } // END of ebgpMaxPathAf definition.


        leaf ibgpMaxPathAf  {
            type  cml_data_types:CML_INT32_T {
                 range "2..64";
            }
            default "2";
            description "max-paths <2-64>";
        } // END of ibgpMaxPathAf definition.



        list bgpAddressFamilyRedistList {
            key "redistTypeAf";
            description
                "bgpAddressFamilyRedistList";
            leaf redistTypeAf  {
                type  cml_data_types:CML_BGP_REDISTRIBUTE_TYPE_T;
                description "redistribute type";
            } // END of redistTypeAf definition.


            leaf redistRmapNameAf  {
                type  cml_data_types:CML_STRING_T {
                    length "0..255";
                }
                description "route-map name";
            } // END of redistRmapNameAf definition.


        } // End of bgpAddressFamilyRedistList-list

        list bgpRedistOspfAf {
            key "redistOspfNoAf";
            description
                "bgpRedistOspfAf";
            leaf redistOspfNoAf  {
                type  cml_data_types:CML_UINT32_T {
                     range "0..65535";
                }
                description "redistribute ospf number";
            } // END of redistOspfNoAf definition.


            leaf redistOspfRmapAf  {
                type  cml_data_types:CML_STRING_T {
                    length "0..255";
                }
                description "route-map name";
            } // END of redistOspfRmapAf definition.


        } // End of bgpRedistOspfAf-list
        container bgpRfdCbCfgParam {
            description
                "BGP Route Flap Dampening User Configurable Parameters";
            leaf halfLifeAf  {
                type  cml_data_types:CML_UINT32_T {
                     range "1..45";
                }
                default "15";
                description "half life";
            } // END of halfLifeAf definition.


            leaf reusePenaltyAf  {
                type  cml_data_types:CML_UINT32_T {
                     range "1..20000";
                }
                description "reuse Penalty <1-20000>";
            } // END of reusePenaltyAf definition.


            leaf suppressPenaltyAf  {
                type  cml_data_types:CML_UINT32_T {
                     range "1..20000";
                }
                description "";
            } // END of suppressPenaltyAf definition.


            leaf maxSuppressAf  {
                type  cml_data_types:CML_UINT32_T {
                     range "1..255";
                }
                description "max suppress <1-255>";
            } // END of maxSuppressAf definition.


            leaf unreachHalfLifeAf  {
                type  cml_data_types:CML_UINT32_T {
                     range "1..45";
                }
                description "unreachable half life <1-45>";
            } // END of unreachHalfLifeAf definition.


            leaf dampeningRmapNameAf  {
                type  cml_data_types:CML_STRING_T {
                    length "0..255";
                }
                description "dampening route-map name";
            } // END of dampeningRmapNameAf definition.


        } // END of bgpRfdCbCfgParam-container definition.
    } // END of bgpAfAttrs definition.
    grouping networkAfAttrs {
        description
            "networkAfAttrs";

        list bgpAddressFamilyNetworkList {
            key "localAddrAf";
            description
                "bgpAddressFamilyNetworkList";
            leaf localAddrAf  {
                type  cml_data_types:CML_BGP_IP_NETWORK_T {
                    length "0..255";
                }
                description "network address";
            } // END of localAddrAf definition.


            leaf networkRmapNameAf  {
                type  cml_data_types:CML_STRING_T {
                    length "0..255";
                }
                description "route-map name";
            } // END of networkRmapNameAf definition.


            leaf backdoorAf  {
                type  cml_data_types:CML_BOOL_T;
                default false;
                description "backdoor";
            } // END of backdoorAf definition.


            uses nwRunTimeAttr;
        } // End of bgpAddressFamilyNetworkList-list
    } // END of networkAfAttrs definition.
    grouping peerRuntimeAttr {
        description
            "peerRuntimeAttr";
        leaf maxPathIbgp  {
            type  cml_data_types:CML_INT16_T;
            config false;
            description "ECMP multipath ibgp maxpath";
        } // END of maxPathIbgp definition.


        leaf asLocalCount  {
            type  cml_data_types:CML_INT32_T;
            default "1";
            config false;
            description "as-local count";
        } // END of asLocalCount definition.


        leaf cfgMaxPathEbgp  {
            type  cml_data_types:CML_INT16_T;
            config false;
            description "Configured ebgp ECMP multipath";
        } // END of cfgMaxPathEbgp definition.


        leaf maxPathEbgp  {
            type  cml_data_types:CML_INT16_T;
            config false;
            description "ECMP multipath ebgp maxpath";
        } // END of maxPathEbgp definition.


        leaf cfgMaxPathIbgp  {
            type  cml_data_types:CML_INT16_T;
            config false;
            description "Configured ibgp ECMP multipath";
        } // END of cfgMaxPathIbgp definition.


        leaf bgpCommunityCount  {
            type  cml_data_types:CML_INT32_T;
            config false;
            description "bgp community count ";
        } // END of bgpCommunityCount definition.


        leaf peerConfedIdCheck  {
            type  cml_data_types:CML_BOOL_T;
            config false;
            description "Check if AS is part of the confed ";
        } // END of peerConfedIdCheck definition.


        leaf peerAndExtAsnCap  {
            type  cml_data_types:BGP_ADV_RCV_TYPE_T;
            config false;
            description "4-Octet ASN Capability: 1(advertise), 2(receive), 3(both advertise and receive)";
        } // END of peerAndExtAsnCap definition.


        leaf addFamilystring  {
            type  cml_data_types:BGP_ADV_RCV_TYPE_T;
            config false;
            description "Address family IPv4 Unicast: 1(advertise), 2(receive),3(both advertise and receive)";
        } // END of addFamilystring definition.


        leaf keepAliveIn  {
            type  cml_data_types:CML_INT32_T;
            config false;
            description "Keepalive input count";
        } // END of keepAliveIn definition.


        leaf keepAliveOut  {
            type  cml_data_types:CML_INT32_T;
            config false;
            description "Keepalive output count";
        } // END of keepAliveOut definition.


        leaf openMsgIn  {
            type  cml_data_types:CML_INT32_T;
            config false;
            description "Open message input count";
        } // END of openMsgIn definition.


        leaf openMsgOut  {
            type  cml_data_types:CML_INT32_T;
            config false;
            description "Open message output count";
        } // END of openMsgOut definition.


        leaf bgpAsPathCount  {
            type  cml_data_types:CML_INT32_T;
            config false;
            description "BGP AS-PATH entries";
        } // END of bgpAsPathCount definition.


        leaf bgpAsPath4BCount  {
            type  cml_data_types:CML_INT32_T;
            config false;
            description "BGP AS-PATH entries";
        } // END of bgpAsPath4BCount definition.


        leaf updateMsgIn  {
            type  cml_data_types:CML_INT32_T;
            default "0";
            config false;
            description "Update message input count";
        } // END of updateMsgIn definition.


        leaf updateMsgOut  {
            type  cml_data_types:CML_INT32_T;
            default "0";
            config false;
            description "Update message ouput count";
        } // END of updateMsgOut definition.


        leaf nextHopGlobal  {
            type  cml_data_types:CML_STRING_T {
                length "0..255";
            }
            config false;
            description "Nexthop global";
        } // END of nextHopGlobal definition.


        leaf nextHopLocal  {
            type  cml_data_types:CML_STRING_T {
                length "0..255";
            }
            config false;
            description "Nexthop local";
        } // END of nextHopLocal definition.


        leaf peerRemotePort  {
            type  cml_data_types:CML_INT32_T;
            config false;
            description "Peer remote port";
        } // END of peerRemotePort definition.


        leaf peerRemoteAddr  {
            type  cml_data_types:CML_HOSTNAME_T {
                length "0..255";
            }
            config false;
            description "Peer remote address";
        } // END of peerRemoteAddr definition.


        leaf peerLocalHost  {
            type  cml_data_types:CML_HOSTNAME_T {
                length "0..255";
            }
            config false;
            description "Peer Local host";
        } // END of peerLocalHost definition.


        leaf nextHop  {
            type  cml_data_types:CML_HOSTNAME_T {
                length "0..255";
            }
            config false;
            description "Nexthop";
        } // END of nextHop definition.


        leaf peerLocalPort  {
            type  cml_data_types:CML_INT32_T;
            config false;
            description "Peer local port";
        } // END of peerLocalPort definition.


        leaf prefixListCount  {
            type  cml_data_types:CML_INT32_T;
            config false;
            description "Prefix list count";
        } // END of prefixListCount definition.


        leaf defInfoOri  {
            type  cml_data_types:CML_BOOL_T;
            config false;
            description "Default information originate";
        } // END of defInfoOri definition.


        leaf InboundPathPolicy  {
            type  cml_data_types:CML_BOOL_T;
            config false;
            description "Inbound path policy configured";
        } // END of InboundPathPolicy definition.


        leaf OutboundPathPolicy  {
            type  cml_data_types:CML_BOOL_T;
            config false;
            description "Outbound path policy configured";
        } // END of OutboundPathPolicy definition.


        leaf defOriInfoSent  {
            type  cml_data_types:CML_STRING_T {
                length "0..255";
            }
            config false;
            description "default sent";
        } // END of defOriInfoSent definition.


        leaf orfPrefixStr  {
            type  cml_data_types:CML_BOOL_T;
            config false;
            description "Outbound Route Filter (ORF)";
        } // END of orfPrefixStr definition.


        leaf orfPrefixSend  {
            type  cml_data_types:CML_STRING_T {
                length "0..255";
            }
            config false;
            description "Outbound Route Filter (ORF) sent";
        } // END of orfPrefixSend definition.


        leaf orfPrefixCount  {
            type  cml_data_types:CML_STRING_T {
                length "0..255";
            }
            config false;
            description "Outbound Route Filter (ORF) received entries";
        } // END of orfPrefixCount definition.


        leaf orfWaitRefresh  {
            type  cml_data_types:CML_BOOL_T;
            config false;
            description "First update is deferred until ORF or ROUTE-REFRESH is received";
        } // END of orfWaitRefresh definition.


        leaf grstRestart  {
            type  cml_data_types:CML_STRING_T {
                length "0..255";
            }
            config false;
            description "Graceful restart-advertised/received";
        } // END of grstRestart definition.


        leaf afDependentCap  {
            type  cml_data_types:CML_BOOL_T;
            config false;
            description "AF-dependant capabilities";
        } // END of afDependentCap definition.


        leaf peerAfTableVersion  {
            type  cml_data_types:CML_INT32_T;
            config false;
            description "neighbor version";
        } // END of peerAfTableVersion definition.


        leaf peerBgpAfTableVersion  {
            type  cml_data_types:CML_INT32_T;
            config false;
            description "BGP table version";
        } // END of peerBgpAfTableVersion definition.


        leaf fwdStatusPreserve  {
            type  cml_data_types:CML_STRING_T {
                length "0..255";
            }
            config false;
            description "Graceful restart:Forwarding states are being preserved";
        } // END of fwdStatusPreserve definition.


        leaf orfTypePrefix  {
            type  cml_data_types:CML_STRING_T {
                length "0..255";
            }
            config false;
            description "Outbound Route Filter (ORF) type Prefix-list";
        } // END of orfTypePrefix definition.


        leaf orfTypePrefixSendMode  {
            type  cml_data_types:CML_STRING_T {
                length "0..255";
            }
            config false;
            description "ORF Send-mode advertised and received";
        } // END of orfTypePrefixSendMode definition.


        leaf orfTypePrefixRecvMode  {
            type  cml_data_types:CML_STRING_T {
                length "0..255";
            }
            config false;
            description "ORF Receive-mode advertised and received";
        } // END of orfTypePrefixRecvMode definition.


        leaf orfTypePrefixOld  {
            type  cml_data_types:CML_STRING_T {
                length "0..255";
            }
            config false;
            description "Outbound Route Filter (ORF) type Prefix-list";
        } // END of orfTypePrefixOld definition.


        leaf orfTypePrefixSendModeOld  {
            type  cml_data_types:CML_STRING_T {
                length "0..255";
            }
            config false;
            description "peer afi orf cap Send-Mode";
        } // END of orfTypePrefixSendModeOld definition.


        leaf orfTypePrefixRecvModeOld  {
            type  cml_data_types:CML_STRING_T {
                length "0..255";
            }
            config false;
            description "peer afi orf cap Receive-mode";
        } // END of orfTypePrefixRecvModeOld definition.


        leaf peerPrefixCount  {
            type  cml_data_types:CML_INT32_T;
            config false;
            description "accepted prefixes";
        } // END of peerPrefixCount definition.


        leaf peerSendPrefixCount  {
            type  cml_data_types:CML_INT32_T;
            config false;
            description "announced prefixes";
        } // END of peerSendPrefixCount definition.


        leaf peerFlagShutDown  {
            type  cml_data_types:CML_PEERFLAG_SHUTDOWN_T;
            config false;
            description "peer flag shutdown status: 1(Idle), 2(Connect), 3(Active), 4(Opensent), 5(Openconfirm), 6(Established), 7(Idle Admin), 8(Idle PfxCt), 9(Idle G-shut)";
        } // END of peerFlagShutDown definition.


        leaf peerCount  {
            type  cml_data_types:CML_INT32_T;
            config false;
            description "peer count";
        } // END of peerCount definition.


        leaf peerNotifyInfo  {
            type  cml_data_types:CML_BOOL_T;
            config false;
            description "BGP notify open error";
        } // END of peerNotifyInfo definition.


        leaf peerNotifyDirect  {
            type  cml_data_types:CML_BOOL_T;
            config false;
            description "Last reset due to notification type 0(sent), 1(received)";
        } // END of peerNotifyDirect definition.


        leaf peerNotifyLastReset  {
            type  cml_data_types:CML_STRING_T {
                length "0..255";
            }
            config false;
            description "Last reset in week:day:hour:min:sec format string";
        } // END of peerNotifyLastReset definition.


        leaf notifyCodeStr  {
            type  cml_data_types:CML_STRING_T {
                length "0..255";
            }
            config false;
            description "Notification Error Message code and subcode";
        } // END of notifyCodeStr definition.


        leaf bgpConnection  {
            type  cml_data_types:CML_BGP_CONNECTION_TYPE_T;
            config false;
            description "Connection: shared network, non shared network";
        } // END of bgpConnection definition.


        leaf nextConnectTimer  {
            type  cml_data_types:CML_INT32_T;
            config false;
            description "Next connect timer due in seconds";
        } // END of nextConnectTimer definition.


        leaf conEstCount  {
            type  cml_data_types:CML_INT32_T;
            config false;
            description "BGP state established count";
        } // END of conEstCount definition.


        leaf conDroppedCount  {
            type  cml_data_types:CML_INT32_T;
            config false;
            description "BGP state drop count";
        } // END of conDroppedCount definition.


        leaf peerGstatusAcceptGrst  {
            type  cml_data_types:CML_STRING_T {
                length "0..255";
            }
            config false;
            description "Graceful Restart Status";
        } // END of peerGstatusAcceptGrst definition.


        leaf peerGrstRestart  {
            type  cml_data_types:CML_INT32_T;
            config false;
            description "Remote restart-time in sec";
        } // END of peerGrstRestart definition.


        leaf bpfEstUpTime  {
            type  cml_data_types:CML_GAUGE32_T;
            config false;
            description "up time";
        } // END of bpfEstUpTime definition.


        leaf lastReadTime  {
            type  cml_data_types:CML_GAUGE32_T;
            config false;
            description "Last read time";
        } // END of lastReadTime definition.


        leaf bpfState  {
            type  cml_data_types:CML_BGP_PEER_STATUS_T;
            config false;
            description "The bgp state of the session with following representation 1(Idle), 2(Connect), 3(Active), 4(Opensent), 5(Openconfirm), 6(Established)
        ";
        } // END of bpfState definition.


        leaf peerLinkType  {
            type  cml_data_types:CML_BGP_LINK_TYPE_T;
            config false;
            description "Link type: internal, external";
        } // END of peerLinkType definition.


        leaf hopAwayCount  {
            type  cml_data_types:CML_INT32_T;
            config false;
            description "External BGP neighbor may be up to given hops away.";
        } // END of hopAwayCount definition.


        leaf peerRouterId  {
            type  cml_data_types:CML_IPV4_PREFIX_T;
            config false;
            description "peer router id";
        } // END of peerRouterId definition.


        leaf recvPacketCount  {
            type  cml_data_types:CML_INT32_T;
            config false;
            description "Received messages";
        } // END of recvPacketCount definition.


        leaf notificationIn  {
            type  cml_data_types:CML_INT32_T;
            config false;
            description "Notify input count";
        } // END of notificationIn definition.


        leaf notificationOut  {
            type  cml_data_types:CML_INT32_T;
            config false;
            description "Notify output count";
        } // END of notificationOut definition.


        leaf pktInQue  {
            type  cml_data_types:CML_INT32_T;
            config false;
            description "messages queued to be processed from the neighbor";
        } // END of pktInQue definition.


        leaf pktOutQue  {
            type  cml_data_types:CML_INT32_T;
            config false;
            description "messages queued to be sent to the neighbor";
        } // END of pktOutQue definition.


        leaf sentPacketCount  {
            type  cml_data_types:CML_INT32_T;
            config false;
            description "Sent messages";
        } // END of sentPacketCount definition.


        leaf refreshRecvPacketCount  {
            type  cml_data_types:CML_INT32_T;
            config false;
            description "Route Refresh input count";
        } // END of refreshRecvPacketCount definition.


        leaf refreshSentPacketCount  {
            type  cml_data_types:CML_INT32_T;
            config false;
            description "Route Refresh output count";
        } // END of refreshSentPacketCount definition.


        leaf advertisementInterval  {
            type  cml_data_types:CML_INT32_T;
            config false;
            description "Minimum time between advertisement runs in seconds";
        } // END of advertisementInterval definition.


        leaf peerHoldTimeRun  {
            type  cml_data_types:CML_INT32_T;
            config false;
            description "hold time in seconds";
        } // END of peerHoldTimeRun definition.


        leaf peerKeepAliveRun  {
            type  cml_data_types:CML_INT32_T;
            config false;
            description "keepalive interval in seconds";
        } // END of peerKeepAliveRun definition.


        leaf advertisedCapability  {
            type  cml_data_types:CML_STRING_T {
                length "0..255";
            }
            config false;
            description "Advertised capability";
        } // END of advertisedCapability definition.


        leaf advCapabilityRefresh  {
            type  cml_data_types:CML_STRING_T {
                length "0..255";
            }
            config false;
            description "Route Refresh";
        } // END of advCapabilityRefresh definition.


        leaf noIfBinding  {
            type  cml_data_types:CML_BOOL_T;
            config false;
            description "No Interfaces bound to BGP Instance";
        } // END of noIfBinding definition.


        leaf advAddPathCapabilitySend  {
            if-feature feature_list:HAVE_BGP_ADD_PATH;
            type  cml_data_types:CML_STRING_T {
                length "0..255";
            }
            config false;
            description "Add-Path Send Capability";
        } // END of advAddPathCapabilitySend definition.


        leaf advAddPathCapabilityRec  {
            if-feature feature_list:HAVE_BGP_ADD_PATH;
            type  cml_data_types:CML_STRING_T {
                length "0..255";
            }
            config false;
            description "Add-Path Receive Capability";
        } // END of advAddPathCapabilityRec definition.


        leaf advCapablityIpv4Multicast  {
            type  cml_data_types:CML_STRING_T {
                length "0..255";
            }
            config false;
            description "IPV4 Multicast neighbour Capability";
        } // END of advCapablityIpv4Multicast definition.


        leaf advCapablityVpnv4Unicast  {
            type  cml_data_types:CML_STRING_T {
                length "0..255";
            }
            config false;
            description "Vpnv4 Unicast neighbour Capability";
        } // END of advCapablityVpnv4Unicast definition.


        leaf advCapablityVpnv6Unicast  {
            type  cml_data_types:CML_STRING_T {
                length "0..255";
            }
            config false;
            description "Vpnv6 Unicast neighbour Capability";
        } // END of advCapablityVpnv6Unicast definition.


        leaf advCapablityRtfilterUnicast  {
            type  cml_data_types:CML_STRING_T {
                length "0..255";
            }
            config false;
            description "Rtfilter Unicast neighbour Capability";
        } // END of advCapablityRtfilterUnicast definition.


        leaf advCapablityL2vpnEvpn  {
            type  cml_data_types:CML_STRING_T {
                length "0..255";
            }
            config false;
            description "L2vpn Evpn neighbour Capability";
        } // END of advCapablityL2vpnEvpn definition.


        leaf advCapablityIpv6Unicast  {
            type  cml_data_types:CML_STRING_T {
                length "0..255";
            }
            config false;
            description "Ipv6 Unicast neighbour Capability";
        } // END of advCapablityIpv6Unicast definition.


        leaf advCapablityIpv6Multicast  {
            type  cml_data_types:CML_STRING_T {
                length "0..255";
            }
            config false;
            description "Ipv6 Multicast neighbour Capability";
        } // END of advCapablityIpv6Multicast definition.


        leaf advCapablityIpv6LabelUnicast  {
            type  cml_data_types:CML_STRING_T {
                length "0..255";
            }
            config false;
            description "Ipv6 Label Unicast neighbour Capability";
        } // END of advCapablityIpv6LabelUnicast definition.


        leaf bgpLuInLabel  {
            type  cml_data_types:CML_INT32_T;
            config false;
            description "bgp LU In Label";
        } // END of bgpLuInLabel definition.


        leaf bgpLuOutLabel  {
            type  cml_data_types:CML_INT32_T;
            config false;
            description "bgp LU Out Label";
        } // END of bgpLuOutLabel definition.



        list peerPrefix {
            key "prefixEntrySeq";
            config false;
            description
                "peerPrefix";
            leaf prefixEntrySeq  {
                type  cml_data_types:CML_INT32_T;
                description "Prefix sequence number";
            } // END of prefixEntrySeq definition.


            leaf prefixEntryType  {
                type  cml_data_types:CML_BGP_PREFIX_ENTRY_TYPE_T;
                description "Prefix type 1(no_match), 2(deny), 3(permit)";
            } // END of prefixEntryType definition.


            leaf prefixEntryGe  {
                type  cml_data_types:CML_INT32_T;
                description "Maximum prefix length to be matched";
            } // END of prefixEntryGe definition.


            leaf prefixEntryLe  {
                type  cml_data_types:CML_INT32_T;
                description "Minimum prefix length to be matched";
            } // END of prefixEntryLe definition.


            leaf peerPrefixLen  {
                type  cml_data_types:CML_INT32_T;
                description "Prefix length";
            } // END of peerPrefixLen definition.


        } // End of peerPrefix-list
        container bgpPeerIndex {
            config false;
            description
                "BGP Peer Adj_RIBs_out index";
            leaf peerIndex  {
                type  cml_data_types:CML_INT32_T;
                description "Peer index";
            } // END of peerIndex definition.


            leaf peerOffset  {
                type  cml_data_types:CML_INT32_T;
                description "Peer offset";
            } // END of peerOffset definition.


            leaf peerMask  {
                type  cml_data_types:CML_STRING_T {
                    length "0..255";
                }
                description "Peer mask";
            } // END of peerMask definition.


        } // END of bgpPeerIndex-container definition.
    } // END of peerRuntimeAttr definition.
    grouping peerAdjInRouteAttrs {
        description
            "peerAdjInRouteAttrs";

        list peerAdjInRoute {
            key "networkAddr";
            config false;
            description
                "peerAdjInRoute";
            leaf networkAddr  {
                type  cml_data_types:CML_BGP_IP_NETWORK_T {
                    length "0..255";
                }
                description "Peer Adj-In Network address";
            } // END of networkAddr definition.



            list nextHop {
                key "nextHopAddr";
                config false;
                description
                    "nextHop";
                leaf nextHopAddr  {
                    type  cml_data_types:CML_HOSTNAME_T {
                        length "0..255";
                    }
                    description " Peer Adj-In Nexthop address";
                } // END of nextHopAddr definition.


                uses nextHopRunTimeAttr;
            } // End of nextHop-list
        } // End of peerAdjInRoute-list
    } // END of peerAdjInRouteAttrs definition.
    grouping peerAdjOutRouteAttrs {
        description
            "peerAdjOutRouteAttrs";

        list peerAdjOutRoute {
            key "networkAddr";
            config false;
            description
                "peerAdjOutRoute";
            leaf networkAddr  {
                type  cml_data_types:CML_BGP_IP_NETWORK_T {
                    length "0..255";
                }
                description "Peer Adj-Out Network address";
            } // END of networkAddr definition.



            list nextHop {
                key "nextHopAddr";
                config false;
                description
                    "nextHop";
                leaf nextHopAddr  {
                    type  cml_data_types:CML_HOSTNAME_T {
                        length "0..255";
                    }
                    description "Peer Adj-Out Nexthop address";
                } // END of nextHopAddr definition.


                uses nextHopRunTimeAttr;
            } // End of nextHop-list
        } // End of peerAdjOutRoute-list
    } // END of peerAdjOutRouteAttrs definition.
    grouping nextHopRunTimeAttr {
        description
            "nextHopRunTimeAttr";
        leaf dampInfoTimes  {
            type  cml_data_types:CML_STRING_T {
                length "0..255";
            }
            config false;
            description "Dampinfo time";
        } // END of dampInfoTimes definition.


        leaf peerNtwkWeight  {
            type  cml_data_types:CML_INT32_T;
            config false;
            description "BGP attribute weight";
        } // END of peerNtwkWeight definition.


        leaf flapTimeReuseList  {
            type  cml_data_types:CML_STRING_T {
                length "0..255";
            }
            config false;
            description "Dampinfo: reuse in";
        } // END of flapTimeReuseList definition.


        leaf flapRecordDuration  {
            type  cml_data_types:CML_STRING_T {
                length "0..255";
            }
            config false;
            description "Flap record duration";
        } // END of flapRecordDuration definition.


        leaf dampTimeToReuse  {
            type  cml_data_types:CML_STRING_T {
                length "0..255";
            }
            config false;
            description "Damp time to reuse";
        } // END of dampTimeToReuse definition.


        leaf medFlagType  {
            type  cml_data_types:CML_STRING_T {
                length "0..255";
            }
            config false;
            description "MED flag type";
        } // END of medFlagType definition.


        leaf bgpMedVal  {
            type  cml_data_types:CML_INT32_T;
            config false;
            description "Metric";
        } // END of bgpMedVal definition.


        leaf bgpAsPathStr  {
            type  cml_data_types:CML_STRING_T {
                length "0..255";
            }
            config false;
            description "AS-path";
        } // END of bgpAsPathStr definition.


        leaf bgpAsPath4BStr  {
            type  cml_data_types:CML_STRING_T {
                length "0..255";
            }
            config false;
            description "AS-path for extended asn capability";
        } // END of bgpAsPath4BStr definition.


        leaf bgpAsPath4BOrigin  {
            type  cml_data_types:CML_BGP_ORIGIN_T;
            config false;
            description "Origin: 0(IGP), 1(EGP), 2(Incomplete)";
        } // END of bgpAsPath4BOrigin definition.


        leaf ibgpMetricRoute  {
            type  cml_data_types:CML_INT32_T;
            config false;
            description "IGP metric value for route selection.";
        } // END of ibgpMetricRoute definition.


        leaf aggregateAsRoute  {
            type  cml_data_types:CML_INT32_T;
            config false;
            description "aggregated by as";
        } // END of aggregateAsRoute definition.


        leaf aggregatorAddrRoute  {
            type  cml_data_types:CML_HOSTNAME_T {
                length "0..255";
            }
            config false;
            description "aggregated by address";
        } // END of aggregatorAddrRoute definition.


        leaf networkRemoteAddrRoute  {
            type  cml_data_types:CML_HOSTNAME_T {
                length "0..255";
            }
            config false;
            description "Remote id";
        } // END of networkRemoteAddrRoute definition.


        leaf originatorIdRoute  {
            type  cml_data_types:CML_STRING_T {
                length "0..255";
            }
            config false;
            description "Originator id";
        } // END of originatorIdRoute definition.


        leaf routePeerAddrRoute  {
            type  cml_data_types:CML_HOSTNAME_T {
                length "0..255";
            }
            config false;
            description "address of the peer";
        } // END of routePeerAddrRoute definition.


        leaf routeLocalPrefRoute  {
            type  cml_data_types:CML_INT32_T;
            config false;
            description "local-preference";
        } // END of routeLocalPrefRoute definition.


        leaf briLabelRoute  {
            type  cml_data_types:CML_INT32_T;
            config false;
            description "label";
        } // END of briLabelRoute definition.


        leaf routeCommNameRoute  {
            type  cml_data_types:CML_STRING_T {
                length "0..255";
            }
            config false;
            description "Community";
        } // END of routeCommNameRoute definition.


        leaf clusterListRoute  {
            type  cml_data_types:CML_HOSTNAME_T {
                length "0..255";
            }
            config false;
            description "Cluster list";
        } // END of clusterListRoute definition.


        leaf routeGetPenaltyRoute  {
            type  cml_data_types:CML_INT32_T;
            config false;
            description "Dampinfo: penalty";
        } // END of routeGetPenaltyRoute definition.


        leaf routeGetFlapCountRoute  {
            type  cml_data_types:CML_INT32_T;
            config false;
            description "Dampinfo: no of times flapped ";
        } // END of routeGetFlapCountRoute definition.


        leaf lastUpdateRoute  {
            type  cml_data_types:CML_STRING_T {
                length "0..255";
            }
            config false;
            description "Last Update";
        } // END of lastUpdateRoute definition.


        leaf reflectorClientRoute  {
            type  cml_data_types:CML_STRING_T {
                length "0..255";
            }
            config false;
            description "Received from a RR-client";
        } // END of reflectorClientRoute definition.


        leaf routeDampeningFlagRoute  {
            type  cml_data_types:CML_STRING_T {
                length "0..255";
            }
            config false;
            description "suppressed due to dampening";
        } // END of routeDampeningFlagRoute definition.


        leaf historyRoute  {
            type  cml_data_types:CML_STRING_T {
                length "0..255";
            }
            config false;
            description "history entry";
        } // END of historyRoute definition.


        leaf nhopValidRoute  {
            type  cml_data_types:CML_STRING_T {
                length "0..255";
            }
            config false;
            description "Inactive redistribute routes";
        } // END of nhopValidRoute definition.


        leaf routeMedFlagTypeRoute  {
            type  cml_data_types:CML_BOOL_T;
            config false;
            description "if REMOVE-MED flag is enabled";
        } // END of routeMedFlagTypeRoute definition.


        leaf routeValidStateRoute  {
            type  cml_data_types:CML_BOOL_T;
            config false;
            description "Check if state is valid";
        } // END of routeValidStateRoute definition.


        leaf bgpInfoStaleRoute  {
            type  cml_data_types:CML_BOOL_T;
            config false;
            description "Check BGP info stale";
        } // END of bgpInfoStaleRoute definition.


        leaf bgpInfoTypeRoute  {
            type  cml_data_types:CML_BGP_RI_TYPE_T;
            config false;
            description "BGP route info type - internal, confed-external, external, sourced, aggregated, local";
        } // END of bgpInfoTypeRoute definition.


        leaf ecmpMultiCandidateRoute  {
            type  cml_data_types:CML_BOOL_T;
            config false;
            description "if ecmp multipath candidate";
        } // END of ecmpMultiCandidateRoute definition.


        leaf multiInstalledRoute  {
            type  cml_data_types:CML_BOOL_T;
            config false;
            description "if bgp info multi install- 1(installed)";
        } // END of multiInstalledRoute definition.


        leaf routeSyncFlagRoute  {
            type  cml_data_types:CML_BOOL_T;
            config false;
            description "BGP info status - 0(not synchronized) 1(synchronized)";
        } // END of routeSyncFlagRoute definition.


        leaf atomicAggregateRoute  {
            type  cml_data_types:CML_BOOL_T;
            config false;
            description "atomic-aggregate";
        } // END of atomicAggregateRoute definition.


        leaf bgpInfoSelectedRoute  {
            type  cml_data_types:CML_BOOL_T;
            config false;
            description "BGP info best selected route";
        } // END of bgpInfoSelectedRoute definition.


        leaf bgpTxPathId  {
            if-feature feature_list:HAVE_BGP_ADD_PATH;
            type  cml_data_types:CML_UINT8_T;
            config false;
            description "bgp add path Tx Id";
        } // END of bgpTxPathId definition.


        leaf bgpRxPathId  {
            if-feature feature_list:HAVE_BGP_ADD_PATH;
            type  cml_data_types:CML_UINT8_T;
            config false;
            description "bgp add path Rx Id";
        } // END of bgpRxPathId definition.


        leaf advCapablityIpv4Multicast  {
            type  cml_data_types:CML_STRING_T {
                length "0..255";
            }
            config false;
            description "IPV4 Multicast neighbour Capability";
        } // END of advCapablityIpv4Multicast definition.


        leaf advCapablityVpnv4Unicast  {
            type  cml_data_types:CML_STRING_T {
                length "0..255";
            }
            config false;
            description "Vpnv4 Unicast neighbour Capability";
        } // END of advCapablityVpnv4Unicast definition.


        leaf advCapablityRtfilterUnicast  {
            type  cml_data_types:CML_STRING_T {
                length "0..255";
            }
            config false;
            description "Rtfilter Unicast neighbour Capability";
        } // END of advCapablityRtfilterUnicast definition.


        leaf advCapablityL2vpnEvpn  {
            type  cml_data_types:CML_STRING_T {
                length "0..255";
            }
            config false;
            description "L2vpn Evpn neighbour Capability";
        } // END of advCapablityL2vpnEvpn definition.


        leaf advCapablityIpv6Unicast  {
            type  cml_data_types:CML_STRING_T {
                length "0..255";
            }
            config false;
            description "Ipv6 Unicast neighbour Capability";
        } // END of advCapablityIpv6Unicast definition.


        leaf advCapablityIpv6Multicast  {
            type  cml_data_types:CML_STRING_T {
                length "0..255";
            }
            config false;
            description "Ipv6 Multicast neighbour Capability";
        } // END of advCapablityIpv6Multicast definition.


        leaf advCapablityIpv6LabelUnicast  {
            type  cml_data_types:CML_STRING_T {
                length "0..255";
            }
            config false;
            description "Ipv6 Label Unicast neighbour Capability";
        } // END of advCapablityIpv6LabelUnicast definition.


    } // END of nextHopRunTimeAttr definition.
    grouping nwRunTimeAttr {
        description
            "nwRunTimeAttr";
        leaf ntwkPathCountRoute  {
            type  cml_data_types:CML_INT32_T;
            config false;
            description "Network path count";
        } // END of ntwkPathCountRoute definition.


        leaf noAdvertiseRoute  {
            type  cml_data_types:CML_STRING_T {
                length "0..255";
            }
            config false;
            description "";
        } // END of noAdvertiseRoute definition.


        leaf noExportRoute  {
            type  cml_data_types:CML_BOOL_T;
            config false;
            description "not advertised to EBGP peer";
        } // END of noExportRoute definition.


        leaf localAsRoute  {
            type  cml_data_types:CML_BOOL_T;
            config false;
            description "not advertised outside local AS";
        } // END of localAsRoute definition.


        leaf suppressRoute  {
            type  cml_data_types:CML_BOOL_T;
            config false;
            description "Advertisements suppressed by an aggregate.";
        } // END of suppressRoute definition.


        leaf ntwkBestPathCountRoute  {
            type  cml_data_types:CML_INT32_T;
            config false;
            description "best";
        } // END of ntwkBestPathCountRoute definition.


        leaf defIPRoutingTbl  {
            type  cml_data_types:CML_STRING_T {
                length "0..255";
            }
            config false;
            description "table Default-IP-Routing-Table";
        } // END of defIPRoutingTbl definition.


        leaf-list advNonPeerGroupAddr  {
            type  cml_data_types:CML_HOSTNAME_T {
                length "0..255";
            }
            config false;
            description "Advertised non peer-group peers.";
        } // END of advNonPeerGroupAddr definition.


        leaf advPeerGroupNameRoute  {
            type  cml_data_types:CML_STRING_T {
                length "0..255";
            }
            config false;
            description "Advertised peer-groups";
        } // END of advPeerGroupNameRoute definition.


        leaf advAnyPeer  {
            type  cml_data_types:CML_STRING_T {
                length "0..255";
            }
            config false;
            description "Not advertised to any peer";
        } // END of advAnyPeer definition.


        leaf rdStr  {
            if-feature feature_list:HAVE_MPLS;
            type  cml_data_types:CML_STRING_T {
                length "0..255";
            }
            config false;
            description "route distinguisher";
        } // END of rdStr definition.



        list nextHop {
            key "nextHopAddr";
            config false;
            description
                "nextHop";
            leaf nextHopAddr  {
                type  cml_data_types:CML_HOSTNAME_T {
                    length "0..255";
                }
                description "NextHop Address";
            } // END of nextHopAddr definition.


            uses nextHopRunTimeAttr;
        } // End of nextHop-list
    } // END of nwRunTimeAttr definition.
    grouping peerVrfAttrs {
        description
            "peerVrfAttrs";
        leaf bgpPortAf  {
            type  cml_data_types:CML_UINT16_T {
                 range "0..65535";
            }
            default "179";
            description "tcp port number <0-65535>";
        } // END of bgpPortAf definition.


        leaf peerActivateAf  {
            type  cml_data_types:CML_BOOL_T;
            description "Activate/Deactivate neighbor";
        } // END of peerActivateAf definition.


        leaf defaultPeerRmapNameAf  {
            type  cml_data_types:CML_BOOL_T;
            description "default originate";
        } // END of defaultPeerRmapNameAf definition.


        leaf peerRmapOriNameAf  {
            type  cml_data_types:CML_STRING_T {
                length "0..255";
            }
            description "Route-map name";
        } // END of peerRmapOriNameAf definition.


        leaf softReconfigInboundAf  {
            type  cml_data_types:CML_BOOL_T;
            description "soft-reconfiguration inbound";
        } // END of softReconfigInboundAf definition.


        leaf weightAf  {
            type  cml_data_types:CML_UINT16_T {
                 range "0..65535";
            }
            default "0";
            description "Weight for routes <0-65535>";
        } // END of weightAf definition.


        leaf peerRouteReflectorAf  {
            type  cml_data_types:CML_BOOL_T;
            description "route-reflector-client";
        } // END of peerRouteReflectorAf definition.


        leaf peerRemovePvtAsAf  {
            type  cml_data_types:CML_BOOL_T;
            description "remove private AS";
        } // END of peerRemovePvtAsAf definition.


        leaf sendCommunityAf  {
            type  cml_data_types:CML_BOOL_T;
            description "send-community";
        } // END of sendCommunityAf definition.


        leaf sendCommunityTypeAf  {
            type  cml_data_types:CML_BGP_SEND_COMMU_TYPE_T;
            description "send-community type";
        } // END of sendCommunityTypeAf definition.


        leaf neighborAttrUnchangedAf  {
            type  cml_data_types:CML_ATTRIBUTE_UNCHANGED_TYPE_T;
            description "attribute-unchanged type";
        } // END of neighborAttrUnchangedAf definition.


        leaf orfPrefixOptAf  {
            type  cml_data_types:CML_BGP_ORF_PREFIX_TYPE_T;
            description "orf capability";
        } // END of orfPrefixOptAf definition.


        leaf peerAllowEbgpVpnAf  {
            if-feature feature_list:HAVE_VRF;
            type  cml_data_types:CML_BOOL_T;
            description "Allow VPN Routes";
        } // END of peerAllowEbgpVpnAf definition.


        leaf allowAsNumAf  {
            type  cml_data_types:CML_UINT32_T {
                 range "1..10";
            }
            default "3";
            description "Allow AS number <1-10>";
        } // END of allowAsNumAf definition.


        leaf neighborCapabilityGrstAf  {
            type  cml_data_types:CML_BOOL_T;
            description "graceful restart";
        } // END of neighborCapabilityGrstAf definition.


        leaf peerGroupTagAf  {
            type  cml_data_types:CML_STRING_T {
                length "0..255";
            }
            description "BGP peer group name";
        } // END of peerGroupTagAf definition.


        leaf maxPrefixesAf  {
            type  cml_data_types:CML_UINT32_T {
                 range "1..4294967295";
            }
            description "Maximum number of prefixes <1-4294967295>";
        } // END of maxPrefixesAf definition.


        leaf stopUpdateAf  {
            type  cml_data_types:CML_BOOL_T;
            description "stop update";
        } // END of stopUpdateAf definition.


        leaf maxPrefixeWarningAf  {
            type  cml_data_types:CML_BOOL_T;
            description "warning-only";
        } // END of maxPrefixeWarningAf definition.


        leaf thresholdAf  {
            type  cml_data_types:CML_UINT8_T {
                 range "1..100";
            }
            default "75";
            description "Threshold-value in percent <1-100>";
        } // END of thresholdAf definition.


        leaf warningAf  {
            type  cml_data_types:CML_BOOL_T;
            description "Throw warning if exceeds threshold-value Yes/No flag";
        } // END of warningAf definition.


        leaf unSuppressAclInfoAf  {
            type  cml_data_types:CML_STRING_T {
                length "0..255";
            }
            description "unsuppress map name";
        } // END of unSuppressAclInfoAf definition.



        list bgpDlistFilter {
            key "distributeListDirectionAf";
            description
                "bgpDlistFilter";
            leaf aclInfoAf  {
                type  cml_data_types:CML_STRING_T {
                    length "0..255";
                }
                mandatory true;
                description "Access-list numbe";
            } // END of aclInfoAf definition.


            leaf distributeListDirectionAf  {
                type  cml_data_types:CML_BGP_DISTRIBUTE_LIST_ACTION_T;
                description "Direction of the filter (0=FILTER_IN |1=FILTER_OUT)";
            } // END of distributeListDirectionAf definition.


        } // End of bgpDlistFilter-list

        list bgpAslistFilter {
            key "asListDirectionAf";
            description
                "bgpAslistFilter";
            leaf asListAclInfoAf  {
                type  cml_data_types:CML_STRING_T {
                    length "0..255";
                }
                mandatory true;
                description "Access-list number";
            } // END of asListAclInfoAf definition.


            leaf asListDirectionAf  {
                type  cml_data_types:CML_BGP_DISTRIBUTE_LIST_ACTION_T;
                description "Direction of the filter (0=FILTER_IN |1=FILTER_OUT)";
            } // END of asListDirectionAf definition.


        } // End of bgpAslistFilter-list

        list bgpPlistFilter {
            key "prefixListDirectionAf";
            description
                "bgpPlistFilter";
            leaf prefixListAclInfoAf  {
                type  cml_data_types:CML_STRING_T {
                    length "0..255";
                }
                mandatory true;
                description "Access-list number";
            } // END of prefixListAclInfoAf definition.


            leaf prefixListDirectionAf  {
                type  cml_data_types:CML_BGP_DISTRIBUTE_LIST_ACTION_T;
                description "Direction of the filter (0=FILTER_IN |1=FILTER_OUT)";
            } // END of prefixListDirectionAf definition.


        } // End of bgpPlistFilter-list

        list bgpRmapFilter {
            key "peerRmapDirectionAf";
            description
                "bgpRmapFilter";
            leaf peerRmapNameAf  {
                type  cml_data_types:CML_STRING_T {
                    length "0..255";
                }
                mandatory true;
                description "route map";
            } // END of peerRmapNameAf definition.


            leaf peerRmapDirectionAf  {
                type  cml_data_types:CML_BGP_DISTRIBUTE_LIST_ACTION_T;
                description "Direction of the filter (0=FILTER_IN |1=FILTER_OUT)";
            } // END of peerRmapDirectionAf definition.


        } // End of bgpRmapFilter-list
    } // END of peerVrfAttrs definition.

    grouping  evpnServiceType-grouping {
    description
        "EVPN VLAN Service Type";
    container evpnServiceType {
        description
            "EVPN VLAN Service Type";
        leaf serviceType  {
            type  cml_data_types:CML_EVPN_SERVICE_TYPE_T;
            description "Vlan-Based EVPN-Service Type";
        } // END of serviceType definition.


    } // END of evpnServiceType-container definition.
    } // END of evpnServiceType-container definition.

    grouping  bgpGlobal-grouping {
    description
        "BGP global commands";
    container bgpGlobal {
        description
            "BGP global commands";
        leaf snmpRestart  {
            if-feature feature_list:HAVE_SNMP;
            type  cml_data_types:CML_BOOL_T;
            description "snmp restart";
        } // END of snmpRestart definition.


        leaf aggNexthop  {
            type  cml_data_types:CML_BOOL_T;
            description "aggregate nexthop check";
        } // END of aggNexthop definition.


        leaf pathSelect  {
            type  cml_data_types:CML_BOOL_T;
            description "RFC1771 path selection";
        } // END of pathSelect definition.


        leaf setDisableAdjOut  {
            type  cml_data_types:CML_BOOL_T;
            description "disable adj out";
        } // END of setDisableAdjOut definition.


        leaf setExtAsnCap  {
            if-feature feature_list:HAVE_EXT_CAP_ASN;
            type  cml_data_types:CML_BOOL_T;
            description "extended asn cap";
        } // END of setExtAsnCap definition.


        leaf setNexthopTriggerEnable  {
            type  cml_data_types:CML_BOOL_T;
            description "bgp nexthop";
        } // END of setNexthopTriggerEnable definition.


        leaf delayInterval  {
            type  cml_data_types:CML_UINT8_T {
                 range "1..100";
            }
            default "5";
            description "nexthop delay";
        } // END of delayInterval definition.


        leaf rfc1771StrictSet  {
            type  cml_data_types:CML_BOOL_T;
            description "rfc1771 strict";
        } // END of rfc1771StrictSet definition.


        leaf multiInstance  {
            type  cml_data_types:CML_BOOL_T;
            description "multiple-instance";
        } // END of multiInstance definition.


        leaf allowSamePeer  {
            type  cml_data_types:CML_BOOL_T;
            description "allow-same-peer";
        } // END of allowSamePeer definition.


        leaf configType  {
            type  cml_data_types:CML_BGP_CONFIG_T;
            description "config-type (standard|zebos)";
        } // END of configType definition.



        list mplsl3Vpn {
            key "afsName";
            description
                "mplsl3Vpn";
            leaf afsName  {
                type  cml_data_types:CML_AF_CONFIG_T;
                description "";
            } // END of afsName definition.


            leaf vrfsName  {
                type  cml_data_types:CML_BGP_VRF_TYPE_T {
                    length "0..255";
                }
                description "";
            } // END of vrfsName definition.


            leaf LabelAllocType  {
                type  cml_data_types:CML_BGP_VRF_MODE_T;
                description "";
            } // END of LabelAllocType definition.


        } // End of mplsl3Vpn-list

        list communityList {
            key "commListName";
            description
                "communityList";
            leaf commListName  {
                type  cml_data_types:CML_STRING_T {
                    length "0..255";
                }
                description "Community list name";
            } // END of commListName definition.



            list commListAction {
                key "action";
                description
                    "commListAction";
                leaf action  {
                    type  cml_data_types:CML_BGP_COMMUNITY_LIST_ACTION_T;
                    description "community type";
                } // END of action definition.



                list commListVal {
                    key "commListValue";
                    description
                        "commListVal";
                    leaf commListValue  {
                        type  cml_data_types:CML_STRING_T {
                            length "0..255";

                            pattern "[^?'=,>|]*";
                        }
                        description "Community value";
                    } // END of commListValue definition.


                } // End of commListVal-list
            } // End of commListAction-list
        } // End of communityList-list

        list communityListNo {
            key "commListStandNo";
            description
                "communityListNo";
            leaf commListStandNo  {
                type  cml_data_types:CML_UINT32_T {
                     range "1..99";
                }
                description "Community list standard number";
            } // END of commListStandNo definition.



            list commListAction {
                key "action";
                description
                    "commListAction";
                leaf action  {
                    type  cml_data_types:CML_BGP_COMMUNITY_LIST_ACTION_T;
                    description "Community list type";
                } // END of action definition.


            } // End of commListAction-list

            list actionListVal {
                key "actionListVal";
                description
                    "actionListVal";
                leaf actionListVal  {
                    type  cml_data_types:CML_BGP_COMMUNITY_LIST_ACTION_T;
                    description "Community list type";
                } // END of actionListVal definition.



                list commListVal {
                    key "commListValue";
                    description
                        "commListVal";
                    leaf commListValue  {
                        type  cml_data_types:CML_STRING_T {
                            length "0..255";

                            pattern "[^?'=,>|]*";
                        }
                        description "Community list value";
                    } // END of commListValue definition.


                } // End of commListVal-list
            } // End of actionListVal-list
        } // End of communityListNo-list

        list communityListStand {
            key "commListName";
            description
                "communityListStand";
            leaf commListName  {
                type  cml_data_types:CML_STRING_T {
                    length "0..255";
                }
                description "Community list standard name";
            } // END of commListName definition.



            list commListAction {
                key "actionStandardList";
                description
                    "commListAction";
                leaf actionStandardList  {
                    type  cml_data_types:CML_BGP_COMMUNITY_LIST_ACTION_T;
                    description "Community list type";
                } // END of actionStandardList definition.


            } // End of commListAction-list

            list actionListVal {
                key "actionListVal";
                description
                    "actionListVal";
                leaf actionListVal  {
                    type  cml_data_types:CML_BGP_COMMUNITY_LIST_ACTION_T;
                    description "Community list type";
                } // END of actionListVal definition.



                list commListVal {
                    key "commListValue";
                    description
                        "commListVal";
                    leaf commListValue  {
                        type  cml_data_types:CML_STRING_T {
                            length "0..255";

                            pattern "[^?'=,>|]*";
                        }
                        description "Community list value";
                    } // END of commListValue definition.


                } // End of commListVal-list
            } // End of actionListVal-list
        } // End of communityListStand-list

        list communityListExp {
            key "commListNo";
            description
                "communityListExp";
            leaf commListNo  {
                type  cml_data_types:CML_UINT32_T {
                     range "100..500";
                }
                description "Community list extended value";
            } // END of commListNo definition.



            list commListAction {
                key "action";
                description
                    "commListAction";
                leaf action  {
                    type  cml_data_types:CML_BGP_COMMUNITY_LIST_ACTION_T;
                    description "Community list extended type";
                } // END of action definition.



                list commListVal {
                    key "regExpList";
                    description
                        "commListVal";
                    leaf regExpList  {
                        type  cml_data_types:CML_LINE_T {
                            length "0..255";
                        }
                        description "Community list extended value";
                    } // END of regExpList definition.


                } // End of commListVal-list
            } // End of commListAction-list
        } // End of communityListExp-list

        list communityListExpand {
            key "commListExpName";
            description
                "communityListExpand";
            leaf commListExpName  {
                type  cml_data_types:CML_STRING_T {
                    length "0..255";
                }
                description "Community list expanded name";
            } // END of commListExpName definition.



            list commListAction {
                key "action";
                description
                    "commListAction";
                leaf action  {
                    type  cml_data_types:CML_BGP_COMMUNITY_LIST_ACTION_T;
                    description "Community list expanded type";
                } // END of action definition.



                list commListVal {
                    key "regExpList";
                    description
                        "commListVal";
                    leaf regExpList  {
                        type  cml_data_types:CML_LINE_T {
                            length "0..255";
                        }
                        description "Community list expanded value";
                    } // END of regExpList definition.


                } // End of commListVal-list
            } // End of commListAction-list
        } // End of communityListExpand-list

        list extCommuListNo {
            key "extCommListStandNo";
            description
                "extCommuListNo";
            leaf extCommListStandNo  {
                type  cml_data_types:CML_UINT32_T {
                     range "1..99";
                }
                description "Extended Community list number";
            } // END of extCommListStandNo definition.



            list extCommListAction {
                key "extAction";
                description
                    "extCommListAction";
                leaf extAction  {
                    type  cml_data_types:CML_BGP_COMMUNITY_LIST_ACTION_T;
                    description "Extended Community list type";
                } // END of extAction definition.



                list extCommListVal {
                    key "extCommListValue";
                    description
                        "extCommListVal";
                    leaf extCommListValue  {
                        type  cml_data_types:CML_LINE_T {
                            length "0..255";
                        }
                        description "Extended Community list value";
                    } // END of extCommListValue definition.


                } // End of extCommListVal-list
            } // End of extCommListAction-list
        } // End of extCommuListNo-list

        list extCommListStand {
            key "extCommListName";
            description
                "extCommListStand";
            leaf extCommListName  {
                type  cml_data_types:CML_STRING_T {
                    length "0..255";
                }
                description "extcommunity Community list name";
            } // END of extCommListName definition.


            leaf delExcomm  {
                type  cml_data_types:CML_STRING_T {
                    length "0..255";
                }
                description "extcommunity Community list value";
            } // END of delExcomm definition.



            list extCommListAction {
                key "extAction";
                description
                    "extCommListAction";
                leaf extAction  {
                    type  cml_data_types:CML_BGP_COMMUNITY_LIST_ACTION_T;
                    description "extcommunity Community list type";
                } // END of extAction definition.



                list routeTargetSoo {
                    key "rtSoo";
                    description
                        "routeTargetSoo";
                    leaf rtSoo  {
                        type  cml_data_types:CML_BGP_ROUTE_TARGET_T;
                        description "route-target soo";
                    } // END of rtSoo definition.



                    list extCommListVal {
                        key "extCommListValue";
                        description
                            "extCommListVal";
                        leaf extCommListValue  {
                            type  cml_data_types:CML_STRING_T {
                                length "0..255";
                            }
                            description "extcommunity Community list value";
                        } // END of extCommListValue definition.


                    } // End of extCommListVal-list
                } // End of routeTargetSoo-list
            } // End of extCommListAction-list
        } // End of extCommListStand-list

        list extCommunityListExp {
            key "extCommListNo";
            description
                "extCommunityListExp";
            leaf extCommListNo  {
                type  cml_data_types:CML_UINT32_T {
                     range "100..500";
                }
                description "extcommunity Extended Community number";
            } // END of extCommListNo definition.



            list extCommListAction {
                key "extAction";
                description
                    "extCommListAction";
                leaf extAction  {
                    type  cml_data_types:CML_BGP_COMMUNITY_LIST_ACTION_T;
                    description "extcommunity Extended Community type";
                } // END of extAction definition.



                list extCommListVal {
                    key "extCommListValue";
                    description
                        "extCommListVal";
                    leaf extCommListValue  {
                        type  cml_data_types:CML_LINE_T {
                            length "0..255";
                        }
                        description "extcommunity Extended Community value";
                    } // END of extCommListValue definition.


                } // End of extCommListVal-list
            } // End of extCommListAction-list
        } // End of extCommunityListExp-list

        list extCommListExpand {
            key "extCommListExpName";
            description
                "extCommListExpand";
            leaf extCommListExpName  {
                type  cml_data_types:CML_STRING_T {
                    length "0..255";
                }
                description "extcommunity expanded Community name";
            } // END of extCommListExpName definition.



            list extCommListAction {
                key "extAction";
                description
                    "extCommListAction";
                leaf extAction  {
                    type  cml_data_types:CML_BGP_COMMUNITY_LIST_ACTION_T;
                    description "extcommunity expanded Community type";
                } // END of extAction definition.



                list extCommListVal {
                    key "extCommListValue";
                    description
                        "extCommListVal";
                    leaf extCommListValue  {
                        type  cml_data_types:CML_LINE_T {
                            length "0..255";
                        }
                        description "extcommunity expanded Community value";
                    } // END of extCommListValue definition.


                } // End of extCommListVal-list
            } // End of extCommListAction-list
        } // End of extCommListExpand-list

        list accessList {
            key "accessListName";
            description
                "accessList";
            leaf accessListName  {
                type  cml_data_types:CML_STRING_T {
                    length "0..255";
                }
                description "list_name AS path access list name";
            } // END of accessListName definition.



            list accessListDirection {
                key "accessListDirection";
                description
                    "accessListDirection";
                leaf accessListDirection  {
                    type  cml_data_types:CML_BGP_COMMUNITY_LIST_ACTION_T;
                    description "Action type <0-1> 0 - Deny 1 - Permit";
                } // END of accessListDirection definition.



                list bgpRegExp {
                    key "bgpRegExp";
                    description
                        "bgpRegExp";
                    leaf bgpRegExp  {
                        type  cml_data_types:CML_LINE_T {
                            length "0..255";
                        }
                        description "Regular expression to match BGP AS paths";
                    } // END of bgpRegExp definition.


                } // End of bgpRegExp-list
            } // End of accessListDirection-list
        } // End of accessList-list
    } // END of bgpGlobal-container definition.
    } // END of bgpGlobal-container definition.

    grouping  bgpDebug-grouping {
    description
        "bgpDebug";
    container bgpDebug {
        description
            "bgpDebug";
        leaf debugFlag  {
            type  cml_data_types:CML_BGP_DEBUG_TYPE_T;
            description "debug flag";
        } // END of debugFlag definition.


        leaf debugTermFlag  {
            type  cml_data_types:CML_BGP_DEBUG_TYPE_T;
            description "debug flag";
        } // END of debugTermFlag definition.


        leaf undebugFlag  {
            type  cml_data_types:CML_BGP_DEBUG_TYPE_T;
            description "undebug flag";
        } // END of undebugFlag definition.


        leaf debugUpdateTypeFlag  {
            type  cml_data_types:CML_BGP_UPDATE_DEBUG_TYPE_T;
            description "debug update flag";
        } // END of debugUpdateTypeFlag definition.


        leaf debugTermUpdateTypeFlag  {
            type  cml_data_types:CML_BGP_UPDATE_DEBUG_TYPE_T;
            description "debug update flag";
        } // END of debugTermUpdateTypeFlag definition.


    } // END of bgpDebug-container definition.
    } // END of bgpDebug-container definition.

    grouping  vrfTable-grouping {
    description
        "vrfTable";
    container vrfTable {
        if-feature feature_list:HAVE_VRF;
        description
            "vrfTable";
        leaf importMap  {
            type  cml_data_types:CML_STRING_T {
                length "0..255";
            }
            description "import map name";
        } // END of importMap definition.


        leaf rdStr  {
            type  cml_data_types:CML_STRING_T {
                length "1..32";
            }
            description "route distinguisher value";
        } // END of rdStr definition.



        list routeTarget {
            key "rtRdStr";
            description
                "routeTarget";
            leaf rtRdStr  {
                type  cml_data_types:CML_STRING_T {
                    length "1..32";
                }
                description "route distinguisher";
            } // END of rtRdStr definition.


            leaf direct  {
                type  cml_data_types:CML_RT_T;
                mandatory true;
                description "route-target value";
            } // END of direct definition.


        } // End of routeTarget-list
        container bgpRd {
            config false;
            description
                "BGP router distinguisher value";
            container bgpRdAs {
                config false;
                description
                    "BGP Router Distinguisher AS-Type";
                leaf brdAs  {
                    type  cml_data_types:CML_INT32_T;
                    description "Route-Distinguisher As";
                } // END of brdAs definition.


                leaf brdAsNum  {
                    type  cml_data_types:CML_INT32_T;
                    description "Route-Distinguisher As num";
                } // END of brdAsNum definition.


            } // END of bgpRdAs-container definition.
            container bgpRdAs4 {
                config false;
                description
                    "BGP Router Distinguisher 4-octect-AS-Type";
                leaf brdAs4  {
                    type  cml_data_types:CML_INT32_T;
                    description "Route-Distinguisher brd as4";
                } // END of brdAs4 definition.


                leaf brdAsNum4  {
                    type  cml_data_types:CML_INT32_T;
                    description "Route-Distinguisher brd asnum4";
                } // END of brdAsNum4 definition.


            } // END of bgpRdAs4-container definition.
            container bgpRdIp {
                config false;
                description
                    "BGP Router Distinguisher IP-Type";
                leaf brdIp  {
                    type  cml_data_types:CML_STRING_T {
                        length "0..255";
                    }
                    description "RD ip";
                } // END of brdIp definition.


                leaf brdIpNum  {
                    type  cml_data_types:CML_INT32_T;
                    description "RD ip num";
                } // END of brdIpNum definition.


            } // END of bgpRdIp-container definition.
        } // END of bgpRd-container definition.
    } // END of vrfTable-container definition.
    } // END of vrfTable-container definition.


}
