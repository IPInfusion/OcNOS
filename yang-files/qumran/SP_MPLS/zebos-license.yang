/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-license.yang
*
*/

submodule zebos-license {

    belongs-to  zebos { prefix zebos; }

    import cml_data_types {
        prefix cml_data_types;
    }

    import feature_list {
        prefix feature_list;
    }

    include zebos-vrf;
    organization
        "IP Infusion Inc.";

    contact
        "Address: 3965 Freedom Circle, Suite 200, Santa Clara, CA 95054
         Phone: +1 408-400-1900
         E-mail: support@ipinfusion.com
         Web: http://www.ipinfusion.com/";

    description
        "license configurations";


    revision "2018-06-21" {
        description " Initial Version.";
        reference "";
    }


    grouping  licenseServer-grouping {
    description
        "licenseServer";
    container licenseServer {
        if-feature feature_list:NOT_HAVE_TBV_ARM;
        description
            "licenseServer";
        leaf serverIp  {
            type  cml_data_types:CML_IP_ADDR_T {
                length "0..255";
            }
            description "";
        } // END of serverIp definition.


        leaf vrfName  {
            type  cml_data_types:CML_STRING_T {
                length "0..255";
            }
            description "";
        } // END of vrfName definition.


        leaf portNo  {
            type  cml_data_types:CML_UINT16_T;
            description "";
        } // END of portNo definition.


        leaf autoRenewal  {
            type  cml_data_types:CML_BOOL_T;
            description "";
        } // END of autoRenewal definition.


    } // END of licenseServer-container definition.
    } // END of licenseServer-container definition.


}
