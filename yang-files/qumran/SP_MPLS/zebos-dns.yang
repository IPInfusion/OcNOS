/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-dns.yang
*
*/

submodule zebos-dns {

    belongs-to  zebos { prefix zebos; }

    import cml_data_types {
        prefix cml_data_types;
    }

    import feature_list {
        prefix feature_list;
    }

    include zebos-vrf;
    organization
        "IP Infusion Inc.";

    contact
        "Address: 3965 Freedom Circle, Suite 200, Santa Clara, CA 95054
         Phone: +1 408-400-1900
         E-mail: support@ipinfusion.com
         Web: http://www.ipinfusion.com/";

    description
        "dns_configuration";


    revision "2018-06-21" {
        description " Initial Version.";
        reference "";
    }



    grouping dns-grouping {
    description
        "vrf list for DNS commands";
        list dns {
            key "vrfName";
            description
                "vrf list for DNS commands";
            leaf vrfName  {
                type  cml_data_types:CML_STRING_T {
                    length "0..255";
                }
                description "";
            } // END of vrfName definition.


            leaf domainlookup  {
                type  cml_data_types:CML_BOOL_T;
                default true;
                description "";
            } // END of domainlookup definition.


            leaf defaultdomain  {
                if-feature feature_list:HAVE_DNS_CLIENT;
                type  cml_data_types:CML_BOOL_T;
                description "";
            } // END of defaultdomain definition.


            leaf domainname  {
                if-feature feature_list:HAVE_DNS_CLIENT;
                type  cml_data_types:CML_STRING_T {
                    length "0..255";
                }
                description "";
            } // END of domainname definition.


            leaf-list nameServer  {
                type  cml_data_types:CML_IP_ADDR_T {
                    length "0..255";
                }
                description "";
            } // END of nameServer definition.



            list domainlistNAME {
                key "domainlist";
                description
                    "domainlistNAME";
                leaf domainlist  {
                    type  cml_data_types:CML_STRING_T {
                        length "0..255";
                    }
                    description "";
                } // END of domainlist definition.


            } // End of domainlistNAME-list

            list hostname {
                key "host";
                description
                    "ip host configurations";
                leaf host  {
                    type  cml_data_types:CML_STRING_T {
                        length "1..63";
                    }
                    description "";
                } // END of host definition.


                leaf ipv4  {
                    type  cml_data_types:CML_IPV4_ADDR_T;
                    description "";
                } // END of ipv4 definition.


                leaf ipv6  {
                    type  cml_data_types:CML_IPV6_ADDR_T;
                    description "";
                } // END of ipv6 definition.


            } // End of hostname-list
        } // End of dns-list
    } // END of dns-grouping definition.

    grouping  debugDns-grouping {
    description
        "debug commands for dns";
    container debugDns {
        description
            "debug commands for dns";
        leaf debugdns  {
            if-feature feature_list:HAVE_DNS_CLIENT;
            type  cml_data_types:CML_BOOL_T;
            description "";
        } // END of debugdns definition.


        leaf debugConfdns  {
            if-feature feature_list:HAVE_DNS_CLIENT;
            type  cml_data_types:CML_BOOL_T;
            description "";
        } // END of debugConfdns definition.


    } // END of debugDns-container definition.
    } // END of debugDns-container definition.


}
