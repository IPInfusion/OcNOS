/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-vr.yang
*
*/

submodule zebos-vr {

    belongs-to  zebos { prefix zebos; }

    import cml_data_types {
        prefix cml_data_types;
    }

    import feature_list {
        prefix feature_list;
    }

    include zebos-vrf;
    include zebos-interface;
    include zebos-broadcom;
    include zebos-vlan;
    include zebos-bridge;
    include zebos-mstp;
    include zebos-lldpv2;
    include zebos-rib;
    include zebos-ospf;
    include zebos-ospfv3;
    include zebos-bgp;
    include zebos-oambfd;
    include zebos-vrrp;
    include zebos-plist;
    include zebos-isis;
    include zebos-keychain;
    include zebos-pim;
    include zebos-pim4;
    include zebos-vxlan;
    include zebos-featuredhcp;
    include zebos-mrib4;
    include zebos-igmp;
    include zebos-routemap;
    include zebos-pbrport;
    include zebos-hqos;
    include zebos-auth;
    include zebos-rip;
    include zebos-acl;
    include zebos-aclinterface;
    include zebos-rpf;
    include zebos-pmirror;
    include zebos-authradius;
    include zebos-ripng;
    include zebos-ndd;
    include zebos-synce;
    include zebos-imi;
    include zebos-cfm;
    include zebos-evpn;
    organization
        "IP Infusion Inc.";

    contact
        "Address: 3965 Freedom Circle, Suite 200, Santa Clara, CA 95054
         Phone: +1 408-400-1900
         E-mail: support@ipinfusion.com
         Web: http://www.ipinfusion.com/";

    description
        "Virtual router";


    revision "2018-06-21" {
        description " Initial Version.";
        reference "";
    }



    grouping vr-grouping {
    description
        "Virtual router object";
        list vr {
            key "vrId";
            description
                "Virtual router object";
            leaf vrId  {
                type  cml_data_types:CML_UINT32_T {
                     range "0..255";
                }
                description "Virtual router id";
            } // END of vrId definition.


            leaf name  {
                type  cml_data_types:CML_STRING_T {
                    length "0..255";
                }
                description "";
            } // END of name definition.



            list vrInstances {
                if-feature feature_list:HAVE_VR;
                key "vrName";
                description
                    "object for virtual router configurations";
                leaf vrName  {
                    type  cml_data_types:CML_STRING_T {
                        length "1..12";
                    }
                    description "Virtual router name";
                } // END of vrName definition.


                leaf description  {
                    type  cml_data_types:CML_LINE_T {
                        length "0..255";
                    }
                    description "Virtual router description";
                } // END of description definition.


                leaf protocol  {
                    type  cml_data_types:CML_VR_PROTOCOL_T;
                    description "protocol load";
                } // END of protocol definition.


                leaf configurationFile  {
                    type  cml_data_types:CML_STRING_T {
                        length "0..255";
                    }
                    description "Virtual router configuration file";
                } // END of configurationFile definition.


                leaf configReadWrite  {
                    type  cml_data_types:CML_VR_CONFIG_T;
                    description "Virtual router configuration file";
                } // END of configReadWrite definition.


            } // End of vrInstances-list
            uses vrf-grouping;
            uses interface-grouping;
            uses portGroupSpeed-grouping;
            uses ifIndexList-grouping;
            uses nsmMaster-grouping;
            uses libhwconf-grouping;
            uses nsmVlanAccess-grouping;
            uses VlanAccessMap-grouping;
            uses vlanClassifierRule-grouping;
            uses vlanClassifierGroup-grouping;
            uses debugConfigMode-grouping;
            uses debugExecMode-grouping;
            uses bridge-grouping;
            uses spanningTree-grouping;
            uses spanningPort-grouping;
            uses mstpPort-grouping;
            uses backboneBridgePort-grouping;
            uses customerSpanningtree-grouping;
            uses mstpDebugMode-grouping;
            uses mstpExecMode-grouping;
            uses lldpMaster-grouping;
            uses rib-grouping;
            uses ospf-grouping;
            uses teLinkOspf-grouping;
            uses ospfMaster-grouping;
            uses ospf6Master-grouping;
            uses bgp-grouping;
            uses bgpGlobal-grouping;
            uses bgpDebug-grouping;
            uses bfdInterface-grouping;
            uses bfd-grouping;
            uses Vrrp4Instance-grouping;
            uses Vrrp6Instance-grouping;
            uses vrrp-grouping;
            uses VrrpDebug-grouping;
            uses prefixMaster-grouping;
            uses prefixMaster6-grouping;
            uses isismaster-grouping;
            uses keychain-grouping;
            uses pimDebug-grouping;
            uses pimTermDebug-grouping;
            uses pim4Vrf-grouping;
            uses pim4Debug-grouping;
            uses nsmipv4prefixroute-grouping;
            uses nsmipv6prefixroute-grouping;
            uses anycastGwMac-grouping;
            uses esiHoldTime-grouping;
            uses nvo-grouping;
            uses featuredhcp-grouping;
            uses mrib4Vrf-grouping;
            uses mrib4Igmp-grouping;
            uses pbrConfig-grouping;
            uses pbrEnable-grouping;
            uses pbrInterface-grouping;
            uses qos-grouping;
            uses authPort-grouping;
            uses authmac-grouping;
            uses ripConfiguration-grouping;
            uses accessMasterIPv4-grouping;
            uses accessMasterARP-grouping;
            uses accessMasterIPv6-grouping;
            uses aclVty-grouping;
            uses rpf-grouping;
            uses pmNode-grouping;
            uses pmNodeALternate-grouping;
            uses Hostradius-grouping;
            uses authradius-grouping;
            uses ripngConfiguration-grouping;
            uses ndstaticarpentry-grouping;
            uses debugndd-grouping;
            uses icmpredirect-grouping;
            uses externalSynceInterface-grouping;
            uses hostname-grouping;
            uses webUser-grouping;
            uses cfmOverMplsService-grouping;
            uses multihoming-grouping;
        } // End of vr-list
    } // END of vr-grouping definition.


}
