/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-port-vlan.yang
*
*/

module ipi-port-vlan {

    yang-version 1.1;

    namespace   "http://www.ipinfusion.com/yang/ocnos/ipi-port-vlan";

    prefix "ipi-port-vlan";

    import cml-data-types {
        prefix cml-data-types;
    }

    import ipi-port-vlan-types {
        prefix ipi-port-vlan-types;
    }

    import ipi-network-instance {
        prefix ipi-network-instance;
    }

    import ipi-interface {
        prefix ipi-interface;
    }

    import ipi-vlan {
        prefix ipi-vlan;
    }

    import ipi-if-aggregate {
        prefix ipi-if-aggregate;
    }

    import ipi-bridge {
        prefix ipi-bridge;
    }

    import feature-list {
        prefix feature-list;
    }

    organization
        "IP Infusion Inc.";

    contact
        "Address: 3965 Freedom Circle, Suite 200, Santa Clara, CA 95054
         Phone: +1 408-400-1900
         E-mail: support@ipinfusion.com
         Web: http://www.ipinfusion.com/";

    description
        "Port vlan configuration";


    revision "2021-03-05" {
        description "Removed dot1q-ether-type attribute and moved to mo_ipi-if-extended.xml file";
        reference " 0.6.0.";
    }

    revision "2021-02-05" {
        description "Change static mac vlan parameters";
        reference " 0.5.0.";
    }

    revision "2021-01-27" {
        description "Change to have descriptions for individual leafs";
        reference " 0.4.0.";
    }

    revision "2020-12-15" {
        description "Change to have data-types in lower case instead of camel case";
        reference " 0.3.0.";
    }

    revision "2018-12-28" {
        description "Provider bridge static MAC support for Qumran platform";
        reference " 0.2.0.";
    }

    revision "2018-06-21" {
        description "Initial Version";
        reference " 0.1.0.";
    }

    grouping oep-mapping-config {
        description
            "Grouping for OEP mapping configuration data";
        leaf type  {
            type  ipi-port-vlan-types:port_vlan_oep_map_type_t;
            description "oep map type";
        } // END of type definition.

        leaf oep-name  {
            type  string {
                length "1..max";
                pattern "[^?' =,>|]+";
            }
            description "oep mapping table name";
        } // END of oep-name definition.

    } // END of oep-mapping-config definition.
    grouping oep-mapping-top {
        description
            "Top level grouping for OEP mapping";
    } // END of oep-mapping-top definition.
    grouping mapping-config {
        description
            "Grouping for private vlan mapping configuration data";
        leaf vlan-id  {
            type  uint16 {
                 range "2..4094"  {
                    description "VLAN id";
                 }
            }
            description "Use this attribute to creates or deletes a mapping between an MSTI
                        (Multiple Spanning Tree Instance) and a VLAN for RPVST+ operation.
                        There can be only one VLAN per MST instance if the bridge is
                        configured to run in RPVST+ mode.The VLAN must have already been
                        created, otherwise an error is returned. Spanning tree is enabled on
                        each configured VLAN, and one instance of spanning-tree runs on each
                        configured VLAN";
        } // END of vlan-id definition.

        leaf associate-vlan-id  {
            when " /ipi-interface:interfaces/ipi-interface:interface/ipi-port-vlan:port-vlan/ipi-port-vlan:private-vlan/ipi-port-vlan:config/ipi-port-vlan:mode = '1' ";
            type  uint32;
            description "Private VLAN Associate";
        } // END of associate-vlan-id definition.

        leaf mapping-vlan-id  {
            when " /ipi-interface:interfaces/ipi-interface:interface/ipi-port-vlan:port-vlan/ipi-port-vlan:private-vlan/ipi-port-vlan:config/ipi-port-vlan:mode != '1' ";
            type  cml-data-types:cml_range_t;
            description "private-vlan Mapping";
        } // END of mapping-vlan-id definition.

    } // END of mapping-config definition.
    grouping association-top {
        description
            "Top level grouping for private vlan data";

        list association {
        when " /ipi-interface:interfaces/ipi-interface:interface/ipi-port-vlan:port-vlan/ipi-port-vlan:private-vlan/ipi-port-vlan:config/ipi-port-vlan:mode != '?' ";
            key "vlan-id";
            description
                "List of private vlan mappings";
            leaf vlan-id  {
                type  leafref {
                    path  "../config/vlan-id";
                }
                description "Use this attribute to creates or deletes a mapping between an MSTI
                            (Multiple Spanning Tree Instance) and a VLAN for RPVST+ operation.
                            There can be only one VLAN per MST instance if the bridge is
                            configured to run in RPVST+ mode.The VLAN must have already been
                            created, otherwise an error is returned. Spanning tree is enabled on
                            each configured VLAN, and one instance of spanning-tree runs on each
                            configured VLAN";
            } // END of vlan-id definition.

            container config {
                when " /ipi-interface:interfaces/ipi-interface:interface/ipi-port-vlan:port-vlan/ipi-port-vlan:private-vlan/ipi-port-vlan:association/ipi-port-vlan:config/ipi-port-vlan:associate-vlan-id  or /ipi-interface:interfaces/ipi-interface:interface/ipi-port-vlan:port-vlan/ipi-port-vlan:private-vlan/ipi-port-vlan:association/ipi-port-vlan:config/ipi-port-vlan:mapping-vlan-id ";
                description
                    "Configuration data for private vlan mapping";
                uses mapping-config;
            } // END of config-container definition.
            container state {
                config false;
                description
                    "Operational state data";
                uses mapping-config;
            } // END of state-container definition.
        } // End of association-list
    } // END of association-top definition.
    grouping port-private-vlan-config {
        description
            "Grouping for private vlan mode configuration";
        leaf mode  {
            type  ipi-port-vlan-types:port_vlan_pvlan_mode_t;
            mandatory true;
            description "Use this attribute to make a layer2 port as a host port or promiscuous
                        port or pvlan-trunk port";
        } // END of mode definition.

    } // END of port-private-vlan-config definition.
    grouping port-private-vlan-top {
        description
            "Top level grouping for private vlan";
    } // END of port-private-vlan-top definition.
    grouping port-security-mac-default-vlan-config {
        description
            "Port security configuration with MAC default vlan";
        leaf mac-address  {
            type  cml-data-types:cml_mac_addr_t;
            description "Use this attribute to configure the static forwarding entry for
                        port-security";
        } // END of mac-address definition.

    } // END of port-security-mac-default-vlan-config definition.
    grouping port-security-mac-vlan-config {
        description
            "Port security configuration with MAC CVLAN or MAC SVLAN";
        leaf mac-address  {
            type  cml-data-types:cml_mac_addr_t;
            description "Use this attribute to configure the static forwarding entry for
                        port-security";
        } // END of mac-address definition.

        leaf-list cvlan-id  {
            type  uint16;
            description "Use this attribute to configure the port-security with static
                        forwarding entry and CVLAN ID";
        } // END of cvlan-id definition.

    } // END of port-security-mac-vlan-config definition.
    grouping port-security-mac-cvlan-svlan-config {
        description
            "Port security configuration with MAC CVLAN SVLAN";
        leaf mac-address  {
            type  cml-data-types:cml_mac_addr_t;
            description "Use this attribute to configure the static forwarding entry for
                        port-security";
        } // END of mac-address definition.

        leaf cvlan-id  {
            type  uint16;
            description "Use this attribute to configure the port-security with static
                        forwarding entry and CVLAN ID";
        } // END of cvlan-id definition.

        leaf svlan-id  {
            type  uint16;
            description "Use this attribute to configure the port-security with static
                        forwarding entry and SVLAN ID";
        } // END of svlan-id definition.

    } // END of port-security-mac-cvlan-svlan-config definition.
    grouping port-security-mac-list {
        description
            "Port security objectlist for configuration of static MAC with default
                        vlan";

        list default-vlan-mapping {
            key "mac-address";
            description
                "List for Static MAC with default vlan";
            leaf mac-address  {
                type  leafref {
                    path  "../config/mac-address";
                }
                description "Use this attribute to configure the static forwarding entry for
                            port-security";
            } // END of mac-address definition.

            container config {
                description
                    "Configuration data for port-security with MAC and default vlan entries";
                uses port-security-mac-default-vlan-config;
            } // END of config-container definition.
            container state {
                config false;
                description
                    "Operational state data for port-security with MAC and default vlan
                            entries";
                uses port-security-mac-default-vlan-config;
            } // END of state-container definition.
        } // End of default-vlan-mapping-list
    } // END of port-security-mac-list definition.
    grouping port-security-mac-vlan-list {
        description
            "Port security objectlist for configuration of static MAC with MAC
                        CVLAN or MAC SVLAN entries";

        list vlan-mapping {
            key "mac-address";
            description
                "List for Static MAC with CVLAN or MAC with SVLAN";
            leaf mac-address  {
                type  leafref {
                    path  "../config/mac-address";
                }
                description "Use this attribute to configure the static forwarding entry for
                            port-security";
            } // END of mac-address definition.

            container config {
                description
                    "Configuration data for port-security with MAC CVLAN or MAC SVLAN
                            entries";
                uses port-security-mac-vlan-config;
            } // END of config-container definition.
            container state {
                config false;
                description
                    "Operational state data for port-security with MAC or CVLAN or SVLAN
                            entries";
                uses port-security-mac-vlan-config;
            } // END of state-container definition.
        } // End of vlan-mapping-list
    } // END of port-security-mac-vlan-list definition.
    grouping port-security-mac-cvlan-svlan-list {
        description
            "Port security objectlist for configuration of static MAC with MAC
                        CVLAN SVLAN entries";
    } // END of port-security-mac-cvlan-svlan-list definition.
    grouping port-security-mac-top {
        description
            "Top level grouping for port MAC security data";
        container secure-mac {
            when " /ipi-interface:interfaces/ipi-interface:interface/ipi-port-vlan:port-vlan/ipi-port-vlan:port-security/ipi-port-vlan:config/ipi-port-vlan:mode ";
            description
                "Configure data for static MAC entries";
            uses port-security-mac-list;
            uses port-security-mac-vlan-list;
            uses port-security-mac-cvlan-svlan-list;
        } // END of secure-mac-container definition.
    } // END of port-security-mac-top definition.
    grouping port-security-config {
        description
            "Port security common configuration data";
        leaf mode  {
            type  ipi-port-vlan-types:port_vlan_port_sec_mode_t;
            mandatory true;
            description "port security mode type";
        } // END of mode definition.

        leaf maximum-limit  {
            type  uint16 {
                 range "1..1000"  {
                    description "Port security maximum limit";
                 }
            }
            default "1";
            description "Maximum limit for port security";
        } // END of maximum-limit definition.

        leaf logging  {
            type  empty;
            description "port security logging";
        } // END of logging definition.

    } // END of port-security-config definition.
    grouping port-security-top {
        description
            "Top level grouping for port security";
        container port-security {
            when " /ipi-interface:interfaces/ipi-interface:interface/ipi-interface:config/ipi-interface:switchport-status = 'true' ";
            description
                "Configuration and state data for port security";
            container config {
                presence "Configure port security mode";
                description
                    "Configuration data for port security";
                uses port-security-config;
            } // END of config-container definition.
            container state {
                config false;
                description
                    "Operational state data for port-security";
                uses port-security-config;
            } // END of state-container definition.
            uses port-security-mac-top;
        } // END of port-security-container definition.
    } // END of port-security-top definition.
    grouping allowed-vlan-config {
        description
            "Configuration data for port allowed vlan";
        leaf allowed-vlan-id  {
            when " not(/ipi-interface:interfaces/ipi-interface:interface/ipi-port-vlan:port-vlan/ipi-port-vlan:switched-vlan/ipi-port-vlan:allowed-vlan/ipi-port-vlan:config/ipi-port-vlan:egress-tagging-enabled-vlans) + not(/ipi-interface:interfaces/ipi-interface:interface/ipi-port-vlan:port-vlan/ipi-port-vlan:switched-vlan/ipi-port-vlan:allowed-vlan/ipi-port-vlan:config/ipi-port-vlan:egress-tagging-disabled-vlans) ";
            type  cml-data-types:cml_range_t;
            description "Use this attribute to create a single/range of VLANs on the VLAN aware
                        bridges";
        } // END of allowed-vlan-id definition.

        leaf egress-tagging-enabled-vlans  {
            when " not(/ipi-interface:interfaces/ipi-interface:interface/ipi-port-vlan:port-vlan/ipi-port-vlan:switched-vlan/ipi-port-vlan:allowed-vlan/ipi-port-vlan:config/ipi-port-vlan:allowed-vlan-id) ";
            type  cml-data-types:cml_range_t;
            description "Egress tagging per vlan";
        } // END of egress-tagging-enabled-vlans definition.

        leaf egress-tagging-disabled-vlans  {
            type  cml-data-types:cml_range_t;
            description "Egress tagging per vlan";
        } // END of egress-tagging-disabled-vlans definition.

    } // END of allowed-vlan-config definition.
    grouping allowed-vlan-top {
        description
            "Top level grouping for port allowed vlans";
        container allowed-vlan {
            when " /ipi-interface:interfaces/ipi-interface:interface/ipi-interface:config/ipi-interface:switchport-status = 'true' ";
            description
                "Configuration and state data for allowed vlans";
            container config {
                description
                    "Configuration data for port allowed vlans";
                uses allowed-vlan-config;
            } // END of config-container definition.
            container state {
                config false;
                description
                    "Operational state data";
                uses allowed-vlan-config;
            } // END of state-container definition.
        } // END of allowed-vlan-container definition.
    } // END of allowed-vlan-top definition.
    grouping cvlan-translation-config {
        description
            "Grouping for cvlan translation configuration";
        leaf cvlan-id  {
            type  uint16 {
                 range "1..4095"  {
                    description "C-VLAN ID range";
                 }
            }
            description "Specifies to be translated customer vlan identifier";
        } // END of cvlan-id definition.

        leaf svlan-id  {
            type  uint16 {
                 range "1..4095"  {
                    description "S-VLAN ID range";
                 }
            }
            description "Specifies to be translated service vlan identifier";
        } // END of svlan-id definition.

        leaf translated-cvlan-id  {
            type  uint16 {
                 range "1..4095"  {
                    description "Translated C-VLAN ID range";
                 }
            }
            mandatory true;
            description "Specifies translated customer vlan identifier";
        } // END of translated-cvlan-id definition.

        leaf translated-svlan-id  {
            type  uint16 {
                 range "1..4095"  {
                    description "Translated S-VLAN ID range";
                 }
            }
            mandatory true;
            description "Specifies translated service vlan identifier";
        } // END of translated-svlan-id definition.

        leaf svlan-cos  {
            if-feature feature-list:NOT_HAVE_DUNE;
            type  int8 {
                 range "0..7"  {
                    description "Specify COS value 0-7";
                 }
            }
            mandatory true;
            description "Service vlan class of service value";
        } // END of svlan-cos definition.

        leaf svlan-cfi  {
            if-feature feature-list:NOT_HAVE_DUNE;
            type  int8 {
                 range "0..1"  {
                    description "Specify CFI value 0-1";
                 }
            }
            mandatory true;
            description "Service vlan Canonical Format Indicator value";
        } // END of svlan-cfi definition.

        leaf cvlan-cos  {
            if-feature feature-list:NOT_HAVE_DUNE;
            type  int8 {
                 range "0..7"  {
                    description "Specify COS value 0-7";
                 }
            }
            mandatory true;
            description "Customer vlan class of service value";
        } // END of cvlan-cos definition.

        leaf cvlan-cfi  {
            if-feature feature-list:NOT_HAVE_DUNE;
            type  int8 {
                 range "0..1"  {
                    description "Specify CFI value 0-1";
                 }
            }
            mandatory true;
            description "Customer vlan Canonical Format Indicator value";
        } // END of cvlan-cfi definition.

    } // END of cvlan-translation-config definition.
    grouping cvlan-translation-top {
        description
            "Top level grouping for cvlan translation";
    } // END of cvlan-translation-top definition.
    grouping svlan-translation-config {
        description
            "Groupnig for svlan translation configuration data";
        leaf translated-svlan-id  {
            type  uint16;
            description "Specifies translated service vlan identifier";
        } // END of translated-svlan-id definition.

        leaf original-svlan-id  {
            type  uint16;
            mandatory true;
            description "original sVlan Id";
        } // END of original-svlan-id definition.

    } // END of svlan-translation-config definition.
    grouping svlan-translation-top {
        description
            "Top level grouping for svlan translation data";
    } // END of svlan-translation-top definition.
    grouping ce-vlan-translation-config {
        description
            "Grouping for customer edge vlan translation configuration";
        leaf original-vlan-id  {
            type  uint16;
            description "Specifies the customer vlan to be translated";
        } // END of original-vlan-id definition.

        leaf translated-vlan-id  {
            type  uint16;
            mandatory true;
            description "Specifies the new customer vlan for translate";
        } // END of translated-vlan-id definition.

    } // END of ce-vlan-translation-config definition.
    grouping ce-vlan-translation-top {
        description
            "Top level grouping for customer edge vlan translation data";
    } // END of ce-vlan-translation-top definition.
    grouping isolated-vlan-config {
        description
            "Grouping for isolated vlan data";
        leaf isolated-vlan-id  {
            type  cml-data-types:cml_range_t;
            description "Isolated vlan identifier";
        } // END of isolated-vlan-id definition.

    } // END of isolated-vlan-config definition.
    grouping isolated-vlan-top {
        description
            "top level grouping for isolated vlan data";

        list isolated-vlan {
        when " /ipi-interface:interfaces/ipi-interface:interface/ipi-port-vlan:port-vlan/ipi-port-vlan:switched-vlan/ipi-port-vlan:config/ipi-port-vlan:interface-mode = '6' ";
            if-feature feature-list:NOT_HAVE_SWFWDR;
            key "isolated-vlan-id";
            description
                "List of isolated vlans";
            leaf isolated-vlan-id  {
                type  leafref {
                    path  "../config/isolated-vlan-id";
                }
                description "Isolated vlan identifier";
            } // END of isolated-vlan-id definition.

            container config {
                description
                    "Configuration data for isolated vlans";
                uses isolated-vlan-config;
            } // END of config-container definition.
            container state {
                config false;
                description
                    "Operational state data";
                uses isolated-vlan-config;
            } // END of state-container definition.
        } // End of isolated-vlan-list
    } // END of isolated-vlan-top definition.
    grouping switched-vlan-config {
        description
            "Grouping for port switched vlan configuration data";
        leaf interface-mode  {
            type  ipi-port-vlan-types:port_vlan_switch_port_mode_t;
            description "Set the interface to access or trunk or hybrid mode for VLANs";
        } // END of interface-mode definition.

        leaf vlan-id  {
            type  uint16 {
                 range "2..4094"  {
                    description "vlan range";
                 }
            }
            description "vlan identifier";
        } // END of vlan-id definition.

        leaf native-vlan-id  {
            type  uint16 {
                 range "2..4094"  {
                    description "vlan range";
                 }
            }
            description "Native Vlan Id";
        } // END of native-vlan-id definition.

        leaf ingress-filter  {
            type  cml-data-types:cml_enable_disable_t;
            description "Use this attribute to set the switching characteristics of the
                        interface as hybrid, and classify both tagged and untagged frames.
                        Received frames are classified based on the VLAN characteristics, then
                        accepted or discarded based on the specified filtering criteria.";
        } // END of ingress-filter definition.

        leaf acceptable-frame-type  {
            type  ipi-port-vlan-types:port_vlan_frame_type_t;
            description "Use this attribute to set the interface acceptable frame types. This
                        processing occurs after VLAN classification";
        } // END of acceptable-frame-type definition.

    } // END of switched-vlan-config definition.
    grouping switched-vlan-top {
        description
            "Top-level grouping for VLAN data associated with an interface";

        list switched-vlan {
        when " /ipi-interface:interfaces/ipi-interface:interface/ipi-interface:config/ipi-interface:switchport-status = 'true' ";
            key "interface-mode";
            description
                "VLAN related configuration that is part of interface";
            leaf interface-mode  {
                type  leafref {
                    path  "../config/interface-mode";
                }
                description "Set the interface to access or trunk or hybrid mode for VLANs";
            } // END of interface-mode definition.

            container config {
                description
                    "Configuration data for port switched vlan";
                uses switched-vlan-config;
            } // END of config-container definition.
            container state {
                config false;
                description
                    "Operational state data";
                uses switched-vlan-config;
            } // END of state-container definition.
            uses allowed-vlan-top;
            uses isolated-vlan-top;
            uses ce-vlan-translation-top;
            uses svlan-translation-top;
            uses cvlan-translation-top;
        } // End of switched-vlan-list
    } // END of switched-vlan-top definition.
    grouping cvlan-registraion-config {
        description
            "Top-level grouping for cvlan registation configuration data";
        leaf table-name  {
            type  string {
                length "1..max";
                pattern "[^?' =,>|]+";
            }
            description "cvlan registration table";
        } // END of table-name definition.

    } // END of cvlan-registraion-config definition.
    grouping cvlan-registraion-top {
        description
            "customer vlan registration table configuration";
    } // END of cvlan-registraion-top definition.
    grouping uni-id-config {
        description
            "Grouping for uni ID configuration";
        leaf id  {
            type  string {
                length "1..max";
                pattern "[^?' =,>|]+";
            }
            description "ethernet uni id";
        } // END of id definition.

    } // END of uni-id-config definition.
    grouping enni-id-config {
        description
            "Grouping for ENNI ID configuration";
        leaf id  {
            if-feature feature-list:HAVE_SWFWDR;
            type  string {
                length "1..max";
                pattern "[^?' =,>|]+";
            }
            description "ethernet uni id";
        } // END of id definition.

    } // END of enni-id-config definition.
    grouping uni-enni-type-config {
        description
            "Grouping for UNI/ENNI type configuration";
        leaf type  {
            type  ipi-port-vlan-types:port_vlan_uni_enni_type_t;
            mandatory true;
            description "ethernet type of UNI";
        } // END of type definition.

    } // END of uni-enni-type-config definition.
    grouping uni-enni-evc-config {
        description
            "Grouping for EVC configuration";
        leaf evc-id  {
            type  string {
                length "1..max";
                pattern "[^?' =,>|]+";
            }
            description "Specifies Ethernet Virtual Connection identifier";
        } // END of evc-id definition.

    } // END of uni-enni-evc-config definition.
    grouping uni-enni-evc-top {
        description
            "Top level grouping for port UNI/ENNI configuration";

        list evc {
            if-feature feature-list:HAVE_PROVIDER_BRIDGE;
            if-feature feature-list:HAVE_SWFWDR;
            key "evc-id";
            max-elements 1;
            description
                "List for EVC entries";
            leaf evc-id  {
                type  leafref {
                    path  "../config/evc-id";
                }
                description "Specifies Ethernet Virtual Connection identifier";
            } // END of evc-id definition.

            container config {
                description
                    "Configuration data EVC";
                uses uni-enni-evc-config;
                uses uni-enni-type-config;
            } // END of config-container definition.
            container state {
                config false;
                description
                    "Operational state data";
                uses uni-enni-evc-config;
                uses uni-enni-type-config;
            } // END of state-container definition.
        } // End of evc-list
    } // END of uni-enni-evc-top definition.
    grouping uni-enni-svlan-config {
        description
            "Grouping for UNI/ENNI svlan configuration data";
        leaf svlan-id  {
            type  uint32;
            description "Service vlan identifier";
        } // END of svlan-id definition.

    } // END of uni-enni-svlan-config definition.
    grouping uni-enni-svlan-top {
        description
            "Top level grouping for UNI/ENNI svlan data";

        list svlan {
            if-feature feature-list:HAVE_PROVIDER_BRIDGE;
            key "svlan-id";
            max-elements 1;
            description
                "List of svlan entries";
            leaf svlan-id  {
                type  leafref {
                    path  "../config/svlan-id";
                }
                description "Service vlan identifier";
            } // END of svlan-id definition.

            container config {
                description
                    "Svlan configuration data";
                uses uni-enni-svlan-config;
                uses uni-enni-type-config;
            } // END of config-container definition.
            container state {
                config false;
                description
                    "Operational state data";
                uses uni-enni-svlan-config;
                uses uni-enni-type-config;
            } // END of state-container definition.
        } // End of svlan-list
    } // END of uni-enni-svlan-top definition.
    grouping port-vlan-enni-top {
        description
            "Top level grouping for port ENNI data";
    } // END of port-vlan-enni-top definition.
    grouping uni-config {
        description
            "Grouping for UNI service data";
        leaf service  {
            when " /ipi-interface:interfaces/ipi-interface:interface/ipi-interface:config/ipi-interface:switchport-status = 'true' ";
            type  ipi-port-vlan-types:port_vlan_uni_service_t;
            description "ethernet uni Service";
        } // END of service definition.

        leaf evc-maximum-number  {
            when " /ipi-interface:interfaces/ipi-interface:interface/ipi-interface:config/ipi-interface:switchport-status = 'true' ";
            type  uint32 {
                 range "1..4094"  {
                    description "enter the maximum number of EVCs for the UNI";
                 }
            }
            description "ethernet uni maximum number of EVC";
        } // END of evc-maximum-number definition.

    } // END of uni-config definition.
    grouping uni-bridge-config {
        description
            "Grouping for bridge UNI data";
        leaf type-mode  {
            if-feature feature-list:HAVE_SWFWDR;
            type  ipi-port-vlan-types:port_vlan_uni_enable_disable_t;
            mandatory true;
            description "Specifies to enable or disable UNI type";
        } // END of type-mode definition.

    } // END of uni-bridge-config definition.
    grouping uni-bridge-top {
        description
            "Top level grouping for bridge UNI data";

        list bridge {
            if-feature feature-list:HAVE_PROVIDER_BRIDGE;
            if-feature feature-list:HAVE_SWFWDR;
            key "instance-name";
            max-elements 1;
            description
                "List for UNI bridge entries";
            leaf instance-name  {
                type  leafref {
                    path  "/ipi-network-instance:network-instances/ipi-network-instance:network-instance/ipi-network-instance:instance-name";
                }
                description "Bridge group number";
            } // END of instance-name definition.

            container config {
                description
                    "Configuration data for UNI bridge";
                uses uni-bridge-config;
            } // END of config-container definition.
            container state {
                config false;
                description
                    "Operational state data";
                uses uni-bridge-config;
            } // END of state-container definition.
        } // End of bridge-list
    } // END of uni-bridge-top definition.
    grouping uni-enni-parameters {
        description
            "Grouping for UNI/ENNI common parameters";

        list parameters {
            if-feature feature-list:HAVE_PROVIDER_BRIDGE;
            if-feature feature-list:HAVE_SWFWDR;
            key "id";
            description
                "List for UNI/ENNI common parameters";
            leaf id  {
                type  leafref {
                    path  "../config/id";
                }
                description "ethernet uni id";
            } // END of id definition.

            container config {
                description
                    "Configuration data for UNI/ENNI";
                uses uni-id-config;
            } // END of config-container definition.
            container state {
                config false;
                description
                    "Operational state data";
                uses uni-id-config;
            } // END of state-container definition.
            uses uni-enni-svlan-top;
            uses uni-enni-evc-top;
        } // End of parameters-list
    } // END of uni-enni-parameters definition.
    grouping port-vlan-uni-top {
        description
            "Top level grouping for port UNI data";
    } // END of port-vlan-uni-top definition.
    grouping vlan-stacking-config {
        description
            "Grouping for vlan stacking data";
        leaf type  {
            type  ipi-port-vlan-types:port_vlan_stack_t;
            mandatory true;
            description "Attribute to select vlan stacking port type";
        } // END of type definition.

        leaf ether-type  {
            type  string {
                pattern "[^?' =,>|]*";
                }
                default "";
                description "Attribute to select ether type for vlan tagging";
            } // END of ether-type definition.

    } // END of vlan-stacking-config definition.
    grouping port-vlan-stacking-top {
        description
            "Top level grouping for port vlan stacking";
    } // END of port-vlan-stacking-top definition.
    grouping port-vlan-global-config {
        description
            "Grouping for port vlan global configuration";
    } // END of port-vlan-global-config definition.
    grouping port-vlan-global-top {
        description
            "Top level groupnig for port vlan global level information";
        container global {
            description
                "Port vlan global level configuration and state data";
            container config {
                description
                    "Global levl configuration data for port vlan";
                uses port-vlan-global-config;
            } // END of config-container definition.
            container state {
                config false;
                description
                    "Operational state data";
                uses port-vlan-global-config;
            } // END of state-container definition.
            uses port-vlan-stacking-top;
        } // END of global-container definition.
    } // END of port-vlan-global-top definition.
    grouping mac-table-config {
        description
            "Grouping for vlan static FDB data";
        leaf mac-address  {
            type  cml-data-types:cml_mac_addr_t;
            description "Use this attribute to configure the static forwarding table entry for
                        the bridge";
        } // END of mac-address definition.

        leaf action  {
            type  ipi-port-vlan-types:port_vlan_l2_fdb_action_t;
            mandatory true;
            description "Specifies to forward or discard packets for particular static MAC
                        entry";
        } // END of action definition.

        leaf vlan-id  {
            type  uint16 {
                 range "2..4094"  {
                    description "vlan range";
                 }
            }
            description "Specifies vlan identifier for static MAC entry";
        } // END of vlan-id definition.

    } // END of mac-table-config definition.
    grouping mac-table-top {
        description
            "Top level grouping for vlan static mac table information";

        list mac-table {
        when " /ipi-network-instance:network-instances/ipi-network-instance:network-instance/ipi-bridge:bridge/ipi-vlan:vlans/ipi-vlan:vlan/ipi-vlan:vlan-id ";
            key "mac-address interface-name vlan-id";
            description
                "List of vlan static fdb mac table configuration and state data";
            leaf mac-address  {
                type  leafref {
                    path  "../config/mac-address";
                }
                description "Use this attribute to configure the static forwarding table entry for
                            the bridge";
            } // END of mac-address definition.

            leaf interface-name  {
                type  leafref {
                    path  "/ipi-interface:interfaces/ipi-interface:interface/ipi-interface:name";
                }
                description "The textual name of the interface";
            } // END of interface-name definition.

            leaf vlan-id  {
                type  leafref {
                    path  "../config/vlan-id";
                }
                description "Specifies vlan identifier for static MAC entry";
            } // END of vlan-id definition.

            container config {
                description
                    "Configuration data for vlan FDB";
                uses mac-table-config;
            } // END of config-container definition.
            container state {
                config false;
                description
                    "Operational state data";
                uses mac-table-config;
            } // END of state-container definition.
        } // End of mac-table-list
    } // END of mac-table-top definition.

    grouping  port-vlan-grouping {
    description
        "Top level container for port level VLAN configuration and state data";
    container port-vlan {
        description
            "Top level container for port level VLAN configuration and state data";
        uses port-vlan-global-top;
        uses port-vlan-uni-top;
        uses port-vlan-enni-top;
        uses switched-vlan-top;
        uses cvlan-registraion-top;
        uses port-security-top;
        uses port-private-vlan-top;
        uses oep-mapping-top;
    } // END of port-vlan-container definition.
    } // END of port-vlan-grouping definition.

    grouping  vlan-static-fdb-grouping {
    description
        "Top level list for vlan static fdb configuration and state data";
    container vlan-static-fdb {
        description
            "Top level list for vlan static fdb configuration and state data";
        uses mac-table-top;
    } // END of vlan-static-fdb-container definition.
    } // END of vlan-static-fdb-grouping definition.

    augment /ipi-interface:interfaces/ipi-interface:interface {
    when " not(/ipi-interface:interfaces/ipi-interface:interface/ipi-if-aggregate:member-aggregation) + /ipi-interface:interfaces/ipi-interface:interface/ipi-interface:config/ipi-interface:switchport-status = 'true' ";
        description
            "Top level container for port level VLAN configuration and state data";
        uses port-vlan-grouping;
    }

    augment /ipi-network-instance:network-instances/ipi-network-instance:network-instance/ipi-bridge:bridge {
        description
            "Top level list for vlan static fdb configuration and state data";
        uses vlan-static-fdb-grouping;
    }


}
