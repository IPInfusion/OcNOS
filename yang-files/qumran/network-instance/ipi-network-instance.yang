/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-network-instance.yang
*
*/

module ipi-network-instance {

    yang-version 1.1;

    namespace   "http://www.ipinfusion.com/yang/ocnos/ipi-network-instance";

    prefix "ipi-network-instance";

    import ipi-network-instance-types {
        prefix ipi-network-instance-types;
    }

    organization
        "IP Infusion Inc.";

    contact
        "Address: 3965 Freedom Circle, Suite 200, Santa Clara, CA 95054
         Phone: +1 408-400-1900
         E-mail: support@ipinfusion.com
         Web: http://www.ipinfusion.com/";

    description
        "Generic Network Instance";


    revision "2020-12-15" {
        description "Change to have data-types in lower case instead of camel case";
        reference " 0.2.0.";
    }

    revision "2020-08-11" {
        description "Datamodel restructuring";
        reference " 0.1.0.";
    }

    grouping network-instance-config {
        description
            "State item grouping for VRF";
        leaf instance-name  {
            type  string {
                length "1..128";
                pattern "[^?' =,>|]+";
            }
            description "Network Instance Name";
        } // END of instance-name definition.

        leaf instance-type  {
            type  ipi-network-instance-types:net_inst_type_t;
            description "Network Instance Type";
        } // END of instance-type definition.

    } // END of network-instance-config definition.

    grouping  network-instances-grouping {
    description
        "Top level container for network instances";
    container network-instances {
        description
            "Top level container for network instances";

        list network-instance {
            key "instance-name instance-type";
            description
                "List of Network instances configured on the local system";
            leaf instance-name  {
                type  leafref {
                    path  "../config/instance-name";
                }
                description "Network Instance Name";
            } // END of instance-name definition.

            leaf instance-type  {
                type  leafref {
                    path  "../config/instance-type";
                }
                description "Network Instance Type";
            } // END of instance-type definition.

            container config {
                description
                    "Config container for network instances";
                uses network-instance-config;
            } // END of config-container definition.
            container state {
                config false;
                description
                    "State container for network instances";
                uses network-instance-config;
            } // END of state-container definition.
        } // End of network-instance-list
    } // END of network-instances-container definition.
    } // END of network-instances-grouping definition.

    uses network-instances-grouping;

}
