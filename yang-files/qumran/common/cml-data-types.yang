/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : cml-data-types.yang
*
*/

module cml-data-types {

    yang-version 1.1;

    namespace   "http://www.ipinfusion.com/yang/ocnos/cml-data-types";

    prefix "cml-data-types";

    import ietf-inet-types {
        prefix inet;
    }

    organization
        "IP Infusion Inc.";

    contact
        "Address: 3965 Freedom Circle, Suite 200, Santa Clara, CA 95054
         Phone: +1 408-400-1900
         E-mail: support@ipinfusion.com
         Web: http://www.ipinfusion.com/";

    description
        "YANG version of the cml-data-types";


    revision "2021-01-27" {
        description "Added CVLAN configurations";
        reference " 0.3.0.";
    }

    revision "2020-12-15" {
        description "Change to have data-types in lower case instead of camel case";
        reference " 0.2.0.";
    }

    revision "2018-06-21" {
        description "Initial Version";
        reference " 0.1.0.";
    }



    typedef  cml_line_t {
        type string {
            pattern "[^?'=,>|]*";
        }
        description "type definition for CML_LINE_T";
    }

    typedef  cml_ssh_pubkey_t {
        type string;
        description "type definition for CML_SSH_PUBKEY_T";
    }

    typedef  cml_md5_password_t {
        type string {
            pattern "[^? ]*";
        }
        description "type definition for CML_MD5_PASSWORD_T";
    }

    typedef  cml_host_string_t {
        type string;
        description "type definition for CML_HOST_STRING_T";
    }

    typedef  cml_range_t {
        type string {
            pattern "[^?'=>|]*";
        }
        description "type definition for CML_RANGE_T";
    }

    typedef  cml_bitmap_t {
        type uint32 {
             range 0..4294967295;
        }
        description "type definition for CML_BITMAP_T";
    }

    typedef  cml_vm_affinity_t {
        type string {
            pattern "[^?' =>|]*";
        }
        description "type definition for CML_VM_AFFINITY_T";
    }

    typedef  cml_mac_addr_t {
        type string;
        description "type definition for CML_MAC_ADDR_T";
    }

    typedef  cml_cmap_match_any_criteria_t {
        type enumeration {
            enum match-any {
                value 2;
                description "Logical-OR of all match statements under this class-map";
            }
        }
        description "type definition for CML_CMAP_MATCH_ANY_CRITERIA_T";
    }

    typedef  cml_cmap_match_criteria_t {
        type enumeration {
            enum default-match-type {
                value 0;
                description "Match type is default which is match-al";
            }
            enum match-all {
                value 1;
                description "Logical-AND of all match statements under this class-map";
            }
            enum match-any {
                value 2;
                description "Logical-OR of all match statements under this class-map";
            }
        }
        description "type definition for CML_CMAP_MATCH_CRITERIA_T";
    }

    typedef  cml_profile_name_t {
        type enumeration {
            enum default {
                value 0;
                description "default";
            }
        }
        description "type definition for CML_PROFILE_NAME_T";
    }

    typedef  cml_exceed_action_t {
        type enumeration {
            enum none {
                value 0;
                description "default value";
            }
            enum drop {
                value 1;
                description "Sets the action to take when the data rate is exceeded.default is drop";
            }
            enum set-dscp-transmit {
                value 2;
                description "Specify the IP DSCP value 0 to 63";
            }
            enum set-prec-transmit {
                value 3;
                description "Specify the IP Precedence value 0 to 7";
            }
            enum set-cos-transmit {
                value 4;
                description "Specify the cos value 0 to 7";
            }
            enum set-mpls-class {
                value 5;
                description "Set the mpls class filed to the give value and tx the packet";
            }
            enum set-flow-control {
                value 6;
                description "Send a pause frame on the ingress port and pass the packet";
            }
            enum set-axe-ret {
                value 7;
                description " Send a pause frame on the ingress port and pass the packet";
            }
            enum transmit {
                value 8;
                description "Pass the packet by setting DEI";
            }
        }
        description "type definition for CML_EXCEED_ACTION_T";
    }

    typedef  cml_violate_action_t {
        type enumeration {
            enum none {
                value 0;
                description "default value";
            }
            enum drop {
                value 1;
                description "Sets the action to take when the data rate is exceeded.default is drop";
            }
            enum set-dscp-transmit {
                value 2;
                description "Specify the IP DSCP value 0 to 63";
            }
            enum set-cos-transmit {
                value 4;
                description "Specify the cos value 0 to 7";
            }
            enum set-mpls-class {
                value 5;
                description "Set the mpls class filed to the give value and tx the packet";
            }
            enum transmit {
                value 8;
                description "Pass the packet by setting DEI";
            }
        }
        description "type definition for CML_VIOLATE_ACTION_T";
    }

    typedef  cml_burst_type_t {
        type enumeration {
            enum none {
                value 0;
                description "default value";
            }
            enum kbytes {
                value 2;
                description "Specifies the units of kilobytes per second";
            }
            enum mbytes {
                value 3;
                description "Specifies the units of megabytes per second";
            }
            enum ms {
                value 4;
                description "Specifies the units of milliseconds";
            }
            enum us {
                value 5;
                description "Specifies the units of microseconds";
            }
        }
        description "type definition for CML_BURST_TYPE_T";
    }

    typedef  cml_flow_control_mode_t {
        type enumeration {
            enum nsm-qos-flow-control {
                value 0;
                description "nsm qos flow control mode none";
            }
            enum nsm-full-bucket-size {
                value 1;
                description "nsm resume on full bucket size";
            }
            enum nsm-cbs-bucket-size {
                value 2;
                description "nsm resume on cbs bucket size";
            }
        }
        description "type definition for CML_FLOW_CONTROL_MODE_T";
    }

    typedef  cml_mstp_instance_type_t {
        type union {
            type int32 {
                range "1..63";

            }
            type cml_mstp_instance_spbm_t {

            }
        }
        description "type definition for CML_MSTP_INSTANCE_TYPE_T";
    }

    typedef  cml_mstp_instance_spbm_t {
        type enumeration {
            enum spbm {
                value 4092;
                description "spbm instance";
            }
        }
        description "type definition for CML_MSTP_INSTANCE_SPBM_T";
    }

    typedef  cml_cfm_ais_mac_t {
        type union {
            type cml_cfm_ais_unicast_t {

            }
            type cml_cfm_ais_multicast_t {

            }
        }
        description "type definition for CML_CFM_AIS_MAC_T";
    }

    typedef  cml_cfm_ais_multicast_t {
        type enumeration {
            enum multicast {
                value 0;
                description "multicast ais frame to be sent";
            }
        }
        description "type definition for CML_CFM_AIS_MULTICAST_T";
    }

    typedef  cml_cfm_ais_unicast_t {
        type string;
        description "type definition for CML_CFM_AIS_UNICAST_T";
    }

    typedef  cml_proto_type_t {
        type enumeration {
            enum arp {
                value 0;
                description "Address Resolution protocol";
            }
            enum bridging {
                value 1;
                description "Bridging";
            }
            enum cdp {
                value 2;
                description "CISCO Discovery Protocol";
            }
            enum clns {
                value 3;
                description "connectionless network service";
            }
            enum clns-es {
                value 4;
                description "CLNS END systems";
            }
            enum clns-is {
                value 5;
                description "CLNS Intermediate systems";
            }
            enum dhcp {
                value 6;
                description "Dynamic host configuration";
            }
            enum isis {
                value 7;
                description "Intermediate system to Intermedaite system";
            }
            enum ldp {
                value 8;
                description "Label Distrubution protocol";
            }
            enum netbios {
                value 9;
                description "NetBIOS Extended User Interface";
            }
        }
        description "type definition for CML_PROTO_TYPE_T";
    }

    typedef  cml_qos_map_profile_type_t {
        type enumeration {
            enum dscp-to-queue {
                value 2;
                description "profile for dscp to queue map";
            }
            enum dscp-to-dscp {
                value 4;
                description "profile for inDscp to outDscp map";
            }
            enum exp-encap {
                value 6;
                description "profile for exp encapsulation map";
            }
        }
        description "type definition for CML_QOS_MAP_PROFILE_TYPE_T";
    }

    typedef  cml_qos_queue_profile_type_t {
        type enumeration {
            enum profile1 {
                value 1;
                description "supported new 4 queue-bundle per service (default)";
            }
            enum profile2 {
                value 2;
                description "supported new 8 queue-bundle per service";
            }
        }
        description "type definition for CML_QOS_QUEUE_PROFILE_TYPE_T";
    }

    typedef  cml_remark_enable_disable_t {
        type enumeration {
            enum disable {
                value 1;
                description "disable remarking";
            }
            enum enable {
                value 2;
                description "enable remarking";
            }
        }
        description "type definition for CML_REMARK_ENABLE_DISABLE_T";
    }

    typedef  cml_qos_dir_t {
        type enumeration {
            enum ingress {
                value 0;
                description "Apply ingress direction";
            }
            enum egress {
                value 1;
                description "Apply Egress direction";
            }
        }
        description "type definition for CML_QOS_DIR_T";
    }

    typedef  cml_qos_egress_dir_t {
        type enumeration {
            enum egress {
                value 1;
                description "Apply Egress direction";
            }
        }
        description "type definition for CML_QOS_EGRESS_DIR_T";
    }

    typedef  cml_qos_ingress_dir_t {
        type enumeration {
            enum ingress {
                value 0;
                description "Apply ingress direction";
            }
        }
        description "type definition for CML_QOS_INGRESS_DIR_T";
    }

    typedef  cml_hostname_t {
        type union {
            type inet:ip-address {

            }
            type string {

            }
        }
        description "type definition for CML_HOSTNAME_T";
    }

    typedef  cml_hostpname_t {
        type union {
            type inet:ip-address {

            }
            type cml_host_string_t {

            }
        }
        description "type definition for CML_HOSTPNAME_T";
    }

    typedef  cml_ipv4hostname_t {
        type union {
            type inet:ipv4-address {

            }
        }
        description "type definition for CML_IPV4HOSTNAME_T";
    }

    typedef  cml_host_t {
        type enumeration {
            enum hostname {
                value 1;
                description "Hostname";
            }
        }
        description "type definition for CML_HOST_T";
    }

    typedef  cml_ipv4_addr_or_prefix_t {
        type union {
            type inet:ipv4-address {

            }
            type inet:ipv4-prefix {

            }
        }
        description "type definition for CML_IPV4_ADDR_OR_PREFIX_T";
    }

    typedef  cml_ip_prefix_addr_t {
        type union {
            type inet:ipv4-prefix {

            }
            type inet:ipv6-prefix {

            }
        }
        description "type definition for CML_IP_PREFIX_ADDR_T";
    }

    typedef  cml_mac_eth_type_t {
        type union {
            type cml_eth_type_t {

            }
            type string {

            }
        }
        description "type definition for CML_MAC_ETH_TYPE_T";
    }

    typedef  cml_eth_type_t {
        type enumeration {
            enum ip4 {
                value 0;
                description "IPv4 Ethertype - 0x0800";
            }
            enum ip6 {
                value 1;
                description "IPv6 Ethertype - 0x86dd";
            }
            enum mpls {
                value 2;
                description "MPLS Ethertype - 0x8847";
            }
        }
        description "type definition for CML_ETH_TYPE_T";
    }

    typedef  cml_hostt_t {
        type enumeration {
            enum emergencies {
                value 0;
                description "Use local0 facility";
            }
            enum alerts {
                value 1;
                description "Use local1 facility";
            }
            enum critical {
                value 2;
                description "Use local2 facility";
            }
            enum errors {
                value 3;
                description "Use local3 facility";
            }
            enum warnings {
                value 4;
                description "Use local4 facility";
            }
            enum notifications {
                value 5;
                description "Use local5 facility";
            }
            enum informational {
                value 6;
                description "Use local6 facility";
            }
            enum debugging {
                value 7;
                description "Use local7 facility";
            }
        }
        description "type definition for CML_HOSTT_T";
    }

    typedef  cml_discardforward_t {
        type enumeration {
            enum discard {
                value 0;
                description "discard";
            }
            enum forward {
                value 1;
                description "forward";
            }
        }
        description "type definition for CML_DISCARDFORWARD_T";
    }

    typedef  cml_ospfv3_link_status_t {
        type enumeration {
            enum up {
                value 1;
                description "Vlink Status is up";
            }
            enum down {
                value 2;
                description "Vlink Status is down";
            }
        }
        description "type definition for CML_OSPFV3_LINK_STATUS_T";
    }

    typedef  cml_ospf6_cspf_type_t {
        type enumeration {
            enum random {
                value 0;
                description "Random";
            }
            enum most-fill {
                value 1;
                description "Most fill";
            }
            enum least-fill {
                value 2;
                description "Least fill";
            }
        }
        description "type definition for CML_OSPF6_CSPF_TYPE_T";
    }

    typedef  cml_ospf6_abr_type_t {
        type enumeration {
            enum standard {
                value 1;
                description "Standard behavior (RFC2328)";
            }
            enum cisco {
                value 2;
                description "Alternative ABR, Cisco implementation (RFC3509)";
            }
            enum ibm {
                value 3;
                description "Alternative ABR, IBM implementation (RFC3509)";
            }
        }
        description "type definition for CML_OSPF6_ABR_TYPE_T";
    }

    typedef  cml_ospf6_translator_role_t {
        type enumeration {
            enum always {
                value 1;
                description "Translate always";
            }
            enum candidate {
                value 2;
                description "Candidate for translator (default)";
            }
        }
        description "type definition for CML_OSPF6_TRANSLATOR_ROLE_T";
    }

    typedef  cml_ospf6_network_t {
        type enumeration {
            enum point-to-point {
                value 1;
                description "OSPF point-to-point network";
            }
            enum broadcast {
                value 2;
                description "OSPF broadcast multi-access network";
            }
            enum non-broadcast {
                value 3;
                description "OSPF NBMA network";
            }
            enum point-to-multipoint {
                value 4;
                description "OSPF point-to-multipoint network";
            }
            enum point-to-multipoint-non-broadcast {
                value 5;
                description "OSPF point-to-multipoint NBMA network,non-broadcast point-to-multipoint network";
            }
        }
        description "type definition for CML_OSPF6_NETWORK_T";
    }

    typedef  cml_ospf6_lsa_supression_state_t {
        type enumeration {
            enum disable {
                value 0;
                description "Disable";
            }
            enum enable {
                value 1;
                description "Enable";
            }
        }
        description "type definition for CML_OSPF6_LSA_SUPRESSION_STATE_T";
    }

    typedef  cml_ospf6_restart_helper_t {
        type enumeration {
            enum only-reload {
                value 4;
                description "Only help on software reloads";
            }
            enum only-upgrade {
                value 8;
                description "Only help on software upgrades";
            }
        }
        description "type definition for CML_OSPF6_RESTART_HELPER_T";
    }

    typedef  cml_ospf6_route_source_type_t {
        type enumeration {
            enum kernel {
                value 1;
                description "Kernel routes";
            }
            enum connected {
                value 2;
                description "Connected";
            }
            enum static {
                value 3;
                description " Static routes";
            }
            enum rip {
                value 4;
                description " Routing Information Protocol (RIP/RIPNG)";
            }
            enum bgp {
                value 8;
                description " Border Gateway Protocol (BGP)";
            }
            enum isis {
                value 9;
                description "ISO IS-IS";
            }
        }
        description "type definition for CML_OSPF6_ROUTE_SOURCE_TYPE_T";
    }

    typedef  cml_ospf6_dist_route_source_type_t {
        type enumeration {
            enum kernel {
                value 1;
                description "Kernel routes";
            }
            enum connected {
                value 2;
                description "Connected";
            }
            enum static {
                value 3;
                description " Static routes";
            }
            enum rip {
                value 4;
                description " Routing Information Protocol (RIP/RIPNG)";
            }
            enum bgp {
                value 8;
                description " Border Gateway Protocol (BGP)";
            }
            enum isis {
                value 9;
                description "ISO IS-IS";
            }
        }
        description "type definition for CML_OSPF6_DIST_ROUTE_SOURCE_TYPE_T";
    }

    typedef  cml_ospf6_af_route_source_type_t {
        type enumeration {
            enum kernel {
                value 1;
                description "Kernel routes";
            }
            enum connected {
                value 2;
                description "Connected";
            }
            enum static {
                value 3;
                description " Static routes";
            }
            enum rip {
                value 4;
                description " Routing Information Protocol (RIP/RIPNG)";
            }
            enum ospf {
                value 6;
                description "Open Shortest Path First (OSPF/OSPF6)";
            }
            enum bgp {
                value 8;
                description " Border Gateway Protocol (BGP)";
            }
            enum isis {
                value 9;
                description "ISO IS-IS";
            }
        }
        description "type definition for CML_OSPF6_AF_ROUTE_SOURCE_TYPE_T";
    }

    typedef  cml_ospf6_area_range_t {
        type enumeration {
            enum not-advertise {
                value 0;
                description "DoNotAdvertise this range";
            }
            enum advertise {
                value 1;
                description "Advertise this range (default)";
            }
        }
        description "type definition for CML_OSPF6_AREA_RANGE_T";
    }

    typedef  cml_ospf_interface_state_msg_t {
        type enumeration {
            enum DependUpon {
                value 0;
                description "DependUpon";
            }
            enum Down {
                value 1;
                description "Down";
            }
            enum Loopback {
                value 2;
                description "Loopback";
            }
            enum Waiting {
                value 3;
                description "Waiting";
            }
            enum Point-To-Point {
                value 4;
                description "Point-To-Point";
            }
            enum DROther {
                value 5;
                description "DROther";
            }
            enum Backup {
                value 6;
                description "Backup";
            }
            enum DR {
                value 7;
                description "DR";
            }
        }
        description "type definition for CML_OSPF_INTERFACE_STATE_MSG_T";
    }

    typedef  cml_ospf_area_t {
        type union {
            type inet:ipv4-address {

            }
            type uint32 {
                range "0..4294967295";

            }
        }
        description "type definition for CML_OSPF_AREA_T";
    }

    typedef  cml_ospf6_path_type_t {
        type enumeration {
            enum Connected {
                value 0;
                description "Connected";
            }
            enum IntraArea {
                value 1;
                description "IntraArea";
            }
            enum InterArea {
                value 2;
                description "InterArea";
            }
            enum External {
                value 3;
                description "External";
            }
            enum Discard {
                value 4;
                description "Discard";
            }
        }
        description "type definition for CML_OSPF6_PATH_TYPE_T";
    }

    typedef  cml_ospf6_path_flags_t {
        type enumeration {
            enum Type2 {
                value 1;
                description "Type2";
            }
            enum ABR {
                value 2;
                description "ABR";
            }
            enum ASBR {
                value 3;
                description "ASBR";
            }
            enum RangeMatched {
                value 4;
                description "RangeMatched";
            }
        }
        description "type definition for CML_OSPF6_PATH_FLAGS_T";
    }

    typedef  cml_ospf_action_type_t {
        type enumeration {
            enum soft {
                value 1;
                description "Soft limit";
            }
            enum hard {
                value 2;
                description "Hard limit";
            }
        }
        description "type definition for CML_OSPF_ACTION_TYPE_T";
    }

    typedef  cml_ospf_telink_local_t {
        type enumeration {
            enum disable-te-link-local {
                value 0;
                description "Disable TE Link local exchange";
            }
            enum enable-te-link-local {
                value 1;
                description "Enable TE Link local exchange";
            }
        }
        description "type definition for CML_OSPF_TELINK_LOCAL_T";
    }

    typedef  cml_ospf_route_source_type_t {
        type enumeration {
            enum kernel {
                value 1;
                description "Kernel routes";
            }
            enum connected {
                value 2;
                description "Connected";
            }
            enum static {
                value 3;
                description " Static routes";
            }
            enum rip {
                value 4;
                description " Routing Information Protocol (RIP)";
            }
            enum ospf {
                value 6;
                description "ISO OSPF";
            }
            enum bgp {
                value 8;
                description " Border Gateway Protocol (BGP)";
            }
            enum isis {
                value 9;
                description "ISO IS-IS";
            }
        }
        description "type definition for CML_OSPF_ROUTE_SOURCE_TYPE_T";
    }

    typedef  cml_ospf_dist_route_source_type_t {
        type enumeration {
            enum kernel {
                value 1;
                description "Kernel routes";
            }
            enum connected {
                value 2;
                description "Connected";
            }
            enum static {
                value 3;
                description " Static routes";
            }
            enum rip {
                value 4;
                description " Routing Information Protocol (RIP)";
            }
            enum bgp {
                value 8;
                description " Border Gateway Protocol (BGP)";
            }
            enum isis {
                value 9;
                description "ISO IS-IS";
            }
        }
        description "type definition for CML_OSPF_DIST_ROUTE_SOURCE_TYPE_T";
    }

    typedef  cml_port_sec_mode_t {
        type enumeration {
            enum default {
                value 2;
                description "dynamic mode";
            }
        }
        description "type definition for CML_PORT_SEC_MODE_T";
    }

    typedef  cml_bridge_type_t {
        type enumeration {
            enum spanning-tree {
                value 1;
                description "IEEE 801.1Q spanning-tree protocol";
            }
            enum rapid-spanning-tree {
                value 3;
                description "IEEE 801.1w rapid spanning-tree protocol";
            }
            enum multiple-spanning-tree {
                value 5;
                description "IEEE 802.1s multiple spanning-tree protocol";
            }
        }
        description "type definition for CML_BRIDGE_TYPE_T";
    }

    typedef  cml_overmactype_t {
        type enumeration {
            enum static {
                value 1;
                description "The MAC is a static entry";
            }
            enum static-priority-override {
                value 2;
                description "The MAC is a Static Management";
            }
            enum static-mgmt {
                value 3;
                description "The MAC is a Static Management with priority override";
            }
            enum static-mgmt-priority-overide {
                value 4;
                description "The MAC is a static with priority override";
            }
        }
        description "type definition for CML_OVERMACTYPE_T";
    }

    typedef  cml_enable_disable_t {
        type enumeration {
            enum disable {
                value 0;
                description "Disable";
            }
            enum enable {
                value 1;
                description "Enable";
            }
        }
        description "type definition for CML_ENABLE_DISABLE_T";
    }

    typedef  cml_sr_enable_disable_t {
        type enumeration {
            enum disable {
                value 0;
                description "Disable processing of remote  mapping server advertisement";
            }
            enum enable {
                value 1;
                description "Enables processing of remote mapping server advertisement";
            }
        }
        description "type definition for CML_SR_ENABLE_DISABLE_T";
    }

    typedef  cml_pbrinterface_t {
        type enumeration {
            enum null0 {
                value 0;
                description "Forward to no interface";
            }
            enum tunnel-te {
                value 1;
                description "Forward to MPLS-TE tunnel";
            }
        }
        description "type definition for CML_PBRINTERFACE_T";
    }

    typedef  cml_spanningtree_enable_disable_t {
        type enumeration {
            enum enable {
                value 0;
                description "Enable";
            }
            enum disable {
                value 1;
                description "Disable";
            }
        }
        description "type definition for CML_SPANNINGTREE_ENABLE_DISABLE_T";
    }

    typedef  cml_pathcost_method_t {
        type enumeration {
            enum short {
                value 0;
                description "short - Use 16 bit based values for default port path cost";
            }
            enum long {
                value 1;
                description "long  - Use 32 bit based values for default port path costs";
            }
            enum default {
                value 2;
                description "Default";
            }
        }
        description "type definition for CML_PATHCOST_METHOD_T";
    }

    typedef  cml_link_type_t {
        type enumeration {
            enum shared {
                value 0;
                description "shared - disable rapid transition";
            }
            enum point-to-point {
                value 1;
                description "point-to-point - enable rapid transition";
            }
            enum auto {
                value 2;
                description "auto - will be set to either p2p or shared based on duplex state";
            }
        }
        description "type definition for CML_LINK_TYPE_T";
    }

    typedef  cml_portedge_t {
        type enumeration {
            enum edgeport {
                value 0;
                description "edgeport - enable it as edgeport";
            }
            enum portfast {
                value 1;
                description "portfast - enable fast transitions";
            }
        }
        description "type definition for CML_PORTEDGE_T";
    }

    typedef  cml_bpdu_t {
        type enumeration {
            enum enable {
                value 0;
                description "Enable";
            }
            enum disable {
                value 1;
                description "Disable";
            }
            enum default {
                value 2;
                description "Default";
            }
        }
        description "type definition for CML_BPDU_T";
    }

    typedef  cml_bridge_topology_t {
        type enumeration {
            enum topology-none {
                value 0;
                description "Topology none";
            }
            enum ring {
                value 1;
                description "RING Topology";
            }
        }
        description "type definition for CML_BRIDGE_TOPOLOGY_T";
    }

    typedef  cml_bridge_forwarding_set_t {
        type enumeration {
            enum disable {
                value 0;
                description "disable bridge forwarding";
            }
            enum enable {
                value 1;
                description "enable bridge forwarding";
            }
        }
        description "type definition for CML_BRIDGE_FORWARDING_SET_T";
    }

    typedef  cml_bridge_mstpenable_t {
        type enumeration {
            enum enable {
                value 1;
                description "enable spanning tree protocol";
            }
        }
        description "type definition for CML_BRIDGE_MSTPENABLE_T";
    }

    typedef  cml_bridge_ageing_state {
        type enumeration {
            enum disable {
                value 0;
                description "disable bridge ageing";
            }
        }
        description "type definition for CML_BRIDGE_AGEING_STATE";
    }

    typedef  cml_ospf_domain_type_t {
        type enumeration {
            enum type-as {
                value 1;
                description "Type 0x0005";
            }
            enum type-as4 {
                value 2;
                description "Type 0x0205";
            }
            enum type-back-comp {
                value 3;
                description "Type 0x8005";
            }
            enum type-ip {
                value 4;
                description "Type 0x0105";
            }
        }
        description "type definition for CML_OSPF_DOMAIN_TYPE_T";
    }

    typedef  cml_ospf_abr_type_t {
        type enumeration {
            enum standard {
                value 1;
                description "Standard behavior (RFC2328)";
            }
            enum cisco {
                value 2;
                description " Cisco implementation (RFC3509)";
            }
            enum ibm {
                value 3;
                description "IBM implementation (RFC3509)";
            }
            enum shortcut {
                value 4;
                description "Shortcut ABR";
            }
        }
        description "type definition for CML_OSPF_ABR_TYPE_T";
    }

    typedef  cml_ospf_area_auth_type_t {
        type enumeration {
            enum simple {
                value 1;
                description "Use simple authentication";
            }
            enum message-digest {
                value 2;
                description "Use message-digest authentication";
            }
        }
        description "type definition for CML_OSPF_AREA_AUTH_TYPE_T";
    }

    typedef  cml_ospf_area_shortcut_type_t {
        type enumeration {
            enum default {
                value 0;
                description "Set default shortcutting behavior";
            }
            enum enable {
                value 1;
                description "Enable shortcutting through the area";
            }
            enum disable {
                value 2;
                description "Disable shortcutting through the area";
            }
        }
        description "type definition for CML_OSPF_AREA_SHORTCUT_TYPE_T";
    }

    typedef  cml_ospf_translator_role_t {
        type enumeration {
            enum never {
                value 0;
                description "Do not translate";
            }
            enum always {
                value 1;
                description "Translate always";
            }
            enum candidate {
                value 2;
                description "Candidate for translator (default)";
            }
        }
        description "type definition for CML_OSPF_TRANSLATOR_ROLE_T";
    }

    typedef  cml_ospf_nssa_translator_role_t {
        type enumeration {
            enum translate-never {
                value 0;
                description "Do not translate";
            }
            enum translate-always {
                value 1;
                description "Translate always";
            }
            enum translate-candidate {
                value 2;
                description "Candidate for translator (default)";
            }
        }
        description "type definition for CML_OSPF_NSSA_TRANSLATOR_ROLE_T";
    }

    typedef  cml_ospf_stub_t {
        type enumeration {
            enum stub {
                value 1;
                description "Configure OSPF area as stub";
            }
        }
        description "type definition for CML_OSPF_STUB_T";
    }

    typedef  cml_ospf_nssa_t {
        type enumeration {
            enum nssa {
                value 1;
                description "Configure OSPF area as nssa";
            }
        }
        description "type definition for CML_OSPF_NSSA_T";
    }

    typedef  cml_ospf_area_filter_type_t {
        type enumeration {
            enum access {
                value 0;
                description "Filter networks by access-list";
            }
            enum prefix {
                value 1;
                description "Filter networks by prefix-list";
            }
        }
        description "type definition for CML_OSPF_AREA_FILTER_TYPE_T";
    }

    typedef  cml_ospf_area_filter_list_prefix_t {
        type enumeration {
            enum in {
                value 0;
                description "Filter networks sent to this area";
            }
            enum out {
                value 1;
                description "Filter networks sent from this area";
            }
        }
        description "type definition for CML_OSPF_AREA_FILTER_LIST_PREFIX_T";
    }

    typedef  cml_ospf_virt_auth_key_t {
        type enumeration {
            enum null {
                value 0;
                description "unencrypted authentication key";
            }
            enum PASSWORD {
                value 1;
                description "Authentication key (8 chars)";
            }
        }
        description "type definition for CML_OSPF_VIRT_AUTH_KEY_T";
    }

    typedef  cml_ospf_virt_auth_type_t {
        type enumeration {
            enum null {
                value 0;
                description "Use no authentication";
            }
            enum simple {
                value 1;
                description "Use simple authentication";
            }
            enum message-digest {
                value 2;
                description "Use message-digest authentication";
            }
        }
        description "type definition for CML_OSPF_VIRT_AUTH_TYPE_T";
    }

    typedef  cml_ospf_restart_method_t {
        type enumeration {
            enum graceful {
                value 1;
                description "Graceful OSPF Restart (default)";
            }
            enum signaling {
                value 2;
                description "OSPF Restart Signaling";
            }
        }
        description "type definition for CML_OSPF_RESTART_METHOD_T";
    }

    typedef  cml_cspf_tie_break_t {
        type enumeration {
            enum least-fill {
                value 1;
                description "least fill";
            }
            enum most-fill {
                value 2;
                description "Most fill";
            }
            enum random {
                value 3;
                description "Random";
            }
        }
        description "type definition for CML_CSPF_TIE_BREAK_T";
    }

    typedef  cml_ospf_metric_type_t {
        type enumeration {
            enum 1 {
                value 1;
                description "Set OSPF External Type 1 metrics";
            }
            enum 2 {
                value 2;
                description "Set OSPF External Type 2 metrics";
            }
        }
        description "type definition for CML_OSPF_METRIC_TYPE_T";
    }

    typedef  cml_ospf_network_t {
        type enumeration {
            enum point-to-point {
                value 1;
                description "OSPF point-to-point network";
            }
            enum broadcast {
                value 2;
                description "OSPF broadcast multi-access network";
            }
            enum non-broadcast {
                value 3;
                description "OSPF NBMA network";
            }
            enum point-to-multipoint {
                value 4;
                description "OSPF point-to-multipoint network";
            }
            enum point-to-multipoint-non-broadcast {
                value 5;
                description "OSPF point-to-multipoint network,non-broadcast point-to-multipoint network";
            }
        }
        description "type definition for CML_OSPF_NETWORK_T";
    }

    typedef  cml_ospf_auth_type_t {
        type enumeration {
            enum null {
                value 0;
                description "Use no authentication";
            }
            enum simple {
                value 1;
                description "Use simple authentication";
            }
            enum message-digest {
                value 2;
                description "Use message-digest authentication";
            }
        }
        description "type definition for CML_OSPF_AUTH_TYPE_T";
    }

    typedef  cml_ospf_frr_tie_break_val_t {
        type enumeration {
            enum primary-path {
                value 20;
                description "Prefer backup path from ECMP set \n\t     *Default value is 20\n";
            }
            enum node-protecting {
                value 30;
                description "Prefer node protecting backup path \n\t     *Default value is 30\n";
            }
            enum interface-disjoint {
                value 60;
                description "Prefer link protecting backup path \n\t     *Default value is 60\n";
            }
            enum broadcast-interface-disjoint {
                value 70;
                description "Prefer broadcast link protecting backup path \n\t\t\t        *Default value is 70\n";
            }
            enum downstream-path {
                value 90;
                description "Prefer backup path from downstream \n\t     *Default value is 90\n";
            }
            enum secondary-path {
                value 255;
                description "Prefer non-ECMP backup path \n\t\t\t        *Default value is 255\n";
            }
        }
        description "type definition for CML_OSPF_FRR_TIE_BREAK_VAL_T";
    }

    typedef  cml_ldp_mldptype_t {
        type enumeration {
            enum p2mp {
                value 0;
                description "mldp P2MP capability";
            }
            enum mp2mp {
                value 1;
                description "mldp MP2MP capability";
            }
            enum make-before-break {
                value 2;
                description "make before break capability";
            }
            enum recursive-fec {
                value 3;
                description "recursive FEC forwarding";
            }
        }
        description "type definition for CML_LDP_MLDPTYPE_T";
    }

    typedef  cml_ldp_secondary_lsp_t {
        type enumeration {
            enum secondary {
                value 1;
                description "secondary";
            }
        }
        description "type definition for CML_LDP_SECONDARY_LSP_T";
    }

    typedef  cml_pim_mode_type_t {
        type enumeration {
            enum dense-mode {
                value 1;
                description "Enable PIM dense-mode operation";
            }
            enum sparse-mode {
                value 2;
                description "Enable PIM sparse-mode operation";
            }
            enum sparse-dense-mode {
                value 3;
                description "Enable PIM sparse-mode and dense-mode operations";
            }
        }
        description "type definition for CML_PIM_MODE_TYPE_T";
    }

    typedef  cml_pim_extended_access_list_t {
        type union {
            type string {

            }
            type uint8 {
                range "1..99";

            }
            type uint16 {
                range "1300..1999";

            }
        }
        description "type definition for CML_PIM_EXTENDED_ACCESS_LIST_T";
    }

    typedef  cml_ifname_t {
        type string;
        description "type definition for CML_IFNAME_T";
    }

    typedef  cml_ipv4_ifname_t {
        type union {
            type inet:ipv4-address {

            }
            type cml_ifname_t {

            }
        }
        description "type definition for CML_IPV4_IFNAME_T";
    }

    typedef  cml_ipv6_ifname_t {
        type union {
            type inet:ipv6-address {

            }
            type cml_ifname_t {

            }
        }
        description "type definition for CML_IPV6_IFNAME_T";
    }

    typedef  cml_pim_ssm_type_t {
        type union {
            type string {

            }
            type uint8 {
                range "1..99";

            }
        }
        description "type definition for CML_PIM_SSM_TYPE_T";
    }

    typedef  cml_ssm_default_t {
        type enumeration {
            enum default {
                value 0;
                description "Use 232/8 group range for SSM";
            }
        }
        description "type definition for CML_SSM_DEFAULT_T";
    }

    typedef  cml_ssm_range_t {
        type string;
        description "type definition for CML_SSM_RANGE_T";
    }

    typedef  cml_pim_ssm_acl_type_t {
        type union {
            type cml_ssm_range_t {

            }
            type cml_ssm_default_t {

            }
        }
        description "type definition for CML_PIM_SSM_ACL_TYPE_T";
    }

    typedef  cml_pim_debug_type_t {
        type bits {
            bit events {
                position 0;
                description "PIM events";
            }
            bit packet-in {
                position 1;
                description "PIM packet,Incoming PIM packet";
            }
            bit packet-out {
                position 2;
                description "PIM packet,Outgoing PIM packet";
            }
            bit state {
                position 3;
                description "PIM state";
            }
            bit mfc {
                position 4;
                description "PIM MFC updates";
            }
            bit timer-hello-ht {
                position 5;
                description "PIM timers,Hello Timers,Hello timer";
            }
            bit timer-hello-nlt {
                position 6;
                description "PIM timers,Hello Timers,Neighbor Liveliness timer";
            }
            bit timer-hello-tht {
                position 7;
                description "PIM timers,Hello Timers,Triggered Hello timer";
            }
            bit timer-joinprune-jt {
                position 8;
                description "PIM timers,JoinPrune Timers,JoinPrune timer";
            }
            bit timer-joinprune-et {
                position 9;
                description "PIM timers,JoinPrune Timers,Expiry timer";
            }
            bit timer-joinprune-ppt {
                position 10;
                description "PIM timers,JoinPrune Timers,Prune Pending timer";
            }
            bit timer-joinprune-kat {
                position 11;
                description "PIM timers,JoinPrune Timers,Keep Alive timer";
            }
            bit timer-joinprune-ot {
                position 12;
                description "PIM timers,JoinPrune Timers,Override timer";
            }
            bit timer-assert {
                position 13;
                description "PIM timers,Assert Timers";
            }
            bit timer-register {
                position 14;
                description "PIM timers,Register Timers";
            }
            bit timer-bsr-bst {
                position 15;
                description "PIM timers,BSR Timers,Bootstrap timer";
            }
            bit timer-bsr-crp {
                position 16;
                description "PIM timers,BSR Timers,Candidate-RP timer";
            }
            bit mib {
                position 17;
                description "PIM mib";
            }
            bit nsm {
                position 18;
                description "NSM message";
            }
            bit nexthop {
                position 19;
                description "PIM nexthop";
            }
            bit mtrace {
                position 20;
                description "Mtrace messages";
            }
        }
        description "type definition for CML_PIM_DEBUG_TYPE_T";
    }

    typedef  cml_mrib_ip_type_t {
        type enumeration {
            enum ip {
                value 1;
                description "Internet Protocol(IP)";
            }
        }
        description "type definition for CML_MRIB_IP_TYPE_T";
    }

    typedef  cml_mrib_ipv6_type_t {
        type enumeration {
            enum ipv6 {
                value 0;
                description "Internet Protocol(IPv6)";
            }
        }
        description "type definition for CML_MRIB_IPV6_TYPE_T";
    }

    typedef  cml_mrib4_debug_t {
        type bits {
            bit event {
                position 0;
                description "None";
            }
            bit vif {
                position 1;
                description "None";
            }
            bit mrt {
                position 2;
                description "None";
            }
            bit stats {
                position 3;
                description "None";
            }
            bit fib-msg {
                position 4;
                description "None";
            }
            bit register-msg {
                position 5;
                description "None";
            }
            bit nsm-msg {
                position 6;
                description "None";
            }
            bit mrib-msg {
                position 7;
                description "None";
            }
            bit mtrace {
                position 8;
                description "None";
            }
            bit mtrace-detail {
                position 9;
                description "None";
            }
        }
        description "type definition for CML_MRIB4_DEBUG_T";
    }

    typedef  cml_mrib6_debug_t {
        type bits {
            bit event {
                position 0;
                description "None";
            }
            bit vif {
                position 1;
                description "None";
            }
            bit mrt {
                position 2;
                description "None";
            }
            bit stats {
                position 3;
                description "None";
            }
            bit fib-msg {
                position 4;
                description "None";
            }
            bit register-msg {
                position 5;
                description "None";
            }
            bit nsm-msg {
                position 6;
                description "None";
            }
            bit mrib-msg {
                position 7;
                description "None";
            }
            bit mtrace {
                position 8;
                description "None";
            }
            bit mtrace-detail {
                position 9;
                description "None";
            }
        }
        description "type definition for CML_MRIB6_DEBUG_T";
    }

    typedef  cml_igmp_debug_t {
        type bits {
            bit encode {
                position 0;
                description "None";
            }
            bit decode {
                position 1;
                description "None";
            }
            bit events {
                position 2;
                description "None";
            }
            bit fsm {
                position 3;
                description "None";
            }
            bit tib {
                position 4;
                description "None";
            }
        }
        description "type definition for CML_IGMP_DEBUG_T";
    }

    typedef  cml_mld_debug_t {
        type bits {
            bit encode {
                position 0;
                description "None";
            }
            bit decode {
                position 1;
                description "None";
            }
            bit events {
                position 2;
                description "None";
            }
            bit fsm {
                position 3;
                description "None";
            }
            bit tib {
                position 4;
                description "None";
            }
        }
        description "type definition for CML_MLD_DEBUG_T";
    }

    typedef  cml_bandwidthconstraintmode_t {
        type enumeration {
            enum MAM {
                value 0;
                description "MAM";
            }
            enum RSDL {
                value 1;
                description "RSDL";
            }
            enum MAR {
                value 2;
                description "MAR";
            }
        }
        description "type definition for CML_BANDWIDTHCONSTRAINTMODE_T";
    }

    typedef  cml_mpls_admn_status_t {
        type enumeration {
            enum up {
                value 1;
                description "None";
            }
            enum down {
                value 2;
                description "None";
            }
            enum testing {
                value 3;
                description "None";
            }
        }
        description "type definition for CML_MPLS_ADMN_STATUS_T";
    }

    typedef  cml_mpls_opr_status_t {
        type enumeration {
            enum up {
                value 1;
                description "None";
            }
            enum down {
                value 2;
                description "None";
            }
            enum testing {
                value 3;
                description "None";
            }
            enum dormant {
                value 4;
                description "None";
            }
            enum not-persent {
                value 5;
                description "None";
            }
            enum ll-down {
                value 6;
                description "None";
            }
        }
        description "type definition for CML_MPLS_OPR_STATUS_T";
    }

    typedef  cml_mpls_row_status_t {
        type enumeration {
            enum active {
                value 1;
                description "None";
            }
            enum not-in-severice {
                value 2;
                description "None";
            }
            enum not-ready {
                value 3;
                description "None";
            }
            enum create-go {
                value 4;
                description "None";
            }
            enum create-wait {
                value 5;
                description "None";
            }
            enum destroy {
                value 6;
                description "None";
            }
        }
        description "type definition for CML_MPLS_ROW_STATUS_T";
    }

    typedef  cml_mpls_bfd_flag_t {
        type enumeration {
            enum configured {
                value 0;
                description "None";
            }
            enum enabled {
                value 1;
                description "None";
            }
            enum disable {
                value 2;
                description "None";
            }
        }
        description "type definition for CML_MPLS_BFD_FLAG_T";
    }

    typedef  cml_nsm_mpls_tpid_t {
        type enumeration {
            enum 88a8 {
                value 34984;
                description "Set tpid value as 88a8";
            }
            enum 9100 {
                value 37120;
                description "Set tpid value as 9100";
            }
        }
        description "type definition for CML_NSM_MPLS_TPID_T";
    }

    typedef  cml_nsm_mpls_admin_status_t {
        type enumeration {
            enum down {
                value 0;
                description "Set the admin role as Down";
            }
            enum up {
                value 1;
                description "Set the admin role as UP";
            }
        }
        description "type definition for CML_NSM_MPLS_ADMIN_STATUS_T";
    }

    typedef  cml_nsm_mpls_if_ether_vctype_t {
        type enumeration {
            enum ethernet {
                value 5;
                description "Ethernet";
            }
        }
        description "type definition for CML_NSM_MPLS_IF_ETHER_VCTYPE_T";
    }

    typedef  cml_nsm_mpls_if_vlan_vctype_t {
        type enumeration {
            enum vlan {
                value 4;
                description "VLAN";
            }
        }
        description "type definition for CML_NSM_MPLS_IF_VLAN_VCTYPE_T";
    }

    typedef  cml_nsm_mpls_bfd_t {
        type enumeration {
            enum ldp {
                value 0;
                description "LDP type LSP";
            }
            enum static {
                value 2;
                description "Static type LSP";
            }
        }
        description "type definition for CML_NSM_MPLS_BFD_T";
    }

    typedef  cml_rsvp_te_srlg_disjoint_type_t {
        type enumeration {
            enum forced {
                value 1;
                description "Seek complete SRLG-Disjoint path";
            }
            enum preferred {
                value 2;
                description "Prefer SRLG Disjoint path over normal path";
            }
        }
        description "type definition for CML_RSVP_TE_SRLG_DISJOINT_TYPE_T";
    }

    typedef  cml_bfd_rsvp_lsp_t {
        type enumeration {
            enum rsvp {
                value 1;
                description "RSVP type LSP";
            }
        }
        description "type definition for CML_BFD_RSVP_LSP_T";
    }

    typedef  cml_nsm_mpls_bfd_type_t {
        type enumeration {
            enum ldp {
                value 0;
                description "LDP type LSP";
            }
            enum rsvp {
                value 1;
                description "RSVP type LSP";
            }
            enum static {
                value 2;
                description "Static type LSP";
            }
        }
        description "type definition for CML_NSM_MPLS_BFD_TYPE_T";
    }

    typedef  cml_nsm_mpls_vccp_state_t {
        type enumeration {
            enum start {
                value 1;
                description "start bfd-vccv";
            }
            enum stop {
                value 2;
                description "stop bfd-vccv";
            }
        }
        description "type definition for CML_NSM_MPLS_VCCP_STATE_T";
    }

    typedef  cml_ospf_row_status {
        type enumeration {
            enum row-status-active {
                value 1;
                description "Active Row status";
            }
            enum row-status-notinservice {
                value 2;
                description "Row status Not in Service";
            }
            enum row-status-notready {
                value 3;
                description "Row status Not Ready";
            }
            enum row-status-createandgo {
                value 4;
                description "Row status Create and Go";
            }
            enum row-status-createandwait {
                value 5;
                description "Row status Create and Wait";
            }
        }
        description "type definition for CML_OSPF_ROW_STATUS";
    }

    typedef  nsm_vpls_ether_action_t {
        type enumeration {
            enum no-op {
                value 1;
                description "Set action as add";
            }
            enum add {
                value 2;
                description "Set action as no operation";
            }
        }
        description "type definition for NSM_VPLS_ETHER_ACTION_T";
    }

    typedef  nsm_vpls_vlan_action_t {
        type enumeration {
            enum no-op {
                value 1;
                description "Set action as add";
            }
            enum remove {
                value 3;
                description "Set action as remove";
            }
            enum replace {
                value 4;
                description "Set action as replace";
            }
        }
        description "type definition for NSM_VPLS_VLAN_ACTION_T";
    }

    typedef  cml_nsm_vpls_peer_tunnel_dir_t {
        type enumeration {
            enum forward {
                value 0;
                description "Tunnel Direction - Forward tunnel identifier - Default Value";
            }
            enum reverse {
                value 1;
                description "Tunnel Direction - Reverse tunnel identifier";
            }
        }
        description "type definition for CML_NSM_VPLS_PEER_TUNNEL_DIR_T";
    }

    typedef  cml_nsm_vpls_peer_type_t {
        type enumeration {
            enum manual {
                value 1;
                description "No signaling is used to set-up the Virtual Circuit";
            }
        }
        description "type definition for CML_NSM_VPLS_PEER_TYPE_T";
    }

    typedef  cml_nsm_vpls_ftn_entry_t {
        type enumeration {
            enum secondary {
                value 0;
                description "Secondary LSP";
            }
            enum primary {
                value 1;
                description "Primary LSP (default)";
            }
        }
        description "type definition for CML_NSM_VPLS_FTN_ENTRY_T";
    }

    typedef  cml_vpls_redundancy_role_t {
        type enumeration {
            enum primary {
                value 0;
                description "Set role as primary";
            }
            enum secondary {
                value 1;
                description "Set role as secondary";
            }
        }
        description "type definition for CML_VPLS_REDUNDANCY_ROLE_T";
    }

    typedef  cml_nsm_vpls_opcode_t {
        type enumeration {
            enum swap {
                value 3;
                description "Swap incoming label";
            }
        }
        description "type definition for CML_NSM_VPLS_OPCODE_T";
    }

    typedef  cml_nsm_mpls_ipv6opcode_t {
        type enumeration {
            enum swap {
                value 3;
                description "Swap incoming label";
            }
        }
        description "type definition for CML_NSM_MPLS_IPV6OPCODE_T";
    }

    typedef  cml_nsm_vpls_popopcode_t {
        type enumeration {
            enum pop {
                value 2;
                description "pop incoming label";
            }
        }
        description "type definition for CML_NSM_VPLS_POPOPCODE_T";
    }

    typedef  cml_vpls_vc_style1_t {
        type enumeration {
            enum peer {
                value 2;
                description "Mesh Peer";
            }
        }
        description "type definition for CML_VPLS_VC_STYLE1_T";
    }

    typedef  cml_vpls_vc_style2_t {
        type enumeration {
            enum spoke-vc {
                value 3;
                description "Spoke Virtual Circuit";
            }
        }
        description "type definition for CML_VPLS_VC_STYLE2_T";
    }

    typedef  cml_l2vpn_protocol_t {
        type enumeration {
            enum ldp-autodiscovery-bgp {
                value 8;
                description "Specify the protocol as LDP for MPLS Layer-2 Virtual Circuit,Specify the protocol with autodiscovery-bgp for MPLS Layer-2 Virtual Circuit";
            }
        }
        description "type definition for CML_L2VPN_PROTOCOL_T";
    }

    typedef  cml_l2vpn_vc_type_t {
        type enumeration {
            enum ethernet {
                value 5;
                description "Ethernet";
            }
            enum hdlc {
                value 6;
                description "Hdlc";
            }
            enum ppp {
                value 7;
                description "Point-to-Point";
            }
            enum tdm-E1 {
                value 17;
                description "TDM - E1 line";
            }
            enum tdm-T1 {
                value 18;
                description "TDM - T1 line";
            }
            enum tdm-E3 {
                value 19;
                description "TDM - E3 line";
            }
            enum tdm-T3 {
                value 20;
                description "TDM - T3 line";
            }
        }
        description "type definition for CML_L2VPN_VC_TYPE_T";
    }

    typedef  cml_metric_style_t {
        type enumeration {
            enum narrow {
                value 1;
                description "Use old style of TLVs with narrow metric";
            }
            enum wide {
                value 2;
                description "Use new style of TLVs to carry wider metric";
            }
            enum transition {
                value 3;
                description "Send and accept both styles of TLVs during transition";
            }
            enum narrow-transition {
                value 4;
                description "Use old style of TLVs with narrow metric,Send and accept both styles of TLVs during transition";
            }
            enum wide-transition {
                value 5;
                description "Use old style of TLVs with wide metric, Send and accept both styles of TLVs during transition";
            }
        }
        description "type definition for CML_METRIC_STYLE_T";
    }

    typedef  cml_transition_metric_style_t {
        type enumeration {
            enum narrow {
                value 1;
                description "Use old style of TLVs with narrow metric";
            }
            enum wide {
                value 2;
                description "Use new style of TLVs to carry wider metric";
            }
        }
        description "type definition for CML_TRANSITION_METRIC_STYLE_T";
    }

    typedef  cml_password_t {
        type string {
            length 1..8;
            pattern "[a-zA-Z0-9].*";
        }
        description "type definition for CML_PASSWORD_T";
    }

    typedef  cml_system_hostname_t {
        type string {
            length 1..64;
            pattern "[a-zA-Z0-9\\-].*";
        }
        description "type definition for CML_SYSTEM_HOSTNAME_T";
    }

    typedef  cml_username_t {
        type string {
            length 1..255;
            pattern "[\\-a-zA-Z0-9].*";
        }
        description "type definition for CML_USERNAME_T";
    }

    typedef  cml_wrap_t {
        type enumeration {
            enum off {
                value 0;
                description "Disable autowrap";
            }
            enum on {
                value 1;
                description "Enable autowrap";
            }
        }
        description "type definition for CML_WRAP_T";
    }

    typedef  cml_interface_t {
        type enumeration {
            enum interface {
                value 0;
                description "Use LDP or TDP (Adapt to peer on multiaccess interface)";
            }
        }
        description "type definition for CML_INTERFACE_T";
    }

    typedef  cml_mtu_t {
        type union {
            type uint16 {

            }
            type uint16 {

            }
            type uint16 {

            }
            type uint16 {

            }
            type uint16 {

            }
            type uint16 {

            }
            type uint16 {

            }
            type uint16 {

            }
            type uint16 {

            }
        }
        description "type definition for CML_MTU_T";
    }

    typedef  cml_area_t {
        type union {
            type uint32 {
                range "0..4294967295";

            }
            type inet:ipv4-address {

            }
        }
        description "type definition for CML_AREA_T";
    }

    typedef  cml_self_test_t {
        type enumeration {
            enum extended {
                value 0;
                description "Extended self test";
            }
            enum fast {
                value 1;
                description "Fast self test";
            }
            enum none {
                value 2;
                description "Turn off self test";
            }
        }
        description "type definition for CML_SELF_TEST_T";
    }

    typedef  cml_baud_rate_t {
        type enumeration {
            enum 9600 {
                value 9600;
                description "9600";
            }
            enum 19200 {
                value 19200;
                description "19200";
            }
            enum 38400 {
                value 38400;
                description "38400";
            }
            enum 115200 {
                value 115200;
                description "115200";
            }
        }
        description "type definition for CML_BAUD_RATE_T";
    }

    typedef  cml_ospf6_instance_t {
        type union {
            type uint8 {

            }
            type uint8 {

            }
            type uint8 {

            }
            type uint8 {

            }
        }
        description "type definition for CML_OSPF6_INSTANCE_T";
    }

    typedef  cml_access_group_direction_t {
        type enumeration {
            enum in {
                value 0;
                description "inbound packets";
            }
            enum out {
                value 1;
                description "outbound packets";
            }
        }
        description "type definition for CML_ACCESS_GROUP_DIRECTION_T";
    }

    typedef  cml_vlan_id_t {
        type uint16 {
             range 0..65535;
        }
        description "type definition for CML_VLAN_ID_T";
    }

    typedef  cml_addr_or_script_t {
        type union {
            type inet:ipv4-address {

            }
            type string {

            }
        }
        description "type definition for CML_ADDR_OR_SCRIPT_T";
    }

    typedef  cml_gi_media_t {
        type enumeration {
            enum 10-full {
                value 0;
                description "10BaseT full duplex";
            }
            enum 10-half {
                value 1;
                description "10BaseT half duplex";
            }
            enum 100-auto {
                value 2;
                description "100BaseTX duplex auto-negotiation and speed up to 100Mbps";
            }
            enum 100-full {
                value 3;
                description "100BaseTX full duplex";
            }
            enum 100-half {
                value 4;
                description "100BaseTX half duplex";
            }
            enum 1000-full {
                value 5;
                description "1000BaseT full duplex";
            }
            enum 1000-half {
                value 6;
                description "1000BaseT half duplex";
            }
            enum auto {
                value 7;
                description "Automatically negotiate speed";
            }
        }
        description "type definition for CML_GI_MEDIA_T";
    }

    typedef  cml_te_media_t {
        type enumeration {
            enum 1000-full {
                value 0;
                description "1000BaseX full duplex";
            }
            enum 10000-full {
                value 1;
                description "10GBase(SR/LR/.../T) full duplex";
            }
            enum auto {
                value 2;
                description "Automatically negotiate speed";
            }
        }
        description "type definition for CML_TE_MEDIA_T";
    }

    typedef  cml_port_type_t {
        type enumeration {
            enum nni {
                value 0;
                description "nni";
            }
        }
        description "type definition for CML_PORT_TYPE_T";
    }

    typedef  cml_mode_t {
        type enumeration {
            enum active {
                value 0;
                description "Enable LACP unconditionally";
            }
            enum auto {
                value 1;
                description "Enable PAgP only if a PAgP device is detected";
            }
            enum desirable {
                value 2;
                description "Enable PAgP unconditionally";
            }
            enum on {
                value 3;
                description "Enable Etherchannel only";
            }
            enum passive {
                value 4;
                description "Enable LACP only if a LACP device is detected";
            }
        }
        description "type definition for CML_MODE_T";
    }

    typedef  cml_channel_protocol_t {
        type enumeration {
            enum lacp {
                value 0;
                description "Prepare interface for LACP protocol";
            }
            enum pagp {
                value 1;
                description "Prepare interface for PAgP protocol";
            }
        }
        description "type definition for CML_CHANNEL_PROTOCOL_T";
    }

    typedef  cml_encapsulation_t {
        type enumeration {
            enum mpls {
                value 0;
                description "Use MPLS encapsulation";
            }
            enum l2tpv3 {
                value 1;
                description "Use L2TPv3 encapsulation";
            }
        }
        description "type definition for CML_ENCAPSULATION_T";
    }

    typedef  cml_sequence_t {
        type enumeration {
            enum both {
                value 0;
                description "Transmit and receive sequence numbers";
            }
            enum receive {
                value 1;
                description "Receive sequence numbers";
            }
            enum transmit {
                value 2;
                description "Transmit sequence numbers";
            }
        }
        description "type definition for CML_SEQUENCE_T";
    }

    typedef  cml_group_enum_t {
        type enumeration {
            enum global {
                value 0;
                description "Attach global PPPoE group";
            }
        }
        description "type definition for CML_GROUP_ENUM_T";
    }

    typedef  cml_group_t {
        type union {
            type cml_group_enum_t {

            }
            type string {

            }
        }
        description "type definition for CML_GROUP_T";
    }

    typedef  cml_rate_type_t {
        type uint32 {
             range 0..4294967295;
        }
        description "type definition for CML_RATE_TYPE_T";
    }

    typedef  cml_ip_rate_t {
        type union {
            type cml_rate_type_t {

            }
            type string {

            }
        }
        description "type definition for CML_IP_RATE_T";
    }

    typedef  cml_spt_name_t {
        type enumeration {
            enum mst {
                value 0;
                description "Global Spanning-Tree configuration";
            }
        }
        description "type definition for CML_SPT_NAME_T";
    }

    typedef  cml_ospf_route_t {
        type enumeration {
            enum connected {
                value 0;
                description "Connected";
            }
            enum kernel {
                value 1;
                description "Kernel routes";
            }
            enum static {
                value 2;
                description "Static routes";
            }
        }
        description "type definition for CML_OSPF_ROUTE_T";
    }

    typedef  cml_policy_map_t {
        type enumeration {
            enum ether-type {
                value 0;
                description "Ethertype";
            }
            enum port {
                value 1;
                description "Entire port";
            }
            enum snpa {
                value 2;
                description "Match a specific MAC address";
            }
            enum vid {
                value 3;
                description "Vlan tag";
            }
        }
        description "type definition for CML_POLICY_MAP_T";
    }

    typedef  cml_policy_map_id_t {
        type union {
            type cml_ip_prefix_addr_t {

            }
            type cml_policy_map_t {

            }
        }
        description "type definition for CML_POLICY_MAP_ID_T";
    }

    typedef  cml_ether_vals_t {
        type enumeration {
            enum ipv4 {
                value 0;
                description "ipv4";
            }
            enum ipv6 {
                value 1;
                description "ipv6";
            }
            enum mpls-unicast {
                value 2;
                description "mpls-unicast";
            }
            enum mpls-multicast {
                value 3;
                description "mpls-multicast";
            }
            enum arp {
                value 4;
                description "arp";
            }
            enum ppoe-discover {
                value 5;
                description "ppoe-discover";
            }
            enum ppoe-session {
                value 6;
                description "ppoe-session";
            }
        }
        description "type definition for CML_ETHER_VALS_T";
    }

    typedef  cml_endis_t {
        type enumeration {
            enum disable {
                value 0;
                description "disable";
            }
            enum enable {
                value 1;
                description "enable";
            }
        }
        description "type definition for CML_ENDIS_T";
    }

    typedef  cml_route_map_type_t {
        type enumeration {
            enum client {
                value 0;
                description "Match dynamic clients";
            }
            enum ip {
                value 1;
                description "IP information";
            }
            enum tag {
                value 2;
                description "Tag value for destination routing protocol";
            }
        }
        description "type definition for CML_ROUTE_MAP_TYPE_T";
    }

    typedef  cml_mirror_direction_t {
        type enumeration {
            enum bidir {
                value 0;
                description "Input and output mirroring";
            }
            enum in {
                value 1;
                description "Input mirroring";
            }
            enum out {
                value 2;
                description "Output mirroring";
            }
        }
        description "type definition for CML_MIRROR_DIRECTION_T";
    }

    typedef  cml_route_map_action_t {
        type enumeration {
            enum deny {
                value 0;
                description "Route map denies set operations";
            }
            enum permit {
                value 1;
                description "Route map permits set operations";
            }
        }
        description "type definition for CML_ROUTE_MAP_ACTION_T";
    }

    typedef  cml_queues_count_t {
        type enumeration {
            enum 256 {
                value 256;
                description "None";
            }
            enum 512 {
                value 512;
                description "None";
            }
            enum 1024 {
                value 1024;
                description "None";
            }
            enum 2048 {
                value 2048;
                description "None";
            }
        }
        description "type definition for CML_QUEUES_COUNT_T";
    }

    typedef  cml_hostp_tacacs_t {
        type enumeration {
            enum tacacs+ {
                value 1;
                description "Command to enable/disable features";
            }
        }
        description "type definition for CML_HOSTP_TACACS_T";
    }

    typedef  cml_hostp_key_type_t {
        type enumeration {
            enum 0 {
                value 0;
                description "To specify shared key in clear-text form";
            }
            enum 7 {
                value 1;
                description "To specify shared key in encrypted form";
            }
        }
        description "type definition for CML_HOSTP_KEY_TYPE_T";
    }

    typedef  cml_hostp_local_type_t {
        type enumeration {
            enum local {
                value 1;
                description "Group list can be followed by local";
            }
        }
        description "type definition for CML_HOSTP_LOCAL_TYPE_T";
    }

    typedef  cml_hostp_local_none_type_t {
        type enumeration {
            enum local {
                value 0;
                description "Group list can be followed by local";
            }
            enum none {
                value 1;
                description "Group list can be followed by none";
            }
        }
        description "type definition for CML_HOSTP_LOCAL_NONE_TYPE_T";
    }

    typedef  cml_hostp_none_type_t {
        type enumeration {
            enum none {
                value 1;
                description "Group list can be followed by none";
            }
        }
        description "type definition for CML_HOSTP_NONE_TYPE_T";
    }

    typedef  cml_snmp_oid_tree_t {
        type enumeration {
            enum included {
                value 1;
                description "Specify to include";
            }
            enum excluded {
                value 2;
                description "Specify to exclude";
            }
        }
        description "type definition for CML_SNMP_OID_TREE_T";
    }

    typedef  cml_snmp_link_type_t {
        type enumeration {
            enum linkUp {
                value 1;
                description "IETF Link state up notification";
            }
            enum linkDown {
                value 2;
                description "IETF Link state down notification";
            }
        }
        description "type definition for CML_SNMP_LINK_TYPE_T";
    }

    typedef  cml_snmp_user_t {
        type enumeration {
            enum network-operator {
                value 1;
                description "System configured role for read-only";
            }
            enum network-admin {
                value 2;
                description "System configured role for read-write";
            }
        }
        description "type definition for CML_SNMP_USER_T";
    }

    typedef  cml_snmp_group_t {
        type enumeration {
            enum network-operator {
                value 1;
                description "System configured group for read-only(default)";
            }
            enum network-admin {
                value 2;
                description "System configured group for read-write";
            }
        }
        description "type definition for CML_SNMP_GROUP_T";
    }

    typedef  cml_ospf6_metric_type_t {
        type enumeration {
            enum 1 {
                value 1;
                description "Set OSPF External Type 1 metrics";
            }
            enum 2 {
                value 2;
                description "Set OSPF External Type 2 metrics";
            }
        }
        description "type definition for CML_OSPF6_METRIC_TYPE_T";
    }

    typedef  cml_udld_mode_type_t {
        type enumeration {
            enum normal {
                value 0;
                description "UDLD Normal Mode";
            }
            enum aggressive {
                value 1;
                description "UDLD Aggressive";
            }
        }
        description "type definition for CML_UDLD_MODE_TYPE_T";
    }

    typedef  cml_udld_state_type_t {
        type enumeration {
            enum enable {
                value 0;
                description "Enable UDLD on an interface";
            }
            enum disable {
                value 1;
                description "Disable UDLD on an interface";
            }
        }
        description "type definition for CML_UDLD_STATE_TYPE_T";
    }

    typedef  cml_udld_t {
        type enumeration {
            enum disable {
                value 0;
                description "Disable UDLD";
            }
            enum enable {
                value 1;
                description "Enable UDLD";
            }
        }
        description "type definition for CML_UDLD_T";
    }

    typedef  cml_snmp_auth_t {
        type enumeration {
            enum md5 {
                value 1;
                description "Specify md5 authentication";
            }
            enum sha {
                value 2;
                description "Specify sha authentication";
            }
        }
        description "type definition for CML_SNMP_AUTH_T";
    }

    typedef  cml_snmp_priv_t {
        type enumeration {
            enum des {
                value 1;
                description "Specify des privilege";
            }
            enum aes {
                value 2;
                description "Specify aes privilege";
            }
        }
        description "type definition for CML_SNMP_PRIV_T";
    }

    typedef  cml_snmp_version_t {
        type enumeration {
            enum 1 {
                value 1;
                description "Use SNMPv1";
            }
            enum 2c {
                value 2;
                description "Use SNMPv2c";
            }
        }
        description "type definition for CML_SNMP_VERSION_T";
    }

    typedef  cml_snmp_informs_version_t {
        type enumeration {
            enum 2c {
                value 2;
                description "Use SNMPv2c";
            }
        }
        description "type definition for CML_SNMP_INFORMS_VERSION_T";
    }

    typedef  cml_snmp_view_version_t {
        type enumeration {
            enum v1 {
                value 1;
                description "Specify v1 for SNMPv1";
            }
            enum v2c {
                value 2;
                description "Specify v2c for SNMPv2c";
            }
        }
        description "type definition for CML_SNMP_VIEW_VERSION_T";
    }

    typedef  cml_snmp_informs_t {
        type enumeration {
            enum informs {
                value 2;
                description "Send Inform messages to this host";
            }
        }
        description "type definition for CML_SNMP_INFORMS_T";
    }

    typedef  cml_snmp_trap_t {
        type enumeration {
            enum traps {
                value 1;
                description "Send Traps messages to this host";
            }
        }
        description "type definition for CML_SNMP_TRAP_T";
    }

    typedef  cml_version3_t {
        type enumeration {
            enum noauth {
                value 1;
                description "Use the SNMPv3 noAuthNoPriv Security Level";
            }
            enum auth {
                value 2;
                description "Use the SNMPv3 authNoPriv Security Level";
            }
            enum priv {
                value 3;
                description "Use the SNMPv3 authPriv Security Level";
            }
        }
        description "type definition for CML_VERSION3_T";
    }

    typedef  cml_snmp_access_t {
        type enumeration {
            enum ro {
                value 1;
                description "Read-only access with this community string";
            }
        }
        description "type definition for CML_SNMP_ACCESS_T";
    }

    typedef  cml_vrrp_vmac_t {
        type enumeration {
            enum enable {
                value 1;
                description "Enabled";
            }
            enum disable {
                value 2;
                description "Disabled";
            }
        }
        description "type definition for CML_VRRP_VMAC_T";
    }

    typedef  cml_vrrp_accept_mode_t {
        type enumeration {
            enum true {
                value 1;
                description "Accept mode enabled";
            }
            enum false {
                value 2;
                description "Accept mode disabled";
            }
        }
        description "type definition for CML_VRRP_ACCEPT_MODE_T";
    }

    typedef  cml_vrrp_preempt_mode_t {
        type enumeration {
            enum true {
                value 1;
                description "Preemption enabled";
            }
            enum false {
                value 2;
                description "Preemption disabled";
            }
        }
        description "type definition for CML_VRRP_PREEMPT_MODE_T";
    }

    typedef  cml_lldp_admin_status_t {
        type enumeration {
            enum rxonly {
                value 2;
                description "default";
            }
            enum txonly {
                value 4;
                description "Group list can be followed by 'local'";
            }
            enum txrx {
                value 8;
                description "default";
            }
        }
        description "type definition for CML_LLDP_ADMIN_STATUS_T";
    }

    typedef  cml_lldp_chassis_id_t {
        type enumeration {
            enum chassis-component {
                value 0;
                description "default";
            }
            enum if-alias {
                value 1;
                description "default";
            }
            enum port-component {
                value 2;
                description "Group list can be followed by 'local'";
            }
            enum mac-address {
                value 3;
                description "Group list can be followed by 'local'";
            }
            enum ip-address {
                value 4;
                description "Group list can be followed by 'local'";
            }
            enum if-name {
                value 5;
                description "Group list can be followed by 'local'";
            }
            enum local {
                value 6;
                description "Group list can be followed by 'local'";
            }
        }
        description "type definition for CML_LLDP_CHASSIS_ID_T";
    }

    typedef  cml_lldp_port_id_t {
        type enumeration {
            enum if-alias {
                value 0;
                description "default";
            }
            enum port-component {
                value 1;
                description "Group list can be followed by 'local'";
            }
            enum mac-address {
                value 2;
                description "Group list can be followed by 'local'";
            }
            enum ip-address {
                value 3;
                description "Group list can be followed by 'local'";
            }
            enum if-name {
                value 4;
                description "Group list can be followed by 'local'";
            }
            enum agent-circuit-id {
                value 5;
                description "Group list can be followed by 'local'";
            }
            enum local {
                value 6;
                description "Group list can be followed by 'local'";
            }
        }
        description "type definition for CML_LLDP_PORT_ID_T";
    }

    typedef  cml_lldp_port_addr_t {
        type enumeration {
            enum mac-address {
                value 1;
                description "default";
            }
            enum ip-address {
                value 2;
                description "Group list can be followed by 'local'";
            }
        }
        description "type definition for CML_LLDP_PORT_ADDR_T";
    }

    typedef  cml_lldp_set_state_t {
        type enumeration {
            enum disable {
                value 0;
                description "Disable";
            }
            enum enable {
                value 1;
                description "Enable";
            }
        }
        description "type definition for CML_LLDP_SET_STATE_T";
    }

    typedef  cml_lldp_tlv_mode_t {
        type enumeration {
            enum manual {
                value 1;
                description "Disable";
            }
            enum auto {
                value 2;
                description "Enable";
            }
        }
        description "type definition for CML_LLDP_TLV_MODE_T";
    }

    typedef  cml_lldp_ieee_8023_t {
        type bits {
            bit mac-phy {
                position 0;
                description "mac-phy TLV";
            }
            bit max-mtu-size {
                position 1;
                description "max-mtu-size TLV";
            }
        }
        description "type definition for CML_LLDP_IEEE_8023_T";
    }

    typedef  cml_lldp_ieee_8021_t {
        type bits {
            bit port-vlanid {
                position 0;
                description "port-vlanid TLV";
            }
            bit port-ptcl-vlanid {
                position 1;
                description "port-ptcl-vlanid TLV";
            }
            bit vlan-name {
                position 2;
                description "vlan-name TLV";
            }
            bit ptcl-identity {
                position 3;
                description "ptcl-identity TLV";
            }
            bit vid-digest {
                position 4;
                description "vid-digest TLV";
            }
            bit mgmt-vid {
                position 5;
                description "mgmt-vid TLV";
            }
            bit link-agg {
                position 6;
                description "link-agg TLV";
            }
        }
        description "type definition for CML_LLDP_IEEE_8021_T";
    }

    typedef  cml_lldp_basic_t {
        type bits {
            bit port-description {
                position 0;
                description "port-description TLV";
            }
            bit system-name {
                position 1;
                description "system-name TLV";
            }
            bit system-description {
                position 2;
                description "system-description TLV";
            }
            bit system-capabilities {
                position 3;
                description "system-capabilities TLV";
            }
            bit management-address {
                position 4;
                description "management-address TLV";
            }
        }
        description "type definition for CML_LLDP_BASIC_T";
    }

    typedef  cml_vxlan_mode_t {
        type enumeration {
            enum vxlan {
                value 1;
                description "vxlan mode or nvrge mode ";
            }
        }
        description "type definition for CML_VXLAN_MODE_T";
    }

    typedef  cml_lacp_timeout_t {
        type enumeration {
            enum long {
                value 0;
                description "Set LACP long timeout";
            }
            enum short {
                value 1;
                description "Set LACP short timeout";
            }
        }
        description "type definition for CML_LACP_TIMEOUT_T";
    }

    typedef  cml_ssh_key_rsa_dsa_t {
        type enumeration {
            enum dsa {
                value 1;
                description "DSA keys";
            }
            enum rsa {
                value 2;
                description "RSA keys";
            }
        }
        description "type definition for CML_SSH_KEY_RSA_DSA_T";
    }

    typedef  cml_nsm_mpls_log_t {
        type bits {
            bit error {
                position 0;
                description "Log Error message in MPLS Forwarder";
            }
            bit warning {
                position 1;
                description "Log Warning message in MPLS Forwarder";
            }
            bit debug {
                position 2;
                description "Log Debug messages in MPLS Forwarder";
            }
            bit notice {
                position 3;
                description "Log Notice messages in MPLS Forwarder";
            }
        }
        description "type definition for CML_NSM_MPLS_LOG_T";
    }

    typedef  cml_nsm_container_ethernet_type_t {
        type enumeration {
            enum ethernet {
                value 0;
                description "VC type Ethernet - needed when one vc is not signaled";
            }
        }
        description "type definition for CML_NSM_CONTAINER_ETHERNET_TYPE_T";
    }

    typedef  cml_interface_admin_state_t {
        type enumeration {
            enum up {
                value 0;
                description "Admin State UP";
            }
            enum down {
                value 1;
                description "Admin State DOWN";
            }
            enum administratively-down {
                value 2;
                description "Admin State ADMINISTRATIVELY DOWN";
            }
        }
        description "type definition for CML_INTERFACE_ADMIN_STATE_T";
    }

    typedef  cml_vxlan_ingress_t {
        type enumeration {
            enum ingress-replication {
                value 1;
                description "Head End Replication";
            }
        }
        description "type definition for CML_VXLAN_INGRESS_T";
    }

    typedef  cml_fog_ifctype_t {
        type enumeration {
            enum mpg {
                value 1;
                description "Monitor Port Group";
            }
            enum cpg {
                value 2;
                description "Control Port Group";
            }
        }
        description "type definition for CML_FOG_IFCTYPE_T";
    }

    typedef  cml_fog_link_type_t {
        type enumeration {
            enum uplink {
                value 1;
                description "Configure Port as Uplink";
            }
            enum downlink {
                value 2;
                description "Configure Port as Downlink";
            }
        }
        description "type definition for CML_FOG_LINK_TYPE_T";
    }

    typedef  cml_vxlan_inner_vid_t {
        type enumeration {
            enum inner-vid-disabled {
                value 1;
                description "Vid not to be carried out of network port";
            }
        }
        description "type definition for CML_VXLAN_INNER_VID_T";
    }

    typedef  cml_vrrp_init_msg_code_t {
        type enumeration {
            enum admin-down {
                value 0;
                description "(admin state down)";
            }
            enum if-not-running {
                value 1;
                description "(interface is not running)";
            }
            enum circuit-down {
                value 2;
                description "(monitored circuit is down)";
            }
            enum no-subnet {
                value 3;
                description "(no matching subnet)";
            }
            enum vip-unset {
                value 4;
                description "(virtual IP address not set)";
            }
            enum switch-back-delay {
                value 5;
                description "(In Switch Back Delay)";
            }
        }
        description "type definition for CML_VRRP_INIT_MSG_CODE_T";
    }

    typedef  cml_vrrp_debug_t {
        type bits {
            bit events {
                position 1;
                description "VRRP events";
            }
            bit packet-send {
                position 2;
                description "VRRP packets,VRRP send packets";
            }
            bit packet-recv {
                position 3;
                description "VRRP packets,VRRP receive packets";
            }
        }
        description "type definition for CML_VRRP_DEBUG_T";
    }

    typedef  cml_vrrp_state_t {
        type enumeration {
            enum init {
                value 1;
                description "VRRP_STATE_INIT";
            }
            enum backup {
                value 2;
                description "VRRP_STATE_BACKUP";
            }
            enum master {
                value 3;
                description "VRRP_STATE_MASTER";
            }
        }
        description "type definition for CML_VRRP_STATE_T";
    }

    typedef  cml_vrrp_memeber_state {
        type enumeration {
            enum joined {
                value 1;
                description "VRRP_IPV4_MCAST_JOINED";
            }
            enum left {
                value 2;
                description "VRRP_IPV4_MCAST_LEFT";
            }
        }
        description "type definition for CML_VRRP_MEMEBER_STATE";
    }

    typedef  cml_lagd_mcec_mode_type {
        type enumeration {
            enum active-standby {
                value 0;
                description "active-standby";
            }
        }
        description "type definition for CML_LAGD_MCEC_MODE_TYPE";
    }

    typedef  cml_mcec_hello_t {
        type enumeration {
            enum long {
                value 0;
                description "Long Timeout";
            }
            enum short {
                value 1;
                description "Short Timeout";
            }
        }
        description "type definition for CML_MCEC_HELLO_T";
    }

    typedef  mcec_debug_t {
        type bits {
            bit hello {
                position 0;
                description "Hello";
            }
            bit info {
                position 1;
                description "Info";
            }
            bit timer {
                position 2;
                description "Timer";
            }
            bit event {
                position 3;
                description "Event";
            }
            bit cli {
                position 4;
                description "CLI";
            }
            bit mac-sync {
                position 5;
                description "MAC Sync";
            }
            bit stp {
                position 6;
                description "STP";
            }
        }
        description "type definition for MCEC_DEBUG_T";
    }

    typedef  cml_ospf_string_t {
        type string {
            pattern "[^?' =,>|]*";
        }
        description "type definition for CML_OSPF_STRING_T";
    }

    typedef  cml_ospf_area_id_t {
        type union {
            type cml_ospf_string_t {

            }
            type uint16 {
                range "1..65535";

            }
        }
        description "type definition for CML_OSPF_AREA_ID_T";
    }

    typedef  cml_common_debug_type_t {
        type bits {
            bit decode {
                position 0;
                description "decode";
            }
            bit encode {
                position 1;
                description "encode";
            }
            bit events {
                position 2;
                description "events";
            }
            bit fsm {
                position 3;
                description "FSM";
            }
            bit tib {
                position 4;
                description "Tree-Info-Base (TIB)";
            }
        }
        description "type definition for CML_COMMON_DEBUG_TYPE_T";
    }

    typedef  cml_unknown_mcast_t {
        type enumeration {
            enum flood {
                value 0;
                description "flood mode";
            }
            enum discard {
                value 1;
                description "Discard mode";
            }
        }
        description "type definition for CML_UNKNOWN_MCAST_T";
    }

    typedef  cml_ospf6_debug_packet_type_t {
        type bits {
            bit hello {
                position 0;
                description "OSPFv3 Hello ";
            }
            bit dd {
                position 1;
                description "OSPFv3 Database Description";
            }
            bit ls-request {
                position 2;
                description "OSPFv3 Link State Request ";
            }
            bit ls-update {
                position 3;
                description "OSPFv3 Link State Update ";
            }
            bit ls-ack {
                position 4;
                description "OSPFv3 Link State Acknowledgment";
            }
            bit send {
                position 5;
                description "Packet sent";
            }
            bit recv {
                position 6;
                description "packet received";
            }
            bit detail {
                position 7;
                description "Detail information";
            }
        }
        description "type definition for CML_OSPF6_DEBUG_PACKET_TYPE_T";
    }

    typedef  cml_ospf6_debug_ifsm_t {
        type bits {
            bit status {
                position 0;
                description "IFSM status Information";
            }
            bit events {
                position 1;
                description "IFSM events Information";
            }
            bit timers {
                position 2;
                description "IFSM Timer Information";
            }
        }
        description "type definition for CML_OSPF6_DEBUG_IFSM_T";
    }

    typedef  cml_ospf6_debug_nfsm_t {
        type bits {
            bit status {
                position 0;
                description "NFSM status Information";
            }
            bit events {
                position 1;
                description "NFSM events Information";
            }
            bit timers {
                position 2;
                description "NFSM Timer Information";
            }
        }
        description "type definition for CML_OSPF6_DEBUG_NFSM_T";
    }

    typedef  cml_ospf6_debug_lsa_t {
        type bits {
            bit generate {
                position 0;
                description "LSA Generation";
            }
            bit flooding {
                position 1;
                description "LSA Flooding";
            }
            bit install {
                position 2;
                description "LSA Installation";
            }
            bit refresh {
                position 3;
                description "LSA Refreshment";
            }
            bit maxage {
                position 4;
                description "LSA MaxAge processing";
            }
        }
        description "type definition for CML_OSPF6_DEBUG_LSA_T";
    }

    typedef  cml_ospf6_debug_nsm_t {
        type bits {
            bit interface {
                position 0;
                description "NSM interface ";
            }
            bit redistribute {
                position 1;
                description "NSM redistribute ";
            }
        }
        description "type definition for CML_OSPF6_DEBUG_NSM_T";
    }

    typedef  cml_ospf6_debug_rib_t {
        type bits {
            bit interface {
                position 0;
                description "OSPF NSM information, NSM interface ";
            }
            bit redistribute {
                position 1;
                description "OSPF NSM information, NSM redistribute ";
            }
        }
        description "type definition for CML_OSPF6_DEBUG_RIB_T";
    }

    typedef  cml_ospf6_debug_route_t {
        type bits {
            bit spf {
                position 0;
                description "OSPF route information,SPF calculation information";
            }
            bit ia {
                position 1;
                description "OSPF route information, Inter-Area route calculation information";
            }
            bit ase {
                position 2;
                description "OSPF route information,External route calculation information";
            }
            bit install {
                position 3;
                description "OSPF route information, Route installation information";
            }
        }
        description "type definition for CML_OSPF6_DEBUG_ROUTE_T";
    }

    typedef  cml_ospf6_debug_event_t {
        type bits {
            bit abr {
                position 0;
                description "OSPF events information, OSPF ABR events";
            }
            bit asbr {
                position 1;
                description "OSPF events information,OSPF ASBR events ";
            }
            bit vlink {
                position 2;
                description "OSPF events information,OSPF Virtual-Link events";
            }
            bit os {
                position 3;
                description "OSPF events information, OSPF OS interaction events ";
            }
            bit router {
                position 4;
                description "OSPF events information,Other router events ";
            }
            bit nssa {
                position 5;
                description "OSPF events information, OSPF NSSA events ";
            }
        }
        description "type definition for CML_OSPF6_DEBUG_EVENT_T";
    }

    typedef  cml_clear_ntp_statistics_t {
        type enumeration {
            enum all-peers {
                value 0;
                description "Clear per-peer statistics counter of all peers";
            }
            enum io {
                value 1;
                description "Clear input-output statistics";
            }
            enum local {
                value 2;
                description "Clear counters maintained by the local NTP";
            }
            enum memory {
                value 3;
                description "Clear statistics counters related to memory code";
            }
        }
        description "type definition for CML_CLEAR_NTP_STATISTICS_T";
    }

    typedef  cml_ntp_prefer_t {
        type enumeration {
            enum prefer {
                value 1;
                description "preferred server";
            }
        }
        description "type definition for CML_NTP_PREFER_T";
    }

    typedef  cml_ntp_feature_t {
        type enumeration {
            enum ntp {
                value 1;
                description "Enable NTP";
            }
        }
        description "type definition for CML_NTP_FEATURE_T";
    }

    typedef  cml_snmp_enable_t {
        type enumeration {
            enum snmp {
                value 1;
                description "Enable SNMP feature";
            }
        }
        description "type definition for CML_SNMP_ENABLE_T";
    }

    typedef  sflow_debug_options_t {
        type enumeration {
            enum agent {
                value 1;
                description "debug sflow agent";
            }
            enum sampling {
                value 2;
                description "debug sflow sampling";
            }
            enum polling {
                value 3;
                description "debug sflow polling";
            }
            enum all {
                value 4;
                description "debug all";
            }
        }
        description "type definition for SFLOW_DEBUG_OPTIONS_T";
    }

    typedef  sflow_direction_option_t {
        type enumeration {
            enum ingress {
                value 1;
                description "Ingress";
            }
            enum egress {
                value 2;
                description "Egress";
            }
            enum both {
                value 3;
                description "Both";
            }
        }
        description "type definition for SFLOW_DIRECTION_OPTION_T";
    }

    typedef  sflow_egress_ingress_t {
        type enumeration {
            enum disabled {
                value 0;
                description "Disable Egress/Ingress";
            }
            enum enabled {
                value 1;
                description "Enable Egress/Ingress";
            }
        }
        description "type definition for SFLOW_EGRESS_INGRESS_T";
    }

    typedef  user_mgmt_role_options_t {
        type enumeration {
            enum network-admin {
                value 1;
                description "Enter the rolename - Network Administrat or - Have all permissions";
            }
            enum network-engineer {
                value 2;
                description "Enter the rolename - Network Engineer  - Can save configuration";
            }
            enum network-operator {
                value 3;
                description "Enter the rolename - Network Operator  - Can not save configuration";
            }
            enum network-user {
                value 4;
                description "Enter the rolename - Network User - Can n ot change configuration";
            }
        }
        description "type definition for USER_MGMT_ROLE_OPTIONS_T";
    }

    typedef  cml_accept_lifetime_t {
        type enumeration {
            enum accept-lifetime {
                value 1;
                description "Set accept lifetime of the key";
            }
        }
        description "type definition for CML_ACCEPT_LIFETIME_T";
    }

    typedef  cml_send_lifetime_t {
        type enumeration {
            enum send-lifetime {
                value 1;
                description "Set send lifetime of the key";
            }
        }
        description "type definition for CML_SEND_LIFETIME_T";
    }

    typedef  cml_ospf_capability_te_t {
        type enumeration {
            enum te {
                value 1;
                description "OSPF Traffic Engineering extension";
            }
            enum traffic-engineering {
                value 2;
                description "OSPF Traffic Engineering extension";
            }
        }
        description "type definition for CML_OSPF_CAPABILITY_TE_T";
    }

    typedef  cml_ospf_area_authentication_type_t {
        type enumeration {
            enum authentication {
                value 1;
                description "Enable authentication";
            }
            enum authentication-message-digest {
                value 2;
                description "Enable authentication, Use message-digest authentication";
            }
        }
        description "type definition for CML_OSPF_AREA_AUTHENTICATION_TYPE_T";
    }

    typedef  cml_ospf_vlink_auth_type_t {
        type enumeration {
            enum authentication-null {
                value 0;
                description "Enable authentication,Use no authentication";
            }
            enum authentication {
                value 1;
                description "Enable authentication";
            }
            enum authentication-message-digest {
                value 2;
                description "Enable authentication,Use message-digest authentication";
            }
        }
        description "type definition for CML_OSPF_VLINK_AUTH_TYPE_T";
    }

    typedef  cml_ospf_vlink_interface_state_t {
        type enumeration {
            enum DependUpon {
                value 0;
                description "IFSM DependUpon";
            }
            enum Down {
                value 1;
                description "IFSM Down";
            }
            enum Loopback {
                value 2;
                description "IFSM Loopback";
            }
            enum Waiting {
                value 3;
                description "IFSM Waiting";
            }
            enum Point-To-Point {
                value 4;
                description "IFSM Point-To-Point";
            }
            enum DROther {
                value 5;
                description "IFSM DROther";
            }
            enum Backup {
                value 6;
                description "IFSM Backup";
            }
            enum DR {
                value 7;
                description "IFSM DR";
            }
        }
        description "type definition for CML_OSPF_VLINK_INTERFACE_STATE_T";
    }

    typedef  cml_ospf_vlink_adj_state_t {
        type enumeration {
            enum DependUpon {
                value 0;
                description "NFSM DependUpon";
            }
            enum Down {
                value 1;
                description "NFSM Down";
            }
            enum Attempt {
                value 2;
                description "NFSM Attempt";
            }
            enum Init {
                value 3;
                description "NFSM Init";
            }
            enum 2-Way {
                value 4;
                description "NFSM 2-Way";
            }
            enum ExStart {
                value 5;
                description "NFSM ExStart";
            }
            enum Exchange {
                value 6;
                description "NFSM Exchange";
            }
            enum Loading {
                value 7;
                description "NFSM Loading";
            }
            enum Full {
                value 8;
                description "NFSM Full";
            }
        }
        description "type definition for CML_OSPF_VLINK_ADJ_STATE_T";
    }

    typedef  cml_ospf_vlink_status_t {
        type enumeration {
            enum Down {
                value 0;
                description "Virtual Link Down";
            }
            enum Up {
                value 1;
                description "Virtual Link Up";
            }
        }
        description "type definition for CML_OSPF_VLINK_STATUS_T";
    }

    typedef  cml_ospf_area_range_advertise_t {
        type enumeration {
            enum not-advertise {
                value 0;
                description "DoNotAdvertise this range";
            }
            enum advertise {
                value 1;
                description "Advertise this range (default)";
            }
        }
        description "type definition for CML_OSPF_AREA_RANGE_ADVERTISE_T";
    }

    typedef  cml_ospf_bfd_state {
        type enumeration {
            enum enable {
                value 0;
                description "enable BFD";
            }
            enum disable {
                value 1;
                description "disable BFD";
            }
        }
        description "type definition for CML_OSPF_BFD_STATE";
    }

    typedef  cml_ospf_all_debug_t {
        type enumeration {
            enum all {
                value 1;
                description "Enable all debugging";
            }
        }
        description "type definition for CML_OSPF_ALL_DEBUG_T";
    }

    typedef  cml_ospf_packet_type_t {
        type bits {
            bit hello {
                position 0;
                description "OSPF Hello";
            }
            bit dd {
                position 1;
                description "OSPF Database Description";
            }
            bit ls-request {
                position 2;
                description "OSPF Link State Request";
            }
            bit ls-update {
                position 3;
                description "OSPF Link State Update";
            }
            bit ls-ack {
                position 4;
                description "OSPF Link State Acknowledgment";
            }
            bit send {
                position 5;
                description "Packet sent";
            }
            bit recv {
                position 6;
                description "packet received";
            }
            bit detail {
                position 7;
                description "Detail information";
            }
        }
        description "type definition for CML_OSPF_PACKET_TYPE_T";
    }

    typedef  cml_ospf_debug_event_type_t {
        type bits {
            bit abr {
                position 0;
                description "OSPF ABR events";
            }
            bit nssa {
                position 1;
                description "OSPF NSSA events";
            }
            bit asbr {
                position 2;
                description "OSPF ASBR events";
            }
            bit vlink {
                position 3;
                description "OSPF Virtual-Link events";
            }
            bit lsa {
                position 4;
                description "OSPF LSA events";
            }
            bit os {
                position 5;
                description "OSPF OS interaction events";
            }
            bit router {
                position 6;
                description "Other router events";
            }
        }
        description "type definition for CML_OSPF_DEBUG_EVENT_TYPE_T";
    }

    typedef  cml_ospf_debug_ifsm_t {
        type bits {
            bit status {
                position 0;
                description "IFSM Status Information";
            }
            bit events {
                position 1;
                description "IFSM Event Information";
            }
            bit timers {
                position 2;
                description "IFSM Timers Information";
            }
        }
        description "type definition for CML_OSPF_DEBUG_IFSM_T";
    }

    typedef  cml_ospf_debug_nfsm_t {
        type bits {
            bit status {
                position 0;
                description "NFSM Status Information";
            }
            bit events {
                position 1;
                description "NFSM Event Information";
            }
            bit timers {
                position 2;
                description "NFSM Timers Information";
            }
        }
        description "type definition for CML_OSPF_DEBUG_NFSM_T";
    }

    typedef  cml_ospf_debug_lsa_t {
        type bits {
            bit generate {
                position 0;
                description "LSA Generation";
            }
            bit flooding {
                position 1;
                description "LSA Flooding";
            }
            bit install {
                position 2;
                description "LSA Installation";
            }
            bit refresh {
                position 3;
                description "LSA Refreshment";
            }
            bit maxage {
                position 4;
                description "LSA MaxAge processing";
            }
        }
        description "type definition for CML_OSPF_DEBUG_LSA_T";
    }

    typedef  cml_ospf_debug_nsm_t {
        type bits {
            bit interface {
                position 0;
                description "NSM interface";
            }
            bit redistribute {
                position 1;
                description "NSM redistribute";
            }
        }
        description "type definition for CML_OSPF_DEBUG_NSM_T";
    }

    typedef  cml_ospf_debug_rib_t {
        type bits {
            bit interface {
                position 0;
                description "RIB interface";
            }
            bit redistribute {
                position 1;
                description "RIB redistribute";
            }
        }
        description "type definition for CML_OSPF_DEBUG_RIB_T";
    }

    typedef  cml_ospf_debug_rib_client_t {
        type bits {
            bit redistribute {
                position 1;
                description "RIB redistribute";
            }
            bit client {
                position 2;
                description "RIB Client";
            }
        }
        description "type definition for CML_OSPF_DEBUG_RIB_CLIENT_T";
    }

    typedef  cml_nsm_err_disable_timeout_t {
        type enumeration {
            enum disable {
                value 0;
                description "disable";
            }
            enum enable {
                value 1;
                description "enable";
            }
        }
        description "type definition for CML_NSM_ERR_DISABLE_TIMEOUT_T";
    }

    typedef  cml_on_off_t {
        type enumeration {
            enum off {
                value 0;
                description "off";
            }
            enum on {
                value 1;
                description "on";
            }
        }
        description "type definition for CML_ON_OFF_T";
    }

    typedef  cml_ospf_debug_route_t {
        type bits {
            bit spf {
                position 0;
                description "SPF calculation information";
            }
            bit ia {
                position 1;
                description "Inter-Area route calculation information";
            }
            bit ase {
                position 2;
                description "External route calculation information";
            }
            bit install {
                position 3;
                description "Route installation information";
            }
            bit spf-terse {
                position 4;
                description "SPF Calculation terse information";
            }
        }
        description "type definition for CML_OSPF_DEBUG_ROUTE_T";
    }

    typedef  cml_ospf_debug_redist_t {
        type bits {
            bit detail {
                position 0;
                description "OSPF redistribute Details";
            }
            bit terse {
                position 1;
                description "OSPF redistribute Terse";
            }
        }
        description "type definition for CML_OSPF_DEBUG_REDIST_T";
    }

    typedef  cml_ospf_debug_graceful_t {
        type bits {
            bit detail {
                position 0;
                description "OSPF graceful-restart Details";
            }
            bit terse {
                position 1;
                description "OSPF graceful-restart Terse";
            }
        }
        description "type definition for CML_OSPF_DEBUG_GRACEFUL_T";
    }

    typedef  cml_ospf_md5_t {
        type enumeration {
            enum 0 {
                value 1;
                description "Unencrypted password option";
            }
        }
        description "type definition for CML_OSPF_MD5_T";
    }

    typedef  cml_ospf_default_info_t {
        type enumeration {
            enum originate {
                value 1;
                description "Distribute a default route";
            }
        }
        description "type definition for CML_OSPF_DEFAULT_INFO_T";
    }

    typedef  cml_bridge_forward_t {
        type enumeration {
            enum bridge-blocked {
                value 0;
                description "put all ports of the bridge into blocked state";
            }
            enum bridge-forward {
                value 1;
                description "put all ports of the bridge into forwarding state";
            }
        }
        description "type definition for CML_BRIDGE_FORWARD_T";
    }

    typedef  cml_bckbone_bridge_grp_t {
        type enumeration {
            enum backbone {
                value 0;
                description "Specifies the backbone bridge group name";
            }
        }
        description "type definition for CML_BCKBONE_BRIDGE_GRP_T";
    }

    typedef  cml_bridge_grp_t {
        type uint8 {
             range 0..255;
        }
        description "type definition for CML_BRIDGE_GRP_T";
    }

    typedef  cml_bridge_grp_cmd_t {
        type union {
            type cml_bridge_grp_t {

            }
            type cml_bckbone_bridge_grp_t {

            }
        }
        description "type definition for CML_BRIDGE_GRP_CMD_T";
    }

    typedef  cml_bridge_spanmode_t {
        type enumeration {
            enum stp {
                value 1;
                description "IEEE 801.1Q spanning-tree protocol";
            }
            enum stp-vlan-bridge {
                value 2;
                description "IEEE 801.1Q spanning-tree protocol";
            }
            enum rstp {
                value 3;
                description "IEEE 801.1w rapid spanning-tree protocol";
            }
            enum rstp-vlan-bridge {
                value 4;
                description "IEEE 801.1w rapid spanning-tree protocol";
            }
            enum mstp {
                value 5;
                description "IEEE 802.1s multiple spanning-tree protocol";
            }
            enum provider-rstp {
                value 6;
                description "IEEE 802.1s rapid spanning-tree protocol";
            }
            enum provider-mstp {
                value 7;
                description "IEEE 802.1s rapid spanning-tree protocol";
            }
            enum rpvst+ {
                value 12;
                description "IEEE 801.1w rapid per vlan spanning-tree protocol";
            }
        }
        description "type definition for CML_BRIDGE_SPANMODE_T";
    }

    typedef  cml_add_remove_t {
        type enumeration {
            enum remove {
                value 0;
                description "Deletes the interface from the vlan list";
            }
            enum add {
                value 1;
                description "Adds the interface in the vlan list";
            }
        }
        description "type definition for CML_ADD_REMOVE_T";
    }

    typedef  cml_enablebpdurx_t {
        type enumeration {
            enum disableBPDUrx {
                value 0;
                description "disableBPDUrx";
            }
            enum enableBPDUrx {
                value 1;
                description "enableBPDUrx";
            }
        }
        description "type definition for CML_ENABLEBPDURX_T";
    }

    typedef  cml_bridge_t {
        type uint8 {
             range 0..255;
        }
        description "type definition for CML_BRIDGE_T";
    }

    typedef  cml_bridge_id_t {
        type union {
            type cml_bridge_t {

            }
            type cml_spanning_tree_t {

            }
        }
        description "type definition for CML_BRIDGE_ID_T";
    }

    typedef  cml_bridge_backbone_id_t {
        type union {
            type cml_bridge_bckbone_t {

            }
            type cml_backbone_t {

            }
        }
        description "type definition for CML_BRIDGE_BACKBONE_ID_T";
    }

    typedef  cml_backbone_t {
        type enumeration {
            enum backbone {
                value 33;
                description "Specifies the backbone bridge group name";
            }
        }
        description "type definition for CML_BACKBONE_T";
    }

    typedef  cml_bridge_bckbone_t {
        type uint8 {
             range 0..255;
        }
        description "type definition for CML_BRIDGE_BCKBONE_T";
    }

    typedef  cml_actiontype_t {
        type enumeration {
            enum forward {
                value 101;
                description "Forward";
            }
            enum drop {
                value 102;
                description "Drop";
            }
            enum redirect {
                value 103;
                description "redirect to";
            }
        }
        description "type definition for CML_ACTIONTYPE_T";
    }

    typedef  cml_vlan_opt_type_t {
        type enumeration {
            enum add {
                value 1;
                description "adds the specified vlans to te-region";
            }
            enum delete {
                value 2;
                description "deletes the vlans from te-region";
            }
        }
        description "type definition for CML_VLAN_OPT_TYPE_T";
    }

    typedef  cml_tesi_mode_t {
        type enumeration {
            enum passive {
                value 1;
                description "mode from active to passive";
            }
            enum active {
                value 2;
                description "mode from passive to active";
            }
        }
        description "type definition for CML_TESI_MODE_T";
    }

    typedef  cml_tesi_type_t {
        type enumeration {
            enum dynamic {
                value 1;
                description "type from static to dynamic";
            }
            enum static {
                value 2;
                description "type from dynamic to static";
            }
        }
        description "type definition for CML_TESI_TYPE_T";
    }

    typedef  cml_pnpadddel_t {
        type enumeration {
            enum add {
                value 1;
                description "deletes the subsequest interface from this tesi";
            }
            enum delete {
                value 2;
                description "interface name";
            }
        }
        description "type definition for CML_PNPADDDEL_T";
    }

    typedef  cml_nsmvlanport_mode_t {
        type enumeration {
            enum pnp {
                value 6;
                description "Default vlan configured on Provider Network Port";
            }
            enum cnp {
                value 8;
                description "Default vlan configured on Customer Network Port";
            }
            enum pip {
                value 10;
                description "Default vlan configured on Provider Instance Port";
            }
            enum cbp {
                value 11;
                description "";
            }
        }
        description "type definition for CML_NSMVLANPORT_MODE_T";
    }

    typedef  cml_cmbckinstance_t {
        type uint32 {
             range 1..16777214;
        }
        description "type definition for CML_CMBCKINSTANCE_T";
    }

    typedef  cml_spanning_tree_t {
        type enumeration {
            enum spanning-tree {
                value 0;
                description "default bridge commands";
            }
        }
        description "type definition for CML_SPANNING_TREE_T";
    }

    typedef  cml_instance_name_t {
        type string;
        description "type definition for CML_INSTANCE_NAME_T";
    }

    typedef  cml_svlan_instance_name_t {
        type union {
            type cml_cmbckinstance_t {

            }
            type cml_instance_name_t {

            }
        }
        description "type definition for CML_SVLAN_INSTANCE_NAME_T";
    }

    typedef  cml_cmbckbone_instance_t {
        type union {
            type cml_cmbckinstance_t {

            }
            type cml_instance_ifname_t {

            }
        }
        description "type definition for CML_CMBCKBONE_INSTANCE_T";
    }

    typedef  cml_instance_ifname_t {
        type string;
        description "type definition for CML_INSTANCE_IFNAME_T";
    }

    typedef  cml_vip_traffic_t {
        type enumeration {
            enum all {
                value 0;
                description "Ingress/egress allowed";
            }
            enum ingress {
                value 1;
                description "Configures ingress service flow";
            }
            enum egress {
                value 2;
                description "Configures egress service flow";
            }
        }
        description "type definition for CML_VIP_TRAFFIC_T";
    }

    typedef  cml_beb_mode_t {
        type enumeration {
            enum tx {
                value 0;
                description "Transmit only";
            }
            enum rx {
                value 1;
                description "Receive only";
            }
            enum rxtx {
                value 2;
                description "Transmit and Receive";
            }
            enum none {
                value 3;
                description "Neither tx nor rx";
            }
        }
        description "type definition for CML_BEB_MODE_T";
    }

    typedef  cml_bridge_backbone_t {
        type union {
            type cml_backbone_t {

            }
            type uint8 {
                range "1..32";

            }
        }
        description "type definition for CML_BRIDGE_BACKBONE_T";
    }

    typedef  cml_aspteisid_t {
        type enumeration {
            enum add {
                value 1;
                description "adds a new ISID to this aps group";
            }
            enum delete {
                value 2;
                description "deletes an existing ISID from this aps group";
            }
        }
        description "type definition for CML_ASPTEISID_T";
    }

    typedef  cml_cnpins_t {
        type uint32 {
             range 1..16777214;
        }
        description "type definition for CML_CNPINS_T";
    }

    typedef  cml_ospf_nbma_row_status {
        type enumeration {
            enum row-status-active {
                value 1;
                description "Row status Active";
            }
            enum row-status-notinservice {
                value 2;
                description "Row status Not in service";
            }
            enum row-status-notready {
                value 3;
                description "Row Status not ready";
            }
            enum row-status-createandgo {
                value 4;
                description "Row status create and go";
            }
            enum row-status-createandwait {
                value 5;
                description "Row status Create and wait";
            }
            enum row-status-destroy {
                value 6;
                description "Row status Destroy";
            }
        }
        description "type definition for CML_OSPF_NBMA_ROW_STATUS";
    }

    typedef  cml_ospf_if_state {
        type enumeration {
            enum enabled {
                value 1;
                description "OSPF_API_STATUS_ENABLED";
            }
            enum disabled {
                value 2;
                description "OSPF_API_STATUS_DISABLED";
            }
        }
        description "type definition for CML_OSPF_IF_STATE";
    }

    typedef  cml_cnp_instance_t {
        type union {
            type cml_cnpins_t {

            }
            type cml_cnp_instance_ifname_t {

            }
        }
        description "type definition for CML_CNP_INSTANCE_T";
    }

    typedef  cml_cnp_instance_ifname_t {
        type string;
        description "type definition for CML_CNP_INSTANCE_IFNAME_T";
    }

    typedef  snmp_trap_options_t {
        type enumeration {
            enum link {
                value 1;
                description "Module notifications enable";
            }
            enum link-linkDown {
                value 2;
                description "Module notifications enable,IETF Link state down notification";
            }
            enum link-linkUp {
                value 3;
                description "Module notifications enable,IETF Link state up notification";
            }
            enum snmp {
                value 4;
                description "Module notifications enable";
            }
            enum snmp-authentication {
                value 5;
                description "Module notifications enable,SNMP authentication trap";
            }
            enum mpls {
                value 6;
                description "mpls notification trap";
            }
            enum pw {
                value 7;
                description "pw notification trap";
            }
            enum pwdelete {
                value 8;
                description "pwdelete notification trap";
            }
            enum rsvp {
                value 9;
                description "rsvp notification trap";
            }
            enum ospf {
                value 10;
                description "ospf notification trap";
            }
            enum bgp {
                value 11;
                description "bgp notification trap";
            }
            enum isis {
                value 12;
                description "isis notification trap";
            }
            enum vrrp {
                value 13;
                description "vrrp notification trap";
            }
            enum vxlan {
                value 14;
                description "vxlan notification trap";
            }
            enum ospf6 {
                value 15;
                description "ospf6 notification trap";
            }
            enum mplsl3vpn {
                value 16;
                description "mpls-l3vpn notification trap";
            }
        }
        description "type definition for SNMP_TRAP_OPTIONS_T";
    }

    typedef  cml_fault_mgmt_en_dis_t {
        type enumeration {
            enum disable-fault-mgmt {
                value 0;
                description "Disable Fault-Management";
            }
            enum enable-fault-mgmt {
                value 1;
                description "Enable Fault-Management";
            }
        }
        description "type definition for CML_FAULT_MGMT_EN_DIS_T";
    }

    typedef  cml_start_stop_lcv_t {
        type enumeration {
            enum stop-lcv {
                value 0;
                description "stop link connectivity verification";
            }
            enum start-lcv {
                value 1;
                description "start link connectivity verification";
            }
        }
        description "type definition for CML_START_STOP_LCV_T";
    }

    typedef  cml_enabel_disable_lcv_t {
        type enumeration {
            enum disable-lcv {
                value 0;
                description "disable lcv";
            }
            enum enable-lcv {
                value 1;
                description "enable lcv";
            }
        }
        description "type definition for CML_ENABEL_DISABLE_LCV_T";
    }

    typedef  cml_vr_protocol_t {
        type bits {
            bit rip {
                position 1;
                description "Routing Information Protocol (RIP)";
            }
            bit ipv6-rip {
                position 2;
                description "Internet Protocol Version 6,Routing Information Protocol (RIP)";
            }
            bit ospf {
                position 3;
                description "Open Shortest Path First (OSPF)";
            }
            bit ipv6-ospf {
                position 4;
                description "Internet Protocol Version 6, Open Shortest Path First (OSPF)";
            }
            bit isis {
                position 5;
                description "Intermediate System - Intermediate System (IS-IS)";
            }
            bit pim {
                position 6;
                description "Protocol Independent Multicast (PIM)";
            }
            bit vrrp {
                position 7;
                description "Virtual Router Redundancy Protocol (VRRP)";
            }
            bit bgp {
                position 9;
                description "Border Gateway Protocol (BGP)";
            }
        }
        description "type definition for CML_VR_PROTOCOL_T";
    }

    typedef  cml_lmp_debug_t {
        type enumeration {
            enum fsm {
                value 0;
                description "Enable/Disable debug lmp fsm";
            }
            enum event {
                value 1;
                description "Enable/Disable debug lmp event";
            }
            enum nsm {
                value 2;
                description "Enable/Disable debug lmp nsm";
            }
            enum cc-mgmt {
                value 3;
                description "Enable/Disable debug lmp cc-mgmt";
            }
            enum lpc {
                value 4;
                description "Enable/Disable debug lmp lpc";
            }
            enum lcv {
                value 5;
                description "Enable/Disable debug lmp lcv";
            }
            enum fault-mgmt {
                value 6;
                description "Enable/Disable debug lmp fault-mgmt";
            }
            enum packet {
                value 7;
                description "Enable/Disable debug lmp packet";
            }
            enum adjacency {
                value 8;
                description "Enable/Disable debug lmp adjacency";
            }
            enum all {
                value 9;
                description "Enable/Disable debug lmp all";
            }
        }
        description "type definition for CML_LMP_DEBUG_T";
    }

    typedef  cml_lmp_cc_opr_state_t {
        type enumeration {
            enum up {
                value 0;
                description "UP";
            }
            enum down {
                value 1;
                description "DOWN";
            }
            enum config-send {
                value 2;
                description "CONFIG SEND";
            }
            enum config-recv {
                value 3;
                description "CONFIG RECV";
            }
            enum active {
                value 4;
                description "ACTIVE";
            }
            enum admin-down {
                value 5;
                description "ADMIN DOWN";
            }
        }
        description "type definition for CML_LMP_CC_OPR_STATE_T";
    }

    typedef  cml_lmp_dlink_fsm_t {
        type enumeration {
            enum up-alloc {
                value 0;
                description "Up/Alloc";
            }
            enum up-free {
                value 1;
                description "Up/Free";
            }
            enum Down {
                value 2;
                description "Down";
            }
            enum testing {
                value 3;
                description "Testing";
            }
            enum pasv-testing {
                value 4;
                description "Testing";
            }
        }
        description "type definition for CML_LMP_DLINK_FSM_T";
    }

    typedef  cml_md5_encrypt_password_t {
        type enumeration {
            enum 0 {
                value 0;
                description "Configure password type 0 to store password as a clear text";
            }
            enum 7 {
                value 7;
                description "Configure password type 7 to encrypt password while storing";
            }
            enum 7-encrypt {
                value 8;
                description "password type 7, Enter encrypted password";
            }
        }
        description "type definition for CML_MD5_ENCRYPT_PASSWORD_T";
    }

    typedef  cml_path_sel_type_t {
        type enumeration {
            enum te {
                value 0;
                description "te-- cspf computated path";
            }
            enum igp {
                value 1;
                description "igp - cspf computated path";
            }
        }
        description "type definition for CML_PATH_SEL_TYPE_T";
    }

    typedef  cml_l2_protocol_t {
        type enumeration {
            enum stp {
                value 0;
                description "Spanning Tree Protocols";
            }
            enum lacp {
                value 7;
                description "Link Aggregation (LACP)";
            }
            enum dot1x {
                value 8;
                description "Port Authentication (802.1 X)";
            }
            enum lldp {
                value 9;
                description "Link layer discovery protocol";
            }
            enum efm {
                value 11;
                description "Ethernet first mile (Link OAM)";
            }
            enum elmi {
                value 12;
                description "Ethernet local management interface";
            }
            enum synce {
                value 14;
                description "Synchronous Ethernet";
            }
        }
        description "type definition for CML_L2_PROTOCOL_T";
    }

    typedef  cml_discard_l2_protocol_t {
        type enumeration {
            enum stp {
                value 0;
                description "Spanning Tree Protocols";
            }
            enum lacp {
                value 7;
                description "Link Aggregation (LACP)";
            }
            enum dot1x {
                value 8;
                description "Port Authentication (802.1 X)";
            }
            enum lldp {
                value 9;
                description "Link layer discovery protocol";
            }
            enum pause {
                value 13;
                description "Pause frames";
            }
            enum efm {
                value 14;
                description "Ethernet first mile (Link OAM)";
            }
            enum elmi {
                value 15;
                description "Ethernet local management interface";
            }
            enum synce {
                value 17;
                description "Synchronous Ethernet";
            }
        }
        description "type definition for CML_DISCARD_L2_PROTOCOL_T";
    }

    typedef  cml_cvlan_config_t {
        type bits {
            bit default {
                position 0;
                description "Default value";
            }
            bit untagged-pep {
                position 1;
                description "Configure PEP as Untagged for this CVLAN";
            }
            bit untagged-cep {
                position 2;
                description "Configure CEP as Untagged for this CVLAN";
            }
        }
        description "type definition for CML_CVLAN_CONFIG_T";
    }

    typedef  cml_pcep_path_dyn_t {
        type enumeration {
            enum pce {
                value 1;
                description "path computation element";
            }
        }
        description "type definition for CML_PCEP_PATH_DYN_T";
    }

    typedef  cml_edge_vlan_type_t {
        type enumeration {
            enum allowed {
                value 1;
                description "Set the Layer2 interface as trunk";
            }
            enum default-svlan {
                value 2;
                description "Set the default SVLAN for the interface";
            }
        }
        description "type definition for CML_EDGE_VLAN_TYPE_T";
    }

    typedef  cml_acl_port_operations_t {
        type enumeration {
            enum eq {
                value 1;
                description "port equal to";
            }
            enum neq {
                value 2;
                description "port not equal to";
            }
            enum lt {
                value 3;
                description "port less than";
            }
            enum gt {
                value 4;
                description "port greater than";
            }
            enum range {
                value 5;
                description "range";
            }
        }
        description "type definition for CML_ACL_PORT_OPERATIONS_T";
    }

    typedef  cml_acl_filter_action_t {
        type enumeration {
            enum deny {
                value 0;
                description "Specify packets to reject";
            }
            enum permit {
                value 1;
                description "Specify packets to forward";
            }
        }
        description "type definition for CML_ACL_FILTER_ACTION_T";
    }

    typedef  cml_acl_default_filter_action_t {
        type enumeration {
            enum deny-all {
                value 3;
                description "Specify all packets to reject";
            }
            enum permit-all {
                value 4;
                description "Specify all packets to forward";
            }
        }
        description "type definition for CML_ACL_DEFAULT_FILTER_ACTION_T";
    }

    typedef  cml_acl_arp_type_t {
        type enumeration {
            enum none {
                value 0;
                description "Match any ARP packets";
            }
        }
        description "type definition for CML_ACL_ARP_TYPE_T";
    }

    typedef  cml_acl_any_t {
        type enumeration {
            enum any {
                value 0;
                description "Wildcard entry matching all addresses";
            }
        }
        description "type definition for CML_ACL_ANY_T";
    }

    typedef  cml_acl_ipv4_host_t {
        type string;
        description "type definition for CML_ACL_IPV4_HOST_T";
    }

    typedef  cml_acl_any_ipv4_addr_t {
        type union {
            type cml_acl_any_t {

            }
            type cml_acl_ipv4_host_t {

            }
            type inet:ipv4-prefix {

            }
        }
        description "type definition for CML_ACL_ANY_IPV4_ADDR_T";
    }

    typedef  cml_acl_ipv6_host_t {
        type string;
        description "type definition for CML_ACL_IPV6_HOST_T";
    }

    typedef  cml_acl_any_ipv6_addr_t {
        type union {
            type cml_acl_any_t {

            }
            type cml_acl_ipv6_host_t {

            }
            type inet:ipv6-prefix {

            }
        }
        description "type definition for CML_ACL_ANY_IPV6_ADDR_T";
    }

    typedef  cml_acl_udp_keyword_enum_t {
        type enumeration {
            enum echo {
                value 7;
                description "echo";
            }
            enum discard {
                value 9;
                description "discard";
            }
            enum time {
                value 37;
                description "time";
            }
            enum nameserver {
                value 42;
                description "nameserver";
            }
            enum tacacs {
                value 49;
                description "tacacs";
            }
            enum domain {
                value 53;
                description "domain";
            }
            enum bootps {
                value 67;
                description "bootps";
            }
            enum bootpc {
                value 68;
                description "bootpc";
            }
            enum tftp {
                value 69;
                description "tftp";
            }
            enum sunrpc {
                value 111;
                description "sunrpc";
            }
            enum netbios_ns {
                value 137;
                description "netbios_ns";
            }
            enum netbios_dgm {
                value 138;
                description "netbios_dgm";
            }
            enum netbios_ss {
                value 139;
                description "netbios_ss";
            }
            enum snmp {
                value 161;
                description "snmp";
            }
            enum snmptrap {
                value 162;
                description "snmptrap";
            }
            enum xdmcp {
                value 177;
                description "xdmcp";
            }
            enum dnsix {
                value 195;
                description "dnsix";
            }
            enum mobile_ip {
                value 434;
                description "mobile_ip";
            }
            enum pim_auto_rp {
                value 496;
                description "pim_auto_rp";
            }
            enum isakmp {
                value 500;
                description "isakmp";
            }
            enum biff {
                value 512;
                description "biff";
            }
            enum who {
                value 513;
                description "who";
            }
            enum syslog {
                value 514;
                description "syslog";
            }
            enum talk {
                value 517;
                description "talk";
            }
            enum rip {
                value 520;
                description "rip";
            }
            enum non500_isakmp {
                value 4500;
                description "non500_isakmp";
            }
        }
        description "type definition for CML_ACL_UDP_KEYWORD_ENUM_T";
    }

    typedef  cml_acl_udp_keyword_t {
        type union {
            type cml_acl_udp_keyword_enum_t {

            }
            type uint32 {
                range "0..65535";

            }
        }
        description "type definition for CML_ACL_UDP_KEYWORD_T";
    }

    typedef  cml_acl_tcp_keyword_enum_t {
        type enumeration {
            enum echo {
                value 7;
                description "echo";
            }
            enum discard {
                value 9;
                description "discard";
            }
            enum daytime {
                value 13;
                description "daytime";
            }
            enum chargen {
                value 19;
                description "chargen";
            }
            enum ftp_data {
                value 20;
                description "ftp_data";
            }
            enum ftp {
                value 21;
                description "ftp";
            }
            enum ssh {
                value 22;
                description "ssh";
            }
            enum telnet {
                value 23;
                description "telnet";
            }
            enum smtp {
                value 25;
                description "smtp";
            }
            enum time {
                value 37;
                description "time";
            }
            enum whois {
                value 43;
                description "whois";
            }
            enum tacacs {
                value 49;
                description "tacacs";
            }
            enum domain {
                value 53;
                description "domain";
            }
            enum gopher {
                value 70;
                description "gopher";
            }
            enum finger {
                value 79;
                description "finger";
            }
            enum www {
                value 80;
                description "www";
            }
            enum hostname {
                value 101;
                description "hostname";
            }
            enum pop2 {
                value 109;
                description "pop2";
            }
            enum pop3 {
                value 110;
                description "pop3";
            }
            enum sunrpc {
                value 111;
                description "sunrpc";
            }
            enum ident {
                value 113;
                description "ident";
            }
            enum nntp {
                value 119;
                description "nntp";
            }
            enum bgp {
                value 179;
                description "bgp";
            }
            enum irc {
                value 194;
                description "irc";
            }
            enum pim_auto_rp {
                value 496;
                description "pim_auto_rp";
            }
            enum exec {
                value 512;
                description "exec";
            }
            enum login {
                value 513;
                description "login";
            }
            enum cmd {
                value 514;
                description "cmd";
            }
            enum lpd {
                value 515;
                description "lpd";
            }
            enum talk {
                value 517;
                description "talk";
            }
            enum uucp {
                value 540;
                description "uucp";
            }
            enum klogin {
                value 543;
                description "klogin";
            }
            enum kshell {
                value 544;
                description "kshell";
            }
            enum drip {
                value 3949;
                description "drip";
            }
        }
        description "type definition for CML_ACL_TCP_KEYWORD_ENUM_T";
    }

    typedef  cml_acl_tcp_keyword_t {
        type union {
            type cml_acl_tcp_keyword_enum_t {

            }
            type uint32 {
                range "0..65535";

            }
        }
        description "type definition for CML_ACL_TCP_KEYWORD_T";
    }

    typedef  cml_acl_ip_proto_enum_t {
        type enumeration {
            enum icmp {
                value 1;
                description "icmp";
            }
            enum igmp {
                value 2;
                description "igmp";
            }
            enum ipip {
                value 4;
                description "ipip";
            }
            enum tcp {
                value 6;
                description "tcp";
            }
            enum udp {
                value 17;
                description "udp";
            }
            enum ipv6ip {
                value 41;
                description "ipv6ip";
            }
            enum rsvp {
                value 46;
                description "rsvp";
            }
            enum gre {
                value 47;
                description "gre";
            }
            enum esp {
                value 50;
                description "esp";
            }
            enum ahp {
                value 51;
                description "ahp";
            }
            enum eigrp {
                value 88;
                description "eigrp";
            }
            enum ospf {
                value 89;
                description "ospf";
            }
            enum pim {
                value 103;
                description "pim";
            }
            enum ipcomp {
                value 108;
                description "ipcomp";
            }
            enum vrrp {
                value 112;
                description "vrrp";
            }
            enum any {
                value 256;
                description "any";
            }
        }
        description "type definition for CML_ACL_IP_PROTO_ENUM_T";
    }

    typedef  cml_acl_ip_proto_t {
        type union {
            type cml_acl_ip_proto_enum_t {

            }
            type uint16 {
                range "0..255";

            }
        }
        description "type definition for CML_ACL_IP_PROTO_T";
    }

    typedef  cml_acl_ipv6_proto_enum_t {
        type enumeration {
            enum ipv6ip {
                value 4;
                description "ipv6ip";
            }
            enum tcp {
                value 6;
                description "tcp";
            }
            enum udp {
                value 17;
                description "udp";
            }
            enum ipv6ipv6 {
                value 41;
                description "ipv6ipv6";
            }
            enum rsvp {
                value 46;
                description "rsvp";
            }
            enum gre {
                value 47;
                description "gre";
            }
            enum esp {
                value 50;
                description "esp";
            }
            enum ahp {
                value 51;
                description "ahp";
            }
            enum icmpv6 {
                value 58;
                description "icmpv6";
            }
            enum ospf {
                value 89;
                description "ospf";
            }
            enum pim {
                value 103;
                description "pim";
            }
            enum ipcomp {
                value 108;
                description "ipcomp";
            }
            enum vrrp {
                value 112;
                description "vrrp";
            }
            enum sctp {
                value 132;
                description "sctp";
            }
            enum any {
                value 256;
                description "any";
            }
        }
        description "type definition for CML_ACL_IPV6_PROTO_ENUM_T";
    }

    typedef  cml_acl_ipv6_proto_t {
        type union {
            type cml_acl_ipv6_proto_enum_t {

            }
            type uint16 {
                range "0..255";

            }
        }
        description "type definition for CML_ACL_IPV6_PROTO_T";
    }

    typedef  cml_acl_dscp_enum_t {
        type enumeration {
            enum default {
                value 0;
                description "default";
            }
            enum cs1 {
                value 8;
                description "cs1";
            }
            enum af11 {
                value 10;
                description "af11";
            }
            enum af12 {
                value 12;
                description "af12";
            }
            enum af13 {
                value 14;
                description "af13";
            }
            enum cs2 {
                value 16;
                description "cs2";
            }
            enum af21 {
                value 18;
                description "af21";
            }
            enum af22 {
                value 20;
                description "af22";
            }
            enum af23 {
                value 22;
                description "af23";
            }
            enum cs3 {
                value 24;
                description "cs3";
            }
            enum af31 {
                value 26;
                description "af31";
            }
            enum af32 {
                value 28;
                description "af32";
            }
            enum af33 {
                value 30;
                description "af33";
            }
            enum cs4 {
                value 32;
                description "cs4";
            }
            enum af41 {
                value 34;
                description "af41";
            }
            enum af42 {
                value 36;
                description "af42";
            }
            enum af43 {
                value 38;
                description "af43";
            }
            enum cs5 {
                value 40;
                description "cs5";
            }
            enum ef {
                value 46;
                description "ef";
            }
            enum cs6 {
                value 48;
                description "cs6";
            }
            enum cs7 {
                value 56;
                description "cs7";
            }
        }
        description "type definition for CML_ACL_DSCP_ENUM_T";
    }

    typedef  cml_acl_dscp_t {
        type union {
            type cml_acl_dscp_enum_t {

            }
            type int8 {
                range "0..63";

            }
        }
        description "type definition for CML_ACL_DSCP_T";
    }

    typedef  cml_acl_precedence_enum_t {
        type enumeration {
            enum routine {
                value 0;
                description "routine";
            }
            enum priority {
                value 1;
                description "priority";
            }
            enum immediate {
                value 2;
                description "immediate";
            }
            enum flash {
                value 3;
                description "flash";
            }
            enum flashoverride {
                value 4;
                description "flashoverride";
            }
            enum critical {
                value 5;
                description "critical";
            }
            enum internet {
                value 6;
                description "internet";
            }
            enum network {
                value 7;
                description "network";
            }
        }
        description "type definition for CML_ACL_PRECEDENCE_ENUM_T";
    }

    typedef  cml_acl_precedence_t {
        type union {
            type cml_acl_precedence_enum_t {

            }
            type int8 {
                range "0..7";

            }
        }
        description "type definition for CML_ACL_PRECEDENCE_T";
    }

    typedef  cml_acl_icmp_options_t {
        type enumeration {
            enum administratively-prohibited {
                value 1;
                description "administrativelyProhibited";
            }
            enum alternate-address {
                value 2;
                description "alternateAddress";
            }
            enum conversion-error {
                value 3;
                description "conversionError";
            }
            enum dod-host-prohibited {
                value 4;
                description "dodHostProhibited";
            }
            enum dod-net-prohibited {
                value 5;
                description "dodNetProhibited";
            }
            enum echo {
                value 6;
                description "echo";
            }
            enum echo-reply {
                value 7;
                description "echoReply";
            }
            enum general-parameter-problem {
                value 8;
                description "generalParameterProblem";
            }
            enum host-isolated {
                value 9;
                description "hostIsolated";
            }
            enum host-precedence-unreachable {
                value 10;
                description "hostPrecedenceUnreachable";
            }
            enum host-redirect {
                value 11;
                description "hostRedirect";
            }
            enum host-tos-redirect {
                value 12;
                description "hostTosRedirect";
            }
            enum host-tos-unreachable {
                value 13;
                description "hostTosUnreachable";
            }
            enum host-unknown {
                value 14;
                description "hostUnknown";
            }
            enum host-unreachable {
                value 15;
                description "hostUnreachable";
            }
            enum information-reply {
                value 16;
                description "informationReply";
            }
            enum information-request {
                value 17;
                description "informationRequest";
            }
            enum mask-reply {
                value 18;
                description "maskReply";
            }
            enum mask-request {
                value 19;
                description "maskRequest";
            }
            enum mobile-redirect {
                value 20;
                description "mobileRedirect";
            }
            enum net-redirect {
                value 21;
                description "netRedirect";
            }
            enum net-tos-redirect {
                value 22;
                description "netTosRedirect";
            }
            enum net-tos-unreachable {
                value 23;
                description "netTosUnreachable";
            }
            enum net-unreachable {
                value 24;
                description "netUnreachable";
            }
            enum network-unknown {
                value 25;
                description "networkUnknown";
            }
            enum no-room-for-option {
                value 26;
                description "noRoomForOption";
            }
            enum option-missing {
                value 27;
                description "optionMissing";
            }
            enum packet-too-big {
                value 28;
                description "packetTooBig";
            }
            enum parameter-problem {
                value 29;
                description "parameterProblem";
            }
            enum port-unreachable {
                value 30;
                description "portUnreachable";
            }
            enum precedence-unreachable {
                value 31;
                description "precedenceUnreachable";
            }
            enum protocol-unreachable {
                value 32;
                description "protocolUnreachable";
            }
            enum reassembly-timeout {
                value 33;
                description "reassemblyTimeout";
            }
            enum redirect {
                value 34;
                description "redirect";
            }
            enum router-advertisement {
                value 35;
                description "routerAdvertisement";
            }
            enum router-solicitation {
                value 36;
                description "routerSolicitation";
            }
            enum source-quench {
                value 37;
                description "sourceQuench";
            }
            enum source-route-failed {
                value 38;
                description "sourceRouteFailed";
            }
            enum time-exceeded {
                value 39;
                description "timeExceeded";
            }
            enum timestamp-reply {
                value 40;
                description "timestampReply";
            }
            enum timestamp-request {
                value 41;
                description "timestampRequest";
            }
            enum traceroute {
                value 42;
                description "traceroute";
            }
            enum ttl-exceeded {
                value 43;
                description "ttlExceeded";
            }
            enum unreachable {
                value 44;
                description "unreachable";
            }
        }
        description "type definition for CML_ACL_ICMP_OPTIONS_T";
    }

    typedef  cml_acl_icmpv6_options_t {
        type enumeration {
            enum beyond-scope {
                value 0;
                description "beyond-scope";
            }
            enum destination-unreachable {
                value 1;
                description "destination-unreachable";
            }
            enum echo-reply {
                value 2;
                description "echo-reply";
            }
            enum echo-request {
                value 3;
                description "echo-request";
            }
            enum header {
                value 4;
                description "header";
            }
            enum hop-limit {
                value 5;
                description "hop-limit";
            }
            enum mld-query {
                value 6;
                description "mld-query";
            }
            enum mld-reduction {
                value 7;
                description "mld-reduction";
            }
            enum mld-report {
                value 8;
                description "mld-report";
            }
            enum nd-na {
                value 9;
                description "nd-na";
            }
            enum nd-ns {
                value 10;
                description "nd-ns";
            }
            enum next-header {
                value 11;
                description "next-header";
            }
            enum no-admin {
                value 12;
                description "no-admin";
            }
            enum no-route {
                value 13;
                description "no-route";
            }
            enum packet-too-big {
                value 14;
                description "packet-too-big";
            }
            enum parameter-option {
                value 15;
                description "parameter-option";
            }
            enum parameter-problem {
                value 16;
                description "parameter-problem";
            }
            enum port-unreachable {
                value 17;
                description "port-unreachable";
            }
            enum reassembly-timeout {
                value 18;
                description "reassembly-timeout";
            }
            enum redirect {
                value 19;
                description "redirect";
            }
            enum renum-command {
                value 20;
                description "renum-command";
            }
            enum renum-result {
                value 21;
                description "renum-result";
            }
            enum renum-seq-number {
                value 22;
                description "renum-seq-number";
            }
            enum router-advertisement {
                value 23;
                description "router-advertisement";
            }
            enum router-renumbering {
                value 24;
                description "router-renumbering";
            }
            enum router-solicitation {
                value 25;
                description "router-solicitation";
            }
            enum time-exceeded {
                value 26;
                description "time-exceeded";
            }
            enum unreachable {
                value 27;
                description "unreachable";
            }
        }
        description "type definition for CML_ACL_ICMPV6_OPTIONS_T";
    }

    typedef  cml_acl_tcp_flags_t {
        type bits {
            bit fin {
                position 0;
                description "fin";
            }
            bit syn {
                position 1;
                description "syn";
            }
            bit rst {
                position 2;
                description "rst";
            }
            bit psh {
                position 3;
                description "psh";
            }
            bit ack {
                position 4;
                description "ack";
            }
            bit urg {
                position 5;
                description "urg";
            }
            bit established {
                position 6;
                description "established";
            }
        }
        description "type definition for CML_ACL_TCP_FLAGS_T";
    }

    typedef  cml_acl_any_mac_addr_t {
        type union {
            type cml_acl_any_t {

            }
            type cml_mac_addr_t {

            }
        }
        description "type definition for CML_ACL_ANY_MAC_ADDR_T";
    }

    typedef  cml_acl_ether_type_enum_t {
        type enumeration {
            enum ipv4 {
                value 2048;
                description "ipv4";
            }
            enum vines-echo {
                value 2991;
                description "vines-echo";
            }
            enum etype-6000 {
                value 24576;
                description "etype-6000";
            }
            enum mop-dump {
                value 24577;
                description "mop-dump";
            }
            enum mop-console {
                value 24578;
                description "mop-console";
            }
            enum decnet-iv {
                value 24579;
                description "decnet-iv";
            }
            enum lat {
                value 24580;
                description "lat";
            }
            enum diagnostic {
                value 24581;
                description "diagnostic";
            }
            enum lavc-sca {
                value 24583;
                description "lavc-sca";
            }
            enum etype-8042 {
                value 32834;
                description "etype-8042";
            }
            enum appletalk {
                value 32923;
                description "appletalk";
            }
            enum aarp {
                value 33011;
                description "aarp";
            }
            enum ipv6 {
                value 34525;
                description "ipv6";
            }
            enum mpls {
                value 34886;
                description "mpls";
            }
        }
        description "type definition for CML_ACL_ETHER_TYPE_ENUM_T";
    }

    typedef  cml_acl_ether_type_t {
        type union {
            type cml_acl_ether_type_enum_t {

            }
            type string {

            }
        }
        description "type definition for CML_ACL_ETHER_TYPE_T";
    }

    typedef  cml_acl_types_t {
        type enumeration {
            enum mac {
                value 1;
                description "Configure MAC parameters";
            }
            enum ip {
                value 3;
                description "Internet Protocol (IP)";
            }
            enum ipv6 {
                value 4;
                description "Internet Protocol version 6 (IPv6)";
            }
            enum arp {
                value 5;
                description "Configure ARP parameters";
            }
        }
        description "type definition for CML_ACL_TYPES_T";
    }

    typedef  cml_vty_acl_types_t {
        type enumeration {
            enum ip {
                value 0;
                description "Internet Protocol (IP)";
            }
            enum ipv6 {
                value 1;
                description "Internet Protocol version 6 (IPv6)";
            }
        }
        description "type definition for CML_VTY_ACL_TYPES_T";
    }

    typedef  cml_acl_packet_dir_t {
        type enumeration {
            enum in {
                value 0;
                description "Specify to filter incoming packets";
            }
            enum out {
                value 1;
                description "Specify to filter outgoing packets";
            }
        }
        description "type definition for CML_ACL_PACKET_DIR_T";
    }

    typedef  cml_auth_port_sec_mode {
        type enumeration {
            enum filter {
                value 0;
                description "Set port to filter mode";
            }
            enum shutdown {
                value 1;
                description "Set port to disable mode";
            }
        }
        description "type definition for CML_AUTH_PORT_SEC_MODE";
    }

    typedef  cml_port_security_logging_t {
        type enumeration {
            enum disable {
                value 0;
                description "Logging Disable";
            }
            enum enable {
                value 1;
                description "Logging Enable";
            }
        }
        description "type definition for CML_PORT_SECURITY_LOGGING_T";
    }

    typedef  cml_port_security_global_t {
        type enumeration {
            enum disable {
                value 0;
                description "Global config Disable";
            }
            enum enable {
                value 1;
                description "Global config Enable";
            }
        }
        description "type definition for CML_PORT_SECURITY_GLOBAL_T";
    }

    typedef  cml_auth_ctrl_dir_t {
        type enumeration {
            enum in {
                value 0;
                description "Discard receive packets from supplicant";
            }
            enum both {
                value 1;
                description "Discard receive and transmit packets from supplicant";
            }
        }
        description "type definition for CML_AUTH_CTRL_DIR_T";
    }

    typedef  cml_auth_port_ctrl {
        type enumeration {
            enum force-unauthorized {
                value 0;
                description "Force port state to unauthorized";
            }
            enum force-authorized {
                value 1;
                description "Force port state to authorized";
            }
            enum auto {
                value 2;
                description "Allow port client to negotiate authentication";
            }
        }
        description "type definition for CML_AUTH_PORT_CTRL";
    }

    typedef  cml_dot1x_debug_t {
        type bits {
            bit event {
                position 0;
                description "802.1X events";
            }
            bit timer {
                position 1;
                description "802.1X timer";
            }
            bit packet {
                position 2;
                description "802.1X packets";
            }
            bit nsm {
                position 3;
                description "802.1X NSM information";
            }
        }
        description "type definition for CML_DOT1X_DEBUG_T";
    }

    typedef  cml_rip_debug_t {
        type bits {
            bit events {
                position 1;
                description "RIP events";
            }
            bit packet {
                position 2;
                description "RIP packets";
            }
            bit packet-send {
                position 3;
                description "RIP packets,RIP send packets";
            }
            bit packet-recv {
                position 4;
                description "RIP packets, RIP receive packets";
            }
            bit packet-detail {
                position 5;
                description "RIP packets, Detailed information display";
            }
            bit packet-send-detail {
                position 6;
                description "RIP packets, RIP send packets, Detailed information display";
            }
            bit packet-recv-detail {
                position 7;
                description "RIP packets, RIP receive packets, Detailed information display";
            }
            bit nsm {
                position 8;
                description "RIP NSM information";
            }
            bit rib {
                position 9;
                description "RIP RIB information";
            }
            bit bfd {
                position 10;
                description "RIP BFD information";
            }
        }
        description "type definition for CML_RIP_DEBUG_T";
    }

    typedef  cml_rip_route_t {
        type enumeration {
            enum kernel {
                value 1;
                description "Kernel routes";
            }
            enum connected {
                value 2;
                description "Connected";
            }
            enum static {
                value 3;
                description "Static routes";
            }
            enum isis {
                value 4;
                description "ISO IS-IS";
            }
            enum ospf {
                value 5;
                description "Open Shortest Path First (OSPF)";
            }
            enum bgp {
                value 6;
                description "Border Gateway Protocol (BGP)";
            }
            enum rip {
                value 7;
                description "Routing Information Protocol (RIP)";
            }
            enum all {
                value 8;
                description "all of the RIP routing tabl";
            }
        }
        description "type definition for CML_RIP_ROUTE_T";
    }

    typedef  cml_rip_instance_t {
        type enumeration {
            enum rip {
                value 1;
                description "Routing Information Protocol (RIP)";
            }
        }
        description "type definition for CML_RIP_INSTANCE_T";
    }

    typedef  cml_rip_direction_t {
        type enumeration {
            enum in {
                value 0;
                description "For incoming updates";
            }
            enum out {
                value 1;
                description "For outgoing updates";
            }
        }
        description "type definition for CML_RIP_DIRECTION_T";
    }

    typedef  cml_rip_dist_type_t {
        type enumeration {
            enum in {
                value 0;
                description "Filter incoming routing updates";
            }
            enum out {
                value 1;
                description "Filter incoming routing updates";
            }
        }
        description "type definition for CML_RIP_DIST_TYPE_T";
    }

    typedef  cml_rip_metric_t {
        type enumeration {
            enum disable {
                value 0;
                description "Disables updating metric consistent with Cisco";
            }
            enum enable {
                value 1;
                description "Enables updating metric consistent with Cisco";
            }
        }
        description "type definition for CML_RIP_METRIC_T";
    }

    typedef  cml_rip_auth_mode_t {
        type enumeration {
            enum text {
                value 2;
                description "Clear text authentication";
            }
            enum md5 {
                value 3;
                description "Keyed message digest";
            }
        }
        description "type definition for CML_RIP_AUTH_MODE_T";
    }

    typedef  cml_rip_split_horizon_t {
        type enumeration {
            enum split-horizon {
                value 0;
                description "Perform split horizon";
            }
            enum split-horizon-poisoned {
                value 1;
                description "Perform split horizon,Perform poisoned reverse";
            }
        }
        description "type definition for CML_RIP_SPLIT_HORIZON_T";
    }

    typedef  cml_rip_default_originate_t {
        type enumeration {
            enum originate {
                value 0;
                description "Distribute a default route";
            }
            enum originate-always {
                value 1;
                description "Distribute a default route,Always advertise default route";
            }
        }
        description "type definition for CML_RIP_DEFAULT_ORIGINATE_T";
    }

    typedef  cml_rip_recv_version_type_t {
        type enumeration {
            enum 1 {
                value 1;
                description "RIP version 1";
            }
            enum 2 {
                value 2;
                description "RIP version 2";
            }
            enum 1-2 {
                value 3;
                description "RIP version 1, RIP version 2";
            }
            enum 2-1 {
                value 5;
                description "RIP version 2, RIP version 1";
            }
        }
        description "type definition for CML_RIP_RECV_VERSION_TYPE_T";
    }

    typedef  cml_rip_send_version_type_t {
        type enumeration {
            enum 1 {
                value 1;
                description "RIP version 1";
            }
            enum 2 {
                value 2;
                description "RIP version 2";
            }
            enum 1-2 {
                value 3;
                description "RIP version 1, RIP version 2";
            }
            enum 1-compatible {
                value 4;
                description "RIPv1-compatible";
            }
            enum 2-1 {
                value 5;
                description "RIP version 2, RIP version 1";
            }
        }
        description "type definition for CML_RIP_SEND_VERSION_TYPE_T";
    }

    typedef  cml_rip_redist_protos_t {
        type enumeration {
            enum kernel {
                value 0;
                description "Kernel routes";
            }
            enum connected {
                value 1;
                description "Connected";
            }
            enum static {
                value 2;
                description "Static routes";
            }
            enum ospf {
                value 3;
                description "Open Shortest Path First (OSPF)";
            }
            enum isis {
                value 4;
                description "ISO IS-IS";
            }
            enum bgp {
                value 5;
                description "Border Gateway Protocol (BGP)";
            }
        }
        description "type definition for CML_RIP_REDIST_PROTOS_T";
    }

    typedef  cml_rip_vrf_redist_protos_t {
        type enumeration {
            enum connected {
                value 1;
                description "Connected";
            }
            enum static {
                value 2;
                description "Static routes";
            }
            enum ospf {
                value 3;
                description "Open Shortest Path First (OSPF)";
            }
            enum bgp {
                value 5;
                description "Border Gateway Protocol (BGP)";
            }
        }
        description "type definition for CML_RIP_VRF_REDIST_PROTOS_T";
    }

    typedef  cml_nsm_load_trill_t {
        type enumeration {
            enum outer-l2 {
                value 1;
                description "TRILL outer l2 header (outer SMAC, outer DMAC, outer VLAN)";
            }
            enum inner-l2 {
                value 2;
                description "TRILL inner l2 header (inner SMAC, inner DMAC, inner VLAN, trill tunnel)";
            }
            enum inner-l3 {
                value 3;
                description "TRILL inner l3 header (inner SIP, inner DIP, L4 srx/dest port)";
            }
        }
        description "type definition for CML_NSM_LOAD_TRILL_T";
    }

    typedef  cml_nsm_load_hash_t {
        type enumeration {
            enum crc16-bisync {
                value 0;
                description "16-bit CRC16 using the BISYNC Polynomial (DEFAULT)";
            }
            enum crc16-ccitt {
                value 1;
                description "16-bit CRC16 using the CCITT Polynomial";
            }
            enum crc32-lo {
                value 2;
                description "16 LSBs of computated CRC32";
            }
            enum crc32-hi {
                value 3;
                description "16 MSBs of computated CRC32";
            }
        }
        description "type definition for CML_NSM_LOAD_HASH_T";
    }

    typedef  cml_lacp_debug_type_t {
        type bits {
            bit event {
                position 0;
                description "Set the debug options for LACP events";
            }
            bit cli {
                position 1;
                description "Echo commands to console";
            }
            bit timer {
                position 2;
                description "Echo timer expiry to console";
            }
            bit packet {
                position 3;
                description "Set the debug option for LACP packet";
            }
            bit rx {
                position 4;
                description "Echo receiving of LACP PDUs to console";
            }
            bit tx {
                position 5;
                description "Echo transmission of LACP PDUs to console";
            }
            bit sync {
                position 6;
                description "Echo synchronization to console";
            }
            bit ha {
                position 7;
                description "Echo High availability events to console";
            }
        }
        description "type definition for CML_LACP_DEBUG_TYPE_T";
    }

    typedef  cml_allowedvlan_t {
        type enumeration {
            enum none {
                value 1;
                description "Add a VLAN to Xmit/Tx through the Layer2 interface";
            }
            enum all {
                value 2;
                description "Allow no VLANs to Xmit/Rx through the Layer2 interface";
            }
        }
        description "type definition for CML_ALLOWEDVLAN_T";
    }

    typedef  cml_dhcpsnoop_debug_t {
        type bits {
            bit event {
                position 0;
                description "enable event debugs";
            }
            bit rx {
                position 1;
                description "enable rx debugs";
            }
            bit tx {
                position 2;
                description "enable tx debugs";
            }
            bit packet {
                position 3;
                description "enable packet debug";
            }
        }
        description "type definition for CML_DHCPSNOOP_DEBUG_T";
    }

    typedef  cml_dhcp_validation_t {
        type enumeration {
            enum src-mac {
                value 0;
                description "source mac validation";
            }
            enum dst-mac {
                value 1;
                description "destination mac validation";
            }
            enum ip {
                value 2;
                description "arp ip address validation";
            }
        }
        description "type definition for CML_DHCP_VALIDATION_T";
    }

    typedef  cml_common_enable_disable_t {
        type enumeration {
            enum Disabled {
                value 0;
                description "Disabled";
            }
            enum Enabled {
                value 1;
                description "Enabled";
            }
        }
        description "type definition for CML_COMMON_ENABLE_DISABLE_T";
    }

    typedef  cml_common_flags_t {
        type enumeration {
            enum False {
                value 0;
                description "None";
            }
            enum True {
                value 1;
                description "None";
            }
        }
        description "type definition for CML_COMMON_FLAGS_T";
    }

    typedef  cml_uni_enni_t {
        type enumeration {
            enum uni {
                value 1;
                description "Configure UNI Parameter";
            }
            enum enni {
                value 2;
                description "Configure ENNI Parameter";
            }
        }
        description "type definition for CML_UNI_ENNI_T";
    }

    typedef  cml_mstp_enum_t {
        type enumeration {
            enum te-msti {
                value 65;
                description "MSTI to be the traffic engineering MSTI instance";
            }
            enum instance-spbm {
                value 4092;
                description "instance,spbm instance";
            }
            enum instance-spbv {
                value 4093;
                description "instance,spbv instance";
            }
        }
        description "type definition for CML_MSTP_ENUM_T";
    }

    typedef  cml_mstp_range_t {
        type uint16 {
             range 1..63;
        }
        description "type definition for CML_MSTP_RANGE_T";
    }

    typedef  cml_mstp_instance_t {
        type union {
            type cml_mstp_enum_t {

            }
            type cml_mstp_range_t {

            }
        }
        description "type definition for CML_MSTP_INSTANCE_T";
    }

    typedef  cml_hostp_snmp_key_type_t {
        type enumeration {
            enum plain {
                value 0;
                description "To specify shared key in clear-text form";
            }
            enum encrypt {
                value 1;
                description "To specify shared key in encrypted form";
            }
        }
        description "type definition for CML_HOSTP_SNMP_KEY_TYPE_T";
    }

    typedef  cml_forwarding_profile_t {
        type enumeration {
            enum l2-profile-one {
                value 0;
                description "Configures the L2 profile One";
            }
            enum l2-profile-two {
                value 1;
                description "Configures the L2 profile Two";
            }
            enum l2-profile-three {
                value 2;
                description "Configures the L2 profile Three (default)";
            }
            enum l3-profile {
                value 3;
                description "Configures the L3 profile";
            }
            enum l3-128bit-profile {
                value 4;
                description "Configures the L3 profile with 128 bit prefix support";
            }
            enum lpm-profile {
                value 5;
                description "Configures the LPM profile profile";
            }
            enum lpm-128bit-profile {
                value 6;
                description "Configures the LPM profile with 128 bit prefix support";
            }
        }
        description "type definition for CML_FORWARDING_PROFILE_T";
    }

    typedef  cml_forwarding_profile_mh_t {
        type enumeration {
            enum l3-nvo-mh-profile {
                value 1;
                description "configures the Multihoming ecmp for nvo";
            }
        }
        description "type definition for CML_FORWARDING_PROFILE_MH_T";
    }

    typedef  cml_forwarding_custom_profile_lpm_t {
        type enumeration {
            enum 2 {
                value 2;
                description "Two banks for lpm and Remaining banks can be used by any";
            }
        }
        description "type definition for CML_FORWARDING_CUSTOM_PROFILE_LPM_T";
    }

    typedef  cml_kaps_profile_t {
        type enumeration {
            enum profile-one {
                value 1;
                description "select kaps profile one";
            }
            enum profile-two {
                value 2;
                description "select kaps profile two";
            }
        }
        description "type definition for CML_KAPS_PROFILE_T";
    }

    typedef  cml_tcam_profile_t {
        type enumeration {
            enum profile-one {
                value 3;
                description "select elk-tcam profile one";
            }
            enum profile-two {
                value 4;
                description "select elk-tcam profile two";
            }
            enum profile-three {
                value 5;
                description "select elk-tcam profile three";
            }
        }
        description "type definition for CML_TCAM_PROFILE_T";
    }

    typedef  cml_tcam_custom_profile_t {
        type enumeration {
            enum custom-profile {
                value 6;
                description "define elk-tcam custom profile";
            }
        }
        description "type definition for CML_TCAM_CUSTOM_PROFILE_T";
    }

    typedef  cml_nsm_config_mode_t {
        type bits {
            bit addressmonitor {
                position 1;
                description "Enable Monitor adddress netlink";
            }
            bit bfd {
                position 2;
                description "Bidirectional Forwarding Detection (BFD)";
            }
            bit events {
                position 3;
                description "NSM events";
            }
            bit hal-events {
                position 4;
                description " Hardware Abstraction Layer,NSM events";
            }
            bit hal-ipc {
                position 5;
                description "Hardware Abstraction Layer,Async Debugging";
            }
            bit linkmonitor {
                position 6;
                description "Enable Monitor link netlink";
            }
            bit packet {
                position 7;
                description "NSM packets";
            }
            bit packet-detail {
                position 8;
                description "NSM packets,Detailed information display";
            }
            bit packet-recv {
                position 9;
                description "NSM packets,NSM receive packets";
            }
            bit packet-recv-detail {
                position 10;
                description "NSM packets,NSM receive packets,Detailed information display";
            }
            bit packet-send {
                position 11;
                description "NSM packets,NSM receive packets";
            }
            bit packet-send-detail {
                position 12;
                description "NSM packets,NSM receive packets,Detailed information display";
            }
            bit mpls {
                position 19;
                description "NSM mpls";
            }
        }
        description "type definition for CML_NSM_CONFIG_MODE_T";
    }

    typedef  cml_nsm_exec_mode_t {
        type bits {
            bit addressmonitor {
                position 1;
                description "Enable Monitor adddress netlink";
            }
            bit bfd {
                position 2;
                description "Bidirectional Forwarding Detection (BFD)";
            }
            bit events {
                position 3;
                description "NSM events";
            }
            bit hal-events {
                position 4;
                description " Hardware Abstraction Layer,NSM events";
            }
            bit hal-ipc {
                position 5;
                description "Hardware Abstraction Layer,Async Debugging";
            }
            bit linkmonitor {
                position 6;
                description "Enable Monitor link netlink";
            }
            bit packet {
                position 7;
                description "NSM packets";
            }
            bit packet-detail {
                position 8;
                description "NSM packets,Detailed information display";
            }
            bit packet-recv {
                position 9;
                description "NSM packets,NSM receive packets";
            }
            bit packet-recv-detail {
                position 10;
                description "NSM packets,NSM receive packets,Detailed information display";
            }
            bit packet-send {
                position 11;
                description "NSM packets,NSM receive packets";
            }
            bit packet-send-detail {
                position 12;
                description "NSM packets,NSM receive packets,Detailed information display";
            }
            bit mpls {
                position 18;
                description "NSM mpls";
            }
        }
        description "type definition for CML_NSM_EXEC_MODE_T";
    }

    typedef  cml_nsm_pkt_mgr_t {
        type bits {
            bit l2-protocol-cfm {
                position 2;
                description "debug pktmgr,layer2,protocol,cfm";
            }
            bit l2-protocol-eapol {
                position 3;
                description "debug pktmgr,layer2,protocol,eapol";
            }
            bit l2-protocol-efm {
                position 4;
                description "debug pktmgr,layer2,protocol,efm";
            }
            bit l2-protocol-igmp-snoop {
                position 5;
                description "debug pktmgr,layer2,protocol,igmp snoop";
            }
            bit l2-protocol-lacp {
                position 6;
                description "debug pktmgr,layer2,protocol,lacp";
            }
            bit l2-protocol-lldp {
                position 7;
                description "debug pktmgr,layer2,protocol,lldp";
            }
            bit l2-protocol-mldp-snoop {
                position 8;
                description "debug pktmgr,layer2,protocol,mldp snoop";
            }
            bit l2-protocol-mstp {
                position 9;
                description "debug pktmgr,layer2,protocol,mstp";
            }
            bit l2-protocol-ptp {
                position 10;
                description "debug pktmgr,layer2,protocol,ptp";
            }
        }
        description "type definition for CML_NSM_PKT_MGR_T";
    }

    typedef  cml_mstp_debug_t {
        type bits {
            bit mstp-protocol {
                position 1;
                description "debug mstp,mstp protocol";
            }
            bit mstp-protocol-detail {
                position 2;
                description "debug mstp,mstp protocol,display detailed information";
            }
            bit mstp-timer {
                position 3;
                description "debug mstp,mstp timer";
            }
            bit mstp-timer-detail {
                position 4;
                description "debug mstp,mstp timer,display detailed information";
            }
            bit mstp-packet-tx {
                position 5;
                description "debug mstp,mstp packet,tx";
            }
            bit mstp-packet-rx {
                position 6;
                description "debug mstp,mstp packet,rx";
            }
            bit mstp-cli {
                position 7;
                description "debug mstp,mstp cli";
            }
            bit mstp-bpdu {
                position 8;
                description "debug mstp,mstp bpdu";
            }
            bit mstp-mcec {
                position 9;
                description "debug mstp,mstp mcec";
            }
        }
        description "type definition for CML_MSTP_DEBUG_T";
    }

    typedef  cml_exec_mstp_t {
        type enumeration {
            enum stats {
                value 1;
                description "STATISTICS";
            }
            enum pkt-errors {
                value 2;
                description "PACKET ERROR STATS";
            }
        }
        description "type definition for CML_EXEC_MSTP_T";
    }

    typedef  cml_sflow_debug_type_t {
        type bits {
            bit agent {
                position 0;
                description "debug sflow agent";
            }
            bit sampling {
                position 1;
                description "debug sflow sampling";
            }
            bit polling {
                position 2;
                description "debug sflow polling";
            }
        }
        description "type definition for CML_SFLOW_DEBUG_TYPE_T";
    }

    typedef  cml_urpf_mode_t {
        type enumeration {
            enum any {
                value 1;
                description "Source is reachable via any interface";
            }
            enum rx {
                value 2;
                description "Source is reachable via interface on which packet was received";
            }
        }
        description "type definition for CML_URPF_MODE_T";
    }

    typedef  cml_int_track_match_type_t {
        type enumeration {
            enum all {
                value 1;
                description "Match criteria all";
            }
            enum any {
                value 2;
                description "Match criteria any";
            }
        }
        description "type definition for CML_INT_TRACK_MATCH_TYPE_T";
    }

    typedef  cml_int_track_state_type_t {
        type enumeration {
            enum down {
                value 1;
                description "Make interface DOWN";
            }
            enum up {
                value 2;
                description "Make interface UP";
            }
        }
        description "type definition for CML_INT_TRACK_STATE_TYPE_T";
    }

    typedef  cml_pmirror_sess_type_t {
        type enumeration {
            enum local {
                value 1;
                description "Create a local session";
            }
            enum remote {
                value 2;
                description "Create a remote source node session";
            }
        }
        description "type definition for CML_PMIRROR_SESS_TYPE_T";
    }

    typedef  cml_pmirror_state_t {
        type enumeration {
            enum shut {
                value 0;
                description "shut";
            }
            enum no-shut {
                value 1;
                description "unser, shut";
            }
        }
        description "type definition for CML_PMIRROR_STATE_T";
    }

    typedef  cml_pmirror_dir_t {
        type bits {
            bit rx {
                position 0;
                description "Ingress";
            }
            bit tx {
                position 1;
                description "Egress";
            }
        }
        description "type definition for CML_PMIRROR_DIR_T";
    }

    typedef  cml_pmirror_alt_dir_t {
        type bits {
            bit receive {
                position 0;
                description "Mirror received traffic";
            }
            bit transmit {
                position 1;
                description "Mirror transmit traffic";
            }
        }
        description "type definition for CML_PMIRROR_ALT_DIR_T";
    }

    typedef  cml_pmirror_all_sess_t {
        type enumeration {
            enum all {
                value 0;
                description "All sessions";
            }
        }
        description "type definition for CML_PMIRROR_ALL_SESS_T";
    }

    typedef  cml_pmirror_sess_t {
        type union {
            type cml_pmirror_all_sess_t {

            }
            type uint32 {
                range "1..18";

            }
        }
        description "type definition for CML_PMIRROR_SESS_T";
    }

    typedef  cml_ripng_debug_t {
        type bits {
            bit events {
                position 1;
                description "RIP events";
            }
            bit packet-send {
                position 2;
                description "RIP packets,RIP send packets";
            }
            bit packet-recv {
                position 3;
                description "RIP packets, RIP receive packets";
            }
            bit nsm {
                position 5;
                description "RIP NSM information";
            }
            bit rib {
                position 6;
                description "RIP RIB information";
            }
        }
        description "type definition for CML_RIPNG_DEBUG_T";
    }

    typedef  cml_ripng_split_horizon_t {
        type enumeration {
            enum split-horizon {
                value 0;
                description "Perform split horizon";
            }
            enum split-horizon-poisoned {
                value 1;
                description "Perform split horizon,Perform poisoned reverse";
            }
        }
        description "type definition for CML_RIPNG_SPLIT_HORIZON_T";
    }

    typedef  cml_ripng_instance_t {
        type enumeration {
            enum rip {
                value 1;
                description "Routing Information Protocol (RIP)";
            }
        }
        description "type definition for CML_RIPNG_INSTANCE_T";
    }

    typedef  cml_ripng_redist_protos_t {
        type enumeration {
            enum kernel {
                value 0;
                description "Kernel routes";
            }
            enum connected {
                value 1;
                description "Connected";
            }
            enum static {
                value 2;
                description "Static routes";
            }
            enum ospf6 {
                value 3;
                description "Open Shortest Path First (OSPF)";
            }
            enum isis {
                value 4;
                description "ISO IS-IS";
            }
            enum bgp {
                value 5;
                description "Border Gateway Protocol (BGP)";
            }
        }
        description "type definition for CML_RIPNG_REDIST_PROTOS_T";
    }

    typedef  cml_ripng_vrf_redist_protos_t {
        type enumeration {
            enum connected {
                value 1;
                description "Connected";
            }
            enum static {
                value 2;
                description "Static routes";
            }
            enum ospf6 {
                value 3;
                description "Open Shortest Path First (OSPF)";
            }
            enum bgp {
                value 5;
                description "Border Gateway Protocol (BGP)";
            }
        }
        description "type definition for CML_RIPNG_VRF_REDIST_PROTOS_T";
    }

    typedef  cml_ripng_filtering_t {
        type enumeration {
            enum in {
                value 0;
                description "For incoming updates";
            }
            enum out {
                value 1;
                description "For outgoing updates";
            }
        }
        description "type definition for CML_RIPNG_FILTERING_T";
    }

    typedef  cml_ripng_route_t {
        type enumeration {
            enum kernel {
                value 1;
                description "Kernel routes";
            }
            enum connected {
                value 2;
                description "Connected";
            }
            enum static {
                value 3;
                description "Static routes";
            }
            enum isis {
                value 4;
                description "ISO IS-IS";
            }
            enum ospf6 {
                value 5;
                description "Open Shortest Path First (OSPF)";
            }
            enum bgp {
                value 6;
                description "Border Gateway Protocol (BGP)";
            }
            enum rip {
                value 7;
                description "Routing Information Protocol (RIP)";
            }
            enum all {
                value 8;
                description "all of the RIP routing tabl";
            }
        }
        description "type definition for CML_RIPNG_ROUTE_T";
    }

    typedef  cml_confidencetype_t {
        type enumeration {
            enum native {
                value 1;
                description "Confidence level associated with MAC learned after decapsulation of frames";
            }
            enum decap {
                value 2;
                description "Confidence level associated with MAC learned from native frames";
            }
            enum static {
                value 3;
                description "Confidence level associated with MAC that are statically configured";
            }
        }
        description "type definition for CML_CONFIDENCETYPE_T";
    }

    typedef  cml_esadi_t {
        type enumeration {
            enum enable {
                value 1;
                description "Enable ESADI";
            }
            enum disable {
                value 2;
                description "Disable ESADI";
            }
        }
        description "type definition for CML_ESADI_T";
    }

    typedef  cml_trill_t {
        type enumeration {
            enum disable {
                value 0;
                description "Disable vlan pruningI";
            }
            enum enable {
                value 1;
                description "Enable vlan pruning";
            }
        }
        description "type definition for CML_TRILL_T";
    }

    typedef  cml_isunicast_t {
        type enumeration {
            enum multicast {
                value 0;
                description "Enable Multipath for multicast";
            }
            enum unicast {
                value 1;
                description "Enable Multipath for unicast";
            }
        }
        description "type definition for CML_ISUNICAST_T";
    }

    typedef  cml_configtype_t {
        type enumeration {
            enum broadcast {
                value 1;
                description "Link is broadcast multi-access";
            }
            enum point-to-point {
                value 2;
                description "Link is point-to-point";
            }
        }
        description "type definition for CML_CONFIGTYPE_T";
    }

    typedef  cml_vlan_enum_t {
        type enumeration {
            enum all {
                value 4095;
                description "All the vlan";
            }
        }
        description "type definition for CML_VLAN_ENUM_T";
    }

    typedef  cml_vlan_range_t {
        type uint16 {
             range 1..4094;
        }
        description "type definition for CML_VLAN_RANGE_T";
    }

    typedef  cml_startvidesadi_t {
        type union {
            type cml_vlan_enum_t {

            }
            type cml_vlan_range_t {

            }
        }
        description "type definition for CML_STARTVIDESADI_T";
    }

    typedef  cml_nsm_dcb_qcn_mode_t {
        type enumeration {
            enum admin {
                value 1;
                description "Admin-Mode";
            }
            enum auto {
                value 2;
                description "Automatic mode - LLDP should be enabled";
            }
            enum component {
                value 3;
                description "Defense mode same as the bridge level defense mode";
            }
        }
        description "type definition for CML_NSM_DCB_QCN_MODE_T";
    }

    typedef  cml_mapping_type_t {
        type enumeration {
            enum admin {
                value 1;
                description "Admin-Mode";
            }
            enum auto {
                value 2;
                description "Automatic mode - LLDP should be enabled";
            }
            enum component {
                value 3;
                description "Defense mode same as the bridge level defense mode";
            }
        }
        description "type definition for CML_MAPPING_TYPE_T";
    }

    typedef  cml_ets_mode_t {
        type enumeration {
            enum on {
                value 1;
                description "ON to force enable Enhanced-trasnsmission-selection";
            }
            enum auto {
                value 2;
                description "AUTO to negotiate Enhanced-transmission-selection capabilities)";
            }
        }
        description "type definition for CML_ETS_MODE_T";
    }

    typedef  cml_dcbstate_t {
        type enumeration {
            enum off {
                value 0;
                description "disable";
            }
            enum on {
                value 1;
                description "enable";
            }
        }
        description "type definition for CML_DCBSTATE_T";
    }

    typedef  cml_prioflag_t {
        type enumeration {
            enum remove {
                value 0;
                description "remove";
            }
            enum add {
                value 1;
                description "add";
            }
        }
        description "type definition for CML_PRIOFLAG_T";
    }

    typedef  cml_protoid_t {
        type enumeration {
            enum tcp {
                value 2;
                description "Protocol Type tcp";
            }
            enum udp {
                value 3;
                description "Protocol Type udp";
            }
            enum both-tcp-udp {
                value 4;
                description "Protocol Type both-tcp-udp";
            }
            enum neither-tcp-udp {
                value 5;
                description "Protocol Type neither-tcp-udp";
            }
        }
        description "type definition for CML_PROTOID_T";
    }

    typedef  cml_defensemode_t {
        type enumeration {
            enum disabled {
                value 1;
                description "Disabled Mode";
            }
            enum interior {
                value 2;
                description "Interior Mode";
            }
            enum interior-ready {
                value 3;
                description "Interior Ready Mode";
            }
            enum edge {
                value 4;
                description "Edge Mode";
            }
        }
        description "type definition for CML_DEFENSEMODE_T";
    }

    typedef  cml_loadshare_t {
        type string;
        description "type definition for CML_LOADSHARE_T";
    }

    typedef  cml_pbr_loadshare_t {
        type union {
            type inet:ipv4-address {

            }
            type cml_loadshare_t {

            }
        }
        description "type definition for CML_PBR_LOADSHARE_T";
    }

    typedef  cml_pbr_v6_loadshare_t {
        type union {
            type inet:ipv6-address {

            }
            type cml_loadshare_t {

            }
        }
        description "type definition for CML_PBR_V6_LOADSHARE_T";
    }

    typedef  cml_vrf_enum_t {
        type enumeration {
            enum all {
                value 1;
                description "All VRFs";
            }
            enum default {
                value 2;
                description "Default VRF";
            }
        }
        description "type definition for CML_VRF_ENUM_T";
    }

    typedef  cml_vrf_string_t {
        type string;
        description "type definition for CML_VRF_STRING_T";
    }

    typedef  cml_vrf_name_t {
        type union {
            type cml_vrf_enum_t {

            }
            type cml_vrf_string_t {

            }
        }
        description "type definition for CML_VRF_NAME_T";
    }

    typedef  cml_adjnbr_t {
        type enumeration {
            enum adjacency {
                value 1;
                description "Clear adjacency";
            }
            enum neighbor {
                value 2;
                description "Clear neighbors";
            }
        }
        description "type definition for CML_ADJNBR_T";
    }

    typedef  cml_mpls_vclinkmode_t {
        type enumeration {
            enum primary {
                value 0;
                description "Primary Link";
            }
            enum secondary {
                value 16;
                description "Secondary Link - Will not be activated unless primary fails";
            }
        }
        description "type definition for CML_MPLS_VCLINKMODE_T";
    }

    typedef  cml_vr_config_t {
        type enumeration {
            enum read {
                value 0;
                description "Read file";
            }
            enum write {
                value 1;
                description "Write file";
            }
        }
        description "type definition for CML_VR_CONFIG_T";
    }

    typedef  cml_static_bfd_enable_disable_t {
        type enumeration {
            enum fall-over-bfd-disable {
                value 0;
                description "static fall-over, BFD, disable bfd";
            }
            enum fall-over-bfd {
                value 1;
                description "Enable static fall-over bfd,BFD";
            }
        }
        description "type definition for CML_STATIC_BFD_ENABLE_DISABLE_T";
    }

    typedef  cml_l2process_t {
        type enumeration {
            enum discard {
                value 1;
                description "Discard the protocol data unit";
            }
            enum peer {
                value 2;
                description "Act as peer to the customer Device instance of the protocol";
            }
            enum tunnel {
                value 3;
                description "Tunnel the Protocol data unit into the SVLAN";
            }
        }
        description "type definition for CML_L2PROCESS_T";
    }

    typedef  if_l2process_clear_t {
        type enumeration {
            enum peer {
                value 0;
                description "Clear stats for Peer protocol pkts";
            }
            enum tunnel {
                value 1;
                description "Clear stats for Tunnel protocol pkts";
            }
            enum discard {
                value 2;
                description "Clear stats for Discard protocol pkts";
            }
            enum tunnel-discard {
                value 3;
                description "Clear stats for Tunnel discard protocol pkts";
            }
            enum all {
                value 4;
                description "Clear stats for all protocol pkts";
            }
        }
        description "type definition for IF_L2PROCESS_CLEAR_T";
    }

    typedef  cml_nat_port_type_t {
        type enumeration {
            enum tcp {
                value 0;
                description "TCP";
            }
            enum udp {
                value 1;
                description "UDP";
            }
        }
        description "type definition for CML_NAT_PORT_TYPE_T";
    }

    typedef  cml_nat_dir_t {
        type enumeration {
            enum inside {
                value 0;
                description "Inside";
            }
            enum outside {
                value 1;
                description "Outside";
            }
        }
        description "type definition for CML_NAT_DIR_T";
    }

    typedef  cml_nat_addr_type_t {
        type enumeration {
            enum source {
                value 0;
                description "Source Address";
            }
            enum destination {
                value 1;
                description "Destination Address";
            }
        }
        description "type definition for CML_NAT_ADDR_TYPE_T";
    }

    typedef  cml_nat_dir_out_t {
        type enumeration {
            enum outside {
                value 1;
                description "Outside";
            }
        }
        description "type definition for CML_NAT_DIR_OUT_T";
    }

    typedef  cml_nat_addr_type_dest_t {
        type enumeration {
            enum destination {
                value 1;
                description "Destination Address";
            }
        }
        description "type definition for CML_NAT_ADDR_TYPE_DEST_T";
    }

    typedef  cml_nat_trans_dir_t {
        type enumeration {
            enum src {
                value 0;
                description "Source address";
            }
            enum dest {
                value 1;
                description "Destination address";
            }
        }
        description "type definition for CML_NAT_TRANS_DIR_T";
    }

    typedef  cml_agentx_debug_type_t {
        type bits {
            bit snmp-send {
                position 0;
                description "SNMP  (AgentX or SMUX),Packet send";
            }
            bit snmp-receive {
                position 1;
                description "SNMP  (AgentX or SMUX),Packet receive";
            }
            bit snmp-process {
                position 2;
                description "SNMP  (AgentX or SMUX),Packet process";
            }
            bit snmp-xdump {
                position 3;
                description "SNMP  (AgentX or SMUX),Packet hexa dump";
            }
            bit snmp-error-string {
                position 4;
                description "SNMP  (AgentX or SMUX),Error string display";
            }
            bit snmp-detail {
                position 5;
                description "SNMP  (AgentX or SMUX),Detail debugging";
            }
        }
        description "type definition for CML_AGENTX_DEBUG_TYPE_T";
    }

    typedef  cml_permastate_t {
        type enumeration {
            enum permanent {
                value 1;
                description "permanent state";
            }
        }
        description "type definition for CML_PERMASTATE_T";
    }

    typedef  cml_ifstate_t {
        type enumeration {
            enum down {
                value 0;
                description "interface state down";
            }
            enum up {
                value 1;
                description "interface state up";
            }
        }
        description "type definition for CML_IFSTATE_T";
    }

    typedef  cml_gmpls_lmptype_t {
        type enumeration {
            enum static {
                value 0;
                description "static";
            }
            enum using-lmp {
                value 1;
                description "lmp";
            }
        }
        description "type definition for CML_GMPLS_LMPTYPE_T";
    }

    typedef  cml_gmpls_type_t {
        type enumeration {
            enum data-control {
                value 1;
                description "Data and Conrol";
            }
            enum data {
                value 2;
                description "Data";
            }
            enum control {
                value 3;
                description "Control";
            }
            enum data-numbered {
                value 4;
                description "Data, Numbered";
            }
        }
        description "type definition for CML_GMPLS_TYPE_T";
    }

    typedef  cml_gmpls_link_id_t {
        type union {
            type inet:ipv4-address {

            }
            type uint32 {
                range "1..4294967295";

            }
        }
        description "type definition for CML_GMPLS_LINK_ID_T";
    }

    typedef  cml_gmpls_remote_link_t {
        type union {
            type inet:ipv4-address {

            }
            type uint32 {
                range "1..4294967295";

            }
        }
        description "type definition for CML_GMPLS_REMOTE_LINK_T";
    }

    typedef  cml_mpls_vpls_opcode_t {
        type enumeration {
            enum swap {
                value 3;
                description "Swap incoming label";
            }
            enum vpnpop {
                value 4;
                description "Pop incoming label and forward VPN packet";
            }
        }
        description "type definition for CML_MPLS_VPLS_OPCODE_T";
    }

    typedef  cml_mpls_vpls_popopcode_t {
        type enumeration {
            enum pop {
                value 2;
                description "pop incoming label";
            }
        }
        description "type definition for CML_MPLS_VPLS_POPOPCODE_T";
    }

    typedef  cml_mpls_ipv6opcode_t {
        type enumeration {
            enum swap {
                value 3;
                description "Swap incoming label";
            }
        }
        description "type definition for CML_MPLS_IPV6OPCODE_T";
    }

    typedef  cml_gmpls_bidirectional_flag_t {
        type enumeration {
            enum False {
                value 0;
                description "Bidirectional flag is not set";
            }
            enum True {
                value 1;
                description "Bidirectional flag is set";
            }
        }
        description "type definition for CML_GMPLS_BIDIRECTIONAL_FLAG_T";
    }

    typedef  cml_gmpls_capability_type_t {
        type enumeration {
            enum psc1 {
                value 1;
                description "Packet Switch Capable-1 (PSC1)";
            }
            enum psc2 {
                value 2;
                description "Packet Switch Capable-2 (PSC2)";
            }
            enum psc3 {
                value 4;
                description "Packet Switch Capable-3 (PSC3)";
            }
            enum psc4 {
                value 8;
                description "Packet Switch Capable-4 (PSC4)";
            }
        }
        description "type definition for CML_GMPLS_CAPABILITY_TYPE_T";
    }

    typedef  cml_gmpls_encoding_type_t {
        type enumeration {
            enum packet {
                value 1;
                description "Packet";
            }
            enum ethernet {
                value 2;
                description "Ethernet";
            }
            enum pdh {
                value 3;
                description "ANSI/ETSI PDH";
            }
            enum sdh {
                value 5;
                description "SDH ITU-T G.707 / SONET ANSI T1.105";
            }
            enum digital {
                value 7;
                description "Digital Wrapper";
            }
            enum lambda {
                value 8;
                description "Lambda (photonic)";
            }
            enum fiber {
                value 9;
                description "Fiber";
            }
            enum fiber-Channel {
                value 11;
                description "FiberChannel";
            }
            enum g709-oduk {
                value 12;
                description "G.709 ODUk (Digital Path)";
            }
            enum g709-och {
                value 13;
                description "G.709 Optical Channel ";
            }
        }
        description "type definition for CML_GMPLS_ENCODING_TYPE_T";
    }

    typedef  cml_gmpls_protection_type_t {
        type enumeration {
            enum extra-traffic {
                value 1;
                description "Extra-traffic";
            }
            enum unprotected {
                value 2;
                description "Unprotected";
            }
            enum shared {
                value 4;
                description "Shared";
            }
            enum dedicated-one-to-one {
                value 8;
                description "Dedicated 1:1";
            }
            enum dedicated-one-plus-one {
                value 16;
                description "Dedicated 1+1";
            }
            enum enhanced {
                value 32;
                description "Enhanced";
            }
        }
        description "type definition for CML_GMPLS_PROTECTION_TYPE_T";
    }

    typedef  cml_gmpls_framing_type_t {
        type enumeration {
            enum sonet {
                value 17;
                description "SONET";
            }
            enum sdh {
                value 18;
                description "SDH";
            }
            enum otn {
                value 19;
                description "OTN";
            }
        }
        description "type definition for CML_GMPLS_FRAMING_TYPE_T";
    }

    typedef  cml_gmpls_sonet_signal_type_t {
        type enumeration {
            enum vt1.5 {
                value 1;
                description "1.5 Mbits/s";
            }
            enum vt2 {
                value 2;
                description "2.0 Mbits/s";
            }
            enum vt3 {
                value 3;
                description "3.15 Mbits/s";
            }
            enum vt6 {
                value 4;
                description "6.3 Mbits/s";
            }
            enum sts1-spe {
                value 5;
                description "44.1 Mbits/s";
            }
            enum sts-3c {
                value 6;
                description "140 Mbits/s";
            }
            enum sts-1 {
                value 7;
                description "51 Mbits/s";
            }
            enum sts-3 {
                value 8;
                description "155.520 Mbits/s";
            }
            enum sts-12 {
                value 9;
                description "622.080 Mbits/s";
            }
            enum sts-48 {
                value 10;
                description "2488.320 Mbits/s";
            }
            enum sts-192 {
                value 11;
                description "9953.28 Mbits/s";
            }
            enum sts-768 {
                value 12;
                description "39813.12 Mbits/s";
            }
        }
        description "type definition for CML_GMPLS_SONET_SIGNAL_TYPE_T";
    }

    typedef  cml_gmpls_sonet_signal_rate_t {
        type enumeration {
            enum sts-1 {
                value 1;
                description "51 Mbits/s";
            }
            enum sts-3 {
                value 2;
                description "155.520 Mbits/s";
            }
            enum sts-12 {
                value 3;
                description "622.080 Mbits/s";
            }
            enum sts-48 {
                value 4;
                description "2488.320 Mbits/s";
            }
            enum sts-192 {
                value 5;
                description "9953.28 Mbits/s";
            }
            enum sts-768 {
                value 6;
                description "39813.12 Mbits/s";
            }
        }
        description "type definition for CML_GMPLS_SONET_SIGNAL_RATE_T";
    }

    typedef  cml_gmpls_sdh_signal_type_t {
        type enumeration {
            enum vc-11 {
                value 1;
                description "1.5 Mbits/s";
            }
            enum vc-12 {
                value 2;
                description "2.0 Mbits/s";
            }
            enum vc-2 {
                value 4;
                description "6.3 Mbits/s";
            }
            enum vc-3 {
                value 5;
                description "44.1 Mbits/s";
            }
            enum vc-4 {
                value 6;
                description "140 Mbits/s";
            }
            enum stm-0 {
                value 7;
                description "51 Mbits/s";
            }
            enum stm-1 {
                value 8;
                description "155.52 Mbits/s";
            }
            enum stm-4 {
                value 9;
                description "622.08 Mbits/s";
            }
            enum stm-16 {
                value 10;
                description "2488.32 Mbits/s";
            }
            enum stm-64 {
                value 11;
                description "9953.28 Mbits/s";
            }
            enum stm-256 {
                value 12;
                description "39813.12 Mbits/s";
            }
        }
        description "type definition for CML_GMPLS_SDH_SIGNAL_TYPE_T";
    }

    typedef  cml_gmpls_sdh_signal_rate_t {
        type enumeration {
            enum stm-0 {
                value 1;
                description "51 Mbits/s";
            }
            enum stm-1 {
                value 2;
                description "155.52 Mbits/s";
            }
            enum stm-4 {
                value 3;
                description "622.08 Mbits/s";
            }
            enum stm-16 {
                value 4;
                description "2488.32 Mbits/s";
            }
            enum stm-64 {
                value 5;
                description "9953.28 Mbits/s";
            }
            enum stm-256 {
                value 6;
                description "39813.12 Mbits/s";
            }
        }
        description "type definition for CML_GMPLS_SDH_SIGNAL_RATE_T";
    }

    typedef  cml_gmpls_otn_signal_type_t {
        type enumeration {
            enum odu1 {
                value 1;
                description "ODU1 at 2.5 Gbps";
            }
            enum odu2 {
                value 2;
                description "ODU2 at 10 Gbps";
            }
            enum odu3 {
                value 3;
                description "ODU3 at 40 Gbps";
            }
            enum och1 {
                value 6;
                description "OCh at 2.5 Gbps";
            }
            enum och2 {
                value 7;
                description "OCh at 10  Gbps";
            }
            enum och3 {
                value 8;
                description "OCh at 40  Gbps";
            }
        }
        description "type definition for CML_GMPLS_OTN_SIGNAL_TYPE_T";
    }

    typedef  cml_gmpls_bandwidth_type_t {
        type enumeration {
            enum vc-11 {
                value 1;
                description "1.5 Mbits/s";
            }
            enum vc-12 {
                value 2;
                description "2.0 Mbits/s";
            }
            enum vc-2 {
                value 3;
                description "6.3 Mbits/s";
            }
            enum vc-3 {
                value 4;
                description "44.1 Mbits/s";
            }
            enum vc-4 {
                value 5;
                description "140 Mbits/s";
            }
            enum stm-0 {
                value 6;
                description "51 Mbits/s";
            }
            enum stm-1 {
                value 7;
                description "155.52 Mbits/s";
            }
            enum stm-4 {
                value 8;
                description "622.08 Mbits/s";
            }
            enum stm-16 {
                value 9;
                description "2488.32 Mbits/s";
            }
            enum stm-64 {
                value 10;
                description "9953.28 Mbits/s";
            }
            enum stm-256 {
                value 11;
                description "39813.12 Mbits/s";
            }
            enum odu1 {
                value 12;
                description "ODU1 at 2.5 Gbps";
            }
            enum odu2 {
                value 13;
                description "ODU2 at 10 Gbps";
            }
            enum odu3 {
                value 14;
                description "ODU3 at 40 Gbps";
            }
            enum och1 {
                value 15;
                description "OCh at 2.5 Gbps";
            }
            enum och2 {
                value 16;
                description "OCh at 10  Gbps";
            }
            enum och3 {
                value 17;
                description "OCh at 40  Gbps";
            }
            enum vt1.5 {
                value 18;
                description "1.5 Mbits/s";
            }
            enum vt2 {
                value 19;
                description "2.0 Mbits/s";
            }
            enum vt3 {
                value 20;
                description "3.15 Mbits/s";
            }
            enum vt6 {
                value 21;
                description "6.3 Mbits/s";
            }
            enum sts1-spe {
                value 22;
                description "44.1 Mbits/s";
            }
            enum sts-3c {
                value 23;
                description "140 Mbits/s";
            }
            enum sts-1 {
                value 24;
                description "51 Mbits/s";
            }
            enum sts-3 {
                value 25;
                description "155.520 Mbits/s";
            }
            enum sts-12 {
                value 26;
                description "622.080 Mbits/s";
            }
            enum sts-48 {
                value 27;
                description "2488.320 Mbits/s";
            }
            enum sts-192 {
                value 28;
                description "9953.28 Mbits/s";
            }
            enum sts-768 {
                value 29;
                description "39813.12 Mbits/s";
            }
        }
        description "type definition for CML_GMPLS_BANDWIDTH_TYPE_T";
    }

    typedef  cml_gmpls_max_lsp_bandwidth_type_t {
        type enumeration {
            enum stm-0 {
                value 6;
                description "51 Mbits/s";
            }
            enum stm-1 {
                value 7;
                description "155.52 Mbits/s";
            }
            enum stm-4 {
                value 8;
                description "622.08 Mbits/s";
            }
            enum stm-16 {
                value 9;
                description "2488.32 Mbits/s";
            }
            enum stm-64 {
                value 10;
                description "9953.28 Mbits/s";
            }
            enum stm-256 {
                value 11;
                description "39813.12 Mbits/s";
            }
            enum odu1 {
                value 12;
                description "ODU1 at 2.5 Gbps";
            }
            enum odu2 {
                value 13;
                description "ODU2 at 10 Gbps";
            }
            enum odu3 {
                value 14;
                description "ODU3 at 40 Gbps";
            }
            enum och1 {
                value 15;
                description "OCh at 2.5 Gbps";
            }
            enum och2 {
                value 16;
                description "OCh at 10  Gbps";
            }
            enum och3 {
                value 17;
                description "OCh at 40  Gbps";
            }
            enum sts-1 {
                value 24;
                description "51 Mbits/s";
            }
            enum sts-3 {
                value 25;
                description "155.520 Mbits/s";
            }
            enum sts-12 {
                value 26;
                description "622.080 Mbits/s";
            }
            enum sts-48 {
                value 27;
                description "2488.320 Mbits/s";
            }
            enum sts-192 {
                value 28;
                description "9953.28 Mbits/s";
            }
            enum sts-768 {
                value 29;
                description "39813.12 Mbits/s";
            }
        }
        description "type definition for CML_GMPLS_MAX_LSP_BANDWIDTH_TYPE_T";
    }

    typedef  cml_gmpls_sonet_gpid_type_t {
        type enumeration {
            enum ds1-sf-asynchronous {
                value 22;
                description "DS1 SF Asynchronous";
            }
            enum ds1-esf-asynchronous {
                value 23;
                description "DS1 ESF Asynchronous";
            }
            enum ds3-m23-asynchronous {
                value 24;
                description "DS3 M23 Asynchronous";
            }
            enum ds3-cbit-parity-asynchronous {
                value 25;
                description "DS3 C-Bit Parity Asynchronous";
            }
        }
        description "type definition for CML_GMPLS_SONET_GPID_TYPE_T";
    }

    typedef  cml_gmpls_sdh_gpid_type_t {
        type enumeration {
            enum asynchronous-mapping-of-E4 {
                value 5;
                description "Asynchronous mapping of E4";
            }
            enum asynchronous-mapping-of-DS3-T3 {
                value 6;
                description "Asynchronous mapping of DS3/T3";
            }
            enum asynchronous-mapping-of-E3 {
                value 7;
                description "Asynchronous mapping of E3";
            }
            enum bit-synchronous-mapping-of-E3 {
                value 8;
                description "Bit synchronous mapping of E3";
            }
            enum byte-synchronous-mapping-of-E3 {
                value 9;
                description "Byte synchronous mapping of E3";
            }
            enum asynchronous-mapping-of-DS2T2 {
                value 10;
                description "Asynchronous mapping of DS2/T2";
            }
            enum bit-synchronous-mapping-of-DS2T2 {
                value 11;
                description "Bit synchronous mapping of DS2/T2";
            }
            enum asynchronous-mapping-of-E1 {
                value 13;
                description "Asynchronous mapping of E1";
            }
            enum byte-synchronous-mapping-of-E1 {
                value 14;
                description "Byte synchronous mapping of E1";
            }
            enum byte-synchronous-mapping-of-31DS0 {
                value 15;
                description "Byte synchronous mapping of 31 * DS0";
            }
            enum asynchronous-mapping-of-DS1T1 {
                value 16;
                description "Asynchronous mapping of DS1/T1";
            }
            enum bit-synchronous-mapping-of-DS1T1 {
                value 17;
                description "Bit synchronous mapping of DS1/T1";
            }
            enum byte-synchronous-mapping-of-DS1T1 {
                value 18;
                description "Byte synchronous mapping of DS1/T1";
            }
            enum vc-11-in-vc12 {
                value 19;
                description "VC-11 in VC-12";
            }
            enum vt-lovc {
                value 26;
                description "VT-LOVC";
            }
            enum ste-spe-hovc {
                value 27;
                description "STS SPE-HOVC";
            }
            enum pos-noscrambling-16bit-CRC {
                value 28;
                description "POS - No Scrambling, 16 bit CRC";
            }
            enum pos-noscrambling-32bit-CRC {
                value 29;
                description "POS - No Scrambling, 32 bit CRC";
            }
            enum pos-scrambling-16bit-CRC {
                value 30;
                description "POS - Scrambling, 16 bit CRC";
            }
            enum pos-scrambling-32bit-CRC {
                value 31;
                description "POS - Scrambling, 32 bit CRC";
            }
            enum atm {
                value 32;
                description "ATM mapping";
            }
            enum ethernet {
                value 33;
                description "Ethernet";
            }
            enum ansi-etsi-pdh {
                value 38;
                description "ANSI-ETSI PDH";
            }
            enum link-access-protocol-SDH {
                value 40;
                description "Link Access Protocol SDH";
            }
            enum fddi {
                value 41;
                description "FDDI";
            }
            enum dqdb {
                value 42;
                description "DQDB";
            }
            enum hdlc {
                value 44;
                description "HDLC";
            }
            enum ethernet-V2-DIX {
                value 45;
                description "Ethernet V2-DIX";
            }
            enum ethernet-802.3 {
                value 46;
                description "Ethernet 802.3";
            }
        }
        description "type definition for CML_GMPLS_SDH_GPID_TYPE_T";
    }

    typedef  cml_gmpls_otn_gpid_type_t {
        type enumeration {
            enum atm-mapping {
                value 32;
                description "atm-mapping";
            }
            enum eth-phy {
                value 33;
                description "eth-phy";
            }
            enum sonet-sdh {
                value 34;
                description "sonet-sdh";
            }
            enum res-sonet {
                value 35;
                description "res-sonet";
            }
            enum g709-oduj {
                value 47;
                description "g709-oduj";
            }
            enum g709-otukv {
                value 48;
                description "g709_otukv";
            }
            enum cbra {
                value 49;
                description "cbra";
            }
            enum cbrb {
                value 50;
                description "cbrb";
            }
            enum bsot {
                value 51;
                description "bsot";
            }
            enum bsnt {
                value 52;
                description "bsnt";
            }
            enum ip-ppp {
                value 53;
                description "ip-ppp";
            }
            enum eth-mac-framed-gfp {
                value 54;
                description "eth-mac-framed-gfp";
            }
            enum eth-phy-trans-gfp {
                value 55;
                description "eth-phy-trans-gfp";
            }
            enum escon {
                value 56;
                description "escon";
            }
            enum ficon {
                value 57;
                description "ficon";
            }
            enum fiber-channel {
                value 58;
                description "fiber-channel";
            }
        }
        description "type definition for CML_GMPLS_OTN_GPID_TYPE_T";
    }

    typedef  cml_gmpls_otn_reservable_bandwidth_t {
        type enumeration {
            enum odu1 {
                value 1;
                description "ODU1 at 2.5 Gbps";
            }
            enum odu2 {
                value 2;
                description "ODU2 at 10 Gbps";
            }
            enum odu3 {
                value 3;
                description "ODU3 at 40 Gbps";
            }
            enum och1 {
                value 6;
                description "OCh at 2.5 Gbps";
            }
            enum och2 {
                value 7;
                description "OCh at 10  Gbps";
            }
            enum och3 {
                value 8;
                description "OCh at 40  Gbps";
            }
        }
        description "type definition for CML_GMPLS_OTN_RESERVABLE_BANDWIDTH_T";
    }

    typedef  cml_gmpls_transparency_type_t {
        type enumeration {
            enum sec-regen {
                value 1;
                description "Section/Regenerator Section layer";
            }
            enum line-mux {
                value 2;
                description "Line/Multiplex Section layer";
            }
        }
        description "type definition for CML_GMPLS_TRANSPARENCY_TYPE_T";
    }

    typedef  cml_gmpls_sdh_indication_t {
        type enumeration {
            enum std {
                value 0;
                description "Standard SONET/SDH";
            }
            enum arbitrary {
                value 1;
                description "Arbitrary SONET/SDH";
            }
        }
        description "type definition for CML_GMPLS_SDH_INDICATION_T";
    }

    typedef  cml_ip_version_t {
        type enumeration {
            enum unknown {
                value 0;
                description "An unknown or unspecified version of the Internet protocol";
            }
            enum ipv4 {
                value 1;
                description "The IPv4 protocol as defined in RFC 2460.";
            }
            enum ipv6 {
                value 2;
                description "The IPv6 protocol as defined in RFC 2460.";
            }
        }
        description "This value represents the version of the IP protocol.";
        reference "RFC 6991: Common YANG data types";
    }

    typedef  cml_psstate_t {
        type enumeration {
            enum Not-Running {
                value 0;
                description "Stop the process";
            }
            enum Running {
                value 1;
                description "Start the process";
            }
        }
        description "type definition for CML_PSSTATE_T";
    }

    typedef  cml_global_psstate_t {
        type enumeration {
            enum False {
                value 0;
                description "one of the process not running";
            }
            enum True {
                value 1;
                description "All process are running";
            }
        }
        description "type definition for CML_GLOBAL_PSSTATE_T";
    }

    typedef  cml_watchdogstatus_t {
        type enumeration {
            enum Disabled {
                value 0;
                description "Watchdog status is disabled globally";
            }
            enum Enabled {
                value 1;
                description "Watchdog status is enabled globally";
            }
        }
        description "type definition for CML_WATCHDOGSTATUS_T";
    }

    typedef  cml_mpls_port_type_t {
        type enumeration {
            enum access-port {
                value 1;
                description "Access interface statistics counters";
            }
            enum network-port {
                value 2;
                description "Network interface statistics counters";
            }
        }
        description "type definition for CML_MPLS_PORT_TYPE_T";
    }

    typedef  cml_mpls_port_access_type_t {
        type enumeration {
            enum access-port {
                value 1;
                description "Access interface statistics counters";
            }
        }
        description "type definition for CML_MPLS_PORT_ACCESS_TYPE_T";
    }

    typedef  cml_mpls_port_network_type_t {
        type enumeration {
            enum network-port {
                value 2;
                description "Network interface statistics counters";
            }
        }
        description "type definition for CML_MPLS_PORT_NETWORK_TYPE_T";
    }

    typedef  cml_raw_string_t {
        type string;
        description "type definition for CML_RAW_STRING_T";
    }

    typedef  cml_kaps_forwading_profile_t {
        type enumeration {
            enum kaps-profile-one {
                value 9;
                description "kaps profile one";
            }
            enum kaps-profile-two {
                value 10;
                description "kaps profile two";
            }
        }
        description "type definition for CML_KAPS_FORWADING_PROFILE_T";
    }

    typedef  cml_elk_tcam_forwading_profile_t {
        type enumeration {
            enum elk-tcam-profile-one {
                value 11;
                description "elk-tcam profile one";
            }
            enum elk-tcam-profile-two {
                value 12;
                description "elk-tcam profile two";
            }
            enum elk-tcam-profile-three {
                value 13;
                description "elk-tcam profile three";
            }
        }
        description "type definition for CML_ELK_TCAM_FORWADING_PROFILE_T";
    }

    typedef  cml_frwd_profile_t {
        type enumeration {
            enum l2-profile-one {
                value 0;
                description "L2 profile One";
            }
            enum l2-profile-two {
                value 1;
                description "L2 profile Two";
            }
            enum l2-profile-three {
                value 2;
                description "L2 profile Three (default)";
            }
            enum l3-profile {
                value 3;
                description "L3 profile";
            }
            enum l3-128bit-profile {
                value 4;
                description "L3 profile with 128 bit prefix support";
            }
            enum lpm-profile {
                value 5;
                description "LPM profile";
            }
            enum lpm-128bit-profile {
                value 6;
                description "LPM profile with 128 bit prefix support";
            }
            enum acl-profile {
                value 7;
                description "ACL profile";
            }
            enum custom-profile {
                value 8;
                description "custom profile";
            }
        }
        description "type definition for CML_FRWD_PROFILE_T";
    }

    typedef  cml_watchdog_t {
        type enumeration {
            enum software-watchdog {
                value 1;
                description "Software Watchdog";
            }
        }
        description "type definition for CML_WATCHDOG_T";
    }

    typedef  cml_watchdog_module_name_t {
        type enumeration {
            enum nsm {
                value 1;
                description "Software watchdog for NSM module";
            }
            enum ripd {
                value 2;
                description "Software watchdog for RIP module";
            }
            enum ripngd {
                value 3;
                description "Software watchdog for RIPNG module";
            }
            enum ospfd {
                value 4;
                description "Software watchdog for OSPF module";
            }
            enum ospf6d {
                value 5;
                description "Software watchdog for OSPF6 module";
            }
            enum isisd {
                value 6;
                description "Software watchdog for ISIS module";
            }
            enum hostpd {
                value 7;
                description "Software watchdog for HOSTP module";
            }
            enum ldpd {
                value 8;
                description "Software watchdog for LDP module";
            }
            enum rsvpd {
                value 9;
                description "Software watchdog for RSVP module";
            }
            enum mribd {
                value 10;
                description "Software watchdog for MRIB module";
            }
            enum pimd {
                value 11;
                description "Software watchdog for PIM module";
            }
            enum authd {
                value 13;
                description "Software watchdog for AUTH module";
            }
            enum mstpd {
                value 17;
                description "Software watchdog for MSTP module";
            }
            enum imi {
                value 18;
                description "Software watchdog for IMI module";
            }
            enum onmd {
                value 24;
                description "Software watchdog for ONM module";
            }
            enum hsl {
                value 26;
                description "Software watchdog for HSL module";
            }
            enum oamd {
                value 28;
                description "Software watchdog for OAM module";
            }
            enum vlogd {
                value 30;
                description "Software watchdog for VLOG module";
            }
            enum ptpd {
                value 34;
                description "Software watchdog for PTP module";
            }
            enum synced {
                value 37;
                description "Software watchdog for SYNCE module";
            }
            enum vrrpd {
                value 39;
                description "Software watchdog for VRRP module";
            }
            enum ndd {
                value 40;
                description "Software watchdog for NDD module";
            }
            enum ribd {
                value 42;
                description "Software watchdog for RIB module";
            }
            enum bgpd {
                value 44;
                description "Software watchdog for BGP module";
            }
            enum l2mribd {
                value 46;
                description "Software watchdog for L2MRIB module";
            }
            enum lagd {
                value 49;
                description "Software watchdog for LAG module";
            }
            enum sflow {
                value 50;
                description "Software watchdog for SFLOW module";
            }
            enum cmld {
                value 52;
                description "Software watchdog for CML module";
            }
            enum cmmd {
                value 69;
                description "Software watchdog for CMM module";
            }
            enum pcepd {
                value 72;
                description "Software watchdog for PCEP module";
            }
        }
        description "type definition for CML_WATCHDOG_MODULE_NAME_T";
    }

    typedef  cml_watchdog_module_status_t {
        type enumeration {
            enum disabled {
                value 0;
                description "Disable software watchdog";
            }
            enum enabled {
                value 1;
                description "Enable software watchdog";
            }
        }
        description "type definition for CML_WATCHDOG_MODULE_STATUS_T";
    }

    typedef  cml_hqos_layer4_protocol_t {
        type enumeration {
            enum any {
                value 0;
                description "Specify ANY protocol- TCP/UDP";
            }
            enum tcp {
                value 1;
                description "Specify TCP protocol";
            }
            enum udp {
                value 2;
                description "Specify UDP protocol";
            }
        }
        description "type definition for CML_HQOS_LAYER4_PROTOCOL_T";
    }

    typedef  cml_redirect_mirror_port_t {
        type enumeration {
            enum redirect-to-port {
                value 5;
                description "Redirect packet to new interface";
            }
            enum mirror-to-port {
                value 6;
                description "Mirror packet to new interface";
            }
        }
        description "type definition for CML_REDIRECT_MIRROR_PORT_T";
    }

    typedef  erps_switch_operation_type {
        type enumeration {
            enum force-switch {
                value 0;
                description "Trigger force switch. This operation overrides all other state of the ring.";
            }
            enum manual-switch {
                value 1;
                description "Trigger manual switch. This operation is allowed only when a ring instance is in idle or pending state. This action allows administrator to temporarily block another ring port and unblock RPL link to perform maintenance operation in the ring.";
            }
        }
        description "G.8032 administrative operation types.";
    }

    typedef  erps_port_id_type {
        type enumeration {
            enum east-interface {
                value 1;
                description "East-interface of the ring node.";
            }
            enum west-interface {
                value 2;
                description "West-interface of the ring node.";
            }
        }
        description "Each ring instance has maximum of two ports. This definition
                    labels these ports as east or west for identifications.";
    }

    typedef  cml_rmep_id_t {
        type union {
            type cml_mep_id_t {

            }
            type cml_rmep_mac_addr_t {

            }
        }
        description "type definition for CML_RMEP_ID_T";
    }

    typedef  cml_mep_id_t {
        type string;
        description "type definition for CML_MEP_ID_T";
    }

    typedef  cml_rmep_mac_addr_t {
        type string;
        description "type definition for CML_RMEP_MAC_ADDR_T";
    }

    typedef  cml_starttime_t {
        type enumeration {
            enum immediate {
                value 1;
                description "Start the measurement session immediately";
            }
        }
        description "type definition for CML_STARTTIME_T";
    }

    typedef  cml_stoptime_t {
        type enumeration {
            enum none {
                value 0;
                description "Never end the measurement session";
            }
        }
        description "type definition for CML_STOPTIME_T";
    }

    typedef  cml_absolute_t {
        type enumeration {
            enum absolute {
                value 3;
                description "This object specifies the scheduled start/stop date/time to perform the on-demand Performance Monitoring OAM operations";
            }
        }
        description "type definition for CML_ABSOLUTE_T";
    }

    typedef  cml_relative_t {
        type enumeration {
            enum relative {
                value 2;
                description "This object specifies the relative start/stop time from the current system time to perform on-demand Performance Monitoring OAM operations";
            }
        }
        description "type definition for CML_RELATIVE_T";
    }

    typedef  cml_evpn_service_type_t {
        type enumeration {
            enum vlan-based {
                value 1;
                description "vlan-based EVPN-Service type";
            }
        }
        description "type definition for CML_EVPN_SERVICE_TYPE_T";
    }

    typedef  cml_evpn_mpls_acc_if_t {
        type enumeration {
            enum access-if {
                value 1;
                description "EVPN MPLS Access interface mode change";
            }
        }
        description "type definition for CML_EVPN_MPLS_ACC_IF_T";
    }

    typedef  cml_evpn_table_show {
        type enumeration {
            enum mac-table {
                value 1;
                description "dynamic and static MAC table";
            }
            enum arp-cache {
                value 2;
                description "dynamic and static MAC-IPv4 table";
            }
            enum nd-cache {
                value 3;
                description "dynamic and static MAC-IPv6 table";
            }
        }
        description "type definition for CML_EVPN_TABLE_SHOW";
    }

    typedef  cml_libhwconf_loadbalance {
        type enumeration {
            enum enable {
                value 1;
                description "Command to enable/disable load-balance";
            }
        }
        description "type definition for CML_LIBHWCONF_LOADBALANCE";
    }

    typedef  cml_macadd_mepid_t {
        type union {
            type uint16 {

            }
            type cml_mac_addr_t {

            }
        }
        description "type definition for CML_MACADD_MEPID_T";
    }

    typedef  cml_suppressra_t {
        type enumeration {
            enum disable {
                value 0;
                description "Disable IPv6 Router Advertisements";
            }
            enum enable {
                value 1;
                description "Enable IPv6 Router Advertisements";
            }
        }
        description "type definition for CML_SUPPRESSRA_T";
    }

    typedef  cml_suppressra_mtu_t {
        type enumeration {
            enum disable {
                value 0;
                description "Disable sending MTU in Router Advertisement messages";
            }
            enum enable {
                value 1;
                description "Enable sending MTU in Router Advertisement messages";
            }
        }
        description "type definition for CML_SUPPRESSRA_MTU_T";
    }

    typedef  cfm_bridge_type {
        type enumeration {
            enum vpws {
                value 1;
                description "Identifying string for VPWS instance";
            }
            enum evpn {
                value 2;
                description "Identifying string for EVPN instance";
            }
        }
        description "type definition for CFM_BRIDGE_TYPE";
    }

    typedef  cml_rmepid_t {
        type string;
        description "type definition for CML_RMEPID_T";
    }

    typedef  cml_rmep_type_t {
        type union {
            type cml_rmep_mac_addr_t {

            }
            type cml_rmepid_t {

            }
        }
        description "type definition for CML_RMEP_TYPE_T";
    }

    typedef  cml_hostp_rbac_rule_type_t {
        type enumeration {
            enum deny {
                value 0;
                description "Remove rule from policy";
            }
            enum permit {
                value 1;
                description "Add rule to policy";
            }
        }
        description "type definition for CML_HOSTP_RBAC_RULE_TYPE_T";
    }

    typedef  cml_hostp_rbac_default_rule_type_t {
        type enumeration {
            enum deny-all {
                value 0;
                description "Set default rule as deny-all";
            }
            enum permit-all {
                value 1;
                description "Set default rule as permit-all";
            }
        }
        description "type definition for CML_HOSTP_RBAC_DEFAULT_RULE_TYPE_T";
    }

    typedef  cml_vm_status_t {
        type enumeration {
            enum DOWN {
                value 0;
                description "DOWN";
            }
            enum UP {
                value 1;
                description "UP";
            }
        }
        description "type definition for CML_VM_STATUS_T";
    }

    typedef  cml_libhwconf_cpu_queue_monitor {
        type enumeration {
            enum no-monitor {
                value 0;
                description "do not monitor cpu queue usage";
            }
            enum monitor {
                value 1;
                description "monitor cpu queue usage";
            }
        }
        description "type definition for CML_LIBHWCONF_CPU_QUEUE_MONITOR";
    }

    typedef  cml_libhwconf_cpu_queue_name {
        type enumeration {
            enum cpu.q0 {
                value 0;
                description "cpu.q0";
            }
            enum cpu.q1 {
                value 1;
                description "cpu.q1";
            }
            enum cpu.q2 {
                value 2;
                description "cpu.q2";
            }
            enum cpu.q3 {
                value 3;
                description "cpu.q3";
            }
            enum cpu.q4 {
                value 4;
                description "cpu.q4";
            }
            enum cpu.q5 {
                value 5;
                description "cpu.q5";
            }
            enum cpu.q6 {
                value 6;
                description "cpu.q6";
            }
            enum cpu.q7 {
                value 7;
                description "cpu.q7";
            }
            enum igmp {
                value 16;
                description "IGMP queue parameters";
            }
            enum isis {
                value 17;
                description "ISIS queue parameters";
            }
            enum reserved-mc {
                value 18;
                description "reserved-mc queue parameters";
            }
            enum link-local {
                value 19;
                description "Link-local  queue parameters";
            }
            enum ospf {
                value 20;
                description "OSPF queue parameters";
            }
            enum bgp {
                value 21;
                description "BGP queue parameters";
            }
            enum rsvp-ldp {
                value 22;
                description "RSVP/LDP queue parameters";
            }
            enum vrrp-rip-dhcp {
                value 23;
                description "VRRP/RIP/DHCP queue parameters";
            }
            enum pim {
                value 24;
                description "PIM queue parameters";
            }
            enum icmp-mpls {
                value 25;
                description "ICMP/MPLS queue parameters";
            }
            enum arp {
                value 26;
                description "ARP queue parameters";
            }
            enum bpdu {
                value 27;
                description "BPDU queue parameters";
            }
            enum oamp {
                value 28;
                description "OAMP queue parameters";
            }
            enum sflow {
                value 29;
                description "sflow queue parameters";
            }
            enum dsp {
                value 30;
                description "DSP queue parameters";
            }
            enum evpn {
                value 31;
                description "EVPN queue parameters";
            }
            enum nhop {
                value 32;
                description "nhop queue parameters";
            }
            enum mgmt-route-leak {
                value 33;
                description "nhop queue parameters";
            }
            enum icmp-redirect {
                value 34;
                description "ICMP-redirect queue parameters";
            }
            enum cfm {
                value 36;
                description "CFM Error queue parameters";
            }
            enum bfd {
                value 37;
                description "BFD queue parameters";
            }
        }
        description "type definition for CML_LIBHWCONF_CPU_QUEUE_NAME";
    }

    typedef  cml_ldp_mldp_lsp_type_t {
        type enumeration {
            enum p2mp {
                value 0;
                description "Create P2MP PMSI";
            }
            enum mp2mp {
                value 1;
                description "Create MP2MP PMSI";
            }
        }
        description "type definition for CML_LDP_MLDP_LSP_TYPE_T";
    }

    typedef  cml_mldp_rnr_type_t {
        type enumeration {
            enum p2mp {
                value 0;
                description "RNR for mLDP P2MP";
            }
            enum mp2mp {
                value 1;
                description "RNR for mLDP MP2MP";
            }
        }
        description "type definition for CML_MLDP_RNR_TYPE_T";
    }

    typedef  cml_mvrf_cms_t {
        type enumeration {
            enum bgp {
                value 1;
                description "bgp";
            }
        }
        description "type definition for CML_MVRF_CMS_T";
    }

    typedef  cml_mvrf_ipmsitunnel_t {
        type enumeration {
            enum rsvp-p2mp {
                value 1;
                description "rsvp-p2mp";
            }
            enum mldp-p2mp {
                value 2;
                description "mldp-p2mp";
            }
            enum ingress-replication {
                value 6;
                description "ingress-replication";
            }
            enum mldp-mp2mp {
                value 7;
                description "mldp-mp2mp";
            }
        }
        description "type definition for CML_MVRF_IPMSITUNNEL_T";
    }

    typedef  cml_mvrf_spmsitunnel_t {
        type enumeration {
            enum rsvp-p2mp {
                value 1;
                description "rsvp-p2mp";
            }
            enum mldp-p2mp {
                value 2;
                description "mldp-p2mp";
            }
            enum ingress-replication {
                value 6;
                description "ingress-replication";
            }
        }
        description "type definition for CML_MVRF_SPMSITUNNEL_T";
    }

    typedef  cml_mvrf_segmented_lsp_t {
        type enumeration {
            enum inter-area-segmented {
                value 1;
                description "inter-area-segmented";
            }
        }
        description "type definition for CML_MVRF_SEGMENTED_LSP_T";
    }

    typedef  cml_mvpn_ipmsimp2mproot_secondary_t {
        type enumeration {
            enum secondary {
                value 1;
                description "secondary root";
            }
        }
        description "type definition for CML_MVPN_IPMSIMP2MPROOT_SECONDARY_T";
    }

    typedef  cml_umh_selection_policy_t {
        type enumeration {
            enum highest-ip {
                value 1;
                description "highest-ip";
            }
            enum hash-based {
                value 2;
                description "hash-based";
            }
        }
        description "type definition for CML_UMH_SELECTION_POLICY_T";
    }

    typedef  cml_gtm_tunnel_t {
        type enumeration {
            enum rsvp-p2mp {
                value 1;
                description "rsvp-p2mp";
            }
            enum mldp-p2mp {
                value 2;
                description "mldp-p2mp";
            }
        }
        description "type definition for CML_GTM_TUNNEL_T";
    }

    typedef  cml_gtm_option_t {
        type enumeration {
            enum option-1 {
                value 1;
                description "Do not use Shared Trees in MPLS Core";
            }
            enum option-2 {
                value 2;
                description "Use Shared Trees in MPLS Core";
            }
        }
        description "type definition for CML_GTM_OPTION_T";
    }

    typedef  cml_ntp_acl_t {
        type bits {
            bit kod {
                position 0;
                description "Send a kiss-of-death packet if the client limit has exceeded";
            }
            bit nopeer {
                position 1;
                description "Prevent the client from establishing a peer association";
            }
            bit noserve {
                position 2;
                description "Prevent the client from performing time queries";
            }
            bit noquery {
                position 3;
                description "Prevent the client from performing ntpq and ntpdc queries, but not time queries";
            }
            bit nomodify {
                position 4;
                description "Restrict the client from making any changes to the NTP configurations";
            }
            bit notrap {
                position 5;
                description "Prevent the client from configuring control message traps";
            }
        }
        description "type definition for CML_NTP_ACL_T";
    }

    typedef  cml_ntp_client_mask_t {
        type union {
            type inet:ipv4-address {

            }
            type int32 {
                range "1..128";

            }
        }
        description "type definition for CML_NTP_CLIENT_MASK_T";
    }

}
