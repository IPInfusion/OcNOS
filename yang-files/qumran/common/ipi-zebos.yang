/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-zebos.yang
*
*/

module ipi-zebos {

    yang-version 1.1;

    namespace   "http://www.ipinfusion.com/yang/ocnos/zebos";

    prefix "ipi-zebos";

    organization
        "IP Infusion Inc.";

    contact
        "Address: 3965 Freedom Circle, Suite 200, Santa Clara, CA 95054
         Phone: +1 408-400-1900
         E-mail: support@ipinfusion.com
         Web: http://www.ipinfusion.com/";

    description
        "ZebOS Managed Object";


    revision "2020-10-07" {
        description "Adding data model for source interface selection for the management protocols";
        reference "Initial Version";
    }

    revision "2020-05-19" {
        description "Datemodel for sys-shutdown command";
        reference "Initial Version";
    }

    revision "2019-08-23" {
        description "Datemodel for system related commands";
        reference "Initial Version";
    }

    revision "2018-12-28" {
        description "Provider bridge static MAC support for Qumran platform";
        reference "Initial Version";
    }

    revision "2018-10-24" {
        description "Adding support for Guest-VM feature";
        reference "Initial Version";
    }

    revision "2018-06-21" {
        description "Initial Version";
        reference "Initial Version";
    }



    notification force_unlock {

        description "Notify force unlck from netconf.";

        // severity "INFO";
        // eventClass "MESSAGE";
        leaf message {
            type string;
            description " alarm message notification";
        }
    }

    notification system_shutdown_or_reload {

        description "Notify netconf about system shutdown or reload.";

        // severity "CRITICAL";
        // eventClass "MESSAGE";
        leaf message {
            type string;
            description " alarm message notification";
        }
    }

    notification config_sync_completion_status {

        description "Notify netconf about config sync being completed.";

        // severity "INFO";
        // eventClass "MESSAGE";
        leaf message {
            type string;
            description " alarm message notification";
        }
    }

    notification notification {

        description "Notify user upon receiving notification.";

        leaf message {
            type string;
            description " config change message notification";
            }
        }

}
