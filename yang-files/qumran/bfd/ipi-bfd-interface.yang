/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-bfd-interface.yang
*
*/

submodule ipi-bfd-interface {

    yang-version 1.1;

    belongs-to  ipi-bfd { prefix ipi-bfd; }

    import feature-list {
        prefix feature-list;
    }

    import ipi-bfd-types {
        prefix ipi-bfd-types;
    }

    import ipi-bfd-common {
        prefix ipi-bfd-common;
    }

    import ipi-interface {
        prefix ipi-interface;
    }

    import ietf-inet-types {
        prefix inet;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for Bidirecional Forwarding Detection (BFD) interface
                information";


    revision "2020-12-15" {
        description "Change to have data-types in lower case instead of camel case";
        reference " 0.2.0.";
    }

    revision "2020-11-30" {
        description "Restructured module as per open-config style";
        reference " 0.1.0.";
    }

    grouping bfd-interface-session-config {
        description
            "Grouping for BFD session config";
        leaf local-address  {
            type  inet:ip-address;
            description "BFD ip user intf src related configs";
        } // END of local-address definition.

        leaf remote-address  {
            type  inet:ip-address;
            description "BFD ip user intf dest related configs";
        } // END of remote-address definition.

        leaf session-type  {
            type  ipi-bfd-types:bfd_session_type_t;
            description "BFD session type";
        } // END of session-type definition.

        leaf administrative-down  {
            type  empty;
            description "BFD administrative down session";
        } // END of administrative-down definition.

        leaf demand-mode  {
            if-feature feature-list:NOT_HAVE_BFD_HW_OFFLOAD;
            type  empty;
            description "BFD demand mode session";
        } // END of demand-mode definition.

        leaf non-persistent  {
            type  empty;
            description "BFD non persistent session";
        } // END of non-persistent definition.

    } // END of bfd-interface-session-config definition.
    grouping bfd-interface-sessions-top {
        description
            "Grouping for BFD sessions configuration on interface";
        container sessions {
            description
                "Set BFD sessions on this interface";

            list session {
                key "local-address remote-address session-type";
                description
                    "BFD session table for runtime attrs";
                leaf local-address  {
                    type  leafref {
                        path  "../config/local-address";
                    }
                    description "BFD ip user intf src related configs";
                } // END of local-address definition.

                leaf remote-address  {
                    type  leafref {
                        path  "../config/remote-address";
                    }
                    description "BFD ip user intf dest related configs";
                } // END of remote-address definition.

                leaf session-type  {
                    type  leafref {
                        path  "../config/session-type";
                    }
                    description "BFD session type";
                } // END of session-type definition.

                container config {
                    description
                        "BFD session config";
                    uses bfd-interface-session-config;
                } // END of config-container definition.
                container state {
                    config false;
                    description
                        "BFD session state";
                    uses bfd-interface-session-config;
                } // END of state-container definition.
            } // End of session-list
        } // END of sessions-container definition.
    } // END of bfd-interface-sessions-top definition.
    grouping bfd-interface-config {
        description
            "Grouping for BFD configuration on interface";
        leaf name  {
            type  leafref {
                path  "/ipi-interface:interfaces/ipi-interface:interface/ipi-interface:name";
            }
            description "Interface name for which BFD is being configured";
        } // END of name definition.

        leaf bfd-enabled  {
            type  boolean;
            default true;
            description "Use this attribute to enable or disable all the BFD sessions on this
                        interface.";
        } // END of bfd-enabled definition.

    } // END of bfd-interface-config definition.
    grouping bfd-interface-state {
        description
            "Grouping for BFD state data on interface";
        leaf interface-index  {
            type  uint32;
            config false;
            description "The internal interface index";
        } // END of interface-index definition.

        leaf interface-state  {
            type  ipi-bfd-types:oambfd_if_state_t;
            config false;
            description "The interface operational state";
        } // END of interface-state definition.

    } // END of bfd-interface-state definition.
    grouping bfd-interval-top {
        description
            "Grouping for generic BFD interval parameters configuration";
        container intervals {
            description
                "BFD intervals configuration";

            list interval {
                if-feature feature-list:HAVE_BFD_MONO;
                key "desired-minimum-tx-interval required-minimum-rx-interval detection-multiplier";
                max-elements 1;
                description
                    "BFD interval parameters.";
                leaf desired-minimum-tx-interval  {
                    type  leafref {
                        path  "../config/desired-minimum-tx-interval";
                    }
                    description "The minimum interval between transmission of BFD control packets that
                                the operator desires. This value is advertised to the peer,
                                however the actual interval used is specified by taking the maximum of
                                desired-minimum-tx-interval and the value of the remote
                                required-minimum-receive
                                interval value.";
                } // END of desired-minimum-tx-interval definition.

                leaf required-minimum-rx-interval  {
                    type  leafref {
                        path  "../config/required-minimum-rx-interval";
                    }
                    description "The minimum interval between received BFD control packets that this
                                system should support. This value is advertised to the
                                remote peer to indicate the maximum frequency (i.e., minimum
                                inter-packet interval) between BFD control packets that is acceptable
                                to the local system.";
                } // END of required-minimum-rx-interval definition.

                leaf detection-multiplier  {
                    type  leafref {
                        path  "../config/detection-multiplier";
                    }
                    description "The number of packets that must be missed to declare this session as
                                down. The detection interval for the BFD session is
                                calculated by multiplying the value of the negotiated transmission
                                interval by this value.";
                } // END of detection-multiplier definition.

                container config {
                    description
                        "BFD intervals configuration parameters";
                    uses ipi-bfd-common:bfd-interval-config-common;
                } // END of config-container definition.
                container state {
                    config false;
                    description
                        "Operational state parameters for BFD intervals";
                    uses ipi-bfd-common:bfd-interval-config-common;
                } // END of state-container definition.
            } // End of interval-list
        } // END of intervals-container definition.
    } // END of bfd-interval-top definition.
    grouping bfd-echo-config {
        description
            "Grouping for BFD echo configuration on interface";
        leaf ipv4-source  {
            type  inet:ipv4-address;
            description "Use this attribute to configure BFD echo packet IPv4 source address";
        } // END of ipv4-source definition.

        leaf required-minimum-tx-interval  {
            type  uint32 {
                 range "50..4294967"  {
                    description "milliseconds";
                 }
            }
            description "Use this attribute to configure BFD echo packet transmission interval,
                        in milliseconds";
        } // END of required-minimum-tx-interval definition.

    } // END of bfd-echo-config definition.
    grouping bfd-echo-top {
        description
            "Grouping for BFD echo configuration on interface";
        container echo {
            description
                "Set BFD echo parameter";
            container config {
                description
                    "Configuration data";
                uses bfd-echo-config;
            } // END of config-container definition.
            container state {
                config false;
                description
                    "Operational state data";
                uses bfd-echo-config;
            } // END of state-container definition.
        } // END of echo-container definition.
    } // END of bfd-echo-top definition.

    grouping  interfaces-grouping {
    description
        "Configuration data";
    container interfaces {
        description
            "Configuration data";

        list interface {
        when " /bfd/interfaces/interface/intervals/interval/desired-minimum-tx-interval  or /bfd/interfaces/interface/authentication/config/key-type  or /bfd/interfaces/interface/echo/config/ipv4-source  or /bfd/interfaces/interface/echo/config/required-minimum-tx-interval  or /bfd/interfaces/interface/sessions/session/local-address  or /bfd/interfaces/interface/config/bfd-enabled ";
            key "name";
            description
                "BFD interface related operations";
            leaf name  {
                type  leafref {
                    path  "../config/name";
                }
                description "Interface name for which BFD is being configured";
            } // END of name definition.

            container config {
                description
                    "Configuration data";
                uses bfd-interface-config;
            } // END of config-container definition.
            container state {
                config false;
                description
                    "Operational state data";
                uses bfd-interface-config;
                uses bfd-interface-state;
            } // END of state-container definition.
            uses bfd-interval-top;
            uses bfd-echo-top;
            uses ipi-bfd-common:bfd-authentication-top;
            uses bfd-interface-sessions-top;
        } // End of interface-list
    } // END of interfaces-container definition.
    } // END of interfaces-grouping definition.


}
