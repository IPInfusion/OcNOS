/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-bfd-common.yang
*
*/

module ipi-bfd-common {

    yang-version 1.1;

    namespace   "http://www.ipinfusion.com/yang/ocnos/ipi-bfd-common";

    prefix "ipi-bfd-common";

    import ipi-bfd-types {
        prefix ipi-bfd-types;
    }

    import feature-list {
        prefix feature-list;
    }

    organization
        "IP Infusion Inc.";

    contact
        "Address: 3965 Freedom Circle, Suite 200, Santa Clara, CA 95054
         Phone: +1 408-400-1900
         E-mail: support@ipinfusion.com
         Web: http://www.ipinfusion.com/";

    description
        "YANG version of the ipi-bfd-common";


    revision "2020-12-15" {
        description "Change to have data-types in lower case instead of camel case";
        reference " 0.2.0.";
    }

    revision "2020-11-30" {
        description "Restructured module as per open-config style";
        reference " 0.1.0.";
    }

    grouping bfd-interval-config-common {
        description
            "Generic interval parameters for BFD.";
        leaf desired-minimum-tx-interval  {
            when " ../required-minimum-rx-interval + ../detection-multiplier ";
            type  uint32 {
                 range "3..999"  {
                    description "milliseconds";
                 }
            }
            units "milliseconds";
            description "The minimum interval between transmission of BFD control packets that
                        the operator desires. This value is advertised to the peer, however
                        the actual interval used is specified by taking the maximum of
                        desired-minimum-tx-interval and the value of the remote
                        required-minimum-receive interval value.";
        } // END of desired-minimum-tx-interval definition.

        leaf required-minimum-rx-interval  {
            when " ../desired-minimum-tx-interval + ../detection-multiplier ";
            type  uint32 {
                 range "3..999"  {
                    description "milliseconds";
                 }
            }
            units "milliseconds";
            description "The minimum interval between received BFD control packets that this
                        system should support. This value is advertised to the remote peer to
                        indicate the maximum frequency (i.e., minimum inter-packet interval)
                        between BFD control packets that is acceptable to the local system.";
        } // END of required-minimum-rx-interval definition.

        leaf detection-multiplier  {
            when " ../desired-minimum-tx-interval + ../required-minimum-rx-interval ";
            type  uint8 {
                 range "3..50"  {
                    description "Multiplier value";
                 }
            }
            description "The number of packets that must be missed to declare this session as
                        down. The detection interval for the BFD session is calculated by
                        multiplying the value of the negotiated transmission interval by this
                        value.";
        } // END of detection-multiplier definition.

    } // END of bfd-interval-config-common definition.
    grouping bfd-authentication-config {
        description
            "Grouping for generic BFD authentication configuration";
        leaf key-type  {
            when " ../key-id ";
            type  ipi-bfd-types:bfd_multihop_auth_type_t;
            description "Use this attribute to specify the authentication type for BFD
                        sessions.
                        There are five types of authentication: simple (simple password),
                        keyed-md5 (keyed message digest),
                        meticulous-keyed-md5 (meticulous keyed message digest), keyed-sha1
                        (keyed secure hashing algorithm),
                        meticulous-keyed-sha1 (meticulous keyed secure hashing algorithm).";
        } // END of key-type definition.

        choice key-option {
            description
                "Use this attribute to choose between key-id and key-chain.";
            case key-id {

                description
                    "Use this attribute to choose key-id.";

                leaf key-id  {
                    when " ../key-string + ../key-encrypted + ../key-type ";
                    type  uint32 {
                         range "0..255"  {
                            description "key-Id";
                         }
                    }
                    description "Use this attribute to specify a key-id for the authentication";
                } // END of key-id definition.

                leaf key-encrypted  {
                    when " ../key-string ";
                    type  ipi-bfd-types:oambfd_encrypt_key_t;
                    description "Use this attribute to configure the authentication key to specify if
                                the key-string is to be encrypted or not.";
                } // END of key-encrypted definition.

                leaf key-string  {
                    when " ../key-id + ../key-type ";
                    type  string {
                        length "1..max";
                        pattern "[^?' =,>|]+";
                    }
                    description "Use this attribute to specify the key authentication string";
                } // END of key-string definition.

            }
            case key-chain {

                description
                    "Use this attribute to choose key-chain.";

                leaf key-chain  {
                    when " ../key-type ";
                    if-feature feature-list:NOT_HAVE_BFD_HW_OFFLOAD;
                    type  string {
                        length "1..max";
                        pattern "[^?' =,>|]+";
                    }
                    description "Use this attribute to specify an key-chain name that is already
                                configured.";
                } // END of key-chain definition.

            }
        } // END of key-option-choice definition.
    } // END of bfd-authentication-config definition.
    grouping bfd-authentication-top {
        description
            "Grouping for generic BFD authentication configuration";
        container authentication {
            description
                "BFD authentication configuration data";
            container config {
                description
                    "Configuration data";
                uses bfd-authentication-config;
            } // END of config-container definition.
            container state {
                config false;
                description
                    "Operational state data";
                uses bfd-authentication-config;
            } // END of state-container definition.
        } // END of authentication-container definition.
    } // END of bfd-authentication-top definition.


}
