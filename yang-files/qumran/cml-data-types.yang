/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : cml-data-types.yang
*
*/

module cml-data-types {

    namespace   "http://www.ipinfusion.com/yang/ocnos/cml-data-types";

    prefix "cml-data-types";

    import ietf-inet-types {
        prefix inet;
    }

    organization
        "IP Infusion Inc.";

    contact
        "Address: 3965 Freedom Circle, Suite 200, Santa Clara, CA 95054
         Phone: +1 408-400-1900
         E-mail: support@ipinfusion.com
         Web: http://www.ipinfusion.com/";

    description
        "YANG version of the cml-data-types";


    revision "2018-06-21" {
        description " Initial Version.";
        reference "Initial Version";
    }



typedef  CML_NONEMPTY_STRING_T {

    type string{
    pattern "[^?' =,>|]+";
    }
    description "type definition for CML_NONEMPTY_STRING_T";
}

typedef  CML_LINE_T {

    type string{
    pattern "[^?'=,>|]*";
    }
    description "type definition for CML_LINE_T";
}

typedef  CML_SSH_PUBKEY_T {

    type string;
    description "type definition for CML_SSH_PUBKEY_T";
}

typedef  CML_MD5_PASSWORD_T {

    type string{
    pattern "[^? ]*";
    }
    description "type definition for CML_MD5_PASSWORD_T";
}

typedef  CML_HOST_STRING_T {

    type string;
    description "type definition for CML_HOST_STRING_T";
}

typedef  CML_RANGE_T {

    type string{
    pattern "[^?'=>|]*";
    }
    description "type definition for CML_RANGE_T";
}

typedef  CML_BITMAP_T {

    type uint32{
     range 0..4294967295;
    }
    description "type definition for CML_BITMAP_T";
}

typedef  CML_VM_AFFINITY_T {

    type string{
    pattern "[^?' =>|]*";
    }
    description "type definition for CML_VM_AFFINITY_T";
}

typedef  CML_IP_ADDR_NO_ZONE_T {
    type union {
        type inet:ipv4-address {

        }
        type inet:ipv4-address {

        }
    }
    description "type definition for CML_IP_ADDR_NO_ZONE_T";
}

typedef  CML_MAC_ADDR_T {

    type string;
    description "type definition for CML_MAC_ADDR_T";
}

typedef  CML_QOS_NAME_T {

    type string;
    description "type definition for CML_QOS_NAME_T";
}

typedef  CML_CMAP_MATCH_ANY_CRITERIA_T {
    type enumeration {
        enum match-any {
            value 2;
            description "Logical-OR of all match statements under this class-map";
        }
    }
    description "type definition for CML_CMAP_MATCH_ANY_CRITERIA_T";
}

typedef  CML_CMAP_MATCH_CRITERIA_T {
    type enumeration {
        enum default-match-type {
            value 0;
            description "Match type is default which is match-al";
        }
        enum match-all {
            value 1;
            description "Logical-AND of all match statements under this class-map";
        }
        enum match-any {
            value 2;
            description "Logical-OR of all match statements under this class-map";
        }
    }
    description "type definition for CML_CMAP_MATCH_CRITERIA_T";
}

typedef  CML_CLEAR_STAT_QOS_T {
    type enumeration {
        enum type-qos {
            value 0;
            description "Type of qos,QoS statistics";
        }
        enum type-qos-input {
            value 1;
            description "Type of qos,QoS statistics,Input direction";
        }
        enum type-qos-output {
            value 2;
            description "Type of qos,QoS statistics,Output direction";
        }
        enum type-queuing {
            value 3;
            description "Type of qos,Queuing statistics";
        }
    }
    description "type definition for CML_CLEAR_STAT_QOS_T";
}

typedef  CML_PROFILE_NAME_T {
    type enumeration {
        enum default {
            value 0;
            description "default";
        }
    }
    description "type definition for CML_PROFILE_NAME_T";
}

typedef  CML_PMAP_TYPE_T {
    type enumeration {
        enum type-qos {
            value 1;
            description "Type,QoS is ingress/egress policy-map";
        }
        enum type-queuing {
            value 2;
            description "Type,Queuing is egress policy-map";
        }
        enum type-queuing-default {
            value 3;
            description "Type,Queuing is egress policy-map,Default queue of port";
        }
    }
    description "type definition for CML_PMAP_TYPE_T";
}

typedef  CML_QOS_FILTER_TYPE_T {
    type enumeration {
        enum ingress-ipv4 {
            value 4;
            description "ingress ipv4";
        }
        enum ingress-ipv6 {
            value 16;
            description "ingress ipv6";
        }
        enum egress-ipv6 {
            value 32;
            description "egress ipv6";
        }
        enum ingress-arp {
            value 128;
            description "ingress arp";
        }
    }
    description "type definition for CML_QOS_FILTER_TYPE_T";
}

typedef  CML_QOS_OPERATION_T {
    type enumeration {
        enum qos-noop {
            value 0;
            description "qos noop";
        }
        enum qos-equal {
            value 1;
            description "qos equal";
        }
        enum qos-not-equal {
            value 2;
            description "qos not equal";
        }
        enum qos-less-than {
            value 3;
            description "qos less than";
        }
        enum qos-greater-than {
            value 4;
            description "qos greater than";
        }
        enum qos-operation-max {
            value 5;
            description "qos operation max";
        }
    }
    description "type definition for CML_QOS_OPERATION_T";
}

typedef  CML_FILTER_TYPE_T {
    type enumeration {
        enum qos-filter-deny {
            value 0;
            description "qos filter deny";
        }
        enum qos-filter-permit {
            value 1;
            description "qos filter permit";
        }
        enum qos-filter-mirror {
            value 2;
            description "qos filter mirror";
        }
        enum qos-filter-dynamic {
            value 3;
            description "qos filter dynamic";
        }
        enum qos-filter-source {
            value 4;
            description "qos filter source";
        }
        enum qos-filter-destination {
            value 5;
            description "qos filter destination";
        }
        enum qos-filter-no-match {
            value 6;
            description "qos filter no match";
        }
    }
    description "type definition for CML_FILTER_TYPE_T";
}

typedef  CML_CONFORM_ACTION_T {
    type enumeration {
        enum none {
            value 0;
            description "Sets the action to take when the data rate is within bounds";
        }
        enum transmit {
            value 1;
            description "Specifies the action of transmitting packets";
        }
        enum set-dscp-transmit {
            value 2;
            description "Specify the IP DSCP value 0 to 63";
        }
        enum set-prec-transmit {
            value 3;
            description "Specify the IP Precedence value 0 to 7";
        }
        enum set-cos-transmit {
            value 4;
            description "Specify the cos value 0 to 7";
        }
        enum set-mpls-class {
            value 5;
            description "Set the mpls class filed to the give value and tx the packet";
        }
        enum set-qos-transmit {
            value 6;
            description "Specify the qos value";
        }
    }
    description "type definition for CML_CONFORM_ACTION_T";
}

typedef  CML_EXCEED_ACTION_T {
    type enumeration {
        enum none {
            value 0;
            description "default value";
        }
        enum drop {
            value 1;
            description "Sets the action to take when the data rate is exceeded.default is drop";
        }
        enum set-dscp-transmit {
            value 2;
            description "Specify the IP DSCP value 0 to 63";
        }
        enum set-prec-transmit {
            value 3;
            description "Specify the IP Precedence value 0 to 7";
        }
        enum set-cos-transmit {
            value 4;
            description "Specify the cos value 0 to 7";
        }
        enum set-mpls-class {
            value 5;
            description "Set the mpls class filed to the give value and tx the packet";
        }
        enum set-flow-control {
            value 6;
            description "Send a pause frame on the ingress port and pass the packet";
        }
        enum set-axe-ret {
            value 7;
            description " Send a pause frame on the ingress port and pass the packet";
        }
        enum transmit {
            value 8;
            description "Pass the packet by setting DEI";
        }
    }
    description "type definition for CML_EXCEED_ACTION_T";
}

typedef  CML_VIOLATE_ACTION_T {
    type enumeration {
        enum none {
            value 0;
            description "default value";
        }
        enum drop {
            value 1;
            description "Sets the action to take when the data rate is exceeded.default is drop";
        }
        enum set-dscp-transmit {
            value 2;
            description "Specify the IP DSCP value 0 to 63";
        }
        enum set-cos-transmit {
            value 4;
            description "Specify the cos value 0 to 7";
        }
        enum set-mpls-class {
            value 5;
            description "Set the mpls class filed to the give value and tx the packet";
        }
        enum transmit {
            value 8;
            description "Pass the packet by setting DEI";
        }
    }
    description "type definition for CML_VIOLATE_ACTION_T";
}

typedef  CML_BURST_TYPE_T {
    type enumeration {
        enum none {
            value 0;
            description "default value";
        }
        enum kbytes {
            value 2;
            description "Specifies the units of kilobytes per second";
        }
        enum mbytes {
            value 3;
            description "Specifies the units of megabytes per second";
        }
        enum ms {
            value 4;
            description "Specifies the units of milliseconds";
        }
        enum us {
            value 5;
            description "Specifies the units of microseconds";
        }
    }
    description "type definition for CML_BURST_TYPE_T";
}

typedef  CML_QOS_POLICE_TYPE_T {
    type enumeration {
        enum none {
            value 0;
            description "no police-type, default will be colour-blind";
        }
        enum colour-blind {
            value 1;
            description "colour blind policer";
        }
        enum colour-aware {
            value 2;
            description "colour aware policer";
        }
    }
    description "type definition for CML_QOS_POLICE_TYPE_T";
}

typedef  CML_QOS_RATE_T {
    type enumeration {
        enum none {
            value 0;
            description "default value";
        }
        enum kbps {
            value 2;
            description "Specifies the units of kilobits per second";
        }
        enum mbps {
            value 3;
            description "Specifies the units of megabits per second";
        }
        enum gbps {
            value 4;
            description "Specifies the units of gigabits per second";
        }
        enum percent {
            value 6;
            description "Specifies the units in percentage";
        }
    }
    description "type definition for CML_QOS_RATE_T";
}

typedef  CML_FLOW_CONTROL_MODE_T {
    type enumeration {
        enum nsm-qos-flow-control {
            value 0;
            description "nsm qos flow control mode none";
        }
        enum nsm-full-bucket-size {
            value 1;
            description "nsm resume on full bucket size";
        }
        enum nsm-cbs-bucket-size {
            value 2;
            description "nsm resume on cbs bucket size";
        }
    }
    description "type definition for CML_FLOW_CONTROL_MODE_T";
}

typedef  CML_QOS_DSCP_VAL_T {
    type union {
        type CML_RANGE_T {

        }
        type CML_DSCP_TYPE_T {

        }
    }
    description "type definition for CML_QOS_DSCP_VAL_T";
}

typedef  CML_MSTP_INSTANCE_TYPE_T {
    type union {
        type int32 {
            range "1..63";

        }
        type CML_MSTP_INSTANCE_SPBM_T {

        }
    }
    description "type definition for CML_MSTP_INSTANCE_TYPE_T";
}

typedef  CML_MSTP_INSTANCE_SPBM_T {
    type enumeration {
        enum spbm {
            value 4092;
            description "spbm instance";
        }
    }
    description "type definition for CML_MSTP_INSTANCE_SPBM_T";
}

typedef  CML_CFM_AIS_MAC_T {
    type union {
        type CML_CFM_AIS_UNICAST_T {

        }
        type CML_CFM_AIS_MULTICAST_T {

        }
    }
    description "type definition for CML_CFM_AIS_MAC_T";
}

typedef  CML_CFM_AIS_MULTICAST_T {
    type enumeration {
        enum multicast {
            value 0;
            description "multicast ais frame to be sent";
        }
    }
    description "type definition for CML_CFM_AIS_MULTICAST_T";
}

typedef  CML_CFM_AIS_UNICAST_T {

    type string;
    description "type definition for CML_CFM_AIS_UNICAST_T";
}

typedef  CML_QOS_SET_PREC_VAL_T {
    type union {
        type int8 {
            range "0..7";

        }
        type CML_PREC_TYPE_T {

        }
    }
    description "type definition for CML_QOS_SET_PREC_VAL_T";
}

typedef  CML_QOS_SET_DSCP_VAL_T {
    type union {
        type int8 {
            range "0..63";

        }
        type CML_DSCP_TYPE_T {

        }
    }
    description "type definition for CML_QOS_SET_DSCP_VAL_T";
}

typedef  CML_DSCP_TYPE_T {
    type enumeration {
        enum default {
            value 0;
            description "Default dscp (000000)";
        }
        enum cs1 {
            value 8;
            description "CS1(precedence 1) dscp (001000)";
        }
        enum af11 {
            value 10;
            description "AF11 dscp (001010)";
        }
        enum af12 {
            value 12;
            description "AF12 dscp (001100)";
        }
        enum af13 {
            value 14;
            description "AF13 dscp (001110)";
        }
        enum cs2 {
            value 16;
            description "CS2(precedence 2) dscp (010000)";
        }
        enum af21 {
            value 18;
            description "AF21 dscp (010010)";
        }
        enum af22 {
            value 20;
            description "AF22 dscp (010100)";
        }
        enum af23 {
            value 22;
            description "AF23 dscp (010110)";
        }
        enum cs3 {
            value 24;
            description "CS3(precedence 3) dscp (011000)";
        }
        enum af31 {
            value 26;
            description "AF31 dscp (011010)";
        }
        enum af32 {
            value 28;
            description "AF32 dscp (011100)";
        }
        enum af33 {
            value 30;
            description "AF33 dscp (011110)";
        }
        enum cs4 {
            value 32;
            description "CS4(precedence 4) dscp (100000)";
        }
        enum af41 {
            value 34;
            description "AF41 dscp (100010)";
        }
        enum af42 {
            value 36;
            description "AF42 dscp (100100)";
        }
        enum af43 {
            value 38;
            description "AF43 dscp (100110)";
        }
        enum cs5 {
            value 40;
            description "CS5(precedence 5) dscp (101000)";
        }
        enum ef {
            value 46;
            description "EF dscp (101110)";
        }
        enum cs6 {
            value 48;
            description "CS6(precedence 6) dscp (110000)";
        }
        enum cs7 {
            value 56;
            description "CS7(precedence 7) dscp (111000)";
        }
    }
    description "type definition for CML_DSCP_TYPE_T";
}

typedef  CML_QOS_PREC_VAL_T {
    type union {
        type CML_RANGE_T {

        }
        type CML_PREC_TYPE_T {

        }
    }
    description "type definition for CML_QOS_PREC_VAL_T";
}

typedef  CML_PREC_TYPE_T {
    type enumeration {
        enum routine {
            value 0;
            description "Routine precedence(0)";
        }
        enum priority {
            value 1;
            description "Priority precedence(1)";
        }
        enum immediate {
            value 2;
            description "Immediate precedence(2)";
        }
        enum flash {
            value 3;
            description "Flash precedence(3)";
        }
        enum flashoverride {
            value 4;
            description "Flash override precedence(4)";
        }
        enum critical {
            value 5;
            description "Critical precedence(5)";
        }
        enum internet {
            value 6;
            description "Internetwork control precedence(6)";
        }
        enum network {
            value 7;
            description "Network control precedence(7)";
        }
    }
    description "type definition for CML_PREC_TYPE_T";
}

typedef  CML_PROTO_TYPE_T {
    type enumeration {
        enum arp {
            value 0;
            description "Address Resolution protocol";
        }
        enum bridging {
            value 1;
            description "Bridging";
        }
        enum cdp {
            value 2;
            description "CISCO Discovery Protocol";
        }
        enum clns {
            value 3;
            description "connectionless network service";
        }
        enum clns-es {
            value 4;
            description "CLNS END systems";
        }
        enum clns-is {
            value 5;
            description "CLNS Intermediate systems";
        }
        enum dhcp {
            value 6;
            description "Dynamic host configuration";
        }
        enum isis {
            value 7;
            description "Intermediate system to Intermedaite system";
        }
        enum ldp {
            value 8;
            description "Label Distrubution protocol";
        }
        enum netbios {
            value 9;
            description "NetBIOS Extended User Interface";
        }
    }
    description "type definition for CML_PROTO_TYPE_T";
}

typedef  CML_QOS_CLASS_DEFAULT_T {
    type enumeration {
        enum class-default {
            value 0;
            description "Default class map";
        }
    }
    description "type definition for CML_QOS_CLASS_DEFAULT_T";
}

typedef  CML_QUEUING_CLASS_DEFAULT_T {
    type enumeration {
        enum class-default-q {
            value 0;
            description "Default class map";
        }
    }
    description "type definition for CML_QUEUING_CLASS_DEFAULT_T";
}

typedef  CML_HQOS_ENABLE_DISABLE_T {
    type enumeration {
        enum disable {
            value 0;
            description "Disable QoS globally";
        }
        enum enable {
            value 1;
            description "Enable QoS globally";
        }
    }
    description "type definition for CML_HQOS_ENABLE_DISABLE_T";
}

typedef  CML_HQOS_CLASS_TYPE_T {
    type enumeration {
        enum q0 {
            value 0;
            description "Queue 0 and priority 0 lowest";
        }
        enum q1 {
            value 1;
            description "Queue 1 and priority 1";
        }
        enum q2 {
            value 2;
            description "Queue 2 and priority 2";
        }
        enum q3 {
            value 3;
            description "Queue 3 and priority 3";
        }
        enum q4 {
            value 4;
            description "Queue 4 and priority 4";
        }
        enum q5 {
            value 5;
            description "Queue 5 and priority 5";
        }
        enum q6 {
            value 6;
            description "Queue 6 and priority 6";
        }
        enum q7 {
            value 7;
            description "Queue 7 and priority 7";
        }
    }
    description "type definition for CML_HQOS_CLASS_TYPE_T";
}

typedef  CML_QOS_PMAPC_CLASS_NAME_T {
    type union {
        type CML_QOS_NAME_T {

        }
        type CML_QUEUING_CLASS_DEFAULT_T {

        }
    }
    description "type definition for CML_QOS_PMAPC_CLASS_NAME_T";
}

typedef  CML_QOS_PMAP_CLASS_NAME_T {
    type union {
        type CML_QOS_NAME_T {

        }
        type CML_QOS_CLASS_DEFAULT_T {

        }
    }
    description "type definition for CML_QOS_PMAP_CLASS_NAME_T";
}

typedef  CML_HQOS_MAC_DIR_T {
    type enumeration {
        enum src {
            value 0;
            description "Source address";
        }
        enum dest {
            value 1;
            description "Destination address";
        }
    }
    description "type definition for CML_HQOS_MAC_DIR_T";
}

typedef  CML_HQOS_TRAFFIC_TYPE_NOT_T {
    type enumeration {
        enum traffic-type {
            value 0;
            description "Traffic Type";
        }
    }
    description "type definition for CML_HQOS_TRAFFIC_TYPE_NOT_T";
}

typedef  CML_HQOS_TRAFFIC_TYPE_T {
    type enumeration {
        enum l2-mc {
            value 3;
            description "L2 Multicast";
        }
        enum l2-bc {
            value 5;
            description "L2 Broadcast";
        }
        enum default {
            value 6;
            description "L2 traffic-type all";
        }
        enum l2-unknown {
            value 7;
            description "Unknown L2 traffic";
        }
    }
    description "type definition for CML_HQOS_TRAFFIC_TYPE_T";
}

typedef  CML_HQOS_MATCH_NOT_T {
    type enumeration {
        enum cos {
            value 0;
            description "List COS Values";
        }
    }
    description "type definition for CML_HQOS_MATCH_NOT_T";
}

typedef  CML_HQOS_SHAPE_TYPE_T {
    type enumeration {
        enum bps {
            value 1;
            description "";
        }
        enum kbps {
            value 2;
            description "";
        }
        enum mbps {
            value 3;
            description "";
        }
        enum gbps {
            value 4;
            description "";
        }
        enum percent {
            value 6;
            description "";
        }
    }
    description "type definition for CML_HQOS_SHAPE_TYPE_T";
}

typedef  CML_HQOS_SHAPE_RATE_TYPE_T {
    type enumeration {
        enum kbps {
            value 2;
            description "Specifies the units of kilobits per second";
        }
        enum mbps {
            value 3;
            description "Specifies the units of megabits per second";
        }
        enum gbps {
            value 4;
            description "Specifies the units of gigabits per second";
        }
    }
    description "type definition for CML_HQOS_SHAPE_RATE_TYPE_T";
}

typedef  CML_HQOS_SET_BRIDGE_T {
    type enumeration {
        enum set-bridge {
            value 0;
            description "Setting a new value in the packet,Remark only Bridged packets";
        }
        enum set {
            value 1;
            description "Setting a new value in the packet";
        }
    }
    description "type definition for CML_HQOS_SET_BRIDGE_T";
}

typedef  CML_HQOS_SET_TYPE_T {
    type enumeration {
        enum cos {
            value 1;
            description "Specify a CoS";
        }
        enum dscp {
            value 2;
            description "Match packets with given dscp value";
        }
        enum precedence {
            value 3;
            description "IP Precedence value";
        }
        enum mpls-class {
            value 4;
            description "MPLS Class(or Queue) which mapped to exp,Specify Class value";
        }
        enum qos-group {
            value 14;
            description "Specify a QoS Group";
        }
    }
    description "type definition for CML_HQOS_SET_TYPE_T";
}

typedef  CML_HQOS_MATCH_NOT_DSCP_T {
    type enumeration {
        enum dscp {
            value 0;
            description "List DSCP Values";
        }
        enum ipv6-dscp {
            value 2;
            description "Specify IPv6 values,List DSCP Values";
        }
    }
    description "type definition for CML_HQOS_MATCH_NOT_DSCP_T";
}

typedef  CML_HQOS_MATCH_NOT_PRECEDENCE_T {
    type enumeration {
        enum precedence {
            value 0;
            description "List precedence Values";
        }
        enum ipv6-precedence {
            value 2;
            description "Specify IPv6 values,List precedence Values";
        }
    }
    description "type definition for CML_HQOS_MATCH_NOT_PRECEDENCE_T";
}

typedef  CML_HQOS_MATCH_NOT_RTP_T {
    type enumeration {
        enum ip {
            value 0;
            description "Internet Protocol (IP)";
        }
    }
    description "type definition for CML_HQOS_MATCH_NOT_RTP_T";
}

typedef  CML_QOS_CMAPDEF_TYPE_T {
    type enumeration {
        enum type-queuing-default {
            value 3;
            description "type,queuing,default";
        }
    }
    description "type definition for CML_QOS_CMAPDEF_TYPE_T";
}

typedef  CML_QOS_CMAP_QOS_TYPE_T {
    type enumeration {
        enum type-qos {
            value 1;
            description "type,qos is ingress/egress class-map";
        }
    }
    description "type definition for CML_QOS_CMAP_QOS_TYPE_T";
}

typedef  CML_QOS_DEI_TYPE_T {
    type enumeration {
        enum 0 {
            value 0;
            description "reset dei";
        }
        enum 1 {
            value 1;
            description "set dei";
        }
        enum all {
            value 2;
            description "all dei";
        }
    }
    description "type definition for CML_QOS_DEI_TYPE_T";
}

typedef  CML_QOS_COLOR_TYPE_T {
    type enumeration {
        enum green {
            value 0;
            description "set mapping for green packets";
        }
        enum yellow {
            value 1;
            description "set mapping for yellow packets";
        }
        enum red {
            value 2;
            description "set mapping for red packets";
        }
        enum all {
            value 3;
            description "set mapping for all packets";
        }
    }
    description "type definition for CML_QOS_COLOR_TYPE_T";
}

typedef  CML_QOS_MAP_PROFILE_TYPE_T {
    type enumeration {
        enum cos-to-queue {
            value 0;
            description "profile for cos to queue map";
        }
        enum queue-color-to-cos {
            value 1;
            description "profile for queue color to cos map";
        }
        enum dscp-to-queue {
            value 2;
            description "profile for dscp to queue map";
        }
        enum dscp-to-dscp {
            value 4;
            description "profile for inDscp to outDscp map";
        }
        enum exp-encap {
            value 6;
            description "profile for exp encapsulation map";
        }
    }
    description "type definition for CML_QOS_MAP_PROFILE_TYPE_T";
}

typedef  CML_VPLS_QOS_MAP_PROFILE_TYPE_T {
    type enumeration {
        enum cos-to-queue {
            value 0;
            description "profile for cos to queue map";
        }
        enum queue-color-to-cos {
            value 1;
            description "profile for queue color to cos map";
        }
    }
    description "type definition for CML_VPLS_QOS_MAP_PROFILE_TYPE_T";
}

typedef  CML_QOS_REMARK_TYPE_T {
    type enumeration {
        enum cos {
            value 1;
            description "Remark CoS";
        }
        enum dscp {
            value 4;
            description "Remark DSCP";
        }
    }
    description "type definition for CML_QOS_REMARK_TYPE_T";
}

typedef  CML_QOS_QUEUE_PROFILE_TYPE_T {
    type enumeration {
        enum profile1 {
            value 1;
            description "supported new 4 queue-bundle per service (default)";
        }
        enum profile2 {
            value 2;
            description "supported new 8 queue-bundle per service";
        }
    }
    description "type definition for CML_QOS_QUEUE_PROFILE_TYPE_T";
}

typedef  CML_REMARK_ENABLE_DISABLE_T {
    type enumeration {
        enum disable {
            value 1;
            description "disable remarking";
        }
        enum enable {
            value 2;
            description "enable remarking";
        }
    }
    description "type definition for CML_REMARK_ENABLE_DISABLE_T";
}

typedef  CML_QOS_CMAP_QUEUING_TYPE_T {
    type enumeration {
        enum type-queuing {
            value 2;
            description "Specify type of this class-map,Match on Egress Queuing class";
        }
    }
    description "type definition for CML_QOS_CMAP_QUEUING_TYPE_T";
}

typedef  CML_VXLAN_QOS_GLOBAL_MODE_T {
    type enumeration {
        enum cos-dscp {
            value 1;
            description "COS vs DSCP mapping";
        }
    }
    description "type definition for CML_VXLAN_QOS_GLOBAL_MODE_T";
}

typedef  CML_VXLAN_QOS_DIR_T {
    type enumeration {
        enum ingress {
            value 0;
            description "Apply ingress direction";
        }
        enum egress {
            value 1;
            description "Apply Egress direction";
        }
    }
    description "type definition for CML_VXLAN_QOS_DIR_T";
}

typedef  CML_VXLAN_QOS_EGRESS_DIR_T {
    type enumeration {
        enum egress {
            value 1;
            description "Apply Egress direction";
        }
    }
    description "type definition for CML_VXLAN_QOS_EGRESS_DIR_T";
}

typedef  CML_VXLAN_QOS_INGRESS_DIR_T {
    type enumeration {
        enum ingress {
            value 0;
            description "Apply ingress direction";
        }
    }
    description "type definition for CML_VXLAN_QOS_INGRESS_DIR_T";
}

typedef  CML_QOS_MATCH_TYPE_T {
    type enumeration {
        enum match-any {
            value 1;
            description "match any";
        }
        enum match-all {
            value 2;
            description "match all";
        }
    }
    description "type definition for CML_QOS_MATCH_TYPE_T";
}

typedef  CML_HQOS_MATCH_NOT_PROTOCOL_T {
    type enumeration {
        enum protocol {
            value 0;
            description "Protocol classification";
        }
    }
    description "type definition for CML_HQOS_MATCH_NOT_PROTOCOL_T";
}

typedef  CML_HQOS_MATCH_NOT_VLAN_T {
    type enumeration {
        enum vlan {
            value 0;
            description "List VLAN ID";
        }
    }
    description "type definition for CML_HQOS_MATCH_NOT_VLAN_T";
}

typedef  CML_HQOS_MATCH_NOT_MPLS_EXP_T {
    type enumeration {
        enum mpls {
            value 0;
            description "Multi Protocol Label Switch list values";
        }
    }
    description "type definition for CML_HQOS_MATCH_NOT_MPLS_EXP_T";
}

typedef  CML_HQOS_SHAPE_AVG_T {
    type enumeration {
        enum shape-average {
            value 0;
            description "Configure Traffic Shaping,Specifies an optional keyword";
        }
        enum shape {
            value 1;
            description "Configure Traffic Shaping";
        }
    }
    description "type definition for CML_HQOS_SHAPE_AVG_T";
}

typedef  CML_HQOS_SHAPE_AVG_UNITS_T {
    type enumeration {
        enum bps {
            value 0;
            description "Specifies the units of bits per second";
        }
        enum kbps {
            value 1;
            description "Specifies the units of kilobits per second";
        }
        enum mbps {
            value 2;
            description "Specifies the units of megabits per second";
        }
        enum gbps {
            value 3;
            description "Specifies the units of gigabits per second";
        }
    }
    description "type definition for CML_HQOS_SHAPE_AVG_UNITS_T";
}

typedef  CML_HQOS_THRESHOLD_TYPE_T {
    type enumeration {
        enum packets {
            value 1;
            description "Number of Packets (max 614400)";
        }
        enum bytes {
            value 2;
            description "bytes (max 629145600)";
        }
        enum kbytes {
            value 3;
            description "kilo-bytes (max 614400)";
        }
        enum mbytes {
            value 4;
            description "mega-bytes (max 600)";
        }
        enum ms {
            value 6;
            description "milli-seconds (max 50)";
        }
        enum us {
            value 7;
            description "micro-seconds (max 50000)";
        }
    }
    description "type definition for CML_HQOS_THRESHOLD_TYPE_T";
}

typedef  CML_SP_TYPE_T {
    type enumeration {
        enum sp {
            value 0;
            description "Currently only VALUE=1 is supported";
        }
    }
    description "type definition for CML_SP_TYPE_T";
}

typedef  CML_QOS_WRR_SP_T {
    type union {
        type int32 {
            range "1..127";

        }
        type CML_SP_TYPE_T {

        }
    }
    description "type definition for CML_QOS_WRR_SP_T";
}

typedef  CML_HOSTNAME_T {
    type union {
        type inet:ip-address {

        }
        type string {

        }
    }
    description "type definition for CML_HOSTNAME_T";
}

typedef  CML_HOSTPNAME_T {
    type union {
        type inet:ip-address {

        }
        type CML_HOST_STRING_T {

        }
    }
    description "type definition for CML_HOSTPNAME_T";
}

typedef  CML_IPV4HOSTNAME_T {
    type union {
        type inet:ipv4-address {

        }
        type CML_HOST_STRING_T {

        }
    }
    description "type definition for CML_IPV4HOSTNAME_T";
}

typedef  CML_HOST_T {
    type enumeration {
        enum hostname {
            value 1;
            description "Hostname";
        }
    }
    description "type definition for CML_HOST_T";
}

typedef  CML_IPV4_ADDR_OR_PREFIX_T {
    type union {
        type inet:ipv4-address {

        }
        type inet:ipv4-prefix {

        }
    }
    description "type definition for CML_IPV4_ADDR_OR_PREFIX_T";
}

typedef  CML_IP_PREFIX_ADDR_T {
    type union {
        type inet:ipv4-prefix {

        }
        type inet:ipv6-prefix {

        }
    }
    description "type definition for CML_IP_PREFIX_ADDR_T";
}

typedef  CML_MAC_ETH_TYPE_T {
    type union {
        type CML_ETH_TYPE_T {

        }
        type string {

        }
    }
    description "type definition for CML_MAC_ETH_TYPE_T";
}

typedef  CML_ETH_TYPE_T {
    type enumeration {
        enum ip4 {
            value 0;
            description "IPv4 Ethertype - 0x0800";
        }
        enum ip6 {
            value 1;
            description "IPv6 Ethertype - 0x86dd";
        }
        enum mpls {
            value 2;
            description "MPLS Ethertype - 0x8847";
        }
    }
    description "type definition for CML_ETH_TYPE_T";
}

typedef  CML_VLAN_OPERSTATUS_T {
    type enumeration {
        enum vlan_oper_up {
            value 1;
            description "VLAN operstatus is up";
        }
        enum vlan_oper_down {
            value 2;
            description "VLAN operstatus is down";
        }
    }
    description "type definition for CML_VLAN_OPERSTATUS_T";
}

typedef  CML_VLAN_TYPE_CUSTOMER_T {
    type enumeration {
        enum customer {
            value 1;
            description "Customer Vlan";
        }
    }
    description "type definition for CML_VLAN_TYPE_CUSTOMER_T";
}

typedef  CML_VLAN_TYPE_SERVICE_T {
    type enumeration {
        enum service-point-point {
            value 16;
            description "VLAN Type,Service VLAN,Service Point to Point Service VLAN";
        }
        enum service-multipoint-multipoint {
            value 32;
            description "VLAN Type,Service VLAN,Service Multi Point to Multi Point Service VLAN";
        }
        enum service-rooted-multipoint {
            value 2048;
            description "VLAN Type,Service VLAN,Service Rooted Multipoint Service VLAN";
        }
    }
    description "type definition for CML_VLAN_TYPE_SERVICE_T";
}

typedef  CML_FACILITY_T {
    type enumeration {
        enum local0 {
            value 0;
            description "Use local0 facility";
        }
        enum local1 {
            value 1;
            description "Use local1 facility";
        }
        enum local2 {
            value 2;
            description "Use local2 facility";
        }
        enum local3 {
            value 3;
            description "Use local3 facility";
        }
        enum local4 {
            value 4;
            description "Use local4 facility";
        }
        enum local5 {
            value 5;
            description "Use local5 facility";
        }
        enum local6 {
            value 6;
            description "Use local6 facility";
        }
        enum local7 {
            value 7;
            description "Use local7 facility";
        }
        enum user {
            value 8;
            description "Use user facility";
        }
    }
    description "type definition for CML_FACILITY_T";
}

typedef  CML_HOSTT_T {
    type enumeration {
        enum emergencies {
            value 0;
            description "Use local0 facility";
        }
        enum alerts {
            value 1;
            description "Use local1 facility";
        }
        enum critical {
            value 2;
            description "Use local2 facility";
        }
        enum errors {
            value 3;
            description "Use local3 facility";
        }
        enum warnings {
            value 4;
            description "Use local4 facility";
        }
        enum notifications {
            value 5;
            description "Use local5 facility";
        }
        enum informational {
            value 6;
            description "Use local6 facility";
        }
        enum debugging {
            value 7;
            description "Use local7 facility";
        }
    }
    description "type definition for CML_HOSTT_T";
}

typedef  CML_DISCARDFORWARD_T {
    type enumeration {
        enum discard {
            value 0;
            description "discard";
        }
        enum forward {
            value 1;
            description "forward";
        }
    }
    description "type definition for CML_DISCARDFORWARD_T";
}

typedef  CML_SWITCH_PORT_MODE_T {
    type enumeration {
        enum access {
            value 1;
            description "Set the Layer2 interface as Access";
        }
        enum hybrid {
            value 2;
            description "Set the Layer2 interface as hybrid";
        }
        enum trunk {
            value 3;
            description "Set the Layer2 interface as trunk";
        }
        enum provider-network {
            value 6;
            description "Set the Layer2 interface as provider network";
        }
        enum customer-edge-access {
            value 41;
            description "Set the Layer2 interface as customer edge,Set the Layer2 interface as Access";
        }
        enum customer-edge-hybrid {
            value 42;
            description "Set the Layer2 interface as customer edge,Set the Layer2 interface as hybrid";
        }
        enum customer-edge-trunk {
            value 43;
            description "Set the Layer2 interface as customer edge,Set the Layer2 interface as trunk";
        }
    }
    description "type definition for CML_SWITCH_PORT_MODE_T";
}

typedef  CML_VLAN_FRAME_TYPE_T {
    type enumeration {
        enum vlan-tagged {
            value 1;
            description "Set vlan-tagged frames can only be received";
        }
        enum all {
            value 2;
            description "Set vlan-tagged frames can only be received";
        }
    }
    description "type definition for CML_VLAN_FRAME_TYPE_T";
}

typedef  CML_OSPFV3_LINK_STATUS_T {
    type enumeration {
        enum up {
            value 1;
            description "Vlink Status is up";
        }
        enum down {
            value 2;
            description "Vlink Status is down";
        }
    }
    description "type definition for CML_OSPFV3_LINK_STATUS_T";
}

typedef  CML_OSPF6_CSPF_TYPE_T {
    type enumeration {
        enum random {
            value 0;
            description "Random";
        }
        enum most-fill {
            value 1;
            description "Most fill";
        }
        enum least-fill {
            value 2;
            description "Least fill";
        }
    }
    description "type definition for CML_OSPF6_CSPF_TYPE_T";
}

typedef  CML_OSPF6_ABR_TYPE_T {
    type enumeration {
        enum standard {
            value 1;
            description "Standard behavior (RFC2328)";
        }
        enum cisco {
            value 2;
            description "Alternative ABR, Cisco implementation (RFC3509)";
        }
        enum ibm {
            value 3;
            description "Alternative ABR, IBM implementation (RFC3509)";
        }
    }
    description "type definition for CML_OSPF6_ABR_TYPE_T";
}

typedef  CML_OSPF6_TRANSLATOR_ROLE_T {
    type enumeration {
        enum always {
            value 1;
            description "Translate always";
        }
        enum candidate {
            value 2;
            description "Candidate for translator (default)";
        }
    }
    description "type definition for CML_OSPF6_TRANSLATOR_ROLE_T";
}

typedef  CML_OSPF6_NETWORK_T {
    type enumeration {
        enum point-to-point {
            value 1;
            description "OSPF point-to-point network";
        }
        enum broadcast {
            value 2;
            description "OSPF broadcast multi-access network";
        }
        enum non-broadcast {
            value 3;
            description "OSPF NBMA network";
        }
        enum point-to-multipoint {
            value 4;
            description "OSPF point-to-multipoint network";
        }
        enum point-to-multipoint-non-broadcast {
            value 5;
            description "OSPF point-to-multipoint NBMA network,non-broadcast point-to-multipoint network";
        }
    }
    description "type definition for CML_OSPF6_NETWORK_T";
}

typedef  CML_OSPF6_LSA_SUPRESSION_STATE_T {
    type enumeration {
        enum disable {
            value 0;
            description "Disable";
        }
        enum enable {
            value 1;
            description "Enable";
        }
    }
    description "type definition for CML_OSPF6_LSA_SUPRESSION_STATE_T";
}

typedef  CML_OSPF6_RESTART_HELPER_T {
    type enumeration {
        enum only-reload {
            value 4;
            description "Only help on software reloads";
        }
        enum only-upgrade {
            value 8;
            description "Only help on software upgrades";
        }
    }
    description "type definition for CML_OSPF6_RESTART_HELPER_T";
}

typedef  CML_OSPF6_ROUTE_SOURCE_TYPE_T {
    type enumeration {
        enum kernel {
            value 1;
            description "Kernel routes";
        }
        enum connected {
            value 2;
            description "Connected";
        }
        enum static {
            value 3;
            description " Static routes";
        }
        enum rip {
            value 4;
            description " Routing Information Protocol (RIP/RIPNG)";
        }
        enum bgp {
            value 8;
            description " Border Gateway Protocol (BGP)";
        }
        enum isis {
            value 9;
            description "ISO IS-IS";
        }
    }
    description "type definition for CML_OSPF6_ROUTE_SOURCE_TYPE_T";
}

typedef  CML_OSPF6_DIST_ROUTE_SOURCE_TYPE_T {
    type enumeration {
        enum kernel {
            value 1;
            description "Kernel routes";
        }
        enum connected {
            value 2;
            description "Connected";
        }
        enum static {
            value 3;
            description " Static routes";
        }
        enum rip {
            value 4;
            description " Routing Information Protocol (RIP/RIPNG)";
        }
        enum bgp {
            value 8;
            description " Border Gateway Protocol (BGP)";
        }
        enum isis {
            value 9;
            description "ISO IS-IS";
        }
    }
    description "type definition for CML_OSPF6_DIST_ROUTE_SOURCE_TYPE_T";
}

typedef  CML_OSPF6_AF_ROUTE_SOURCE_TYPE_T {
    type enumeration {
        enum kernel {
            value 1;
            description "Kernel routes";
        }
        enum connected {
            value 2;
            description "Connected";
        }
        enum static {
            value 3;
            description " Static routes";
        }
        enum rip {
            value 4;
            description " Routing Information Protocol (RIP/RIPNG)";
        }
        enum ospf {
            value 6;
            description "Open Shortest Path First (OSPF/OSPF6)";
        }
        enum bgp {
            value 8;
            description " Border Gateway Protocol (BGP)";
        }
        enum isis {
            value 9;
            description "ISO IS-IS";
        }
    }
    description "type definition for CML_OSPF6_AF_ROUTE_SOURCE_TYPE_T";
}

typedef  CML_OSPF6_AREA_RANGE_T {
    type enumeration {
        enum not-advertise {
            value 0;
            description "DoNotAdvertise this range";
        }
        enum advertise {
            value 1;
            description "Advertise this range (default)";
        }
    }
    description "type definition for CML_OSPF6_AREA_RANGE_T";
}

typedef  CML_OSPF_INTERFACE_STATE_MSG_T {
    type enumeration {
        enum DependUpon {
            value 0;
            description "DependUpon";
        }
        enum Down {
            value 1;
            description "Down";
        }
        enum Loopback {
            value 2;
            description "Loopback";
        }
        enum Waiting {
            value 3;
            description "Waiting";
        }
        enum Point-To-Point {
            value 4;
            description "Point-To-Point";
        }
        enum DROther {
            value 5;
            description "DROther";
        }
        enum Backup {
            value 6;
            description "Backup";
        }
        enum DR {
            value 7;
            description "DR";
        }
    }
    description "type definition for CML_OSPF_INTERFACE_STATE_MSG_T";
}

typedef  CML_OSPF_AREA_T {
    type union {
        type inet:ipv4-address {

        }
        type uint32 {
            range "0..4294967295";

        }
    }
    description "type definition for CML_OSPF_AREA_T";
}

typedef  CML_OSPF6_PATH_TYPE_T {
    type enumeration {
        enum Connected {
            value 0;
            description "Connected";
        }
        enum IntraArea {
            value 1;
            description "IntraArea";
        }
        enum InterArea {
            value 2;
            description "InterArea";
        }
        enum External {
            value 3;
            description "External";
        }
        enum Discard {
            value 4;
            description "Discard";
        }
    }
    description "type definition for CML_OSPF6_PATH_TYPE_T";
}

typedef  CML_OSPF6_PATH_FLAGS_T {
    type enumeration {
        enum Type2 {
            value 1;
            description "Type2";
        }
        enum ABR {
            value 2;
            description "ABR";
        }
        enum ASBR {
            value 3;
            description "ASBR";
        }
        enum RangeMatched {
            value 4;
            description "RangeMatched";
        }
    }
    description "type definition for CML_OSPF6_PATH_FLAGS_T";
}

typedef  CML_OSPF_ACTION_TYPE_T {
    type enumeration {
        enum soft {
            value 1;
            description "Soft limit";
        }
        enum hard {
            value 2;
            description "Hard limit";
        }
    }
    description "type definition for CML_OSPF_ACTION_TYPE_T";
}

typedef  CML_OSPF_TELINK_LOCAL_T {
    type enumeration {
        enum disable-te-link-local {
            value 0;
            description "Disable TE Link local exchange";
        }
        enum enable-te-link-local {
            value 1;
            description "Enable TE Link local exchange";
        }
    }
    description "type definition for CML_OSPF_TELINK_LOCAL_T";
}

typedef  CML_OSPF_ROUTE_SOURCE_TYPE_T {
    type enumeration {
        enum kernel {
            value 1;
            description "Kernel routes";
        }
        enum connected {
            value 2;
            description "Connected";
        }
        enum static {
            value 3;
            description " Static routes";
        }
        enum rip {
            value 4;
            description " Routing Information Protocol (RIP)";
        }
        enum ospf {
            value 6;
            description "ISO OSPF";
        }
        enum bgp {
            value 8;
            description " Border Gateway Protocol (BGP)";
        }
        enum isis {
            value 9;
            description "ISO IS-IS";
        }
    }
    description "type definition for CML_OSPF_ROUTE_SOURCE_TYPE_T";
}

typedef  CML_OSPF_DIST_ROUTE_SOURCE_TYPE_T {
    type enumeration {
        enum kernel {
            value 1;
            description "Kernel routes";
        }
        enum connected {
            value 2;
            description "Connected";
        }
        enum static {
            value 3;
            description " Static routes";
        }
        enum rip {
            value 4;
            description " Routing Information Protocol (RIP)";
        }
        enum bgp {
            value 8;
            description " Border Gateway Protocol (BGP)";
        }
        enum isis {
            value 9;
            description "ISO IS-IS";
        }
    }
    description "type definition for CML_OSPF_DIST_ROUTE_SOURCE_TYPE_T";
}

typedef  CML_PORT_SEC_MODE_T {
    type enumeration {
        enum static {
            value 1;
            description "static mode";
        }
        enum default {
            value 2;
            description "dynamic mode";
        }
    }
    description "type definition for CML_PORT_SEC_MODE_T";
}

typedef  CML_PROVIDER_EDGE_T {
    type enumeration {
        enum edge {
            value 1;
            description "Configure as Edge bridge";
        }
    }
    description "type definition for CML_PROVIDER_EDGE_T";
}

typedef  CML_BRIDGE_PROTOCOL_T {
    type enumeration {
        enum ieee {
            value 1;
            description "IEEE 801.1Q spanning-tree protocol";
        }
        enum ieee-vlan-bridge {
            value 2;
            description "IEEE 801.1Q spanning-tree protocol";
        }
        enum rstp {
            value 3;
            description "IEEE 801.1w rapid spanning-tree protocol";
        }
        enum rstp-vlan-bridge {
            value 4;
            description "IEEE 801.1w rapid spanning-tree protocol";
        }
        enum mstp {
            value 5;
            description "IEEE 802.1s multiple spanning-tree protocol";
        }
        enum provider-rstp {
            value 6;
            description "IEEE 802.1s multiple spanning-tree protocol";
        }
        enum provider-mstp {
            value 7;
            description "IEEE 802.1s rapid spanning-tree protocol";
        }
        enum rpvst+ {
            value 8;
            description "IEEE 801.1w rapid per vlan spanning-tree protocol";
        }
        enum provider-rpvst+ {
            value 9;
            description "IEEE 801.1w rapid per vlan spanning-tree protocol";
        }
        enum trill {
            value 20;
            description "Transparent Interconnection of Lots of Link";
        }
    }
    description "type definition for CML_BRIDGE_PROTOCOL_T";
}

typedef  CML_BRIDGE_TYPE_T {
    type enumeration {
        enum spanning-tree {
            value 1;
            description "IEEE 801.1Q spanning-tree protocol";
        }
        enum rapid-spanning-tree {
            value 3;
            description "IEEE 801.1w rapid spanning-tree protocol";
        }
        enum multiple-spanning-tree {
            value 5;
            description "IEEE 802.1s multiple spanning-tree protocol";
        }
    }
    description "type definition for CML_BRIDGE_TYPE_T";
}

typedef  CML_OVERMACTYPE_T {
    type enumeration {
        enum static {
            value 1;
            description "The MAC is a static entry";
        }
        enum static-priority-override {
            value 2;
            description "The MAC is a Static Management";
        }
        enum static-mgmt {
            value 3;
            description "The MAC is a Static Management with priority override";
        }
        enum static-mgmt-priority-overide {
            value 4;
            description "The MAC is a static with priority override";
        }
    }
    description "type definition for CML_OVERMACTYPE_T";
}

typedef  CML_ENABLE_DISABLE_T {
    type enumeration {
        enum disable {
            value 0;
            description "Disable";
        }
        enum enable {
            value 1;
            description "Enable";
        }
    }
    description "type definition for CML_ENABLE_DISABLE_T";
}

typedef  CML_SR_ENABLE_DISABLE_T {
    type enumeration {
        enum disable {
            value 0;
            description "Disable processing of remote  mapping server advertisement";
        }
        enum enable {
            value 1;
            description "Enables processing of remote mapping server advertisement";
        }
    }
    description "type definition for CML_SR_ENABLE_DISABLE_T";
}

typedef  CML_VLANSTATE_T {
    type enumeration {
        enum disable {
            value 1;
            description "Disable";
        }
        enum enable {
            value 2;
            description "Enable";
        }
    }
    description "type definition for CML_VLANSTATE_T";
}

typedef  CML_PBRINTERFACE_T {
    type enumeration {
        enum null0 {
            value 0;
            description "Forward to no interface";
        }
        enum tunnel-te {
            value 1;
            description "Forward to MPLS-TE tunnel";
        }
    }
    description "type definition for CML_PBRINTERFACE_T";
}

typedef  CML_SPANNINGTREE_ENABLE_DISABLE_T {
    type enumeration {
        enum enable {
            value 0;
            description "Enable";
        }
        enum disable {
            value 1;
            description "Disable";
        }
    }
    description "type definition for CML_SPANNINGTREE_ENABLE_DISABLE_T";
}

typedef  CML_PATHCOST_METHOD_T {
    type enumeration {
        enum short {
            value 0;
            description "short - Use 16 bit based values for default port path cost";
        }
        enum long {
            value 1;
            description "long  - Use 32 bit based values for default port path costs";
        }
        enum default {
            value 2;
            description "Default";
        }
    }
    description "type definition for CML_PATHCOST_METHOD_T";
}

typedef  CML_LINK_TYPE_T {
    type enumeration {
        enum shared {
            value 0;
            description "shared - disable rapid transition";
        }
        enum point-to-point {
            value 1;
            description "point-to-point - enable rapid transition";
        }
        enum auto {
            value 2;
            description "auto - will be set to either p2p or shared based on duplex state";
        }
    }
    description "type definition for CML_LINK_TYPE_T";
}

typedef  CML_PORTEDGE_T {
    type enumeration {
        enum edgeport {
            value 0;
            description "edgeport - enable it as edgeport";
        }
        enum portfast {
            value 1;
            description "portfast - enable fast transitions";
        }
    }
    description "type definition for CML_PORTEDGE_T";
}

typedef  CML_BPDU_T {
    type enumeration {
        enum enable {
            value 0;
            description "Enable";
        }
        enum disable {
            value 1;
            description "Disable";
        }
        enum default {
            value 2;
            description "Default";
        }
    }
    description "type definition for CML_BPDU_T";
}

typedef  CML_BRIDGE_TOPOLOGY_T {
    type enumeration {
        enum topology-none {
            value 0;
            description "Topology none";
        }
        enum ring {
            value 1;
            description "RING Topology";
        }
    }
    description "type definition for CML_BRIDGE_TOPOLOGY_T";
}

typedef  CML_BRIDGE_FORWARDING_SET_T {
    type enumeration {
        enum disable {
            value 0;
            description "disable bridge forwarding";
        }
        enum enable {
            value 1;
            description "enable bridge forwarding";
        }
    }
    description "type definition for CML_BRIDGE_FORWARDING_SET_T";
}

typedef  CML_BRIDGE_MSTPENABLE_T {
    type enumeration {
        enum enable {
            value 1;
            description "enable spanning tree protocol";
        }
    }
    description "type definition for CML_BRIDGE_MSTPENABLE_T";
}

typedef  CML_BRIDGE_AGEING_STATE {
    type enumeration {
        enum disable {
            value 0;
            description "disable bridge ageing";
        }
    }
    description "type definition for CML_BRIDGE_AGEING_STATE";
}

typedef  CML_OSPF_DOMAIN_TYPE_T {
    type enumeration {
        enum type-as {
            value 1;
            description "Type 0x0005";
        }
        enum type-as4 {
            value 2;
            description "Type 0x0205";
        }
        enum type-back-comp {
            value 3;
            description "Type 0x8005";
        }
        enum type-ip {
            value 4;
            description "Type 0x0105";
        }
    }
    description "type definition for CML_OSPF_DOMAIN_TYPE_T";
}

typedef  CML_OSPF_ABR_TYPE_T {
    type enumeration {
        enum standard {
            value 1;
            description "Standard behavior (RFC2328)";
        }
        enum cisco {
            value 2;
            description " Cisco implementation (RFC3509)";
        }
        enum ibm {
            value 3;
            description "IBM implementation (RFC3509)";
        }
        enum shortcut {
            value 4;
            description "Shortcut ABR";
        }
    }
    description "type definition for CML_OSPF_ABR_TYPE_T";
}

typedef  CML_OSPF_AREA_AUTH_TYPE_T {
    type enumeration {
        enum simple {
            value 1;
            description "Use simple authentication";
        }
        enum message-digest {
            value 2;
            description "Use message-digest authentication";
        }
    }
    description "type definition for CML_OSPF_AREA_AUTH_TYPE_T";
}

typedef  CML_OSPF_AREA_SHORTCUT_TYPE_T {
    type enumeration {
        enum default {
            value 0;
            description "Set default shortcutting behavior";
        }
        enum enable {
            value 1;
            description "Enable shortcutting through the area";
        }
        enum disable {
            value 2;
            description "Disable shortcutting through the area";
        }
    }
    description "type definition for CML_OSPF_AREA_SHORTCUT_TYPE_T";
}

typedef  CML_OSPF_TRANSLATOR_ROLE_T {
    type enumeration {
        enum never {
            value 0;
            description "Do not translate";
        }
        enum always {
            value 1;
            description "Translate always";
        }
        enum candidate {
            value 2;
            description "Candidate for translator (default)";
        }
    }
    description "type definition for CML_OSPF_TRANSLATOR_ROLE_T";
}

typedef  CML_OSPF_NSSA_TRANSLATOR_ROLE_T {
    type enumeration {
        enum translate-never {
            value 0;
            description "Do not translate";
        }
        enum translate-always {
            value 1;
            description "Translate always";
        }
        enum translate-candidate {
            value 2;
            description "Candidate for translator (default)";
        }
    }
    description "type definition for CML_OSPF_NSSA_TRANSLATOR_ROLE_T";
}

typedef  CML_OSPF_STUB_T {
    type enumeration {
        enum stub {
            value 1;
            description "Configure OSPF area as stub";
        }
    }
    description "type definition for CML_OSPF_STUB_T";
}

typedef  CML_OSPF_NSSA_T {
    type enumeration {
        enum nssa {
            value 1;
            description "Configure OSPF area as nssa";
        }
    }
    description "type definition for CML_OSPF_NSSA_T";
}

typedef  CML_OSPF_AREA_FILTER_TYPE_T {
    type enumeration {
        enum access {
            value 0;
            description "Filter networks by access-list";
        }
        enum prefix {
            value 1;
            description "Filter networks by prefix-list";
        }
    }
    description "type definition for CML_OSPF_AREA_FILTER_TYPE_T";
}

typedef  CML_OSPF_AREA_FILTER_LIST_PREFIX_T {
    type enumeration {
        enum in {
            value 0;
            description "Filter networks sent to this area";
        }
        enum out {
            value 1;
            description "Filter networks sent from this area";
        }
    }
    description "type definition for CML_OSPF_AREA_FILTER_LIST_PREFIX_T";
}

typedef  CML_OSPF_VIRT_AUTH_KEY_T {
    type enumeration {
        enum null {
            value 0;
            description "unencrypted authentication key";
        }
        enum PASSWORD {
            value 1;
            description "Authentication key (8 chars)";
        }
    }
    description "type definition for CML_OSPF_VIRT_AUTH_KEY_T";
}

typedef  CML_OSPF_VIRT_AUTH_TYPE_T {
    type enumeration {
        enum null {
            value 0;
            description "Use no authentication";
        }
        enum simple {
            value 1;
            description "Use simple authentication";
        }
        enum message-digest {
            value 2;
            description "Use message-digest authentication";
        }
    }
    description "type definition for CML_OSPF_VIRT_AUTH_TYPE_T";
}

typedef  CML_OSPF_RESTART_METHOD_T {
    type enumeration {
        enum graceful {
            value 1;
            description "Graceful OSPF Restart (default)";
        }
        enum signaling {
            value 2;
            description "OSPF Restart Signaling";
        }
    }
    description "type definition for CML_OSPF_RESTART_METHOD_T";
}

typedef  CML_CSPF_TIE_BREAK_T {
    type enumeration {
        enum least-fill {
            value 1;
            description "least fill";
        }
        enum most-fill {
            value 2;
            description "Most fill";
        }
        enum random {
            value 3;
            description "Random";
        }
    }
    description "type definition for CML_CSPF_TIE_BREAK_T";
}

typedef  CML_OSPF_METRIC_TYPE_T {
    type enumeration {
        enum 1 {
            value 1;
            description "Set OSPF External Type 1 metrics";
        }
        enum 2 {
            value 2;
            description "Set OSPF External Type 2 metrics";
        }
    }
    description "type definition for CML_OSPF_METRIC_TYPE_T";
}

typedef  CML_OSPF_NETWORK_T {
    type enumeration {
        enum point-to-point {
            value 1;
            description "OSPF point-to-point network";
        }
        enum broadcast {
            value 2;
            description "OSPF broadcast multi-access network";
        }
        enum non-broadcast {
            value 3;
            description "OSPF NBMA network";
        }
        enum point-to-multipoint {
            value 4;
            description "OSPF point-to-multipoint network";
        }
        enum point-to-multipoint-non-broadcast {
            value 5;
            description "OSPF point-to-multipoint network,non-broadcast point-to-multipoint network";
        }
    }
    description "type definition for CML_OSPF_NETWORK_T";
}

typedef  CML_OSPF_AUTH_TYPE_T {
    type enumeration {
        enum null {
            value 0;
            description "Use no authentication";
        }
        enum simple {
            value 1;
            description "Use simple authentication";
        }
        enum message-digest {
            value 2;
            description "Use message-digest authentication";
        }
    }
    description "type definition for CML_OSPF_AUTH_TYPE_T";
}

typedef  CML_LDP_HELPER_MODE_T {
    type enumeration {
        enum disable {
            value 0;
            description "Disable graceful restart";
        }
        enum enable {
            value 1;
            description "Enable graceful restart";
        }
    }
    description "type definition for CML_LDP_HELPER_MODE_T";
}

typedef  CML_OSPF_FRR_TIE_BREAK_VAL_T {
    type enumeration {
        enum primary-path {
            value 20;
            description "Prefer backup path from ECMP set \n\t     *Default value is 20\n";
        }
        enum node-protecting {
            value 30;
            description "Prefer node protecting backup path \n\t     *Default value is 30\n";
        }
        enum interface-disjoint {
            value 60;
            description "Prefer link protecting backup path \n\t     *Default value is 60\n";
        }
        enum broadcast-interface-disjoint {
            value 70;
            description "Prefer broadcast link protecting backup path \n\t\t\t        *Default value is 70\n";
        }
        enum downstream-path {
            value 90;
            description "Prefer backup path from downstream \n\t     *Default value is 90\n";
        }
        enum secondary-path {
            value 255;
            description "Prefer non-ECMP backup path \n\t\t\t        *Default value is 255\n";
        }
    }
    description "type definition for CML_OSPF_FRR_TIE_BREAK_VAL_T";
}

typedef  CML_LDP_ADVERTISE_MODE_T {
    type enumeration {
        enum downstream-unsolicited {
            value 0;
            description "DU advertisement mode";
        }
        enum downstream-on-demand {
            value 1;
            description "DOD advertisement mode";
        }
    }
    description "type definition for CML_LDP_ADVERTISE_MODE_T";
}

typedef  CML_LDP_CONTROLMODE_T {
    type enumeration {
        enum independent {
            value 0;
            description "DU advertisement mode";
        }
        enum ordered {
            value 1;
            description "DOD advertisement mode";
        }
    }
    description "type definition for CML_LDP_CONTROLMODE_T";
}

typedef  CML_LDP_LABEL_T {
    type enumeration {
        enum liberal {
            value 0;
            description "Set liberal label retention mode";
        }
        enum conservative {
            value 1;
            description "Set conservative label retention mode";
        }
    }
    description "type definition for CML_LDP_LABEL_T";
}

typedef  CML_LDP_MERGE_CAPABLE_T {
    type enumeration {
        enum merge-capable {
            value 0;
            description "Set merge capable";
        }
        enum non-merge-capable {
            value 1;
            description "Set non merge capable";
        }
    }
    description "type definition for CML_LDP_MERGE_CAPABLE_T";
}

typedef  CML_PIM_MODE_TYPE_T {
    type enumeration {
        enum dense-mode {
            value 1;
            description "Enable PIM dense-mode operation";
        }
        enum sparse-mode {
            value 2;
            description "Enable PIM sparse-mode operation";
        }
        enum sparse-dense-mode {
            value 3;
            description "Enable PIM sparse-mode and dense-mode operations";
        }
    }
    description "type definition for CML_PIM_MODE_TYPE_T";
}

typedef  CML_PIM_EXTENDED_ACCESS_LIST_T {
    type union {
        type string {

        }
        type uint8 {
            range "1..99";

        }
        type uint16 {
            range "1300..1999";

        }
    }
    description "type definition for CML_PIM_EXTENDED_ACCESS_LIST_T";
}

typedef  CML_IFNAME_T {

    type string;
    description "type definition for CML_IFNAME_T";
}

typedef  CML_IPV4_IFNAME_T {
    type union {
        type inet:ipv4-address {

        }
        type CML_IFNAME_T {

        }
    }
    description "type definition for CML_IPV4_IFNAME_T";
}

typedef  CML_IPV6_IFNAME_T {
    type union {
        type inet:ipv6-address {

        }
        type CML_IFNAME_T {

        }
    }
    description "type definition for CML_IPV6_IFNAME_T";
}

typedef  CML_PIM_SSM_TYPE_T {
    type union {
        type string {

        }
        type uint8 {
            range "1..99";

        }
    }
    description "type definition for CML_PIM_SSM_TYPE_T";
}

typedef  CML_SSM_DEFAULT_T {
    type enumeration {
        enum default {
            value 0;
            description "Use 232/8 group range for SSM";
        }
    }
    description "type definition for CML_SSM_DEFAULT_T";
}

typedef  CML_SSM_RANGE_T {

    type string;
    description "type definition for CML_SSM_RANGE_T";
}

typedef  CML_PIM_SSM_ACL_TYPE_T {
    type union {
        type CML_SSM_RANGE_T {

        }
        type CML_SSM_DEFAULT_T {

        }
    }
    description "type definition for CML_PIM_SSM_ACL_TYPE_T";
}

typedef  CML_PIM_DEBUG_TYPE_T {
    type bits {
        bit events {
            position 0;
            description "PIM events";
        }
        bit packet-in {
            position 1;
            description "PIM packet,Incoming PIM packet";
        }
        bit packet-out {
            position 2;
            description "PIM packet,Outgoing PIM packet";
        }
        bit state {
            position 3;
            description "PIM state";
        }
        bit mfc {
            position 4;
            description "PIM MFC updates";
        }
        bit timer-hello-ht {
            position 5;
            description "PIM timers,Hello Timers,Hello timer";
        }
        bit timer-hello-nlt {
            position 6;
            description "PIM timers,Hello Timers,Neighbor Liveliness timer";
        }
        bit timer-hello-tht {
            position 7;
            description "PIM timers,Hello Timers,Triggered Hello timer";
        }
        bit timer-joinprune-jt {
            position 8;
            description "PIM timers,JoinPrune Timers,JoinPrune timer";
        }
        bit timer-joinprune-et {
            position 9;
            description "PIM timers,JoinPrune Timers,Expiry timer";
        }
        bit timer-joinprune-ppt {
            position 10;
            description "PIM timers,JoinPrune Timers,Prune Pending timer";
        }
        bit timer-joinprune-kat {
            position 11;
            description "PIM timers,JoinPrune Timers,Keep Alive timer";
        }
        bit timer-joinprune-ot {
            position 12;
            description "PIM timers,JoinPrune Timers,Override timer";
        }
        bit timer-assert {
            position 13;
            description "PIM timers,Assert Timers";
        }
        bit timer-register {
            position 14;
            description "PIM timers,Register Timers";
        }
        bit timer-bsr-bst {
            position 15;
            description "PIM timers,BSR Timers,Bootstrap timer";
        }
        bit timer-bsr-crp {
            position 16;
            description "PIM timers,BSR Timers,Candidate-RP timer";
        }
        bit mib {
            position 17;
            description "PIM mib";
        }
        bit nsm {
            position 18;
            description "NSM message";
        }
        bit nexthop {
            position 19;
            description "PIM nexthop";
        }
        bit mtrace {
            position 20;
            description "Mtrace messages";
        }
    }
    description "type definition for CML_PIM_DEBUG_TYPE_T";
}

typedef  CML_MRIB_IP_TYPE_T {
    type enumeration {
        enum ip {
            value 1;
            description "Internet Protocol(IP)";
        }
    }
    description "type definition for CML_MRIB_IP_TYPE_T";
}

typedef  CML_MRIB_IPV6_TYPE_T {
    type enumeration {
        enum ipv6 {
            value 0;
            description "Internet Protocol(IPv6)";
        }
    }
    description "type definition for CML_MRIB_IPV6_TYPE_T";
}

typedef  CML_MRIB4_DEBUG_T {
    type bits {
        bit event {
            position 0;
            description "None";
        }
        bit vif {
            position 1;
            description "None";
        }
        bit mrt {
            position 2;
            description "None";
        }
        bit stats {
            position 3;
            description "None";
        }
        bit fib-msg {
            position 4;
            description "None";
        }
        bit register-msg {
            position 5;
            description "None";
        }
        bit nsm-msg {
            position 6;
            description "None";
        }
        bit mrib-msg {
            position 7;
            description "None";
        }
        bit mtrace {
            position 8;
            description "None";
        }
        bit mtrace-detail {
            position 9;
            description "None";
        }
    }
    description "type definition for CML_MRIB4_DEBUG_T";
}

typedef  CML_MRIB6_DEBUG_T {
    type bits {
        bit event {
            position 0;
            description "None";
        }
        bit vif {
            position 1;
            description "None";
        }
        bit mrt {
            position 2;
            description "None";
        }
        bit stats {
            position 3;
            description "None";
        }
        bit fib-msg {
            position 4;
            description "None";
        }
        bit register-msg {
            position 5;
            description "None";
        }
        bit nsm-msg {
            position 6;
            description "None";
        }
        bit mrib-msg {
            position 7;
            description "None";
        }
        bit mtrace {
            position 8;
            description "None";
        }
        bit mtrace-detail {
            position 9;
            description "None";
        }
    }
    description "type definition for CML_MRIB6_DEBUG_T";
}

typedef  CML_IGMP_DEBUG_T {
    type bits {
        bit encode {
            position 0;
            description "None";
        }
        bit decode {
            position 1;
            description "None";
        }
        bit events {
            position 2;
            description "None";
        }
        bit fsm {
            position 3;
            description "None";
        }
        bit tib {
            position 4;
            description "None";
        }
    }
    description "type definition for CML_IGMP_DEBUG_T";
}

typedef  CML_MLD_DEBUG_T {
    type bits {
        bit encode {
            position 0;
            description "None";
        }
        bit decode {
            position 1;
            description "None";
        }
        bit events {
            position 2;
            description "None";
        }
        bit fsm {
            position 3;
            description "None";
        }
        bit tib {
            position 4;
            description "None";
        }
    }
    description "type definition for CML_MLD_DEBUG_T";
}

typedef  CML_BANDWIDTHCONSTRAINTMODE_T {
    type enumeration {
        enum MAM {
            value 0;
            description "MAM";
        }
        enum RSDL {
            value 1;
            description "RSDL";
        }
        enum MAR {
            value 2;
            description "MAR";
        }
    }
    description "type definition for CML_BANDWIDTHCONSTRAINTMODE_T";
}

typedef  CML_AFI_TYPE_T {
    type enumeration {
        enum ipv4 {
            value 1;
            description "Address family";
        }
        enum ipv6 {
            value 2;
            description "Address family";
        }
        enum vpnv4 {
            value 3;
            description "Address family";
        }
        enum vpnv6 {
            value 4;
            description "Address family";
        }
        enum rtfilter {
            value 5;
            description "Address family";
        }
        enum l2vpn {
            value 25;
            description "Address family";
        }
        enum link-state {
            value 16388;
            description "Address family";
        }
    }
    description "type definition for CML_AFI_TYPE_T";
}

typedef  CML_VRF_AFI_TYPE_T {
    type enumeration {
        enum ipv4 {
            value 1;
            description "Address family";
        }
        enum ipv6 {
            value 2;
            description "Address family";
        }
    }
    description "type definition for CML_VRF_AFI_TYPE_T";
}

typedef  CML_VRF_SAFI_TYPE_T {
    type enumeration {
        enum unicast {
            value 1;
            description "Address family modifier";
        }
    }
    description "type definition for CML_VRF_SAFI_TYPE_T";
}

typedef  CML_SAFI_TYPE_T {
    type enumeration {
        enum unicast {
            value 1;
            description "Address family modifier";
        }
        enum multicast {
            value 2;
            description "Address family modifier";
        }
        enum labeled-unicast {
            value 4;
            description "Address family modifier";
        }
        enum l2vpn-vpls {
            value 65;
            description "Address family modifier";
        }
        enum evpn {
            value 70;
            description "Address family modifier";
        }
        enum link-state {
            value 71;
            description "Address family modifier";
        }
        enum vpn-unicast {
            value 128;
            description "Address family modifier";
        }
        enum rtfilter-unicast {
            value 132;
            description "Address family modifier";
        }
    }
    description "type definition for CML_SAFI_TYPE_T";
}

typedef  CML_BGP_NETWORK_T {
    type union {
        type inet:ipv4-address {

        }
        type inet:ipv4-prefix {

        }
    }
    description "type definition for CML_BGP_NETWORK_T";
}

typedef  CML_BGP_IP_NETWORK_T {
    type union {
        type inet:ipv4-address {

        }
        type inet:ipv4-prefix {

        }
        type inet:ipv6-prefix {

        }
    }
    description "type definition for CML_BGP_IP_NETWORK_T";
}

typedef  CML_BGP_ROUTE_TARGET_T {
    type enumeration {
        enum rt {
            value 0;
            description "Specify route target";
        }
        enum soo {
            value 1;
            description "specify site of origin";
        }
    }
    description "type definition for CML_BGP_ROUTE_TARGET_T";
}

typedef  CML_BGP_CONFIG_T {
    type enumeration {
        enum standard {
            value 0;
            description "standard";
        }
        enum zebos {
            value 1;
            description "ZebOS";
        }
    }
    description "type definition for CML_BGP_CONFIG_T";
}

typedef  CML_AF_CONFIG_T {
    type enumeration {
        enum all-afs {
            value 0;
            description "configure for all vpn address-families";
        }
        enum vpnv4 {
            value 1;
            description "Virtual Private Network version 4(VPNv4)";
        }
        enum vpnv6 {
            value 2;
            description "Virtual Private Network version 6(VPNv6)";
        }
    }
    description "type definition for CML_AF_CONFIG_T";
}

typedef  CML_ALL_VRF_T {
    type enumeration {
        enum all-vrfs {
            value 1;
            description "all-vrfs";
        }
    }
    description "type definition for CML_ALL_VRF_T";
}

typedef  CML_BGP_VRF_NAME_T {

    type string;
    description "type definition for CML_BGP_VRF_NAME_T";
}

typedef  CML_BGP_VRF_TYPE_T {
    type union {
        type CML_BGP_VRF_NAME_T {

        }
        type CML_ALL_VRF_T {

        }
    }
    description "type definition for CML_BGP_VRF_TYPE_T";
}

typedef  CML_BGP_VRF_MODE_T {
    type enumeration {
        enum per-prefix {
            value 0;
            description "configure mode to be per-prefix";
        }
        enum per-vrf {
            value 1;
            description "configure mode to be per-vrf";
        }
    }
    description "type definition for CML_BGP_VRF_MODE_T";
}

typedef  CML_BGP_MED_TYPE_T {
    type bits {
        bit confed {
            position 0;
            description "Compare MED among confederation paths";
        }
        bit missing-as-worst {
            position 1;
            description "Treat missing MED as the least preferred one";
        }
        bit remove-recv-med {
            position 2;
            description "To remove rcvd MED attribute";
        }
        bit remove-send-med {
            position 3;
            description "To remove send MED attribute";
        }
    }
    description "type definition for CML_BGP_MED_TYPE_T";
}

typedef  CML_CLEAR_TYPE_T {
    type enumeration {
        enum clear_all {
            value 0;
            description "clear all";
        }
        enum clear_peer {
            value 1;
            description "clear peer";
        }
        enum clear_group {
            value 2;
            description "clear group";
        }
        enum clear_external {
            value 3;
            description "clear external";
        }
        enum clear_as {
            value 4;
            description "clear as";
        }
        enum clear_rfd {
            value 5;
            description "clear rfd";
        }
        enum clear_prefix {
            value 6;
            description "clear prefix";
        }
    }
    description "type definition for CML_CLEAR_TYPE_T";
}

typedef  CML_CLEAR_SOFT_T {
    type enumeration {
        enum soft_none {
            value 1;
            description "clear peer";
        }
        enum soft_out {
            value 2;
            description "clear group";
        }
        enum soft_in {
            value 3;
            description "clear external";
        }
        enum soft_both {
            value 4;
            description "clear as";
        }
        enum soft_in_orf_prefix {
            value 5;
            description "clear rfd";
        }
        enum table_map {
            value 6;
            description "clear prefix";
        }
        enum rfd_damp {
            value 7;
            description "clear prefix";
        }
        enum rfd_flap_stat {
            value 8;
            description "clear prefix";
        }
    }
    description "type definition for CML_CLEAR_SOFT_T";
}

typedef  CML_BGP_ORF_PREFIX_TYPE_T {
    type bits {
        bit receive {
            position 1;
            description "Capability to RECEIVE the ORF from this neighbor";
        }
        bit send {
            position 2;
            description "Capability to SEND the ORF to this neighbor";
        }
    }
    description "type definition for CML_BGP_ORF_PREFIX_TYPE_T";
}

typedef  CML_BGP_COMMUNITY_LIST_ACTION_T {
    type enumeration {
        enum deny {
            value 1;
            description "Specify community to reject";
        }
        enum permit {
            value 2;
            description "Specify community to accept";
        }
    }
    description "type definition for CML_BGP_COMMUNITY_LIST_ACTION_T";
}

typedef  CML_RMAP_PERMIT_T {
    type enumeration {
        enum permit {
            value 0;
            description "Route map permits set operations";
        }
        enum deny {
            value 1;
            description "Route map denies set operations";
        }
    }
    description "type definition for CML_RMAP_PERMIT_T";
}

typedef  BGP_ADDITIONAL_PATH_TYPE_T {
    type bits {
        bit receive {
            position 1;
            description "Receive additional paths from neighbors";
        }
        bit send {
            position 2;
            description "Send additional paths to neighbors";
        }
    }
    description "type definition for BGP_ADDITIONAL_PATH_TYPE_T";
}

typedef  BGP_PEER_ADDITIONAL_PATH_TYPE_T {
    type enumeration {
        enum receive {
            value 1;
            description "Receive additional paths from neighbors";
        }
        enum send {
            value 2;
            description "Send additional paths to neighbors";
        }
        enum send-receive {
            value 3;
            description "Send and Receive additional paths from neighbors";
        }
        enum disable {
            value 4;
            description "disable additional-paths";
        }
    }
    description "type definition for BGP_PEER_ADDITIONAL_PATH_TYPE_T";
}

typedef  BGP_ADV_RCV_TYPE_T {
    type enumeration {
        enum advertise {
            value 1;
            description "advertised";
        }
        enum receive {
            value 2;
            description "received";
        }
        enum advertise-receive {
            value 3;
            description "advertised and received both";
        }
    }
    description "type definition for BGP_ADV_RCV_TYPE_T";
}

typedef  CML_BGP_SEND_COMMU_TYPE_T {
    type bits {
        bit standard {
            position 1;
            description "Send Standard Community attributes";
        }
        bit extended {
            position 2;
            description "Send Extended Community attributes";
        }
    }
    description "type definition for CML_BGP_SEND_COMMU_TYPE_T";
}

typedef  CML_BGP_UPDATE_DEBUG_TYPE_T {
    type bits {
        bit in {
            position 8;
            description "Inbound updates";
        }
        bit out {
            position 9;
            description "Outbound updates";
        }
    }
    description "type definition for CML_BGP_UPDATE_DEBUG_TYPE_T";
}

typedef  CML_ATTRIBUTE_UNCHANGED_TYPE_T {
    type bits {
        bit as-path {
            position 1;
            description "As-path attribute";
        }
        bit next-hop {
            position 2;
            description "Next-hop attribute";
        }
        bit med {
            position 3;
            description "Med attribute";
        }
    }
    description "type definition for CML_ATTRIBUTE_UNCHANGED_TYPE_T";
}

typedef  CML_BGP_DEBUG_TYPE_T {
    type bits {
        bit nht {
            position 1;
            description "NHT message";
        }
        bit nsm {
            position 2;
            description "NSM message";
        }
        bit fsm {
            position 3;
            description "Finite state machine";
        }
        bit events {
            position 4;
            description "BGP events";
        }
        bit filters {
            position 5;
            description "BGP filter";
        }
        bit keepalives {
            position 6;
            description "BGP keepalives";
        }
        bit updates {
            position 7;
            description "BGP updates";
        }
        bit dampening {
            position 10;
            description "BGP Dampening";
        }
        bit bfd {
            position 11;
            description "Bidirectional Forwarding Detection (BFD)";
        }
        bit mpls {
            position 12;
            description "BGP mpls";
        }
        bit vpls {
            position 13;
            description "BGP vpls";
        }
        bit link-state {
            position 14;
            description "BGP Link State";
        }
    }
    description "type definition for CML_BGP_DEBUG_TYPE_T";
}

typedef  CML_BGP_DISTRIBUTE_LIST_ACTION_T {
    type enumeration {
        enum in {
            value 0;
            description "Filter incoming updates";
        }
        enum out {
            value 1;
            description "Filter outgoing updates";
        }
    }
    description "type definition for CML_BGP_DISTRIBUTE_LIST_ACTION_T";
}

typedef  CML_BGP_REDISTRIBUTE_TYPE_T {
    type enumeration {
        enum kernel {
            value 1;
            description "Kernel routes";
        }
        enum connected {
            value 2;
            description "Connected";
        }
        enum static {
            value 3;
            description "Static routes";
        }
        enum rip {
            value 4;
            description "Routing Information Protocol(RIP)";
        }
        enum ospf {
            value 5;
            description "Kernel routes";
        }
        enum isis {
            value 6;
            description "ISO IS-IS";
        }
    }
    description "type definition for CML_BGP_REDISTRIBUTE_TYPE_T";
}

typedef  CML_BGP_COMMUNITY_LIST_ENTRY_T {
    type enumeration {
        enum standard {
            value 0;
            description "Add a standard community-list entry";
        }
        enum expanded {
            value 1;
            description "Add an expanded community-list entry";
        }
        enum default {
            value 2;
            description "default community-list entry";
        }
    }
    description "type definition for CML_BGP_COMMUNITY_LIST_ENTRY_T";
}

typedef  CML_BGP_AGGREGATE_ADDR_TYPE_T {
    type enumeration {
        enum summary-only {
            value 1;
            description "Add a standard community-list entry";
        }
        enum as-set {
            value 2;
            description "Add an expanded community-list entry";
        }
    }
    description "type definition for CML_BGP_AGGREGATE_ADDR_TYPE_T";
}

typedef  CML_BGP_PEER_STATUS_T {
    type enumeration {
        enum idle {
            value 1;
            description "Idle";
        }
        enum connect {
            value 2;
            description "Connect";
        }
        enum active {
            value 3;
            description "Active";
        }
        enum opensent {
            value 4;
            description "Opensent";
        }
        enum openconfirm {
            value 5;
            description "Openconfirm";
        }
        enum established {
            value 6;
            description "Established";
        }
    }
    description "type definition for CML_BGP_PEER_STATUS_T";
}

typedef  CML_PEERFLAG_SHUTDOWN_T {
    type enumeration {
        enum idle {
            value 1;
            description "Idle";
        }
        enum connect {
            value 2;
            description "Connect";
        }
        enum active {
            value 3;
            description "Active";
        }
        enum opensent {
            value 4;
            description "Opensent";
        }
        enum openconfirm {
            value 5;
            description "Openconfirm";
        }
        enum established {
            value 6;
            description "Established";
        }
        enum idle-dmin {
            value 7;
            description "Idle Admin";
        }
        enum idle-pfxct {
            value 8;
            description "Idle PfxCt";
        }
        enum idle-g-shut {
            value 9;
            description "Idle G-shut";
        }
    }
    description "type definition for CML_PEERFLAG_SHUTDOWN_T";
}

typedef  CML_BGP_PREFIX_ENTRY_TYPE_T {
    type enumeration {
        enum no_match {
            value 1;
            description "No match";
        }
        enum deny {
            value 2;
            description "Deny";
        }
        enum permit {
            value 3;
            description "Permit";
        }
    }
    description "type definition for CML_BGP_PREFIX_ENTRY_TYPE_T";
}

typedef  CML_BGP_RI_TYPE_T {
    type enumeration {
        enum internal {
            value 1;
            description "internal";
        }
        enum confed-external {
            value 2;
            description "confed-external";
        }
        enum external {
            value 3;
            description "external";
        }
        enum aggregated-and-local {
            value 4;
            description "aggregated and local";
        }
        enum sourced {
            value 5;
            description "sourced";
        }
        enum sourced-and-local {
            value 6;
            description "sourced and local";
        }
    }
    description "type definition for CML_BGP_RI_TYPE_T";
}

typedef  CML_BGP_ORIGIN_T {
    type enumeration {
        enum igp {
            value 0;
            description "IGP";
        }
        enum egp {
            value 1;
            description "EGP";
        }
        enum incomplete {
            value 2;
            description "incomplete";
        }
    }
    description "type definition for CML_BGP_ORIGIN_T";
}

typedef  CML_BGP_LINK_TYPE_T {
    type enumeration {
        enum internal {
            value 0;
            description "internal";
        }
        enum external {
            value 1;
            description "external";
        }
    }
    description "type definition for CML_BGP_LINK_TYPE_T";
}

typedef  CML_BGP_CONNECTION_TYPE_T {
    type enumeration {
        enum shared {
            value 0;
            description "shared network";
        }
        enum non_shared {
            value 1;
            description "non shared network";
        }
    }
    description "type definition for CML_BGP_CONNECTION_TYPE_T";
}

typedef  CML_CLUSTER_ID_T {
    type union {
        type inet:ipv4-address {

        }
        type uint32 {
            range "1..4294967295";

        }
    }
    description "type definition for CML_CLUSTER_ID_T";
}

typedef  CML_MPLS_VLAN_ACTIONTYPE_T {
    type enumeration {
        enum pop {
            value 0;
            description "Pop the outer vid";
        }
    }
    description "type definition for CML_MPLS_VLAN_ACTIONTYPE_T";
}

typedef  CML_MPLS_MODULE_T {
    type enumeration {
        enum rsvp {
            value 0;
            description "Specify label range value for rsvp";
        }
        enum ldp {
            value 1;
            description "Specify label range value for ldp";
        }
        enum bgp {
            value 4;
            description "Specify label range value for bgp";
        }
    }
    description "type definition for CML_MPLS_MODULE_T";
}

typedef  CML_MPLS_ADMN_STATUS_T {
    type enumeration {
        enum up {
            value 1;
            description "None";
        }
        enum down {
            value 2;
            description "None";
        }
        enum testing {
            value 3;
            description "None";
        }
    }
    description "type definition for CML_MPLS_ADMN_STATUS_T";
}

typedef  CML_MPLS_OPR_STATUS_T {
    type enumeration {
        enum up {
            value 1;
            description "None";
        }
        enum down {
            value 2;
            description "None";
        }
        enum testing {
            value 3;
            description "None";
        }
        enum dormant {
            value 4;
            description "None";
        }
        enum not-persent {
            value 5;
            description "None";
        }
        enum ll-down {
            value 6;
            description "None";
        }
    }
    description "type definition for CML_MPLS_OPR_STATUS_T";
}

typedef  CML_MPLS_ROW_STATUS_T {
    type enumeration {
        enum active {
            value 1;
            description "None";
        }
        enum not-in-severice {
            value 2;
            description "None";
        }
        enum not-ready {
            value 3;
            description "None";
        }
        enum create-go {
            value 4;
            description "None";
        }
        enum create-wait {
            value 5;
            description "None";
        }
        enum destroy {
            value 6;
            description "None";
        }
    }
    description "type definition for CML_MPLS_ROW_STATUS_T";
}

typedef  CML_MPLS_BFD_FLAG_T {
    type enumeration {
        enum configured {
            value 0;
            description "None";
        }
        enum enabled {
            value 1;
            description "None";
        }
        enum disable {
            value 2;
            description "None";
        }
    }
    description "type definition for CML_MPLS_BFD_FLAG_T";
}

typedef  CML_NSM_MPLS_TPID_T {
    type enumeration {
        enum 88a8 {
            value 34984;
            description "Set tpid value as 88a8";
        }
        enum 9100 {
            value 37120;
            description "Set tpid value as 9100";
        }
    }
    description "type definition for CML_NSM_MPLS_TPID_T";
}

typedef  CML_NSM_SVC_TPID_T {
    type enumeration {
        enum dot1.q {
            value 33024;
            description "Set tpid value as 0x8100";
        }
        enum dot1.ad {
            value 34984;
            description "Set tpid value as 0x88a8";
        }
        enum 0x9100 {
            value 37120;
            description "Set tpid value as 0x9100";
        }
    }
    description "type definition for CML_NSM_SVC_TPID_T";
}

typedef  CML_NSM_MPLS_ADMIN_STATUS_T {
    type enumeration {
        enum down {
            value 0;
            description "Set the admin role as Down";
        }
        enum up {
            value 1;
            description "Set the admin role as UP";
        }
    }
    description "type definition for CML_NSM_MPLS_ADMIN_STATUS_T";
}

typedef  CML_NSM_MPLS_VPLS_LEARNING_T {
    type enumeration {
        enum reset {
            value 0;
            description "reset learning to global config";
        }
        enum enable {
            value 1;
            description "Enable MAC learning";
        }
        enum disable {
            value 2;
            description "Disable MAC learning";
        }
    }
    description "type definition for CML_NSM_MPLS_VPLS_LEARNING_T";
}

typedef  CML_NSM_MPLS_VCMODE_T {
    type enumeration {
        enum standby {
            value 2;
            description "VC runtime Standby mode";
        }
        enum revertive {
            value 4;
            description "VC redundancy revertive mode";
        }
    }
    description "type definition for CML_NSM_MPLS_VCMODE_T";
}

typedef  CML_NSM_MPLS_VCLINKMODE_T {
    type enumeration {
        enum primary {
            value 0;
            description "Primary Link";
        }
        enum secondary {
            value 16;
            description "Secondary Link - Will not be activated unless primary fails";
        }
    }
    description "type definition for CML_NSM_MPLS_VCLINKMODE_T";
}

typedef  CML_NSM_MPLS_IF_VCTYPE_T {
    type enumeration {
        enum hdlc {
            value 6;
            description "Hdlc";
        }
        enum ppp {
            value 7;
            description "Point-to-Point";
        }
        enum tdm-E1 {
            value 17;
            description "TDM - E1 line";
        }
        enum tdm-T1 {
            value 18;
            description "TDM - T1 line";
        }
        enum tdm-E3 {
            value 19;
            description "TDM - E3 line";
        }
        enum tdm-T3 {
            value 20;
            description "TDM - T3 line";
        }
    }
    description "type definition for CML_NSM_MPLS_IF_VCTYPE_T";
}

typedef  CML_NSM_MPLS_IF_ETHER_VCTYPE_T {
    type enumeration {
        enum ethernet {
            value 5;
            description "Ethernet";
        }
    }
    description "type definition for CML_NSM_MPLS_IF_ETHER_VCTYPE_T";
}

typedef  CML_NSM_MPLS_IF_VLAN_VCTYPE_T {
    type enumeration {
        enum vlan {
            value 4;
            description "VLAN";
        }
    }
    description "type definition for CML_NSM_MPLS_IF_VLAN_VCTYPE_T";
}

typedef  CML_NSM_MPLS_BFD_T {
    type enumeration {
        enum ldp {
            value 0;
            description "LDP type LSP";
        }
        enum static {
            value 2;
            description "Static type LSP";
        }
    }
    description "type definition for CML_NSM_MPLS_BFD_T";
}

typedef  CML_RSVP_TE_SRLG_DISJOINT_TYPE_T {
    type enumeration {
        enum forced {
            value 1;
            description "Forced";
        }
        enum preferred {
            value 2;
            description "Preferred";
        }
    }
    description "type definition for CML_RSVP_TE_SRLG_DISJOINT_TYPE_T";
}

typedef  CML_BFD_RSVP_LSP_T {
    type enumeration {
        enum rsvp {
            value 1;
            description "RSVP type LSP";
        }
    }
    description "type definition for CML_BFD_RSVP_LSP_T";
}

typedef  CML_NSM_MPLS_BFD_TYPE_T {
    type enumeration {
        enum ldp {
            value 0;
            description "LDP type LSP";
        }
        enum rsvp {
            value 1;
            description "RSVP type LSP";
        }
        enum static {
            value 2;
            description "Static type LSP";
        }
    }
    description "type definition for CML_NSM_MPLS_BFD_TYPE_T";
}

typedef  CML_NSM_MPLS_VCCP_STATE_T {
    type enumeration {
        enum start {
            value 1;
            description "start bfd-vccv";
        }
        enum stop {
            value 2;
            description "stop bfd-vccv";
        }
    }
    description "type definition for CML_NSM_MPLS_VCCP_STATE_T";
}

typedef  CML_OSPF_ROW_STATUS {
    type enumeration {
        enum row-status-active {
            value 1;
            description "Active Row status";
        }
        enum row-status-notinservice {
            value 2;
            description "Row status Not in Service";
        }
        enum row-status-notready {
            value 3;
            description "Row status Not Ready";
        }
        enum row-status-createandgo {
            value 4;
            description "Row status Create and Go";
        }
        enum row-status-createandwait {
            value 5;
            description "Row status Create and Wait";
        }
    }
    description "type definition for CML_OSPF_ROW_STATUS";
}

typedef  CML_NSM_VPLS_TYPE_T {
    type enumeration {
        enum vlan {
            value 4;
            description "VLAN";
        }
        enum ethernet {
            value 5;
            description "Ethernet";
        }
    }
    description "type definition for CML_NSM_VPLS_TYPE_T";
}

typedef  NSM_VPLS_ETHER_ACTION_T {
    type enumeration {
        enum no-op {
            value 1;
            description "Set action as add";
        }
        enum add {
            value 2;
            description "Set action as no operation";
        }
    }
    description "type definition for NSM_VPLS_ETHER_ACTION_T";
}

typedef  NSM_VPLS_VLAN_ACTION_T {
    type enumeration {
        enum no-op {
            value 1;
            description "Set action as add";
        }
        enum remove {
            value 3;
            description "Set action as remove";
        }
        enum replace {
            value 4;
            description "Set action as replace";
        }
    }
    description "type definition for NSM_VPLS_VLAN_ACTION_T";
}

typedef  CML_NSM_VPLS_VC_SPOKE_TYPE_T {
    type enumeration {
        enum vlan {
            value 4;
            description "VC Spoke type:VLAN";
        }
        enum ethernet {
            value 5;
            description "VC Spoke type:Ethernet";
        }
    }
    description "type definition for CML_NSM_VPLS_VC_SPOKE_TYPE_T";
}

typedef  CML_NSM_VPLS_PEER_TUNNEL_DIR_T {
    type enumeration {
        enum forward {
            value 0;
            description "Tunnel Direction - Forward tunnel identifier - Default Value";
        }
        enum reverse {
            value 1;
            description "Tunnel Direction - Reverse tunnel identifier";
        }
    }
    description "type definition for CML_NSM_VPLS_PEER_TUNNEL_DIR_T";
}

typedef  CML_NSM_VPLS_PEER_TYPE_T {
    type enumeration {
        enum manual {
            value 1;
            description "No signaling is used to set-up the Virtual Circuit";
        }
    }
    description "type definition for CML_NSM_VPLS_PEER_TYPE_T";
}

typedef  CML_NSM_VPLS_FTN_ENTRY_T {
    type enumeration {
        enum secondary {
            value 0;
            description "Secondary LSP";
        }
        enum primary {
            value 1;
            description "Primary LSP (default)";
        }
    }
    description "type definition for CML_NSM_VPLS_FTN_ENTRY_T";
}

typedef  CML_VPLS_REDUNDANCY_ROLE_T {
    type enumeration {
        enum primary {
            value 0;
            description "Set role as primary";
        }
        enum secondary {
            value 1;
            description "Set role as secondary";
        }
    }
    description "type definition for CML_VPLS_REDUNDANCY_ROLE_T";
}

typedef  CML_NSM_VPLS_OPCODE_T {
    type enumeration {
        enum swap {
            value 3;
            description "Swap incoming label";
        }
    }
    description "type definition for CML_NSM_VPLS_OPCODE_T";
}

typedef  CML_NSM_MPLS_IPV6OPCODE_T {
    type enumeration {
        enum swap {
            value 3;
            description "Swap incoming label";
        }
    }
    description "type definition for CML_NSM_MPLS_IPV6OPCODE_T";
}

typedef  CML_NSM_VPLS_POPOPCODE_T {
    type enumeration {
        enum pop {
            value 2;
            description "pop incoming label";
        }
    }
    description "type definition for CML_NSM_VPLS_POPOPCODE_T";
}

typedef  CML_VPLS_VC_STYLE1_T {
    type enumeration {
        enum peer {
            value 2;
            description "Mesh Peer";
        }
    }
    description "type definition for CML_VPLS_VC_STYLE1_T";
}

typedef  CML_VPLS_VC_STYLE2_T {
    type enumeration {
        enum spoke-vc {
            value 3;
            description "Spoke Virtual Circuit";
        }
    }
    description "type definition for CML_VPLS_VC_STYLE2_T";
}

typedef  CML_L2VPN_PROTOCOL_T {
    type enumeration {
        enum ldp-autodiscovery-bgp {
            value 8;
            description "Specify the protocol as LDP for MPLS Layer-2 Virtual Circuit,Specify the protocol with autodiscovery-bgp for MPLS Layer-2 Virtual Circuit";
        }
    }
    description "type definition for CML_L2VPN_PROTOCOL_T";
}

typedef  CML_L2VPN_VC_TYPE_T {
    type enumeration {
        enum ethernet {
            value 5;
            description "Ethernet";
        }
        enum hdlc {
            value 6;
            description "Hdlc";
        }
        enum ppp {
            value 7;
            description "Point-to-Point";
        }
        enum tdm-E1 {
            value 17;
            description "TDM - E1 line";
        }
        enum tdm-T1 {
            value 18;
            description "TDM - T1 line";
        }
        enum tdm-E3 {
            value 19;
            description "TDM - E3 line";
        }
        enum tdm-T3 {
            value 20;
            description "TDM - T3 line";
        }
    }
    description "type definition for CML_L2VPN_VC_TYPE_T";
}

typedef  CML_RSVP_PATH_STATUS_T {
    type enumeration {
        enum loose {
            value 0;
            description "Make this node loose";
        }
        enum strict {
            value 1;
            description "Make this node strict";
        }
    }
    description "type definition for CML_RSVP_PATH_STATUS_T";
}

typedef  CML_RSVP_PROT_STATUS_T {
    type enumeration {
        enum one-to-one {
            value 1;
            description "One-to-One protection";
        }
        enum facility {
            value 2;
            description "Facility Backup (Bypass) protection";
        }
    }
    description "type definition for CML_RSVP_PROT_STATUS_T";
}

typedef  CML_RSVP_IP_ADDR_T {
    type union {
        type inet:ipv4-address {

        }
        type inet:ipv6-address {

        }
    }
    description "type definition for CML_RSVP_IP_ADDR_T";
}

typedef  CML_RSVP_FRR_ADMIN_TYPE_T {
    type enumeration {
        enum exclude-any {
            value 0;
            description "Exclude-any attribute";
        }
        enum include-any {
            value 1;
            description "Include-any attribute";
        }
    }
    description "type definition for CML_RSVP_FRR_ADMIN_TYPE_T";
}

typedef  CML_RSVP_TRAFFIC_TYPE_T {
    type enumeration {
        enum controlled-load {
            value 1;
            description "Controlled load traffic";
        }
        enum guaranteed {
            value 2;
            description "Guaranteed traffic";
        }
    }
    description "type definition for CML_RSVP_TRAFFIC_TYPE_T";
}

typedef  CML_RSVP_UPDATE_TYPE_T {
    type enumeration {
        enum break-before-make {
            value 1;
            description "Break Before Make";
        }
        enum make-before-break {
            value 2;
            description "Make Before Break";
        }
    }
    description "type definition for CML_RSVP_UPDATE_TYPE_T";
}

typedef  CML_RSVP_BACKUP_BW_TYPE {
    type enumeration {
        enum best-effort {
            value 0;
            description "best-effort backup bandwidth";
        }
        enum dedicated {
            value 1;
            description "dedicated backup bandwidth";
        }
    }
    description "type definition for CML_RSVP_BACKUP_BW_TYPE";
}

typedef  CML_RSVP_CAPABILITY_TYPE_T {
    type enumeration {
        enum psc-1 {
            value 1;
            description "Packet Switch Capable-1";
        }
        enum psc-2 {
            value 2;
            description "Packet Switch Capable-2";
        }
        enum psc-3 {
            value 4;
            description "Packet Switch Capable-3";
        }
        enum psc-4 {
            value 8;
            description "Packet Switch Capable-4";
        }
    }
    description "type definition for CML_RSVP_CAPABILITY_TYPE_T";
}

typedef  CML_RSVP_DIRECTION_TYPE_T {
    type enumeration {
        enum unidirectional {
            value 0;
            description "Unidirectional";
        }
        enum bidirectional {
            value 1;
            description "Bidirectional";
        }
    }
    description "type definition for CML_RSVP_DIRECTION_TYPE_T";
}

typedef  CML_RSVP_GPID_TYPE_T {
    type enumeration {
        enum ethernet {
            value 33;
            description "Ethernet gpid type";
        }
        enum ipv4 {
            value 2048;
            description "IPv4 gpid type";
        }
    }
    description "type definition for CML_RSVP_GPID_TYPE_T";
}

typedef  CML_RSVP_EXPLICIT_FWD_DIR_T {
    type enumeration {
        enum forward {
            value 1;
            description "Forward LSP Direction - Ingress to Egress (Downstream)";
        }
        enum packet-forward {
            value 3;
            description "Default label-type is packet, Forward LSP Direction - Ingress to Egress (Downstream)";
        }
    }
    description "type definition for CML_RSVP_EXPLICIT_FWD_DIR_T";
}

typedef  CML_RSVP_EXPLICIT_REV_DIR_T {
    type enumeration {
        enum reverse {
            value 2;
            description "Reverse LSP Direction - Egress to Ingress (Upstream)";
        }
        enum packet-reverse {
            value 4;
            description "Default label-type is packet,Reverse LSP Direction - Egress to Ingress (Upstream)";
        }
    }
    description "type definition for CML_RSVP_EXPLICIT_REV_DIR_T";
}

typedef  CML_RSVP_FILTER_TYPE_T {
    type enumeration {
        enum default {
            value 0;
            description "default";
        }
        enum fixed {
            value 1;
            description "Use a Fixed Filter for this LSP";
        }
        enum shared-explicit {
            value 2;
            description "Use a Shared Explicit Filter for this LSP";
        }
    }
    description "type definition for CML_RSVP_FILTER_TYPE_T";
}

typedef  CML_RSVP_PROTECTION_TYPE_T {
    type enumeration {
        enum extra-traffic {
            value 1;
            description "Extra-traffic";
        }
        enum unprotected {
            value 2;
            description "Unprotected";
        }
        enum shared {
            value 4;
            description "Shared";
        }
        enum dedicated-one-to-one {
            value 8;
            description "Dedicated 1:1";
        }
        enum dedicated-one-plus-one {
            value 16;
            description "Dedicated 1+1";
        }
        enum enhanced {
            value 32;
            description "Enhanced";
        }
    }
    description "type definition for CML_RSVP_PROTECTION_TYPE_T";
}

typedef  CML_RSVP_EXCLUDE_ADDR_TYPE_T {
    type enumeration {
        enum link {
            value 1;
            description "Enables a Link Protection - NHOP";
        }
        enum node {
            value 2;
            description "Enables a Node Protection - NNHOP";
        }
    }
    description "type definition for CML_RSVP_EXCLUDE_ADDR_TYPE_T";
}

typedef  CML_IS_TYPE_T {
    type enumeration {
        enum level-1 {
            value 1;
            description "Act as a station router only";
        }
        enum level-2-only {
            value 2;
            description "Act as an area router only";
        }
        enum level-1-2 {
            value 3;
            description "Act as both a station router and an area router";
        }
    }
    description "type definition for CML_IS_TYPE_T";
}

typedef  CML_IS_TYPE2_T {
    type enumeration {
        enum level-1 {
            value 1;
            description "Act as a station router only";
        }
        enum level-2 {
            value 2;
            description "Act as an area router only";
        }
        enum level-1-2 {
            value 3;
            description "Act as both a station router and an area router";
        }
    }
    description "type definition for CML_IS_TYPE2_T";
}

typedef  CML_ISIS_SYSTEMID_T {

    type string{
    pattern "[0-9a-fA-F]{4}\\.[0-9a-f]{4}\\.[0-9a-f]{4}";
    }
    description "type definition for CML_ISIS_SYSTEMID_T";
}

typedef  CML_ISIS_LEVEL_T {
    type enumeration {
        enum level-1 {
            value 1;
            description "Set interval for level 1 only";
        }
        enum level-2 {
            value 2;
            description "Set interval for level 2 only";
        }
        enum level-1-2 {
            value 3;
            description "Set interval for both level 1 and level 2";
        }
    }
    description "type definition for CML_ISIS_LEVEL_T";
}

typedef  CML_ISIS_LEVEL2_T {
    type enumeration {
        enum level-1 {
            value 1;
            description "Level-1";
        }
        enum level-2 {
            value 2;
            description "Level-2";
        }
    }
    description "type definition for CML_ISIS_LEVEL2_T";
}

typedef  CML_ISIS_LEVEL_PROTO_T {
    type enumeration {
        enum ipv4 {
            value 1;
            description "IPv4 address family";
        }
        enum ipv6 {
            value 2;
            description "IPv6 address family";
        }
    }
    description "type definition for CML_ISIS_LEVEL_PROTO_T";
}

typedef  CML_ISIS_LFA_LEVEL_PROTO_T {
    type enumeration {
        enum ipv4 {
            value 1;
            description "IPv4 address family";
        }
    }
    description "type definition for CML_ISIS_LFA_LEVEL_PROTO_T";
}

typedef  CML_ISIS_FRR_ENUM_T {
    type enumeration {
        enum all {
            value 1;
            description "On all prefixes";
        }
    }
    description "type definition for CML_ISIS_FRR_ENUM_T";
}

typedef  CML_ISIS_FRR_TIE_BREAK_VAL_T {
    type enumeration {
        enum primary-path {
            value 1;
            description "Primary Path";
        }
        enum node-protecting {
            value 2;
            description "broadcast-interface-disjoint";
        }
        enum interface-disjoint {
            value 3;
            description "Link Protecting";
        }
        enum broadcast-interface-disjoint {
            value 4;
            description "Broadcast Link Protecting";
        }
        enum downstream-path {
            value 5;
            description "Downstream path";
        }
        enum secondary-path {
            value 6;
            description "Secondary path";
        }
    }
    description "type definition for CML_ISIS_FRR_TIE_BREAK_VAL_T";
}

typedef  CML_ISIS_IFLEVEL_T {
    type enumeration {
        enum level-1 {
            value 1;
            description "Act as a station router only";
        }
        enum level-2 {
            value 2;
            description "Act as an area router only";
        }
        enum p2p {
            value 3;
            description "P2p index";
        }
    }
    description "type definition for CML_ISIS_IFLEVEL_T";
}

typedef  CML_ISIS_NBR_ADJ_T {
    type enumeration {
        enum Suppress {
            value 1;
            description "show Adjacency Suppress";
        }
        enum Advertise {
            value 2;
            description "show Adjacency Advertisement";
        }
    }
    description "type definition for CML_ISIS_NBR_ADJ_T";
}

typedef  CML_ISIS_ORIGIN_TYPE_T {
    type enumeration {
        enum originate {
            value 4;
            description "Distribute a default route";
        }
        enum originate-level-1 {
            value 5;
            description "Distribute a default route,Distribute in level-1";
        }
        enum originate-always {
            value 32;
            description "Distribute a default route,Always advertise default route";
        }
    }
    description "type definition for CML_ISIS_ORIGIN_TYPE_T";
}

typedef  CML_ISIS_NETWORK_T {
    type enumeration {
        enum broadcast {
            value 1;
            description "Specify IS-IS broadcast multi-access network";
        }
        enum point-to-point {
            value 2;
            description "Specify IS-IS point-to-point network";
        }
    }
    description "type definition for CML_ISIS_NETWORK_T";
}

typedef  CML_ISIS_DYNAMIC_HOSTANME_T {
    type enumeration {
        enum dynamic-hostname {
            value 0;
            description "Enable dynamic hostname";
        }
        enum area-tag {
            value 1;
            description "Use area-tag as hostname";
        }
    }
    description "type definition for CML_ISIS_DYNAMIC_HOSTANME_T";
}

typedef  CML_ISIS_STATE_T {
    type enumeration {
        enum Down {
            value 0;
            description "LAN Neighbor Down";
        }
        enum Init {
            value 1;
            description "LAN Neighbor Init";
        }
        enum Up {
            value 2;
            description "LAN Neighbor Up";
        }
    }
    description "type definition for CML_ISIS_STATE_T";
}

typedef  CML_METRIC_STYLE_T {
    type enumeration {
        enum narrow {
            value 1;
            description "Use old style of TLVs with narrow metric";
        }
        enum wide {
            value 2;
            description "Use new style of TLVs to carry wider metric";
        }
        enum transition {
            value 3;
            description "Send and accept both styles of TLVs during transition";
        }
        enum narrow-transition {
            value 4;
            description "Use old style of TLVs with narrow metric,Send and accept both styles of TLVs during transition";
        }
        enum wide-transition {
            value 5;
            description "Use old style of TLVs with wide metric, Send and accept both styles of TLVs during transition";
        }
    }
    description "type definition for CML_METRIC_STYLE_T";
}

typedef  CML_TRANSITION_METRIC_STYLE_T {
    type enumeration {
        enum narrow {
            value 1;
            description "Use old style of TLVs with narrow metric";
        }
        enum wide {
            value 2;
            description "Use new style of TLVs to carry wider metric";
        }
    }
    description "type definition for CML_TRANSITION_METRIC_STYLE_T";
}

typedef  CML_ISIS_AUTH_MODE_T {
    type enumeration {
        enum md5 {
            value 1;
            description "Keyed message digest";
        }
        enum text {
            value 2;
            description "Text mode";
        }
    }
    description "type definition for CML_ISIS_AUTH_MODE_T";
}

typedef  CML_ISIS_ROUTE_T {
    type enumeration {
        enum redistribution {
            value 0;
            description "Clear ISIS IP local redistribution routes";
        }
        enum all {
            value 1;
            description "all of the IS-IS routing table";
        }
    }
    description "type definition for CML_ISIS_ROUTE_T";
}

typedef  CML_ISIS_SNP_T {
    type enumeration {
        enum send-only {
            value 1;
            description "Keyed message digest";
        }
        enum validate {
            value 2;
            description "Text mode";
        }
    }
    description "type definition for CML_ISIS_SNP_T";
}

typedef  CML_ISIS_LIFETIME_T {
    type enumeration {
        enum accept-lifetime {
            value 1;
            description "Set accept lifetime of the key";
        }
        enum send-lifetime {
            value 2;
            description "Set send lifetime of the key";
        }
    }
    description "type definition for CML_ISIS_LIFETIME_T";
}

typedef  CML_ISIS_REDISTRIBUTE_T {
    type enumeration {
        enum kernel {
            value 1;
            description "Kernel routes";
        }
        enum connected {
            value 2;
            description "Connected";
        }
        enum static {
            value 3;
            description "Static routes";
        }
        enum rip {
            value 4;
            description "Routing Information Protocol(RIP)";
        }
        enum ospf {
            value 5;
            description "Open Shortest Path First (OSPF)";
        }
        enum bgp {
            value 6;
            description "Border Gateway Protocol (BGP)";
        }
    }
    description "type definition for CML_ISIS_REDISTRIBUTE_T";
}

typedef  CML_ISIS_DEBUG_T {
    type bits {
        bit ifsm {
            position 0;
            description "IS-IS Interface Finite State Machine";
        }
        bit nfsm {
            position 1;
            description "IS-IS Neighbor Finite State Machine";
        }
        bit pdu {
            position 2;
            description "IS-IS Protocol Data Unit";
        }
        bit lsp {
            position 3;
            description "IS-IS Link State PDU";
        }
        bit spf {
            position 4;
            description "IS-IS SPF Calculation";
        }
        bit events {
            position 5;
            description "IS-IS Events";
        }
        bit nsm {
            position 6;
            description "IS-IS NSM information";
        }
        bit checksum {
            position 7;
            description "IS-IS Check-Sum";
        }
        bit authentication {
            position 8;
            description "IS-IS Authentication";
        }
        bit local-updates {
            position 9;
            description "IS-IS Local Updates";
        }
        bit protocol-errors {
            position 10;
            description "IS-IS Protocol Errors";
        }
        bit bfd {
            position 12;
            description "Bidirectional Forwarding Detection (BFD)";
        }
        bit mpls {
            position 13;
            description "Multi-Protocol Label Switching (MPLS)";
        }
        bit rib {
            position 14;
            description "IS-IS RIB information";
        }
        bit sr {
            position 15;
            description "Segment Routing";
        }
        bit lfa {
            position 16;
            description "Loop Free Alternate";
        }
        bit all {
            position 31;
            description "Enable all debugging";
        }
    }
    description "type definition for CML_ISIS_DEBUG_T";
}

typedef  CML_ISIS_DEBUG_HELLO_T {
    type enumeration {
        enum hello {
            value 1;
            description "IS-IS Hello Debug";
        }
    }
    description "type definition for CML_ISIS_DEBUG_HELLO_T";
}

typedef  CML_ISIS_CSPF_DEBUG_T {
    type bits {
        bit events {
            position 0;
            description "None";
        }
        bit hexdump {
            position 1;
            description "None";
        }
    }
    description "type definition for CML_ISIS_CSPF_DEBUG_T";
}

typedef  CML_PASSWORD_T {

    type string{
    length 1..8;
    pattern "[a-zA-Z0-9].*";
    }
    description "type definition for CML_PASSWORD_T";
}

typedef  CML_SYSTEM_HOSTNAME_T {

    type string{
    length 1..64;
    pattern "[a-zA-Z0-9\\-].*";
    }
    description "type definition for CML_SYSTEM_HOSTNAME_T";
}

typedef  CML_USERNAME_T {

    type string{
    length 1..255;
    pattern "[\\-a-zA-Z0-9].*";
    }
    description "type definition for CML_USERNAME_T";
}

typedef  CML_WRAP_T {
    type enumeration {
        enum off {
            value 0;
            description "Disable autowrap";
        }
        enum on {
            value 1;
            description "Enable autowrap";
        }
    }
    description "type definition for CML_WRAP_T";
}

typedef  CML_LDP_TDP_PROTOCOL_T {
    type enumeration {
        enum both {
            value 0;
            description "Use LDP or TDP (Adapt to peer on multiaccess interface)";
        }
        enum ldp {
            value 1;
            description "Use LDP (default)";
        }
        enum tdp {
            value 2;
            description "Use TDP";
        }
    }
    description "type definition for CML_LDP_TDP_PROTOCOL_T";
}

typedef  CML_INTERFACE_T {
    type enumeration {
        enum interface {
            value 0;
            description "Use LDP or TDP (Adapt to peer on multiaccess interface)";
        }
    }
    description "type definition for CML_INTERFACE_T";
}

typedef  CML_LDP_DISCOVERY_ADDRESS_T {
    type union {
        type CML_INTERFACE_T {

        }
        type inet:ipv4-address {

        }
    }
    description "type definition for CML_LDP_DISCOVERY_ADDRESS_T";
}

typedef  CML_MTU_T {
    type union {
        type uint16 {

        }
        type uint16 {

        }
        type uint16 {

        }
        type uint16 {

        }
        type uint16 {

        }
        type uint16 {

        }
        type uint16 {

        }
        type uint16 {

        }
        type uint16 {

        }
    }
    description "type definition for CML_MTU_T";
}

typedef  CML_AREA_T {
    type union {
        type uint32 {
            range "0..4294967295";

        }
        type inet:ipv4-address {

        }
    }
    description "type definition for CML_AREA_T";
}

typedef  CML_SELF_TEST_T {
    type enumeration {
        enum extended {
            value 0;
            description "Extended self test";
        }
        enum fast {
            value 1;
            description "Fast self test";
        }
        enum none {
            value 2;
            description "Turn off self test";
        }
    }
    description "type definition for CML_SELF_TEST_T";
}

typedef  CML_BAUD_RATE_T {
    type enumeration {
        enum 9600 {
            value 9600;
            description "9600";
        }
        enum 19200 {
            value 19200;
            description "19200";
        }
        enum 38400 {
            value 38400;
            description "38400";
        }
        enum 115200 {
            value 115200;
            description "115200";
        }
    }
    description "type definition for CML_BAUD_RATE_T";
}

typedef  CML_OSPF6_INSTANCE_T {
    type union {
        type uint8 {

        }
        type uint8 {

        }
        type uint8 {

        }
        type uint8 {

        }
    }
    description "type definition for CML_OSPF6_INSTANCE_T";
}

typedef  CML_QOS_DIRECTION_T {
    type enumeration {
        enum input {
            value 0;
            description "inbound packets";
        }
    }
    description "type definition for CML_QOS_DIRECTION_T";
}

typedef  CML_ACCESS_GROUP_DIRECTION_T {
    type enumeration {
        enum in {
            value 0;
            description "inbound packets";
        }
        enum out {
            value 1;
            description "outbound packets";
        }
    }
    description "type definition for CML_ACCESS_GROUP_DIRECTION_T";
}

typedef  CML_VLAN_ID_T {

    type uint16{
     range 0..65535;
    }
    description "type definition for CML_VLAN_ID_T";
}

typedef  CML_ADDR_OR_SCRIPT_T {
    type union {
        type inet:ipv4-address {

        }
        type string {

        }
    }
    description "type definition for CML_ADDR_OR_SCRIPT_T";
}

typedef  CML_GI_MEDIA_T {
    type enumeration {
        enum 10-full {
            value 0;
            description "10BaseT full duplex";
        }
        enum 10-half {
            value 1;
            description "10BaseT half duplex";
        }
        enum 100-auto {
            value 2;
            description "100BaseTX duplex auto-negotiation and speed up to 100Mbps";
        }
        enum 100-full {
            value 3;
            description "100BaseTX full duplex";
        }
        enum 100-half {
            value 4;
            description "100BaseTX half duplex";
        }
        enum 1000-full {
            value 5;
            description "1000BaseT full duplex";
        }
        enum 1000-half {
            value 6;
            description "1000BaseT half duplex";
        }
        enum auto {
            value 7;
            description "Automatically negotiate speed";
        }
    }
    description "type definition for CML_GI_MEDIA_T";
}

typedef  CML_TE_MEDIA_T {
    type enumeration {
        enum 1000-full {
            value 0;
            description "1000BaseX full duplex";
        }
        enum 10000-full {
            value 1;
            description "10GBase(SR/LR/.../T) full duplex";
        }
        enum auto {
            value 2;
            description "Automatically negotiate speed";
        }
    }
    description "type definition for CML_TE_MEDIA_T";
}

typedef  CML_PORT_TYPE_T {
    type enumeration {
        enum nni {
            value 0;
            description "nni";
        }
    }
    description "type definition for CML_PORT_TYPE_T";
}

typedef  CML_MODE_T {
    type enumeration {
        enum active {
            value 0;
            description "Enable LACP unconditionally";
        }
        enum auto {
            value 1;
            description "Enable PAgP only if a PAgP device is detected";
        }
        enum desirable {
            value 2;
            description "Enable PAgP unconditionally";
        }
        enum on {
            value 3;
            description "Enable Etherchannel only";
        }
        enum passive {
            value 4;
            description "Enable LACP only if a LACP device is detected";
        }
    }
    description "type definition for CML_MODE_T";
}

typedef  CML_CHANNEL_PROTOCOL_T {
    type enumeration {
        enum lacp {
            value 0;
            description "Prepare interface for LACP protocol";
        }
        enum pagp {
            value 1;
            description "Prepare interface for PAgP protocol";
        }
    }
    description "type definition for CML_CHANNEL_PROTOCOL_T";
}

typedef  CML_ENCAPSULATION_T {
    type enumeration {
        enum mpls {
            value 0;
            description "Use MPLS encapsulation";
        }
        enum l2tpv3 {
            value 1;
            description "Use L2TPv3 encapsulation";
        }
    }
    description "type definition for CML_ENCAPSULATION_T";
}

typedef  CML_SEQUENCE_T {
    type enumeration {
        enum both {
            value 0;
            description "Transmit and receive sequence numbers";
        }
        enum receive {
            value 1;
            description "Receive sequence numbers";
        }
        enum transmit {
            value 2;
            description "Transmit sequence numbers";
        }
    }
    description "type definition for CML_SEQUENCE_T";
}

typedef  CML_GROUP_ENUM_T {
    type enumeration {
        enum global {
            value 0;
            description "Attach global PPPoE group";
        }
    }
    description "type definition for CML_GROUP_ENUM_T";
}

typedef  CML_GROUP_T {
    type union {
        type CML_GROUP_ENUM_T {

        }
        type string {

        }
    }
    description "type definition for CML_GROUP_T";
}

typedef  CML_RATE_TYPE_T {

    type uint32{
     range 0..4294967295;
    }
    description "type definition for CML_RATE_TYPE_T";
}

typedef  CML_IP_RATE_T {
    type union {
        type CML_RATE_TYPE_T {

        }
        type string {

        }
    }
    description "type definition for CML_IP_RATE_T";
}

typedef  CML_SPT_NAME_T {
    type enumeration {
        enum mst {
            value 0;
            description "Global Spanning-Tree configuration";
        }
    }
    description "type definition for CML_SPT_NAME_T";
}

typedef  CML_OSPF_ROUTE_T {
    type enumeration {
        enum connected {
            value 0;
            description "Connected";
        }
        enum kernel {
            value 1;
            description "Kernel routes";
        }
        enum static {
            value 2;
            description "Static routes";
        }
    }
    description "type definition for CML_OSPF_ROUTE_T";
}

typedef  CML_POLICY_MAP_T {
    type enumeration {
        enum ether-type {
            value 0;
            description "Ethertype";
        }
        enum port {
            value 1;
            description "Entire port";
        }
        enum snpa {
            value 2;
            description "Match a specific MAC address";
        }
        enum vid {
            value 3;
            description "Vlan tag";
        }
    }
    description "type definition for CML_POLICY_MAP_T";
}

typedef  CML_POLICY_MAP_ID_T {
    type union {
        type CML_IP_PREFIX_ADDR_T {

        }
        type CML_POLICY_MAP_T {

        }
    }
    description "type definition for CML_POLICY_MAP_ID_T";
}

typedef  CML_ETHER_VALS_T {
    type enumeration {
        enum ipv4 {
            value 0;
            description "ipv4";
        }
        enum ipv6 {
            value 1;
            description "ipv6";
        }
        enum mpls-unicast {
            value 2;
            description "mpls-unicast";
        }
        enum mpls-multicast {
            value 3;
            description "mpls-multicast";
        }
        enum arp {
            value 4;
            description "arp";
        }
        enum ppoe-discover {
            value 5;
            description "ppoe-discover";
        }
        enum ppoe-session {
            value 6;
            description "ppoe-session";
        }
    }
    description "type definition for CML_ETHER_VALS_T";
}

typedef  CML_ENDIS_T {
    type enumeration {
        enum disable {
            value 0;
            description "disable";
        }
        enum enable {
            value 1;
            description "enable";
        }
    }
    description "type definition for CML_ENDIS_T";
}

typedef  CML_ROUTE_MAP_TYPE_T {
    type enumeration {
        enum client {
            value 0;
            description "Match dynamic clients";
        }
        enum ip {
            value 1;
            description "IP information";
        }
        enum tag {
            value 2;
            description "Tag value for destination routing protocol";
        }
    }
    description "type definition for CML_ROUTE_MAP_TYPE_T";
}

typedef  CML_MIRROR_DIRECTION_T {
    type enumeration {
        enum bidir {
            value 0;
            description "Input and output mirroring";
        }
        enum in {
            value 1;
            description "Input mirroring";
        }
        enum out {
            value 2;
            description "Output mirroring";
        }
    }
    description "type definition for CML_MIRROR_DIRECTION_T";
}

typedef  CML_ROUTE_MAP_ACTION_T {
    type enumeration {
        enum deny {
            value 0;
            description "Route map denies set operations";
        }
        enum permit {
            value 1;
            description "Route map permits set operations";
        }
    }
    description "type definition for CML_ROUTE_MAP_ACTION_T";
}

typedef  CML_QUEUES_COUNT_T {
    type enumeration {
        enum 256 {
            value 256;
            description "None";
        }
        enum 512 {
            value 512;
            description "None";
        }
        enum 1024 {
            value 1024;
            description "None";
        }
        enum 2048 {
            value 2048;
            description "None";
        }
    }
    description "type definition for CML_QUEUES_COUNT_T";
}

typedef  CML_RT_T {
    type bits {
        bit import {
            position 0;
            description "import";
        }
        bit export {
            position 1;
            description "export";
        }
    }
    description "type definition for CML_RT_T";
}

typedef  CML_RSVP_ADDR_T {
    type enumeration {
        enum p2mp {
            value 1;
            description "IPV4 address family trunk";
        }
    }
    description "type definition for CML_RSVP_ADDR_T";
}

typedef  CML_HOSTP_TACACS_T {
    type enumeration {
        enum tacacs+ {
            value 1;
            description "Command to enable/disable features";
        }
    }
    description "type definition for CML_HOSTP_TACACS_T";
}

typedef  CML_HOSTP_KEY_TYPE_T {
    type enumeration {
        enum 0 {
            value 0;
            description "To specify shared key in clear-text form";
        }
        enum 7 {
            value 1;
            description "To specify shared key in encrypted form";
        }
    }
    description "type definition for CML_HOSTP_KEY_TYPE_T";
}

typedef  CML_HOSTP_LOCAL_TYPE_T {
    type enumeration {
        enum local {
            value 1;
            description "Group list can be followed by local";
        }
    }
    description "type definition for CML_HOSTP_LOCAL_TYPE_T";
}

typedef  CML_HOSTP_LOCAL_NONE_TYPE_T {
    type enumeration {
        enum local {
            value 0;
            description "Group list can be followed by local";
        }
        enum none {
            value 1;
            description "Group list can be followed by none";
        }
    }
    description "type definition for CML_HOSTP_LOCAL_NONE_TYPE_T";
}

typedef  CML_HOSTP_NONE_TYPE_T {
    type enumeration {
        enum none {
            value 1;
            description "Group list can be followed by none";
        }
    }
    description "type definition for CML_HOSTP_NONE_TYPE_T";
}

typedef  CML_SNMP_OID_TREE_T {
    type enumeration {
        enum included {
            value 1;
            description "Specify to include";
        }
        enum excluded {
            value 2;
            description "Specify to exclude";
        }
    }
    description "type definition for CML_SNMP_OID_TREE_T";
}

typedef  CML_SNMP_LINK_TYPE_T {
    type enumeration {
        enum linkUp {
            value 1;
            description "IETF Link state up notification";
        }
        enum linkDown {
            value 2;
            description "IETF Link state down notification";
        }
    }
    description "type definition for CML_SNMP_LINK_TYPE_T";
}

typedef  CML_SNMP_USER_T {
    type enumeration {
        enum network-operator {
            value 1;
            description "System configured role for read-only";
        }
        enum network-admin {
            value 2;
            description "System configured role for read-write";
        }
    }
    description "type definition for CML_SNMP_USER_T";
}

typedef  CML_SNMP_GROUP_T {
    type enumeration {
        enum network-operator {
            value 1;
            description "System configured group for read-only(default)";
        }
        enum network-admin {
            value 2;
            description "System configured group for read-write";
        }
    }
    description "type definition for CML_SNMP_GROUP_T";
}

typedef  CML_REMOTEID_STRING_T {

    type string{
    pattern "^[a-zA-Z0-9]*";
    }
    description "type definition for CML_REMOTEID_STRING_T";
}

typedef  CML_REMOTEID_ENUM_T {
    type enumeration {
        enum hostname {
            value 0;
            description "Use hostname as remote-id";
        }
    }
    description "type definition for CML_REMOTEID_ENUM_T";
}

typedef  CML_REMOTEID_T {
    type union {
        type CML_REMOTEID_ENUM_T {

        }
        type CML_REMOTEID_STRING_T {

        }
    }
    description "type definition for CML_REMOTEID_T";
}

typedef  CML_OSPF6_METRIC_TYPE_T {
    type enumeration {
        enum 1 {
            value 1;
            description "Set OSPF External Type 1 metrics";
        }
        enum 2 {
            value 2;
            description "Set OSPF External Type 2 metrics";
        }
    }
    description "type definition for CML_OSPF6_METRIC_TYPE_T";
}

typedef  CML_UDLD_MODE_TYPE_T {
    type enumeration {
        enum normal {
            value 0;
            description "UDLD Normal Mode";
        }
        enum aggressive {
            value 1;
            description "UDLD Aggressive";
        }
    }
    description "type definition for CML_UDLD_MODE_TYPE_T";
}

typedef  CML_UDLD_STATE_TYPE_T {
    type enumeration {
        enum enable {
            value 0;
            description "Enable UDLD on an interface";
        }
        enum disable {
            value 1;
            description "Disable UDLD on an interface";
        }
    }
    description "type definition for CML_UDLD_STATE_TYPE_T";
}

typedef  CML_UDLD_T {
    type enumeration {
        enum disable {
            value 0;
            description "Disable UDLD";
        }
        enum enable {
            value 1;
            description "Enable UDLD";
        }
    }
    description "type definition for CML_UDLD_T";
}

typedef  CML_SNMP_AUTH_T {
    type enumeration {
        enum md5 {
            value 1;
            description "Specify md5 authentication";
        }
        enum sha {
            value 2;
            description "Specify sha authentication";
        }
    }
    description "type definition for CML_SNMP_AUTH_T";
}

typedef  CML_SNMP_PRIV_T {
    type enumeration {
        enum des {
            value 1;
            description "Specify des privilege";
        }
        enum aes {
            value 2;
            description "Specify aes privilege";
        }
    }
    description "type definition for CML_SNMP_PRIV_T";
}

typedef  CML_SNMP_VERSION_T {
    type enumeration {
        enum 1 {
            value 1;
            description "Use SNMPv1";
        }
        enum 2c {
            value 2;
            description "Use SNMPv2c";
        }
    }
    description "type definition for CML_SNMP_VERSION_T";
}

typedef  CML_SNMP_INFORMS_VERSION_T {
    type enumeration {
        enum 2c {
            value 2;
            description "Use SNMPv2c";
        }
    }
    description "type definition for CML_SNMP_INFORMS_VERSION_T";
}

typedef  CML_SNMP_VIEW_VERSION_T {
    type enumeration {
        enum v1 {
            value 1;
            description "Specify v1 for SNMPv1";
        }
        enum v2c {
            value 2;
            description "Specify v2c for SNMPv2c";
        }
    }
    description "type definition for CML_SNMP_VIEW_VERSION_T";
}

typedef  CML_SNMP_INFORMS_T {
    type enumeration {
        enum informs {
            value 2;
            description "Send Inform messages to this host";
        }
    }
    description "type definition for CML_SNMP_INFORMS_T";
}

typedef  CML_SNMP_TRAP_T {
    type enumeration {
        enum traps {
            value 1;
            description "Send Traps messages to this host";
        }
    }
    description "type definition for CML_SNMP_TRAP_T";
}

typedef  CML_VERSION3_T {
    type enumeration {
        enum noauth {
            value 1;
            description "Use the SNMPv3 noAuthNoPriv Security Level";
        }
        enum auth {
            value 2;
            description "Use the SNMPv3 authNoPriv Security Level";
        }
        enum priv {
            value 3;
            description "Use the SNMPv3 authPriv Security Level";
        }
    }
    description "type definition for CML_VERSION3_T";
}

typedef  CML_SNMP_ACCESS_T {
    type enumeration {
        enum ro {
            value 1;
            description "Read-only access with this community string";
        }
    }
    description "type definition for CML_SNMP_ACCESS_T";
}

typedef  CML_BFD_GTSM_STATE_T {
    type enumeration {
        enum enable {
            value 1;
            description "Enable gtsm protection";
        }
        enum disable {
            value 2;
            description "Disable gtsm protection";
        }
    }
    description "type definition for CML_BFD_GTSM_STATE_T";
}

typedef  CML_BFD_MULTIHOP_AUTH_TYPE_T {
    type enumeration {
        enum simple {
            value 1;
            description "Simple Password";
        }
        enum keyed-sha1 {
            value 4;
            description "Keyed Secure hashing algorithm";
        }
        enum meticulous-keyed-sha1 {
            value 5;
            description "Meticulous Keyed Secure hashing algorithm";
        }
    }
    description "type definition for CML_BFD_MULTIHOP_AUTH_TYPE_T";
}

typedef  CML_HW_BFD_MULTIHOP_AUTH_TYPE_T {
    type enumeration {
        enum simple {
            value 1;
            description "Simple Password";
        }
        enum keyed-sha1 {
            value 4;
            description "Keyed Secure hashing algorithm";
        }
        enum meticulous-keyed-sha1 {
            value 5;
            description "Meticulous Keyed Secure hashing algorithm";
        }
    }
    description "type definition for CML_HW_BFD_MULTIHOP_AUTH_TYPE_T";
}

typedef  CML_BFD_SESSION_STATE_T {
    type enumeration {
        enum disable {
            value 0;
            description "Disable all the bfd sessions on this interface";
        }
        enum enable {
            value 1;
            description "Enable all the bfd sessions on this interface";
        }
    }
    description "type definition for CML_BFD_SESSION_STATE_T";
}

typedef  CML_OAMBFD_SESSION_FLAGS_T {
    type bits {
        bit rem-heard-up {
            position 0;
            description "BFD_SESSION_FLAG_REM_HEARD";
        }
        bit admin-down {
            position 1;
            description "BFD_SESSION_FLAG_ADMIN_DOWN";
        }
        bit Fate-Shared {
            position 2;
            description "BFD_SESSION_FLAG_FATE_SHARE";
        }
        bit remote-admin-down {
            position 3;
            description "BFD_SESSION_FLAG_REM_ADMIN_DOWN";
        }
        bit Echo-Enabled {
            position 4;
            description "BFD_SESSION_FLAG_ECHO_ENABLED";
        }
        bit Demand-Enabled {
            position 5;
            description "BFD_SESSION_FLAG_DEMAND";
        }
        bit Remote-Demand-Enabled {
            position 6;
            description "BFD_SESSION_FLAG_REM_DEMAND";
        }
        bit Poll-seq-Init {
            position 8;
            description "BFD_SESSION_FLAG_POLL_INIT";
        }
    }
    description "type definition for CML_OAMBFD_SESSION_FLAGS_T";
}

typedef  CML_OAMBFD_PERFORM_DIAG_T {
    type enumeration {
        enum Diagnostics--None {
            value 0;
            description "bfd_diag_no_diag";
        }
        enum Diagnostics-Control-Detected-Expiry {
            value 1;
            description "bfd_diag_ctrl_detect_exp";
        }
        enum Diagnostics-Echo-Failed {
            value 2;
            description "bfd_diag_echo_failed";
        }
        enum Diagnostics-Neighbor-Session-Down {
            value 3;
            description "bfd_diag_nbr_session_down";
        }
        enum Diagnostics-Forwarding-Plane-Reset {
            value 4;
            description "bfd_diag_fwd_reset";
        }
        enum Diagnostics-Path-Down {
            value 5;
            description "bfd_diag_path_down";
        }
        enum Diagnostics-Concatenated-Path-Down {
            value 6;
            description "bfd_diag_concat_path_down";
        }
        enum Diagnostics-Admin-Down {
            value 7;
            description "bfd_diag_admin_down";
        }
        enum Diagnostics-Reverse-Concatenated-Path-Down {
            value 8;
            description "bfd_diag_rev_concat_path_down";
        }
        enum Diagnostics-Configuration-Error {
            value 9;
            description "bfd_diag_config_error";
        }
        enum Diagnostics--Not-forwarding {
            value 10;
            description "bfd_diag_not_forwarding";
        }
    }
    description "type definition for CML_OAMBFD_PERFORM_DIAG_T";
}

typedef  CML_OAMBFD_SESSION_STATE_T {
    type enumeration {
        enum Admin-Down {
            value 0;
            description "BFD_SESSION_STATE_ADMIN_DOWN";
        }
        enum Down {
            value 1;
            description "BFD_SESSION_STATE_DOWN";
        }
        enum Init {
            value 2;
            description "BFD_SESSION_STATE_INIT";
        }
        enum Up {
            value 3;
            description "BFD_SESSION_STATE_UP";
        }
    }
    description "type definition for CML_OAMBFD_SESSION_STATE_T";
}

typedef  CML_OAMBFD_IMAGE_TYPE_T {
    type enumeration {
        enum MONOLITHIC {
            value 1;
            description "BFD_IMAGE_MONOLITHIC";
        }
        enum DISTRIBUTED {
            value 2;
            description "BFD_IMAGE_DIST_MAIN";
        }
        enum DISTRIBUTE {
            value 3;
            description "BFD_IMAGE_DIST_LINE";
        }
    }
    description "type definition for CML_OAMBFD_IMAGE_TYPE_T";
}

typedef  CML_OAMBFD_ADMIN_STATE_T {
    type enumeration {
        enum Up {
            value 1;
            description "BFD_ADMINSTATE_ENABLED";
        }
        enum Down {
            value 2;
            description "BFD_ADMINSTATE_DISABLED";
        }
    }
    description "type definition for CML_OAMBFD_ADMIN_STATE_T";
}

typedef  CML_OAMBFD_SESSION_TYPE_T {
    type enumeration {
        enum Single-Hop {
            value 1;
            description "BFD_SESSION_TYPE_SINGLE_HOP";
        }
        enum Multihop-Arbit-Path {
            value 2;
            description "BFD_SESSION_TYPE_ARBIT_MHOP";
        }
        enum Multihop-OOB-Signalled {
            value 3;
            description "BFD_SESSION_TYPE_OOB_MHOP";
        }
        enum Multihop-Unidirectional {
            value 4;
            description "BFD_SESSION_TYPE_UDLR_MHOP";
        }
    }
    description "type definition for CML_OAMBFD_SESSION_TYPE_T";
}

typedef  CML_OAMBFD_SESS_LOWER_LAYER_T {
    type enumeration {
        enum UNKNOWN {
            value 0;
            description "";
        }
        enum IPv4 {
            value 1;
            description "";
        }
        enum IPv6 {
            value 2;
            description "";
        }
        enum MPLS-LSP {
            value 3;
            description "";
        }
        enum MPLS-VCCV {
            value 4;
            description "";
        }
        enum MPLS-TP {
            value 5;
            description "";
        }
    }
    description "type definition for CML_OAMBFD_SESS_LOWER_LAYER_T";
}

typedef  CML_OAMBFD_HW_MULTIHOP_VAL_T {
    type enumeration {
        enum multi-hop {
            value 4784;
            description "Enable multihop session";
        }
        enum micro-bfd {
            value 6784;
            description "Enable micro-bfd session";
        }
    }
    description "type definition for CML_OAMBFD_HW_MULTIHOP_VAL_T";
}

typedef  CML_VRRP_VMAC_T {
    type enumeration {
        enum enable {
            value 1;
            description "Enabled";
        }
        enum disable {
            value 2;
            description "Disabled";
        }
    }
    description "type definition for CML_VRRP_VMAC_T";
}

typedef  CML_VRRP_ACCEPT_MODE_T {
    type enumeration {
        enum true {
            value 1;
            description "Accept mode enabled";
        }
        enum false {
            value 2;
            description "Accept mode disabled";
        }
    }
    description "type definition for CML_VRRP_ACCEPT_MODE_T";
}

typedef  CML_VRRP_PREEMPT_MODE_T {
    type enumeration {
        enum true {
            value 1;
            description "Preemption enabled";
        }
        enum false {
            value 2;
            description "Preemption disabled";
        }
    }
    description "type definition for CML_VRRP_PREEMPT_MODE_T";
}

typedef  CML_LLDP_ADMIN_STATUS_T {
    type enumeration {
        enum rxonly {
            value 2;
            description "default";
        }
        enum txonly {
            value 4;
            description "Group list can be followed by 'local'";
        }
        enum txrx {
            value 8;
            description "default";
        }
    }
    description "type definition for CML_LLDP_ADMIN_STATUS_T";
}

typedef  CML_LLDP_CHASSIS_ID_T {
    type enumeration {
        enum chassis-component {
            value 0;
            description "default";
        }
        enum if-alias {
            value 1;
            description "default";
        }
        enum port-component {
            value 2;
            description "Group list can be followed by 'local'";
        }
        enum mac-address {
            value 3;
            description "Group list can be followed by 'local'";
        }
        enum ip-address {
            value 4;
            description "Group list can be followed by 'local'";
        }
        enum if-name {
            value 5;
            description "Group list can be followed by 'local'";
        }
        enum local {
            value 6;
            description "Group list can be followed by 'local'";
        }
    }
    description "type definition for CML_LLDP_CHASSIS_ID_T";
}

typedef  CML_LLDP_PORT_ID_T {
    type enumeration {
        enum if-alias {
            value 0;
            description "default";
        }
        enum port-component {
            value 1;
            description "Group list can be followed by 'local'";
        }
        enum mac-address {
            value 2;
            description "Group list can be followed by 'local'";
        }
        enum ip-address {
            value 3;
            description "Group list can be followed by 'local'";
        }
        enum if-name {
            value 4;
            description "Group list can be followed by 'local'";
        }
        enum agent-circuit-id {
            value 5;
            description "Group list can be followed by 'local'";
        }
        enum local {
            value 6;
            description "Group list can be followed by 'local'";
        }
    }
    description "type definition for CML_LLDP_PORT_ID_T";
}

typedef  CML_LLDP_PORT_ADDR_T {
    type enumeration {
        enum mac-address {
            value 1;
            description "default";
        }
        enum ip-address {
            value 2;
            description "Group list can be followed by 'local'";
        }
    }
    description "type definition for CML_LLDP_PORT_ADDR_T";
}

typedef  CML_LLDP_SET_STATE_T {
    type enumeration {
        enum disable {
            value 0;
            description "Disable";
        }
        enum enable {
            value 1;
            description "Enable";
        }
    }
    description "type definition for CML_LLDP_SET_STATE_T";
}

typedef  CML_LLDP_TLV_MODE_T {
    type enumeration {
        enum manual {
            value 1;
            description "Disable";
        }
        enum auto {
            value 2;
            description "Enable";
        }
    }
    description "type definition for CML_LLDP_TLV_MODE_T";
}

typedef  CML_LLDP_IEEE_8023_T {
    type bits {
        bit mac-phy {
            position 0;
            description "mac-phy TLV";
        }
        bit max-mtu-size {
            position 1;
            description "max-mtu-size TLV";
        }
    }
    description "type definition for CML_LLDP_IEEE_8023_T";
}

typedef  CML_LLDP_IEEE_8021_T {
    type bits {
        bit port-vlanid {
            position 0;
            description "port-vlanid TLV";
        }
        bit port-ptcl-vlanid {
            position 1;
            description "port-ptcl-vlanid TLV";
        }
        bit vlan-name {
            position 2;
            description "vlan-name TLV";
        }
        bit ptcl-identity {
            position 3;
            description "ptcl-identity TLV";
        }
        bit vid-digest {
            position 4;
            description "vid-digest TLV";
        }
        bit mgmt-vid {
            position 5;
            description "mgmt-vid TLV";
        }
        bit link-agg {
            position 6;
            description "link-agg TLV";
        }
    }
    description "type definition for CML_LLDP_IEEE_8021_T";
}

typedef  CML_LLDP_BASIC_T {
    type bits {
        bit port-description {
            position 0;
            description "port-description TLV";
        }
        bit system-name {
            position 1;
            description "system-name TLV";
        }
        bit system-description {
            position 2;
            description "system-description TLV";
        }
        bit system-capabilities {
            position 3;
            description "system-capabilities TLV";
        }
        bit management-address {
            position 4;
            description "management-address TLV";
        }
    }
    description "type definition for CML_LLDP_BASIC_T";
}

typedef  CML_VXLAN_MODE_T {
    type enumeration {
        enum vxlan {
            value 1;
            description "vxlan mode or nvrge mode ";
        }
    }
    description "type definition for CML_VXLAN_MODE_T";
}

typedef  CML_LACP_TIMEOUT_T {
    type enumeration {
        enum long {
            value 0;
            description "Set LACP long timeout";
        }
        enum short {
            value 1;
            description "Set LACP short timeout";
        }
    }
    description "type definition for CML_LACP_TIMEOUT_T";
}

typedef  CML_LACP_MODE_T {
    type enumeration {
        enum passive {
            value 0;
            description "Disable initiation of LACP negotiation on a port";
        }
        enum active {
            value 1;
            description "Enable initiation of LACP negotiation on a port";
        }
    }
    description "type definition for CML_LACP_MODE_T";
}

typedef  CML_SSH_KEY_RSA_DSA_T {
    type enumeration {
        enum dsa {
            value 1;
            description "DSA keys";
        }
        enum rsa {
            value 2;
            description "RSA keys";
        }
    }
    description "type definition for CML_SSH_KEY_RSA_DSA_T";
}

typedef  CML_NSM_MPLS_LOG_T {
    type bits {
        bit error {
            position 0;
            description "Log Error message in MPLS Forwarder";
        }
        bit warning {
            position 1;
            description "Log Warning message in MPLS Forwarder";
        }
        bit debug {
            position 2;
            description "Log Debug messages in MPLS Forwarder";
        }
        bit notice {
            position 3;
            description "Log Notice messages in MPLS Forwarder";
        }
    }
    description "type definition for CML_NSM_MPLS_LOG_T";
}

typedef  CML_LDP_ENABLE_TYPE_T {
    type enumeration {
        enum ipv4 {
            value 1;
            description "Enable/Disable LDP for IPV4";
        }
        enum ipv6 {
            value 2;
            description "Enable/Disable LDP for IPV6";
        }
        enum both {
            value 3;
            description "Enable/Disable LDP for both IPV4 and IPV6";
        }
    }
    description "type definition for CML_LDP_ENABLE_TYPE_T";
}

typedef  CML_NSM_CONTAINER_ETHERNET_TYPE_T {
    type enumeration {
        enum ethernet {
            value 0;
            description "VC type Ethernet - needed when one vc is not signaled";
        }
    }
    description "type definition for CML_NSM_CONTAINER_ETHERNET_TYPE_T";
}

typedef  CML_INTERFACE_ADMIN_STATE_T {
    type enumeration {
        enum up {
            value 0;
            description "Admin State UP";
        }
        enum down {
            value 1;
            description "Admin State DOWN";
        }
        enum administratively-down {
            value 2;
            description "Admin State ADMINISTRATIVELY DOWN";
        }
    }
    description "type definition for CML_INTERFACE_ADMIN_STATE_T";
}

typedef  CML_NSM_TUNNEL_DIRECTION_TYPE_T {
    type enumeration {
        enum forward {
            value 0;
            description "Tunnel Direction - Forward tunnel identifier - Default Value";
        }
        enum reverse {
            value 1;
            description "Tunnel Direction - Reverse tunnel identifier";
        }
    }
    description "type definition for CML_NSM_TUNNEL_DIRECTION_TYPE_T";
}

typedef  CML_LACP_BRIDGETYPE_T {
    type enumeration {
        enum customer-bridge-group-address {
            value 0;
            description "customer bridge group address";
        }
        enum multicast-group-address {
            value 1;
            description "multicast group address";
        }
        enum non-tmpr-group-address {
            value 2;
            description "non TPMR group address";
        }
    }
    description "type definition for CML_LACP_BRIDGETYPE_T";
}

typedef  CML_LACP_DISCARD_CONV_T {
    type enumeration {
        enum disable {
            value 0;
            description "disable";
        }
        enum enable {
            value 1;
            description "enable";
        }
    }
    description "type definition for CML_LACP_DISCARD_CONV_T";
}

typedef  CML_VXLAN_INGRESS_T {
    type enumeration {
        enum ingress-replication {
            value 1;
            description "Head End Replication";
        }
    }
    description "type definition for CML_VXLAN_INGRESS_T";
}

typedef  CML_FOG_IFCTYPE_T {
    type enumeration {
        enum mpg {
            value 1;
            description "Monitor Port Group";
        }
        enum cpg {
            value 2;
            description "Control Port Group";
        }
    }
    description "type definition for CML_FOG_IFCTYPE_T";
}

typedef  CML_FOG_LINK_TYPE_T {
    type enumeration {
        enum uplink {
            value 1;
            description "Configure Port as Uplink";
        }
        enum downlink {
            value 2;
            description "Configure Port as Downlink";
        }
    }
    description "type definition for CML_FOG_LINK_TYPE_T";
}

typedef  CML_VXLAN_INNER_VID_T {
    type enumeration {
        enum inner-vid-disabled {
            value 1;
            description "Vid not to be carried out of network port";
        }
    }
    description "type definition for CML_VXLAN_INNER_VID_T";
}

typedef  CML_MROUTE_ROUTETYPE_T {
    type enumeration {
        enum default {
            value 0;
            description "Default route type";
        }
        enum static {
            value 3;
            description "Static routes";
        }
        enum rip {
            value 4;
            description "Routing Information Protocol (RIP)";
        }
        enum ospf {
            value 6;
            description "Open Shortest Patch First (OSPF)";
        }
        enum bgp {
            value 8;
            description "Border Gateway Protocol (BGP)";
        }
        enum isis {
            value 9;
            description "ISO IS-IS";
        }
    }
    description "type definition for CML_MROUTE_ROUTETYPE_T";
}

typedef  CML_MROUTE_IPV6_ROUTETYPE_T {
    type enumeration {
        enum default {
            value 0;
            description "Default route type";
        }
        enum static {
            value 3;
            description "Static routes";
        }
        enum rip {
            value 5;
            description "Routing Information Protocol (RIP)";
        }
        enum ospf {
            value 7;
            description "Open Shortest Patch First (OSPF)";
        }
        enum bgp {
            value 8;
            description "Border Gateway Protocol (BGP)";
        }
        enum isis {
            value 9;
            description "ISO IS-IS";
        }
    }
    description "type definition for CML_MROUTE_IPV6_ROUTETYPE_T";
}

typedef  CML_MROUTE_IFNAME_T {

    type string{
    length 0..20;
    }
    description "type definition for CML_MROUTE_IFNAME_T";
}

typedef  CML_MROUTE_GW_ADDR_T {
    type union {
        type inet:ipv6-address {

        }
        type CML_MROUTE_IFNAME_T {

        }
    }
    description "type definition for CML_MROUTE_GW_ADDR_T";
}

typedef  CML_FIB_RETAIN_T {
    type union {
        type CML_FIB_RETAIN_TIME_T {

        }
        type CML_FIB_RETAIN_FOREVER_T {

        }
    }
    description "type definition for CML_FIB_RETAIN_T";
}

typedef  CML_FIB_RETAIN_FOREVER_T {
    type enumeration {
        enum forever {
            value 0;
            description "Retain FIB forever";
        }
    }
    description "type definition for CML_FIB_RETAIN_FOREVER_T";
}

typedef  CML_FIB_RETAIN_TIME_T {

    type uint32{
     range 0..4294967295;
    }
    description "type definition for CML_FIB_RETAIN_TIME_T";
}

typedef  CML_RIB_DEBUG_TYPE_T {
    type bits {
        bit events {
            position 1;
            description "RIB events";
        }
        bit packet {
            position 2;
            description "RIB packets";
        }
        bit packet-send {
            position 3;
            description "RIB packets,RIB send packets";
        }
        bit packet-recv {
            position 4;
            description "RIB packets,RIB receive packets";
        }
        bit packet-detail {
            position 5;
            description "RIB packets,Detailed information display";
        }
        bit packet-send-detail {
            position 6;
            description "RIB packets,RIB send packets,Detailed information display";
        }
        bit packet-recv-detail {
            position 7;
            description "RIB packets,RIB receive packets,Detailed information display";
        }
        bit kernel {
            position 8;
            description "RIB kernel";
        }
        bit ha {
            position 9;
            description "RIB High Availability";
        }
        bit ha-all {
            position 10;
            description "RIB High Availability,All RIB High Availability events";
        }
        bit nsm {
            position 11;
            description "NSM messages";
        }
        bit bfd {
            position 12;
            description "BFD messages";
        }
        bit monitor {
            position 13;
            description "Enable Monitor route netlink";
        }
        bit hal-events {
            position 18;
            description "Hardware Abstraction Layer,RIB events";
        }
        bit hal-ipc {
            position 19;
            description "Hardware Abstraction Layer,Async Debugging";
        }
    }
    description "type definition for CML_RIB_DEBUG_TYPE_T";
}

typedef  CML_RIB_BFD_STATE {
    type enumeration {
        enum enable {
            value 0;
            description "enable BFD";
        }
        enum disable {
            value 1;
            description "disable BFD";
        }
    }
    description "type definition for CML_RIB_BFD_STATE";
}

typedef  CML_RIB_DEBUG_ROUTING_TYPE_T {
    type bits {
        bit routing {
            position 20;
            description "Enable debugging for routing events";
        }
        bit routing-add-route {
            position 21;
            description "Enable debugging for routing events,Add route events";
        }
        bit routing-delete-route {
            position 22;
            description "Enable debugging for routing events, Delete route events";
        }
        bit routing-mod-route {
            position 23;
            description "Enable debugging for routing events, Modify route events";
        }
    }
    description "type definition for CML_RIB_DEBUG_ROUTING_TYPE_T";
}

typedef  CML_RIB_PACKET_DEBUG_TYPE_T {
    type enumeration {
        enum recv {
            value 1;
            description "RIB receive packets";
        }
        enum send {
            value 2;
            description "RIB send packets";
        }
    }
    description "type definition for CML_RIB_PACKET_DEBUG_TYPE_T";
}

typedef  CML_VRRP_INIT_MSG_CODE_T {
    type enumeration {
        enum admin-down {
            value 0;
            description "(admin state down)";
        }
        enum if-not-running {
            value 1;
            description "(interface is not running)";
        }
        enum circuit-down {
            value 2;
            description "(monitored circuit is down)";
        }
        enum no-subnet {
            value 3;
            description "(no matching subnet)";
        }
        enum vip-unset {
            value 4;
            description "(virtual IP address not set)";
        }
        enum switch-back-delay {
            value 5;
            description "(In Switch Back Delay)";
        }
    }
    description "type definition for CML_VRRP_INIT_MSG_CODE_T";
}

typedef  CML_VRRP_DEBUG_T {
    type bits {
        bit events {
            position 1;
            description "VRRP events";
        }
        bit packet-send {
            position 2;
            description "VRRP packets,VRRP send packets";
        }
        bit packet-recv {
            position 3;
            description "VRRP packets,VRRP receive packets";
        }
    }
    description "type definition for CML_VRRP_DEBUG_T";
}

typedef  CML_VRRP_STATE_T {
    type enumeration {
        enum init {
            value 1;
            description "VRRP_STATE_INIT";
        }
        enum backup {
            value 2;
            description "VRRP_STATE_BACKUP";
        }
        enum master {
            value 3;
            description "VRRP_STATE_MASTER";
        }
    }
    description "type definition for CML_VRRP_STATE_T";
}

typedef  CML_VRRP_MEMEBER_STATE {
    type enumeration {
        enum joined {
            value 1;
            description "VRRP_IPV4_MCAST_JOINED";
        }
        enum left {
            value 2;
            description "VRRP_IPV4_MCAST_LEFT";
        }
    }
    description "type definition for CML_VRRP_MEMEBER_STATE";
}

typedef  CML_MCEC_HELLO_T {
    type enumeration {
        enum long {
            value 0;
            description "Long Timeout";
        }
        enum short {
            value 1;
            description "Short Timeout";
        }
    }
    description "type definition for CML_MCEC_HELLO_T";
}

typedef  MCEC_DEBUG_T {
    type bits {
        bit hello {
            position 0;
            description "Hello";
        }
        bit info {
            position 1;
            description "Info";
        }
        bit timer {
            position 2;
            description "Timer";
        }
        bit event {
            position 3;
            description "Event";
        }
        bit cli {
            position 4;
            description "CLI";
        }
        bit mac-sync {
            position 5;
            description "MAC Sync";
        }
        bit stp {
            position 6;
            description "STP";
        }
    }
    description "type definition for MCEC_DEBUG_T";
}

typedef  CML_OSPF_STRING_T {

    type string{
    pattern "[^?' =,>|]*";
    }
    description "type definition for CML_OSPF_STRING_T";
}

typedef  CML_OSPF_AREA_ID_T {
    type union {
        type CML_OSPF_STRING_T {

        }
        type uint16 {
            range "1..65535";

        }
    }
    description "type definition for CML_OSPF_AREA_ID_T";
}

typedef  CML_COMMON_DEBUG_TYPE_T {
    type bits {
        bit decode {
            position 0;
            description "decode";
        }
        bit encode {
            position 1;
            description "encode";
        }
        bit events {
            position 2;
            description "events";
        }
        bit fsm {
            position 3;
            description "FSM";
        }
        bit tib {
            position 4;
            description "Tree-Info-Base (TIB)";
        }
    }
    description "type definition for CML_COMMON_DEBUG_TYPE_T";
}

typedef  CML_UNKNOWN_MCAST_T {
    type enumeration {
        enum flood {
            value 0;
            description "flood mode";
        }
        enum discard {
            value 1;
            description "Discard mode";
        }
    }
    description "type definition for CML_UNKNOWN_MCAST_T";
}

typedef  CML_OSPF6_DEBUG_PACKET_TYPE_T {
    type bits {
        bit hello {
            position 0;
            description "OSPFv3 Hello ";
        }
        bit dd {
            position 1;
            description "OSPFv3 Database Description";
        }
        bit ls-request {
            position 2;
            description "OSPFv3 Link State Request ";
        }
        bit ls-update {
            position 3;
            description "OSPFv3 Link State Update ";
        }
        bit ls-ack {
            position 4;
            description "OSPFv3 Link State Acknowledgment";
        }
        bit send {
            position 5;
            description "Packet sent";
        }
        bit recv {
            position 6;
            description "packet received";
        }
        bit detail {
            position 7;
            description "Detail information";
        }
    }
    description "type definition for CML_OSPF6_DEBUG_PACKET_TYPE_T";
}

typedef  CML_OSPF6_DEBUG_IFSM_T {
    type bits {
        bit status {
            position 0;
            description "IFSM status Information";
        }
        bit events {
            position 1;
            description "IFSM events Information";
        }
        bit timers {
            position 2;
            description "IFSM Timer Information";
        }
    }
    description "type definition for CML_OSPF6_DEBUG_IFSM_T";
}

typedef  CML_OSPF6_DEBUG_NFSM_T {
    type bits {
        bit status {
            position 0;
            description "NFSM status Information";
        }
        bit events {
            position 1;
            description "NFSM events Information";
        }
        bit timers {
            position 2;
            description "NFSM Timer Information";
        }
    }
    description "type definition for CML_OSPF6_DEBUG_NFSM_T";
}

typedef  CML_OSPF6_DEBUG_LSA_T {
    type bits {
        bit generate {
            position 0;
            description "LSA Generation";
        }
        bit flooding {
            position 1;
            description "LSA Flooding";
        }
        bit install {
            position 2;
            description "LSA Installation";
        }
        bit refresh {
            position 3;
            description "LSA Refreshment";
        }
        bit maxage {
            position 4;
            description "LSA MaxAge processing";
        }
    }
    description "type definition for CML_OSPF6_DEBUG_LSA_T";
}

typedef  CML_OSPF6_DEBUG_NSM_T {
    type bits {
        bit interface {
            position 0;
            description "NSM interface ";
        }
        bit redistribute {
            position 1;
            description "NSM redistribute ";
        }
    }
    description "type definition for CML_OSPF6_DEBUG_NSM_T";
}

typedef  CML_OSPF6_DEBUG_RIB_T {
    type bits {
        bit interface {
            position 0;
            description "OSPF NSM information, NSM interface ";
        }
        bit redistribute {
            position 1;
            description "OSPF NSM information, NSM redistribute ";
        }
    }
    description "type definition for CML_OSPF6_DEBUG_RIB_T";
}

typedef  CML_OSPF6_DEBUG_ROUTE_T {
    type bits {
        bit spf {
            position 0;
            description "OSPF route information,SPF calculation information";
        }
        bit ia {
            position 1;
            description "OSPF route information, Inter-Area route calculation information";
        }
        bit ase {
            position 2;
            description "OSPF route information,External route calculation information";
        }
        bit install {
            position 3;
            description "OSPF route information, Route installation information";
        }
    }
    description "type definition for CML_OSPF6_DEBUG_ROUTE_T";
}

typedef  CML_OSPF6_DEBUG_EVENT_T {
    type bits {
        bit abr {
            position 0;
            description "OSPF events information, OSPF ABR events";
        }
        bit asbr {
            position 1;
            description "OSPF events information,OSPF ASBR events ";
        }
        bit vlink {
            position 2;
            description "OSPF events information,OSPF Virtual-Link events";
        }
        bit os {
            position 3;
            description "OSPF events information, OSPF OS interaction events ";
        }
        bit router {
            position 4;
            description "OSPF events information,Other router events ";
        }
        bit nssa {
            position 5;
            description "OSPF events information, OSPF NSSA events ";
        }
    }
    description "type definition for CML_OSPF6_DEBUG_EVENT_T";
}

typedef  CML_MODULE_NAME_T {
    type enumeration {
        enum auth {
            value 1;
            description "Set logging level for auth messages";
        }
        enum bgp {
            value 2;
            description "Set logging level for bgp messages";
        }
        enum cmm {
            value 3;
            description "Set logging level for cmm messages";
        }
        enum hostp {
            value 5;
            description "Set logging level for hostp messages";
        }
        enum hsl {
            value 6;
            description "Set logging level for hsl messages";
        }
        enum isis {
            value 7;
            description "Set logging level for isis messages";
        }
        enum ldp {
            value 8;
            description "Set logging level for ldp messages";
        }
        enum lag {
            value 9;
            description "Set logging level for lagd messages";
        }
        enum l2mrib {
            value 10;
            description "Set logging level for l2mrib messages";
        }
        enum mstp {
            value 11;
            description "Set logging level for mstp messages";
        }
        enum mrib {
            value 12;
            description "Set logging level for mrib messages";
        }
        enum nsm {
            value 13;
            description "Set logging level for nsm messages";
        }
        enum onm {
            value 14;
            description "Set logging level for onm messages";
        }
        enum oam {
            value 15;
            description "Set logging level for oam messages";
        }
        enum ospf {
            value 16;
            description "Set logging level for ospf messages";
        }
        enum ospf6 {
            value 17;
            description "Set logging level for ospf6 messages";
        }
        enum rip {
            value 19;
            description "Set logging level for rip messages";
        }
        enum pim {
            value 21;
            description "Set logging level for pim messages";
        }
        enum rib {
            value 22;
            description "Set logging level for rib messages";
        }
        enum vrrp {
            value 23;
            description "Set logging level for vrrp messages";
        }
        enum sflow {
            value 24;
            description "Set logging level for sflow messages";
        }
        enum rsvp {
            value 26;
            description "Set logging level for rsvp messages";
        }
        enum pserv {
            value 27;
            description "Set logging level for pservd messages";
        }
        enum cml {
            value 28;
            description "Set logging level for cml messages";
        }
        enum ndd {
            value 29;
            description "Set logging level for ndd messages";
        }
        enum ripng {
            value 30;
            description "Set logging level for ripng messages";
        }
        enum vlog {
            value 31;
            description "Set logging level for vlog messages";
        }
    }
    description "type definition for CML_MODULE_NAME_T";
}

typedef  CML_TIMESTAMP_UNITS_T {
    type enumeration {
        enum none {
            value 0;
            description "No timestamp in log messages";
        }
        enum microseconds {
            value 1;
            description "Timestamp in micro-seconds";
        }
        enum milliseconds {
            value 2;
            description "Timestamp in milli-seconds (Default)";
        }
        enum seconds {
            value 3;
            description "Timestamp in seconds";
        }
    }
    description "type definition for CML_TIMESTAMP_UNITS_T";
}

typedef  CML_LEVEL_T {
    type enumeration {
        enum debuglogging {
            value 0;
            description "Logging host";
        }
        enum emergencies {
            value 1;
            description "Logging emergency";
        }
        enum alerts {
            value 2;
            description "Logging alert";
        }
        enum critical {
            value 3;
            description "Logging critical";
        }
        enum errors {
            value 4;
            description "Logging Error";
        }
        enum warnings {
            value 5;
            description "Logging warning";
        }
        enum notifications {
            value 6;
            description "Logging notify";
        }
        enum informational {
            value 7;
            description "Logging Info";
        }
        enum debugging {
            value 8;
            description "Logging Debug";
        }
    }
    description "type definition for CML_LEVEL_T";
}

typedef  CML_CLEAR_NTP_STATISTICS_T {
    type enumeration {
        enum all-peers {
            value 0;
            description "Clear per-peer statistics counter of all peers";
        }
        enum io {
            value 1;
            description "Clear input-output statistics";
        }
        enum local {
            value 2;
            description "Clear counters maintained by the local NTP";
        }
        enum memory {
            value 3;
            description "Clear statistics counters related to memory code";
        }
    }
    description "type definition for CML_CLEAR_NTP_STATISTICS_T";
}

typedef  CML_NTP_PREFER_T {
    type enumeration {
        enum prefer {
            value 1;
            description "preferred server";
        }
    }
    description "type definition for CML_NTP_PREFER_T";
}

typedef  CML_NTP_FEATURE_T {
    type enumeration {
        enum ntp {
            value 1;
            description "Enable NTP";
        }
    }
    description "type definition for CML_NTP_FEATURE_T";
}

typedef  CML_RSYSLOG_FEATURE_T {
    type enumeration {
        enum rsyslog {
            value 1;
            description "Remote Logging feature";
        }
    }
    description "type definition for CML_RSYSLOG_FEATURE_T";
}

typedef  CML_SNMP_ENABLE_T {
    type enumeration {
        enum snmp {
            value 1;
            description "Enable SNMP feature";
        }
    }
    description "type definition for CML_SNMP_ENABLE_T";
}

typedef  SFLOW_DEBUG_OPTIONS_T {
    type enumeration {
        enum agent {
            value 1;
            description "debug sflow agent";
        }
        enum sampling {
            value 2;
            description "debug sflow sampling";
        }
        enum polling {
            value 3;
            description "debug sflow polling";
        }
        enum all {
            value 4;
            description "debug all";
        }
    }
    description "type definition for SFLOW_DEBUG_OPTIONS_T";
}

typedef  SFLOW_DIRECTION_OPTION_T {
    type enumeration {
        enum ingress {
            value 1;
            description "Ingress";
        }
        enum egress {
            value 2;
            description "Egress";
        }
        enum both {
            value 3;
            description "Both";
        }
    }
    description "type definition for SFLOW_DIRECTION_OPTION_T";
}

typedef  SFLOW_EGRESS_INGRESS_T {
    type enumeration {
        enum disabled {
            value 0;
            description "Disable Egress/Ingress";
        }
        enum enabled {
            value 1;
            description "Enable Egress/Ingress";
        }
    }
    description "type definition for SFLOW_EGRESS_INGRESS_T";
}

typedef  USER_MGMT_ROLE_OPTIONS_T {
    type enumeration {
        enum network-admin {
            value 1;
            description "Enter the rolename - Network Administrat or - Have all permissions";
        }
        enum network-engineer {
            value 2;
            description "Enter the rolename - Network Engineer  - Can save configuration";
        }
        enum network-operator {
            value 3;
            description "Enter the rolename - Network Operator  - Can not save configuration";
        }
        enum network-user {
            value 4;
            description "Enter the rolename - Network User - Can n ot change configuration";
        }
    }
    description "type definition for USER_MGMT_ROLE_OPTIONS_T";
}

typedef  CML_ACCEPT_LIFETIME_T {
    type enumeration {
        enum accept-lifetime {
            value 1;
            description "Set accept lifetime of the key";
        }
    }
    description "type definition for CML_ACCEPT_LIFETIME_T";
}

typedef  CML_ISIS_ADDRESS_IPV6_T {
    type enumeration {
        enum ipv6 {
            value 1;
            description "Address family";
        }
    }
    description "type definition for CML_ISIS_ADDRESS_IPV6_T";
}

typedef  CML_SEND_LIFETIME_T {
    type enumeration {
        enum send-lifetime {
            value 1;
            description "Set send lifetime of the key";
        }
    }
    description "type definition for CML_SEND_LIFETIME_T";
}

typedef  CML_PREFIX_LIST_TYPE {
    type enumeration {
        enum deny {
            value 1;
            description "Specify packets to reject";
        }
        enum permit {
            value 2;
            description "Specify packets to forward";
        }
    }
    description "type definition for CML_PREFIX_LIST_TYPE";
}

typedef  CML_PREFIX_LIST_ANY_T {
    type enumeration {
        enum any {
            value 1;
            description "Any prefix match. Same as 0.0.0.0/0 le 32 ";
        }
    }
    description "type definition for CML_PREFIX_LIST_ANY_T";
}

typedef  CML_ISIS_METRIC_T {
    type enumeration {
        enum internal {
            value 0;
            description "Set IS-IS Internal metric type";
        }
        enum external {
            value 1;
            description "Set IS-IS External metric type";
        }
    }
    description "type definition for CML_ISIS_METRIC_T";
}

typedef  CML_OAM_BFD_FW_T {
    type enumeration {
        enum multi-hop {
            value 1;
            description "Enable multihop session";
        }
        enum micro-bfd {
            value 2;
            description "Enable micro-bfd session (DEFAULT)";
        }
    }
    description "type definition for CML_OAM_BFD_FW_T";
}

typedef  CML_IS_TYPE3_T {
    type enumeration {
        enum level-1 {
            value 1;
            description "IS-IS level-1 routes only";
        }
        enum level-2 {
            value 2;
            description "IS-IS level-2 routes only";
        }
        enum level-1-2 {
            value 3;
            description "IS-IS level-1 and level-2 routes";
        }
    }
    description "type definition for CML_IS_TYPE3_T";
}

typedef  CML_ISIS_SUMMARY_LEVEL_T {
    type enumeration {
        enum level-1 {
            value 1;
            description "Summarize into level-1 area";
        }
        enum level-2 {
            value 2;
            description "Summarize into level-2 sub-domain";
        }
        enum level-1-2 {
            value 3;
            description "Summarize into both area and sub-domain";
        }
    }
    description "type definition for CML_ISIS_SUMMARY_LEVEL_T";
}

typedef  CML_ISIS_LEVEL3_T {
    type enumeration {
        enum level-1 {
            value 1;
            description "Level-1 only";
        }
        enum level-2 {
            value 2;
            description "Level-2 only";
        }
        enum level-1-2 {
            value 3;
            description "Level-1-2";
        }
    }
    description "type definition for CML_ISIS_LEVEL3_T";
}

typedef  CML_ISIS_SYNC_TYPE_T {
    type enumeration {
        enum level-1 {
            value 1;
            description "Enable LDP ISIS synchronization for level-1 only";
        }
        enum level-2 {
            value 2;
            description "Enable LDP ISIS synchronization for level-2 only";
        }
        enum level-1-2 {
            value 3;
            description "Enable LDP ISIS synchronization for level-1 and level-2";
        }
    }
    description "type definition for CML_ISIS_SYNC_TYPE_T";
}

typedef  CML_ISIS_CIRCUIT_TYPE_T {
    type enumeration {
        enum level-1 {
            value 1;
            description "Level-1 only adjacencies are formed";
        }
        enum level-2-only {
            value 2;
            description "Level-2 only adjacencies are formed";
        }
        enum level-1-2 {
            value 3;
            description "Level-1-2 adjacencies are formed";
        }
    }
    description "type definition for CML_ISIS_CIRCUIT_TYPE_T";
}

typedef  CML_ISIS_SUPPRESS_T {
    type enumeration {
        enum default {
            value 0;
            description "Only for set-overload bit value";
        }
        enum external {
            value 1;
            description "If overload-bit set do not advertise IP prefixes learned from other protocols";
        }
        enum interlevel {
            value 2;
            description "If overload-bit set do not advertise IP prefixes learned from another ISIS level";
        }
        enum external-interlevel {
            value 3;
            description "If overload-bit set donot advertise IP prefixes learned from other protocols,If overload-bit set do not advertise IP prefixes learned from another ISIS level";
        }
        enum interlevel-external {
            value 4;
            description "If overload-bit set donot advertise IP prefixes learned from another ISIS level,If overload-bit set donot advertise IP prefixes learned from other protocols";
        }
    }
    description "type definition for CML_ISIS_SUPPRESS_T";
}

typedef  CML_WAITFORBGP_T {
    type enumeration {
        enum default {
            value 0;
            description "Only for set-overload bit value";
        }
        enum wait-for-bgp {
            value 1;
            description "Let BGP decide when to unset the overload bit";
        }
    }
    description "type definition for CML_WAITFORBGP_T";
}

typedef  CML_QOS_ALL_T {
    type enumeration {
        enum all {
            value -1;
            description "Include all cos-queues";
        }
    }
    description "type definition for CML_QOS_ALL_T";
}

typedef  CML_QOS_DATA_T {
    type union {
        type CML_QOS_ALL_T {

        }
        type uint8 {
            range "0..7";

        }
    }
    description "type definition for CML_QOS_DATA_T";
}

typedef  CML_ISIS_ONSTARTUP_T {
    type union {
        type CML_WAITFORBGP_T {

        }
        type uint32 {
            range "5..86400";

        }
    }
    description "type definition for CML_ISIS_ONSTARTUP_T";
}

typedef  CML_MESH_BLOCKED_T {
    type enumeration {
        enum blocked {
            value 0;
            description "Block LSPs on this interface";
        }
    }
    description "type definition for CML_MESH_BLOCKED_T";
}

typedef  CML_ISIS_MESH_TYPE_T {
    type union {
        type CML_MESH_BLOCKED_T {

        }
        type uint32 {
            range "1..4294967295";

        }
    }
    description "type definition for CML_ISIS_MESH_TYPE_T";
}

typedef  CML_ISIS_MINIMAL_T {
    type enumeration {
        enum minimal {
            value 0;
            description "Holdtime 1 second interval depends on multiplier";
        }
    }
    description "type definition for CML_ISIS_MINIMAL_T";
}

typedef  CML_ISIS_HELLO_INTERVAL_TYPE_T {
    type union {
        type CML_ISIS_MINIMAL_T {

        }
        type uint16 {
            range "1..65535";

        }
    }
    description "type definition for CML_ISIS_HELLO_INTERVAL_TYPE_T";
}

typedef  CML_OSPF_CAPABILITY_TE_T {
    type enumeration {
        enum te {
            value 1;
            description "OSPF Traffic Engineering extension";
        }
        enum traffic-engineering {
            value 2;
            description "OSPF Traffic Engineering extension";
        }
    }
    description "type definition for CML_OSPF_CAPABILITY_TE_T";
}

typedef  CML_OSPF_AREA_AUTHENTICATION_TYPE_T {
    type enumeration {
        enum authentication {
            value 1;
            description "Enable authentication";
        }
        enum authentication-message-digest {
            value 2;
            description "Enable authentication, Use message-digest authentication";
        }
    }
    description "type definition for CML_OSPF_AREA_AUTHENTICATION_TYPE_T";
}

typedef  CML_OSPF_VLINK_AUTH_TYPE_T {
    type enumeration {
        enum authentication-null {
            value 0;
            description "Enable authentication,Use no authentication";
        }
        enum authentication {
            value 1;
            description "Enable authentication";
        }
        enum authentication-message-digest {
            value 2;
            description "Enable authentication,Use message-digest authentication";
        }
    }
    description "type definition for CML_OSPF_VLINK_AUTH_TYPE_T";
}

typedef  CML_OSPF_VLINK_INTERFACE_STATE_T {
    type enumeration {
        enum DependUpon {
            value 0;
            description "IFSM DependUpon";
        }
        enum Down {
            value 1;
            description "IFSM Down";
        }
        enum Loopback {
            value 2;
            description "IFSM Loopback";
        }
        enum Waiting {
            value 3;
            description "IFSM Waiting";
        }
        enum Point-To-Point {
            value 4;
            description "IFSM Point-To-Point";
        }
        enum DROther {
            value 5;
            description "IFSM DROther";
        }
        enum Backup {
            value 6;
            description "IFSM Backup";
        }
        enum DR {
            value 7;
            description "IFSM DR";
        }
    }
    description "type definition for CML_OSPF_VLINK_INTERFACE_STATE_T";
}

typedef  CML_OSPF_VLINK_ADJ_STATE_T {
    type enumeration {
        enum DependUpon {
            value 0;
            description "NFSM DependUpon";
        }
        enum Down {
            value 1;
            description "NFSM Down";
        }
        enum Attempt {
            value 2;
            description "NFSM Attempt";
        }
        enum Init {
            value 3;
            description "NFSM Init";
        }
        enum 2-Way {
            value 4;
            description "NFSM 2-Way";
        }
        enum ExStart {
            value 5;
            description "NFSM ExStart";
        }
        enum Exchange {
            value 6;
            description "NFSM Exchange";
        }
        enum Loading {
            value 7;
            description "NFSM Loading";
        }
        enum Full {
            value 8;
            description "NFSM Full";
        }
    }
    description "type definition for CML_OSPF_VLINK_ADJ_STATE_T";
}

typedef  CML_OSPF_VLINK_STATUS_T {
    type enumeration {
        enum Down {
            value 0;
            description "Virtual Link Down";
        }
        enum Up {
            value 1;
            description "Virtual Link Up";
        }
    }
    description "type definition for CML_OSPF_VLINK_STATUS_T";
}

typedef  CML_OSPF_AREA_RANGE_ADVERTISE_T {
    type enumeration {
        enum not-advertise {
            value 0;
            description "DoNotAdvertise this range";
        }
        enum advertise {
            value 1;
            description "Advertise this range (default)";
        }
    }
    description "type definition for CML_OSPF_AREA_RANGE_ADVERTISE_T";
}

typedef  CML_OSPF_BFD_STATE {
    type enumeration {
        enum enable {
            value 0;
            description "enable BFD";
        }
        enum disable {
            value 1;
            description "disable BFD";
        }
    }
    description "type definition for CML_OSPF_BFD_STATE";
}

typedef  CML_OSPF_ALL_DEBUG_T {
    type enumeration {
        enum all {
            value 1;
            description "Enable all debugging";
        }
    }
    description "type definition for CML_OSPF_ALL_DEBUG_T";
}

typedef  CML_OSPF_PACKET_TYPE_T {
    type bits {
        bit hello {
            position 0;
            description "OSPF Hello";
        }
        bit dd {
            position 1;
            description "OSPF Database Description";
        }
        bit ls-request {
            position 2;
            description "OSPF Link State Request";
        }
        bit ls-update {
            position 3;
            description "OSPF Link State Update";
        }
        bit ls-ack {
            position 4;
            description "OSPF Link State Acknowledgment";
        }
        bit send {
            position 5;
            description "Packet sent";
        }
        bit recv {
            position 6;
            description "packet received";
        }
        bit detail {
            position 7;
            description "Detail information";
        }
    }
    description "type definition for CML_OSPF_PACKET_TYPE_T";
}

typedef  CML_OSPF_DEBUG_EVENT_TYPE_T {
    type bits {
        bit abr {
            position 0;
            description "OSPF ABR events";
        }
        bit nssa {
            position 1;
            description "OSPF NSSA events";
        }
        bit asbr {
            position 2;
            description "OSPF ASBR events";
        }
        bit vlink {
            position 3;
            description "OSPF Virtual-Link events";
        }
        bit lsa {
            position 4;
            description "OSPF LSA events";
        }
        bit os {
            position 5;
            description "OSPF OS interaction events";
        }
        bit router {
            position 6;
            description "Other router events";
        }
    }
    description "type definition for CML_OSPF_DEBUG_EVENT_TYPE_T";
}

typedef  CML_OSPF_DEBUG_IFSM_T {
    type bits {
        bit status {
            position 0;
            description "IFSM Status Information";
        }
        bit events {
            position 1;
            description "IFSM Event Information";
        }
        bit timers {
            position 2;
            description "IFSM Timers Information";
        }
    }
    description "type definition for CML_OSPF_DEBUG_IFSM_T";
}

typedef  CML_OSPF_DEBUG_NFSM_T {
    type bits {
        bit status {
            position 0;
            description "NFSM Status Information";
        }
        bit events {
            position 1;
            description "NFSM Event Information";
        }
        bit timers {
            position 2;
            description "NFSM Timers Information";
        }
    }
    description "type definition for CML_OSPF_DEBUG_NFSM_T";
}

typedef  CML_OSPF_DEBUG_LSA_T {
    type bits {
        bit generate {
            position 0;
            description "LSA Generation";
        }
        bit flooding {
            position 1;
            description "LSA Flooding";
        }
        bit install {
            position 2;
            description "LSA Installation";
        }
        bit refresh {
            position 3;
            description "LSA Refreshment";
        }
        bit maxage {
            position 4;
            description "LSA MaxAge processing";
        }
    }
    description "type definition for CML_OSPF_DEBUG_LSA_T";
}

typedef  CML_OSPF_DEBUG_NSM_T {
    type bits {
        bit interface {
            position 0;
            description "NSM interface";
        }
        bit redistribute {
            position 1;
            description "NSM redistribute";
        }
    }
    description "type definition for CML_OSPF_DEBUG_NSM_T";
}

typedef  CML_OSPF_DEBUG_RIB_T {
    type bits {
        bit interface {
            position 0;
            description "RIB interface";
        }
        bit redistribute {
            position 1;
            description "RIB redistribute";
        }
    }
    description "type definition for CML_OSPF_DEBUG_RIB_T";
}

typedef  CML_OSPF_DEBUG_RIB_CLIENT_T {
    type bits {
        bit redistribute {
            position 1;
            description "RIB redistribute";
        }
        bit client {
            position 2;
            description "RIB Client";
        }
    }
    description "type definition for CML_OSPF_DEBUG_RIB_CLIENT_T";
}

typedef  CML_NSM_ERR_DISABLE_TIMEOUT_T {
    type enumeration {
        enum disable {
            value 0;
            description "disable";
        }
        enum enable {
            value 1;
            description "enable";
        }
    }
    description "type definition for CML_NSM_ERR_DISABLE_TIMEOUT_T";
}

typedef  CML_ON_OFF_T {
    type enumeration {
        enum off {
            value 0;
            description "off";
        }
        enum on {
            value 1;
            description "on";
        }
    }
    description "type definition for CML_ON_OFF_T";
}

typedef  CML_OSPF_DEBUG_ROUTE_T {
    type bits {
        bit spf {
            position 0;
            description "SPF calculation information";
        }
        bit ia {
            position 1;
            description "Inter-Area route calculation information";
        }
        bit ase {
            position 2;
            description "External route calculation information";
        }
        bit install {
            position 3;
            description "Route installation information";
        }
        bit spf-terse {
            position 4;
            description "SPF Calculation terse information";
        }
    }
    description "type definition for CML_OSPF_DEBUG_ROUTE_T";
}

typedef  CML_OSPF_DEBUG_REDIST_T {
    type bits {
        bit detail {
            position 0;
            description "OSPF redistribute Details";
        }
        bit terse {
            position 1;
            description "OSPF redistribute Terse";
        }
    }
    description "type definition for CML_OSPF_DEBUG_REDIST_T";
}

typedef  CML_OSPF_DEBUG_GRACEFUL_T {
    type bits {
        bit detail {
            position 0;
            description "OSPF graceful-restart Details";
        }
        bit terse {
            position 1;
            description "OSPF graceful-restart Terse";
        }
    }
    description "type definition for CML_OSPF_DEBUG_GRACEFUL_T";
}

typedef  CML_OSPF_MD5_T {
    type enumeration {
        enum 0 {
            value 1;
            description "Unencrypted password (key)";
        }
    }
    description "type definition for CML_OSPF_MD5_T";
}

typedef  CML_OSPF_DEFAULT_INFO_T {
    type enumeration {
        enum originate {
            value 1;
            description "Distribute a default route";
        }
    }
    description "type definition for CML_OSPF_DEFAULT_INFO_T";
}

typedef  CML_ROUTEMAP_EXTERNAL_TYPE_LIST {
    type enumeration {
        enum type-1 {
            value 1;
            description "Match OSPF External Type 1 metrics";
        }
        enum type-2 {
            value 2;
            description "Match OSPF External Type 2 metrics";
        }
    }
    description "type definition for CML_ROUTEMAP_EXTERNAL_TYPE_LIST";
}

typedef  CML_ROUTEMAP_OSPF_METRIC_TYPE_LIST {
    type enumeration {
        enum type-1 {
            value 1;
            description "Match OSPF External Type 1 metrics";
        }
        enum type-2 {
            value 2;
            description "Match OSPF External Type 2 metrics";
        }
    }
    description "type definition for CML_ROUTEMAP_OSPF_METRIC_TYPE_LIST";
}

typedef  CML_ROUTEMAP_ISIS_METRIC_TYPE_LIST {
    type enumeration {
        enum internal {
            value 1;
            description "IS-IS internal metric type";
        }
        enum external {
            value 2;
            description "IS-IS external metric type";
        }
    }
    description "type definition for CML_ROUTEMAP_ISIS_METRIC_TYPE_LIST";
}

typedef  CML_LEVEL_LIST_T {
    type enumeration {
        enum level-1 {
            value 1;
            description "Export into a level-1 area";
        }
        enum level-2 {
            value 2;
            description "Export into level-2 sub-domain";
        }
        enum level-1-2 {
            value 3;
            description "Export into level-1 and level-2";
        }
    }
    description "type definition for CML_LEVEL_LIST_T";
}

typedef  CML_ROUTEMAP_ORIGIN_CODE {
    type enumeration {
        enum egp {
            value 1;
            description "remote EGP";
        }
        enum igp {
            value 2;
            description "local IGP";
        }
        enum incomplete {
            value 3;
            description "unknown heritage";
        }
    }
    description "type definition for CML_ROUTEMAP_ORIGIN_CODE";
}

typedef  CML_ROUTEMAP_COST_COMPARISION_T {
    type enumeration {
        enum igp {
            value 1;
            description "Compare following IGP cost comparison";
        }
        enum pre-bestpath {
            value 2;
            description "Compare before all other steps in bestpath calculation";
        }
    }
    description "type definition for CML_ROUTEMAP_COST_COMPARISION_T";
}

typedef  CML_FORWARDTYPE_T {
    type enumeration {
        enum null0 {
            value 0;
            description "Forward to no interface";
        }
        enum tunnel-te {
            value 1;
            description "Forward to MPLS-TE tunnel";
        }
    }
    description "type definition for CML_FORWARDTYPE_T";
}

typedef  CML_ROUTEMAP_COMMUNITY_LIST_T {
    type union {
        type int32 {
            range "1..99 | 100..500";

        }
        type string {

        }
    }
    description "type definition for CML_ROUTEMAP_COMMUNITY_LIST_T";
}

typedef  CML_ROUT_MAP_EXACT_MATCH_T {
    type enumeration {
        enum exact-match {
            value 1;
            description "Do exact matching of communities";
        }
    }
    description "type definition for CML_ROUT_MAP_EXACT_MATCH_T";
}

typedef  CML_ROUTEMAP_MATCH_T {
    type union {
        type inet:ipv6-address {

        }
        type string {

        }
    }
    description "type definition for CML_ROUTEMAP_MATCH_T";
}

typedef  CML_COMMUNITY_T {

    type string;
    description "type definition for CML_COMMUNITY_T";
}

typedef  CML_ROUTEMAP_COMMUNITY_T {
    type union {
        type uint32 {
            range "65536..4294901759";

        }
        type CML_COMMUNITY_T {

        }
    }
    description "type definition for CML_ROUTEMAP_COMMUNITY_T";
}

typedef  CML_ROUTEMAP_ADDITIVE_LIST_T {
    type enumeration {
        enum default {
            value 0;
            description "BGP community attribute set to default";
        }
        enum additive {
            value 1;
            description "BGP community attribute";
        }
    }
    description "type definition for CML_ROUTEMAP_ADDITIVE_LIST_T";
}

typedef  CML_AP_RMAP_ALL_T {
    type enumeration {
        enum all {
            value 1;
            description "Select all available paths";
        }
    }
    description "type definition for CML_AP_RMAP_ALL_T";
}

typedef  CML_AP_RMAP_BEST_T {

    type uint8{
     range 0..255;
    }
    description "type definition for CML_AP_RMAP_BEST_T";
}

typedef  CML_ADDPATH_RMAP_T {
    type union {
        type CML_AP_RMAP_BEST_T {

        }
        type CML_AP_RMAP_ALL_T {

        }
    }
    description "type definition for CML_ADDPATH_RMAP_T";
}

typedef  CML_BRIDGE_FORWARD_T {
    type enumeration {
        enum bridge-blocked {
            value 0;
            description "put all ports of the bridge into blocked state";
        }
        enum bridge-forward {
            value 1;
            description "put all ports of the bridge into forwarding state";
        }
    }
    description "type definition for CML_BRIDGE_FORWARD_T";
}

typedef  CML_BCKBONE_BRIDGE_GRP_T {
    type enumeration {
        enum backbone {
            value 0;
            description "Specifies the backbone bridge group name";
        }
    }
    description "type definition for CML_BCKBONE_BRIDGE_GRP_T";
}

typedef  CML_BRIDGE_GRP_T {

    type uint8{
     range 0..255;
    }
    description "type definition for CML_BRIDGE_GRP_T";
}

typedef  CML_BRIDGE_GRP_CMD_T {
    type union {
        type CML_BRIDGE_GRP_T {

        }
        type CML_BCKBONE_BRIDGE_GRP_T {

        }
    }
    description "type definition for CML_BRIDGE_GRP_CMD_T";
}

typedef  CML_BRIDGE_SPANMODE_T {
    type enumeration {
        enum stp {
            value 1;
            description "IEEE 801.1Q spanning-tree protocol";
        }
        enum stp-vlan-bridge {
            value 2;
            description "IEEE 801.1Q spanning-tree protocol";
        }
        enum rstp {
            value 3;
            description "IEEE 801.1w rapid spanning-tree protocol";
        }
        enum rstp-vlan-bridge {
            value 4;
            description "IEEE 801.1w rapid spanning-tree protocol";
        }
        enum mstp {
            value 5;
            description "IEEE 802.1s multiple spanning-tree protocol";
        }
        enum provider-rstp {
            value 6;
            description "IEEE 802.1s rapid spanning-tree protocol";
        }
        enum provider-mstp {
            value 7;
            description "IEEE 802.1s rapid spanning-tree protocol";
        }
        enum rpvst+ {
            value 12;
            description "IEEE 801.1w rapid per vlan spanning-tree protocol";
        }
    }
    description "type definition for CML_BRIDGE_SPANMODE_T";
}

typedef  CML_ALLOWED_FORBIDDEN_T {
    type enumeration {
        enum forbidden {
            value 0;
            description "forbidden list";
        }
        enum allowed {
            value 1;
            description "allowed list";
        }
    }
    description "type definition for CML_ALLOWED_FORBIDDEN_T";
}

typedef  CML_ADD_REMOVE_T {
    type enumeration {
        enum remove {
            value 0;
            description "Deletes the interface from the vlan list";
        }
        enum add {
            value 1;
            description "Adds the interface in the vlan list";
        }
    }
    description "type definition for CML_ADD_REMOVE_T";
}

typedef  CML_VLANSTACK_T {
    type enumeration {
        enum customer-edge-port {
            value 4;
            description "Set the switching characteristics of the Layer2 interface to Customer-edge port";
        }
        enum provider-port {
            value 6;
            description "Set the switching characteristics of the Layer2 interface to Provider port";
        }
    }
    description "type definition for CML_VLANSTACK_T";
}

typedef  CML_ENABLEBPDURX_T {
    type enumeration {
        enum disableBPDUrx {
            value 0;
            description "disableBPDUrx";
        }
        enum enableBPDUrx {
            value 1;
            description "enableBPDUrx";
        }
    }
    description "type definition for CML_ENABLEBPDURX_T";
}

typedef  CML_ACLTYPE_T {
    type enumeration {
        enum mac {
            value 1;
            description "Mac access-list";
        }
        enum ip {
            value 3;
            description "ip access-list";
        }
        enum ipv6 {
            value 4;
            description "ipv6 access-list";
        }
    }
    description "type definition for CML_ACLTYPE_T";
}

typedef  CML_BRIDGE_T {

    type uint8{
     range 0..255;
    }
    description "type definition for CML_BRIDGE_T";
}

typedef  CML_BRIDGE_ID_T {
    type union {
        type CML_BRIDGE_T {

        }
        type CML_SPANNING_TREE_T {

        }
    }
    description "type definition for CML_BRIDGE_ID_T";
}

typedef  CML_BRIDGE_BACKBONE_ID_T {
    type union {
        type CML_BRIDGE_BCKBONE_T {

        }
        type CML_BACKBONE_T {

        }
    }
    description "type definition for CML_BRIDGE_BACKBONE_ID_T";
}

typedef  CML_BACKBONE_T {
    type enumeration {
        enum backbone {
            value 33;
            description "Specifies the backbone bridge group name";
        }
    }
    description "type definition for CML_BACKBONE_T";
}

typedef  CML_BRIDGE_BCKBONE_T {

    type uint8{
     range 0..255;
    }
    description "type definition for CML_BRIDGE_BCKBONE_T";
}

typedef  CML_ACTIONTYPE_T {
    type enumeration {
        enum forward {
            value 101;
            description "Forward";
        }
        enum drop {
            value 102;
            description "Drop";
        }
        enum redirect {
            value 103;
            description "redirect to";
        }
    }
    description "type definition for CML_ACTIONTYPE_T";
}

typedef  CML_VLAN_OPT_TYPE_T {
    type enumeration {
        enum add {
            value 1;
            description "adds the specified vlans to te-region";
        }
        enum delete {
            value 2;
            description "deletes the vlans from te-region";
        }
    }
    description "type definition for CML_VLAN_OPT_TYPE_T";
}

typedef  CML_TESI_MODE_T {
    type enumeration {
        enum passive {
            value 1;
            description "mode from active to passive";
        }
        enum active {
            value 2;
            description "mode from passive to active";
        }
    }
    description "type definition for CML_TESI_MODE_T";
}

typedef  CML_TESI_TYPE_T {
    type enumeration {
        enum dynamic {
            value 1;
            description "type from static to dynamic";
        }
        enum static {
            value 2;
            description "type from dynamic to static";
        }
    }
    description "type definition for CML_TESI_TYPE_T";
}

typedef  CML_PNPADDDEL_T {
    type enumeration {
        enum add {
            value 1;
            description "deletes the subsequest interface from this tesi";
        }
        enum delete {
            value 2;
            description "interface name";
        }
    }
    description "type definition for CML_PNPADDDEL_T";
}

typedef  CML_NSMVLANPORT_MODE_T {
    type enumeration {
        enum pnp {
            value 6;
            description "Default vlan configured on Provider Network Port";
        }
        enum cnp {
            value 8;
            description "Default vlan configured on Customer Network Port";
        }
        enum pip {
            value 10;
            description "Default vlan configured on Provider Instance Port";
        }
        enum cbp {
            value 11;
            description "";
        }
    }
    description "type definition for CML_NSMVLANPORT_MODE_T";
}

typedef  CML_CMBCKINSTANCE_T {

    type uint32{
     range 1..16777214;
    }
    description "type definition for CML_CMBCKINSTANCE_T";
}

typedef  CML_SPANNING_TREE_T {
    type enumeration {
        enum spanning-tree {
            value 0;
            description "default bridge commands";
        }
    }
    description "type definition for CML_SPANNING_TREE_T";
}

typedef  CML_INSTANCE_NAME_T {

    type string;
    description "type definition for CML_INSTANCE_NAME_T";
}

typedef  CML_SVLAN_INSTANCE_NAME_T {
    type union {
        type CML_CMBCKINSTANCE_T {

        }
        type CML_INSTANCE_NAME_T {

        }
    }
    description "type definition for CML_SVLAN_INSTANCE_NAME_T";
}

typedef  CML_CMBCKBONE_INSTANCE_T {
    type union {
        type CML_CMBCKINSTANCE_T {

        }
        type CML_INSTANCE_IFNAME_T {

        }
    }
    description "type definition for CML_CMBCKBONE_INSTANCE_T";
}

typedef  CML_INSTANCE_IFNAME_T {

    type string;
    description "type definition for CML_INSTANCE_IFNAME_T";
}

typedef  CML_VIP_TRAFFIC_T {
    type enumeration {
        enum all {
            value 0;
            description "Ingress/egress allowed";
        }
        enum ingress {
            value 1;
            description "Configures ingress service flow";
        }
        enum egress {
            value 2;
            description "Configures egress service flow";
        }
    }
    description "type definition for CML_VIP_TRAFFIC_T";
}

typedef  CML_BEB_MODE_T {
    type enumeration {
        enum tx {
            value 0;
            description "Transmit only";
        }
        enum rx {
            value 1;
            description "Receive only";
        }
        enum rxtx {
            value 2;
            description "Transmit and Receive";
        }
        enum none {
            value 3;
            description "Neither tx nor rx";
        }
    }
    description "type definition for CML_BEB_MODE_T";
}

typedef  CML_BRIDGE_BACKBONE_T {
    type union {
        type CML_BACKBONE_T {

        }
        type uint8 {
            range "1..32";

        }
    }
    description "type definition for CML_BRIDGE_BACKBONE_T";
}

typedef  CML_ASPTEISID_T {
    type enumeration {
        enum add {
            value 1;
            description "adds a new ISID to this aps group";
        }
        enum delete {
            value 2;
            description "deletes an existing ISID from this aps group";
        }
    }
    description "type definition for CML_ASPTEISID_T";
}

typedef  CML_CNPINS_T {

    type uint32{
     range 1..16777214;
    }
    description "type definition for CML_CNPINS_T";
}

typedef  CML_OSPF_NBMA_ROW_STATUS {
    type enumeration {
        enum row-status-active {
            value 1;
            description "Row status Active";
        }
        enum row-status-notinservice {
            value 2;
            description "Row status Not in service";
        }
        enum row-status-notready {
            value 3;
            description "Row Status not ready";
        }
        enum row-status-createandgo {
            value 4;
            description "Row status create and go";
        }
        enum row-status-createandwait {
            value 5;
            description "Row status Create and wait";
        }
        enum row-status-destroy {
            value 6;
            description "Row status Destroy";
        }
    }
    description "type definition for CML_OSPF_NBMA_ROW_STATUS";
}

typedef  CML_OSPF_IF_STATE {
    type enumeration {
        enum enabled {
            value 1;
            description "OSPF_API_STATUS_ENABLED";
        }
        enum disabled {
            value 2;
            description "OSPF_API_STATUS_DISABLED";
        }
    }
    description "type definition for CML_OSPF_IF_STATE";
}

typedef  CML_CNP_INSTANCE_T {
    type union {
        type CML_CNPINS_T {

        }
        type CML_CNP_INSTANCE_IFNAME_T {

        }
    }
    description "type definition for CML_CNP_INSTANCE_T";
}

typedef  CML_CNP_INSTANCE_IFNAME_T {

    type string;
    description "type definition for CML_CNP_INSTANCE_IFNAME_T";
}

typedef  SNMP_TRAP_OPTIONS_T {
    type enumeration {
        enum link {
            value 1;
            description "Module notifications enable";
        }
        enum link-linkDown {
            value 2;
            description "Module notifications enable,IETF Link state down notification";
        }
        enum link-linkUp {
            value 3;
            description "Module notifications enable,IETF Link state up notification";
        }
        enum snmp {
            value 4;
            description "Module notifications enable";
        }
        enum snmp-authentication {
            value 5;
            description "Module notifications enable,SNMP authentication trap";
        }
        enum mpls {
            value 6;
            description "mpls notification trap";
        }
        enum pw {
            value 7;
            description "pw notification trap";
        }
        enum pwdelete {
            value 8;
            description "pwdelete notification trap";
        }
        enum rsvp {
            value 9;
            description "rsvp notification trap";
        }
        enum ospf {
            value 10;
            description "ospf notification trap";
        }
        enum bgp {
            value 11;
            description "bgp notification trap";
        }
        enum isis {
            value 12;
            description "isis notification trap";
        }
        enum vrrp {
            value 13;
            description "vrrp notification trap";
        }
        enum vxlan {
            value 14;
            description "vxlan notification trap";
        }
        enum ospf6 {
            value 15;
            description "ospf6 notification trap";
        }
    }
    description "type definition for SNMP_TRAP_OPTIONS_T";
}

typedef  CML_VR_PROTOCOL_T {
    type bits {
        bit rip {
            position 1;
            description "Routing Information Protocol (RIP)";
        }
        bit ipv6-rip {
            position 2;
            description "Internet Protocol Version 6,Routing Information Protocol (RIP)";
        }
        bit ospf {
            position 3;
            description "Open Shortest Path First (OSPF)";
        }
        bit ipv6-ospf {
            position 4;
            description "Internet Protocol Version 6, Open Shortest Path First (OSPF)";
        }
        bit isis {
            position 5;
            description "Intermediate System - Intermediate System (IS-IS)";
        }
        bit pim {
            position 6;
            description "Protocol Independent Multicast (PIM)";
        }
        bit vrrp {
            position 7;
            description "Virtual Router Redundancy Protocol (VRRP)";
        }
        bit bgp {
            position 9;
            description "Border Gateway Protocol (BGP)";
        }
    }
    description "type definition for CML_VR_PROTOCOL_T";
}

typedef  CML_LDP_ENABLE_IPV4_TYPE_T {
    type enumeration {
        enum disable-ldp {
            value 0;
            description "Disable LDP on interface";
        }
        enum enable-ldp {
            value 1;
            description "Enable LDP on Interface";
        }
    }
    description "type definition for CML_LDP_ENABLE_IPV4_TYPE_T";
}

typedef  CML_LDP_ENABLE_IPV6_TYPE_T {
    type enumeration {
        enum disable-ldp {
            value 0;
            description "Disable LDP on interface";
        }
        enum enable-ldp {
            value 1;
            description "Enable LDP on Interface";
        }
    }
    description "type definition for CML_LDP_ENABLE_IPV6_TYPE_T";
}

typedef  CML_LDP_IGP_SYNC_T {
    type enumeration {
        enum igp-sync {
            value 0;
            description "Enable/Disable LDP for IPV4";
        }
        enum no-igp-sync {
            value 1;
            description "Enable/Disable LDP for IPV6";
        }
    }
    description "type definition for CML_LDP_IGP_SYNC_T";
}

typedef  CML_MD5_ENCRYPT_PASSWORD_T {
    type enumeration {
        enum 0 {
            value 0;
            description "Configure password type 0 to store password as a clear text";
        }
        enum 7 {
            value 7;
            description "Configure password type 7 to encrypt password while storing";
        }
        enum 7-encrypt {
            value 8;
            description "password type 7, Enter encrypted password";
        }
    }
    description "type definition for CML_MD5_ENCRYPT_PASSWORD_T";
}

typedef  CML_RSVP_INSTANCE_T {
    type enumeration {
        enum rsvp {
            value 1;
            description "Resource Reservation Protocol (RSVP)";
        }
    }
    description "type definition for CML_RSVP_INSTANCE_T";
}

typedef  CML_LDP_INSTANCE_T {
    type enumeration {
        enum ldp {
            value 1;
            description "Label Distribution Protocol (LDP)";
        }
    }
    description "type definition for CML_LDP_INSTANCE_T";
}

typedef  CML_LDP_DEBUG_T {
    type bits {
        bit events {
            position 0;
            description "LDP events";
        }
        bit fsm {
            position 1;
            description "Enable FSM debugging";
        }
        bit hexdump {
            position 2;
            description "Enable HEXDUMP";
        }
        bit dsm {
            position 3;
            description "Enable Downstream SM";
        }
        bit usm {
            position 4;
            description "LDP Upstream SM";
        }
        bit tsm {
            position 5;
            description "LDP Trunk SM";
        }
        bit qos {
            position 6;
            description "LDP QoS";
        }
        bit nsm {
            position 7;
            description "NSM messages";
        }
        bit advertise-labels {
            position 8;
            description "List IP access lists of advertise-labels";
        }
        bit cspf {
            position 9;
            description "CSPF messages";
        }
        bit vc-usm {
            position 10;
            description "LDP VC Info,LDP VC USM";
        }
        bit vc-dsm {
            position 11;
            description "LDP VC Info,LDP VC DSM";
        }
        bit graceful-restart {
            position 12;
            description "LDP Graceful Restart Debugging";
        }
        bit rib {
            position 13;
            description "RIB messages";
        }
    }
    description "type definition for CML_LDP_DEBUG_T";
}

typedef  CML_LDP_DEBUG_PACKET_T {
    type bits {
        bit notification {
            position 0;
            description "LDP notification packet";
        }
        bit hello {
            position 1;
            description "LDP hello packet";
        }
        bit initialization {
            position 2;
            description "LDP initialization packet";
        }
        bit keepalive {
            position 3;
            description "LDP keepalive packet";
        }
        bit address {
            position 4;
            description "LDP address (withdraw) packet";
        }
        bit label {
            position 5;
            description "LDP label mapping/request(abort)/withdraw/release packet";
        }
    }
    description "type definition for CML_LDP_DEBUG_PACKET_T";
}

typedef  CML_PCEP_DEBUG_T {
    type enumeration {
        enum events {
            value 0;
            description "Enable/Disable debug pcep events";
        }
        enum error {
            value 1;
            description "Enable/Disable debug pcep error";
        }
        enum packet {
            value 2;
            description "Enable/Disable debug pcep packet";
        }
        enum timer {
            value 3;
            description "Enable/Disable debug pcep timer";
        }
        enum all {
            value 4;
            description "Enable/Disable debug pcep all";
        }
    }
    description "type definition for CML_PCEP_DEBUG_T";
}

typedef  CML_PCEP_LSP_STATE_TIMEOUT_T {
    type union {
        type CML_PCEP_INFINITY_T {

        }
        type uint32 {
            range "1..600";

        }
    }
    description "type definition for CML_PCEP_LSP_STATE_TIMEOUT_T";
}

typedef  CML_PCEP_INFINITY_T {
    type enumeration {
        enum infinity {
            value 0;
            description "Maintain the LSP state infinitely";
        }
    }
    description "type definition for CML_PCEP_INFINITY_T";
}

typedef  CML_PCEP_DLG_RECOVERY_TYPE_T {
    type enumeration {
        enum local-control {
            value 1;
            description "Signaling the LSP using local CSPF";
        }
        enum removal {
            value 2;
            description "Cleanup of the LSP";
        }
    }
    description "type definition for CML_PCEP_DLG_RECOVERY_TYPE_T";
}

typedef  CML_LDP_FAILURE_T {
    type enumeration {
        enum restart {
            value 0;
            description "Restart LSP";
        }
    }
    description "type definition for CML_LDP_FAILURE_T";
}

typedef  CML_LDP_CSPF_T {
    type enumeration {
        enum no-cspf {
            value 0;
            description "Use Hop-by-Hop Routing";
        }
        enum cspf {
            value 1;
            description "Use CSPF for Path Computation";
        }
    }
    description "type definition for CML_LDP_CSPF_T";
}

typedef  CML_LDP_LOOSE_T {
    type enumeration {
        enum strict {
            value 0;
            description "Make this node strict";
        }
        enum loose {
            value 1;
            description "Make this node loose";
        }
    }
    description "type definition for CML_LDP_LOOSE_T";
}

typedef  CML_LDP_TRUNK_ADMIN_GROUP_T {
    type enumeration {
        enum exclude-any {
            value 0;
            description "Exclude any of the administrative groups from the explicit route";
        }
        enum include-any {
            value 1;
            description "Include any of the administrative groups in the explicit route";
        }
    }
    description "type definition for CML_LDP_TRUNK_ADMIN_GROUP_T";
}

typedef  CML_LDP_IP_ADDR_T {
    type union {
        type inet:ipv4-address {

        }
        type inet:ipv6-address {

        }
    }
    description "type definition for CML_LDP_IP_ADDR_T";
}

typedef  CML_LDP_ICCP_DEBUG_T {
    type bits {
        bit events {
            position 0;
            description "Events";
        }
        bit fsm {
            position 1;
            description "FSM";
        }
        bit hexdump {
            position 2;
            description "hexdump of messages";
        }
        bit packet {
            position 3;
            description "Packets";
        }
        bit bfd {
            position 4;
            description "BFD";
        }
    }
    description "type definition for CML_LDP_ICCP_DEBUG_T";
}

typedef  CML_RSVP_PATH_TYPE_T {
    type enumeration {
        enum mpls {
            value 0;
            description "Path type is mpls";
        }
        enum gmpls {
            value 1;
            description "Path type is gmpls";
        }
    }
    description "type definition for CML_RSVP_PATH_TYPE_T";
}

typedef  CML_RSVP_TRUNK_ADDRFAMILY_T {
    type enumeration {
        enum ipv4 {
            value 0;
            description "IPv4 address family trunk";
        }
        enum ipv6 {
            value 1;
            description "IPv6 address family trunk";
        }
        enum gmpls {
            value 2;
            description "GMPLS enabled trunk";
        }
    }
    description "type definition for CML_RSVP_TRUNK_ADDRFAMILY_T";
}

typedef  CML_PATH_SEL_TYPE_T {
    type enumeration {
        enum te {
            value 0;
            description "te-- cspf computated path";
        }
        enum igp {
            value 1;
            description "igp - cspf computated path";
        }
    }
    description "type definition for CML_PATH_SEL_TYPE_T";
}

typedef  CML_RSVP_RESTART_STATUS_T {
    type enumeration {
        enum disable {
            value 0;
            description "Disable Graceful Restart";
        }
        enum enable {
            value 1;
            description "Enable Graceful Restart";
        }
    }
    description "type definition for CML_RSVP_RESTART_STATUS_T";
}

typedef  CML_RSVP_DETOUR_IDEN_T {
    type enumeration {
        enum sender-template {
            value 1;
            description "Sender Template specific detour identification method";
        }
        enum path {
            value 2;
            description "Path Secific detour identification method (using detour object)";
        }
    }
    description "type definition for CML_RSVP_DETOUR_IDEN_T";
}

typedef  CML_RSVP_P2MP_ADDR_T {
    type enumeration {
        enum ipv4 {
            value 1;
            description "IPV4 address family trunk";
        }
        enum ipv6 {
            value 2;
            description "IPV6 address family trunk";
        }
    }
    description "type definition for CML_RSVP_P2MP_ADDR_T";
}

typedef  CML_RSVP_CSPF_TYPE_T {
    type enumeration {
        enum no-cspf {
            value 0;
            description "Use Hop-by-Hop Routing";
        }
        enum cspf {
            value 1;
            description "Use CSPF for Path Computation";
        }
    }
    description "type definition for CML_RSVP_CSPF_TYPE_T";
}

typedef  CML_RSVP_TRUNK_METRIC_TYPE_T {
    type enumeration {
        enum igp-metric {
            value 1;
            description "(admin state down)";
        }
        enum te-metric {
            value 2;
            description "(interface is not running)";
        }
        enum hop-count {
            value 3;
            description "(monitored circuit is down)";
        }
    }
    description "type definition for CML_RSVP_TRUNK_METRIC_TYPE_T";
}

typedef  CML_RSVP_CSPF_STATUS_T {
    type enumeration {
        enum no-cspf {
            value 0;
            description "Disable CSPF usage for RSVP";
        }
        enum cspf {
            value 1;
            description "Enable CSPF usage for RSVP";
        }
    }
    description "type definition for CML_RSVP_CSPF_STATUS_T";
}

typedef  CML_LOOP_DETECTION_T {
    type enumeration {
        enum no-loop-detection {
            value 0;
            description "Disable loop detection";
        }
        enum loop-detection {
            value 1;
            description "Enable loop detection";
        }
    }
    description "type definition for CML_LOOP_DETECTION_T";
}

typedef  CML_RSVP_PHP_T {
    type enumeration {
        enum no-php {
            value 0;
            description "Disable Penultimate-Hop-Popping for router";
        }
        enum php {
            value 1;
            description "Enable Penultimate-Hop-Popping for router";
        }
    }
    description "type definition for CML_RSVP_PHP_T";
}

typedef  CML_RSVP_PREEMP_T {
    type enumeration {
        enum less-lsp-preempted {
            value 0;
            description "less lsp preempted";
        }
        enum less-unused-bandwidth {
            value 1;
            description "less unused bandwidth preempted";
        }
    }
    description "type definition for CML_RSVP_PREEMP_T";
}

typedef  CML_REFRESH_PATH_PARSING_T {
    type enumeration {
        enum no-refresh-path-parsing {
            value 0;
            description "Disable parsing of refresh PATH messages";
        }
        enum refresh-path-parsing {
            value 1;
            description "Enable parsing of refresh PATH messages";
        }
    }
    description "type definition for CML_REFRESH_PATH_PARSING_T";
}

typedef  CML_REFRESH_RESV_PARSING_T {
    type enumeration {
        enum no-refresh-resv-parsing {
            value 0;
            description "Disable parsing of refresh RESV messages";
        }
        enum refresh-resv-parsing {
            value 1;
            description "Enable parsing of refresh RESV messages";
        }
    }
    description "type definition for CML_REFRESH_RESV_PARSING_T";
}

typedef  CML_RSVP_DEBUG_T {
    type bits {
        bit events {
            position 0;
            description "RSVP events";
        }
        bit packet {
            position 1;
            description "RSVP packet";
        }
        bit packet-in {
            position 2;
            description "RSVP packet,Incoming RSVP packet";
        }
        bit packet-out {
            position 3;
            description "RSVP packet, Outgoing RSVP packet";
        }
        bit hexdump {
            position 4;
            description "RSVP Hexdump";
        }
        bit nsm {
            position 5;
            description "NSM messages";
        }
        bit cspf {
            position 6;
            description "CSPF messages";
        }
        bit fsm-egress {
            position 7;
            description "Enable FSM debugging,Enable RSVP Egress FSM debugging";
        }
        bit fsm-transit-downstream {
            position 8;
            description "Enable FSM debugging, Enable RSVP Transit FSM debugging, Enable RSVP Transit Downstream FSM debugging";
        }
        bit fsm-transit-upstream {
            position 9;
            description "Enable FSM debugging,Enable RSVP Transit FSM debugging,Enable RSVP Transit Upstream FSM dugging";
        }
        bit fsm-ingress {
            position 10;
            description "Enable FSM debugging, Enable RSVP Ingress FSM debugging";
        }
        bit rib {
            position 11;
            description "RIB messages";
        }
        bit neighbor {
            position 12;
            description "RSVP neighbor";
        }
    }
    description "type definition for CML_RSVP_DEBUG_T";
}

typedef  CML_L2_PROTOCOL_T {
    type enumeration {
        enum stp {
            value 0;
            description "Spanning Tree Protocols";
        }
        enum lacp {
            value 7;
            description "Link Aggregation (LACP)";
        }
        enum dot1x {
            value 8;
            description "Port Authentication (802.1 X)";
        }
        enum lldp {
            value 9;
            description "Link layer discovery protocol";
        }
        enum efm {
            value 11;
            description "Ethernet first mile (Link OAM)";
        }
        enum elmi {
            value 12;
            description "Ethernet local management interface";
        }
    }
    description "type definition for CML_L2_PROTOCOL_T";
}

typedef  CML_DISCARD_L2_PROTOCOL_T {
    type enumeration {
        enum stp {
            value 0;
            description "Spanning Tree Protocols";
        }
        enum lacp {
            value 7;
            description "Link Aggregation (LACP)";
        }
        enum dot1x {
            value 8;
            description "Port Authentication (802.1 X)";
        }
        enum lldp {
            value 9;
            description "Link layer discovery protocol";
        }
        enum pause {
            value 13;
            description "Pause frames";
        }
        enum efm {
            value 14;
            description "Ethernet first mile (Link OAM)";
        }
        enum elmi {
            value 15;
            description "Ethernet local management interface";
        }
        enum synce {
            value 17;
            description "Synchronous Ethernet";
        }
    }
    description "type definition for CML_DISCARD_L2_PROTOCOL_T";
}

typedef  CML_PVLAN_MODE_T {
    type enumeration {
        enum host {
            value 1;
            description "host port";
        }
        enum promiscuous {
            value 2;
            description "promiscuous port";
        }
        enum trunk {
            value 3;
            description "pvlan-trunk port";
        }
    }
    description "type definition for CML_PVLAN_MODE_T";
}

typedef  CML_PVLAN_TYPE_T {
    type enumeration {
        enum community {
            value 1;
            description "vlan type to community";
        }
        enum isolated {
            value 2;
            description "vlan type to isolated";
        }
        enum primary {
            value 3;
            description "vlan type to primary";
        }
        enum association {
            value 4;
            description "association to secondary vlan";
        }
    }
    description "type definition for CML_PVLAN_TYPE_T";
}

typedef  CML_PCEP_PATH_DYN_T {
    type enumeration {
        enum pce {
            value 1;
            description "path computation element";
        }
    }
    description "type definition for CML_PCEP_PATH_DYN_T";
}

typedef  CML_PVLAN_ADD_REMOVE_TYPE_T {
    type enumeration {
        enum add {
            value 1;
            description "add secondary vlan";
        }
        enum remove {
            value 2;
            description "remove secondary vlan";
        }
    }
    description "type definition for CML_PVLAN_ADD_REMOVE_TYPE_T";
}

typedef  CML_CVLAN_CONFIG_T {
    type bits {
        bit default {
            position 0;
            description "Default value";
        }
        bit untagged-pep {
            position 1;
            description "Configure PEP as Untagged for this CVLAN";
        }
        bit untagged-cep {
            position 2;
            description "Configure CEP as Untagged for this CVLAN";
        }
    }
    description "type definition for CML_CVLAN_CONFIG_T";
}

typedef  CML_OEP_VLAN_TYPE_T {
    type enumeration {
        enum cvlan {
            value 1;
            description "configure C-VLAN oep-mapping table entry";
        }
        enum svlan {
            value 2;
            description "configure S-VLAN oep-mapping table entry";
        }
    }
    description "type definition for CML_OEP_VLAN_TYPE_T";
}

typedef  CML_EDGE_VLAN_TYPE_T {
    type enumeration {
        enum allowed {
            value 1;
            description "Set the Layer2 interface as trunk";
        }
        enum default-svlan {
            value 2;
            description "Set the default SVLAN for the interface";
        }
    }
    description "type definition for CML_EDGE_VLAN_TYPE_T";
}

typedef  CML_ACL_PORT_OPERATIONS_T {
    type enumeration {
        enum eq {
            value 1;
            description "port equal to";
        }
        enum neq {
            value 2;
            description "port not equal to";
        }
        enum lt {
            value 3;
            description "port less than";
        }
        enum gt {
            value 4;
            description "port greater than";
        }
        enum range {
            value 5;
            description "range";
        }
    }
    description "type definition for CML_ACL_PORT_OPERATIONS_T";
}

typedef  CML_ACL_FILTER_ACTION_T {
    type enumeration {
        enum deny {
            value 0;
            description "Specify packets to reject";
        }
        enum permit {
            value 1;
            description "Specify packets to forward";
        }
    }
    description "type definition for CML_ACL_FILTER_ACTION_T";
}

typedef  CML_ACL_DEFAULT_FILTER_ACTION_T {
    type enumeration {
        enum deny-all {
            value 3;
            description "Specify all packets to reject";
        }
        enum permit-all {
            value 4;
            description "Specify all packets to forward";
        }
    }
    description "type definition for CML_ACL_DEFAULT_FILTER_ACTION_T";
}

typedef  CML_ACL_ARP_TYPE_T {
    type enumeration {
        enum none {
            value 0;
            description "Match any ARP packets";
        }
    }
    description "type definition for CML_ACL_ARP_TYPE_T";
}

typedef  CML_ACL_ANY_T {
    type enumeration {
        enum any {
            value 0;
            description "Wildcard entry matching all addresses";
        }
    }
    description "type definition for CML_ACL_ANY_T";
}

typedef  CML_ACL_IPV4_HOST_T {

    type string;
    description "type definition for CML_ACL_IPV4_HOST_T";
}

typedef  CML_ACL_ANY_IPV4_ADDR_T {
    type union {
        type CML_ACL_ANY_T {

        }
        type CML_ACL_IPV4_HOST_T {

        }
        type inet:ipv4-prefix {

        }
    }
    description "type definition for CML_ACL_ANY_IPV4_ADDR_T";
}

typedef  CML_ACL_IPV6_HOST_T {

    type string;
    description "type definition for CML_ACL_IPV6_HOST_T";
}

typedef  CML_ACL_ANY_IPV6_ADDR_T {
    type union {
        type CML_ACL_ANY_T {

        }
        type CML_ACL_IPV6_HOST_T {

        }
        type inet:ipv6-prefix {

        }
    }
    description "type definition for CML_ACL_ANY_IPV6_ADDR_T";
}

typedef  CML_ACL_UDP_KEYWORD_ENUM_T {
    type enumeration {
        enum echo {
            value 7;
            description "echo";
        }
        enum discard {
            value 9;
            description "discard";
        }
        enum time {
            value 37;
            description "time";
        }
        enum nameserver {
            value 42;
            description "nameserver";
        }
        enum tacacs {
            value 49;
            description "tacacs";
        }
        enum domain {
            value 53;
            description "domain";
        }
        enum bootps {
            value 67;
            description "bootps";
        }
        enum bootpc {
            value 68;
            description "bootpc";
        }
        enum tftp {
            value 69;
            description "tftp";
        }
        enum sunrpc {
            value 111;
            description "sunrpc";
        }
        enum netbios_ns {
            value 137;
            description "netbios_ns";
        }
        enum netbios_dgm {
            value 138;
            description "netbios_dgm";
        }
        enum netbios_ss {
            value 139;
            description "netbios_ss";
        }
        enum snmp {
            value 161;
            description "snmp";
        }
        enum snmptrap {
            value 162;
            description "snmptrap";
        }
        enum xdmcp {
            value 177;
            description "xdmcp";
        }
        enum dnsix {
            value 195;
            description "dnsix";
        }
        enum mobile_ip {
            value 434;
            description "mobile_ip";
        }
        enum pim_auto_rp {
            value 496;
            description "pim_auto_rp";
        }
        enum isakmp {
            value 500;
            description "isakmp";
        }
        enum biff {
            value 512;
            description "biff";
        }
        enum who {
            value 513;
            description "who";
        }
        enum syslog {
            value 514;
            description "syslog";
        }
        enum talk {
            value 517;
            description "talk";
        }
        enum rip {
            value 520;
            description "rip";
        }
        enum non500_isakmp {
            value 4500;
            description "non500_isakmp";
        }
    }
    description "type definition for CML_ACL_UDP_KEYWORD_ENUM_T";
}

typedef  CML_ACL_UDP_KEYWORD_T {
    type union {
        type CML_ACL_UDP_KEYWORD_ENUM_T {

        }
        type uint32 {
            range "0..65535";

        }
    }
    description "type definition for CML_ACL_UDP_KEYWORD_T";
}

typedef  CML_ACL_TCP_KEYWORD_ENUM_T {
    type enumeration {
        enum echo {
            value 7;
            description "echo";
        }
        enum discard {
            value 9;
            description "discard";
        }
        enum daytime {
            value 13;
            description "daytime";
        }
        enum chargen {
            value 19;
            description "chargen";
        }
        enum ftp_data {
            value 20;
            description "ftp_data";
        }
        enum ftp {
            value 21;
            description "ftp";
        }
        enum ssh {
            value 22;
            description "ssh";
        }
        enum telnet {
            value 23;
            description "telnet";
        }
        enum smtp {
            value 25;
            description "smtp";
        }
        enum time {
            value 37;
            description "time";
        }
        enum whois {
            value 43;
            description "whois";
        }
        enum tacacs {
            value 49;
            description "tacacs";
        }
        enum domain {
            value 53;
            description "domain";
        }
        enum gopher {
            value 70;
            description "gopher";
        }
        enum finger {
            value 79;
            description "finger";
        }
        enum www {
            value 80;
            description "www";
        }
        enum hostname {
            value 101;
            description "hostname";
        }
        enum pop2 {
            value 109;
            description "pop2";
        }
        enum pop3 {
            value 110;
            description "pop3";
        }
        enum sunrpc {
            value 111;
            description "sunrpc";
        }
        enum ident {
            value 113;
            description "ident";
        }
        enum nntp {
            value 119;
            description "nntp";
        }
        enum bgp {
            value 179;
            description "bgp";
        }
        enum irc {
            value 194;
            description "irc";
        }
        enum pim_auto_rp {
            value 496;
            description "pim_auto_rp";
        }
        enum exec {
            value 512;
            description "exec";
        }
        enum login {
            value 513;
            description "login";
        }
        enum cmd {
            value 514;
            description "cmd";
        }
        enum lpd {
            value 515;
            description "lpd";
        }
        enum talk {
            value 517;
            description "talk";
        }
        enum uucp {
            value 540;
            description "uucp";
        }
        enum klogin {
            value 543;
            description "klogin";
        }
        enum kshell {
            value 544;
            description "kshell";
        }
        enum drip {
            value 3949;
            description "drip";
        }
    }
    description "type definition for CML_ACL_TCP_KEYWORD_ENUM_T";
}

typedef  CML_ACL_TCP_KEYWORD_T {
    type union {
        type CML_ACL_TCP_KEYWORD_ENUM_T {

        }
        type uint32 {
            range "0..65535";

        }
    }
    description "type definition for CML_ACL_TCP_KEYWORD_T";
}

typedef  CML_ACL_IP_PROTO_ENUM_T {
    type enumeration {
        enum icmp {
            value 1;
            description "icmp";
        }
        enum igmp {
            value 2;
            description "igmp";
        }
        enum ipip {
            value 4;
            description "ipip";
        }
        enum tcp {
            value 6;
            description "tcp";
        }
        enum udp {
            value 17;
            description "udp";
        }
        enum ipv6ip {
            value 41;
            description "ipv6ip";
        }
        enum rsvp {
            value 46;
            description "rsvp";
        }
        enum gre {
            value 47;
            description "gre";
        }
        enum esp {
            value 50;
            description "esp";
        }
        enum ahp {
            value 51;
            description "ahp";
        }
        enum eigrp {
            value 88;
            description "eigrp";
        }
        enum ospf {
            value 89;
            description "ospf";
        }
        enum pim {
            value 103;
            description "pim";
        }
        enum ipcomp {
            value 108;
            description "ipcomp";
        }
        enum vrrp {
            value 112;
            description "vrrp";
        }
        enum any {
            value 256;
            description "any";
        }
    }
    description "type definition for CML_ACL_IP_PROTO_ENUM_T";
}

typedef  CML_ACL_IP_PROTO_T {
    type union {
        type CML_ACL_IP_PROTO_ENUM_T {

        }
        type uint16 {
            range "0..255";

        }
    }
    description "type definition for CML_ACL_IP_PROTO_T";
}

typedef  CML_ACL_IPV6_PROTO_ENUM_T {
    type enumeration {
        enum ipv6ip {
            value 4;
            description "ipv6ip";
        }
        enum tcp {
            value 6;
            description "tcp";
        }
        enum udp {
            value 17;
            description "udp";
        }
        enum ipv6ipv6 {
            value 41;
            description "ipv6ipv6";
        }
        enum rsvp {
            value 46;
            description "rsvp";
        }
        enum gre {
            value 47;
            description "gre";
        }
        enum esp {
            value 50;
            description "esp";
        }
        enum ahp {
            value 51;
            description "ahp";
        }
        enum icmpv6 {
            value 58;
            description "icmpv6";
        }
        enum ospf {
            value 89;
            description "ospf";
        }
        enum pim {
            value 103;
            description "pim";
        }
        enum ipcomp {
            value 108;
            description "ipcomp";
        }
        enum vrrp {
            value 112;
            description "vrrp";
        }
        enum sctp {
            value 132;
            description "sctp";
        }
        enum any {
            value 256;
            description "any";
        }
    }
    description "type definition for CML_ACL_IPV6_PROTO_ENUM_T";
}

typedef  CML_ACL_IPV6_PROTO_T {
    type union {
        type CML_ACL_IPV6_PROTO_ENUM_T {

        }
        type uint16 {
            range "0..255";

        }
    }
    description "type definition for CML_ACL_IPV6_PROTO_T";
}

typedef  CML_ACL_DSCP_ENUM_T {
    type enumeration {
        enum default {
            value 0;
            description "default";
        }
        enum cs1 {
            value 8;
            description "cs1";
        }
        enum af11 {
            value 10;
            description "af11";
        }
        enum af12 {
            value 12;
            description "af12";
        }
        enum af13 {
            value 14;
            description "af13";
        }
        enum cs2 {
            value 16;
            description "cs2";
        }
        enum af21 {
            value 18;
            description "af21";
        }
        enum af22 {
            value 20;
            description "af22";
        }
        enum af23 {
            value 22;
            description "af23";
        }
        enum cs3 {
            value 24;
            description "cs3";
        }
        enum af31 {
            value 26;
            description "af31";
        }
        enum af32 {
            value 28;
            description "af32";
        }
        enum af33 {
            value 30;
            description "af33";
        }
        enum cs4 {
            value 32;
            description "cs4";
        }
        enum af41 {
            value 34;
            description "af41";
        }
        enum af42 {
            value 36;
            description "af42";
        }
        enum af43 {
            value 38;
            description "af43";
        }
        enum cs5 {
            value 40;
            description "cs5";
        }
        enum ef {
            value 46;
            description "ef";
        }
        enum cs6 {
            value 48;
            description "cs6";
        }
        enum cs7 {
            value 56;
            description "cs7";
        }
    }
    description "type definition for CML_ACL_DSCP_ENUM_T";
}

typedef  CML_ACL_DSCP_T {
    type union {
        type CML_ACL_DSCP_ENUM_T {

        }
        type int8 {
            range "0..63";

        }
    }
    description "type definition for CML_ACL_DSCP_T";
}

typedef  CML_ACL_PRECEDENCE_ENUM_T {
    type enumeration {
        enum routine {
            value 0;
            description "routine";
        }
        enum priority {
            value 1;
            description "priority";
        }
        enum immediate {
            value 2;
            description "immediate";
        }
        enum flash {
            value 3;
            description "flash";
        }
        enum flashoverride {
            value 4;
            description "flashoverride";
        }
        enum critical {
            value 5;
            description "critical";
        }
        enum internet {
            value 6;
            description "internet";
        }
        enum network {
            value 7;
            description "network";
        }
    }
    description "type definition for CML_ACL_PRECEDENCE_ENUM_T";
}

typedef  CML_ACL_PRECEDENCE_T {
    type union {
        type CML_ACL_PRECEDENCE_ENUM_T {

        }
        type int8 {
            range "0..7";

        }
    }
    description "type definition for CML_ACL_PRECEDENCE_T";
}

typedef  CML_ACL_ICMP_OPTIONS_T {
    type enumeration {
        enum administratively-prohibited {
            value 1;
            description "administrativelyProhibited";
        }
        enum alternate-address {
            value 2;
            description "alternateAddress";
        }
        enum conversion-error {
            value 3;
            description "conversionError";
        }
        enum dod-host-prohibited {
            value 4;
            description "dodHostProhibited";
        }
        enum dod-net-prohibited {
            value 5;
            description "dodNetProhibited";
        }
        enum echo {
            value 6;
            description "echo";
        }
        enum echo-reply {
            value 7;
            description "echoReply";
        }
        enum general-parameter-problem {
            value 8;
            description "generalParameterProblem";
        }
        enum host-isolated {
            value 9;
            description "hostIsolated";
        }
        enum host-precedence-unreachable {
            value 10;
            description "hostPrecedenceUnreachable";
        }
        enum host-redirect {
            value 11;
            description "hostRedirect";
        }
        enum host-tos-redirect {
            value 12;
            description "hostTosRedirect";
        }
        enum host-tos-unreachable {
            value 13;
            description "hostTosUnreachable";
        }
        enum host-unknown {
            value 14;
            description "hostUnknown";
        }
        enum host-unreachable {
            value 15;
            description "hostUnreachable";
        }
        enum information-reply {
            value 16;
            description "informationReply";
        }
        enum information-request {
            value 17;
            description "informationRequest";
        }
        enum mask-reply {
            value 18;
            description "maskReply";
        }
        enum mask-request {
            value 19;
            description "maskRequest";
        }
        enum mobile-redirect {
            value 20;
            description "mobileRedirect";
        }
        enum net-redirect {
            value 21;
            description "netRedirect";
        }
        enum net-tos-redirect {
            value 22;
            description "netTosRedirect";
        }
        enum net-tos-unreachable {
            value 23;
            description "netTosUnreachable";
        }
        enum net-unreachable {
            value 24;
            description "netUnreachable";
        }
        enum network-unknown {
            value 25;
            description "networkUnknown";
        }
        enum no-room-for-option {
            value 26;
            description "noRoomForOption";
        }
        enum option-missing {
            value 27;
            description "optionMissing";
        }
        enum packet-too-big {
            value 28;
            description "packetTooBig";
        }
        enum parameter-problem {
            value 29;
            description "parameterProblem";
        }
        enum port-unreachable {
            value 30;
            description "portUnreachable";
        }
        enum precedence-unreachable {
            value 31;
            description "precedenceUnreachable";
        }
        enum protocol-unreachable {
            value 32;
            description "protocolUnreachable";
        }
        enum reassembly-timeout {
            value 33;
            description "reassemblyTimeout";
        }
        enum redirect {
            value 34;
            description "redirect";
        }
        enum router-advertisement {
            value 35;
            description "routerAdvertisement";
        }
        enum router-solicitation {
            value 36;
            description "routerSolicitation";
        }
        enum source-quench {
            value 37;
            description "sourceQuench";
        }
        enum source-route-failed {
            value 38;
            description "sourceRouteFailed";
        }
        enum time-exceeded {
            value 39;
            description "timeExceeded";
        }
        enum timestamp-reply {
            value 40;
            description "timestampReply";
        }
        enum timestamp-request {
            value 41;
            description "timestampRequest";
        }
        enum traceroute {
            value 42;
            description "traceroute";
        }
        enum ttl-exceeded {
            value 43;
            description "ttlExceeded";
        }
        enum unreachable {
            value 44;
            description "unreachable";
        }
    }
    description "type definition for CML_ACL_ICMP_OPTIONS_T";
}

typedef  CML_ACL_ICMPV6_OPTIONS_T {
    type enumeration {
        enum beyond-scope {
            value 0;
            description "beyond-scope";
        }
        enum destination-unreachable {
            value 1;
            description "destination-unreachable";
        }
        enum echo-reply {
            value 2;
            description "echo-reply";
        }
        enum echo-request {
            value 3;
            description "echo-request";
        }
        enum header {
            value 4;
            description "header";
        }
        enum hop-limit {
            value 5;
            description "hop-limit";
        }
        enum mld-query {
            value 6;
            description "mld-query";
        }
        enum mld-reduction {
            value 7;
            description "mld-reduction";
        }
        enum mld-report {
            value 8;
            description "mld-report";
        }
        enum nd-na {
            value 9;
            description "nd-na";
        }
        enum nd-ns {
            value 10;
            description "nd-ns";
        }
        enum next-header {
            value 11;
            description "next-header";
        }
        enum no-admin {
            value 12;
            description "no-admin";
        }
        enum no-route {
            value 13;
            description "no-route";
        }
        enum packet-too-big {
            value 14;
            description "packet-too-big";
        }
        enum parameter-option {
            value 15;
            description "parameter-option";
        }
        enum parameter-problem {
            value 16;
            description "parameter-problem";
        }
        enum port-unreachable {
            value 17;
            description "port-unreachable";
        }
        enum reassembly-timeout {
            value 18;
            description "reassembly-timeout";
        }
        enum redirect {
            value 19;
            description "redirect";
        }
        enum renum-command {
            value 20;
            description "renum-command";
        }
        enum renum-result {
            value 21;
            description "renum-result";
        }
        enum renum-seq-number {
            value 22;
            description "renum-seq-number";
        }
        enum router-advertisement {
            value 23;
            description "router-advertisement";
        }
        enum router-renumbering {
            value 24;
            description "router-renumbering";
        }
        enum router-solicitation {
            value 25;
            description "router-solicitation";
        }
        enum time-exceeded {
            value 26;
            description "time-exceeded";
        }
        enum unreachable {
            value 27;
            description "unreachable";
        }
    }
    description "type definition for CML_ACL_ICMPV6_OPTIONS_T";
}

typedef  CML_ACL_TCP_FLAGS_T {
    type bits {
        bit fin {
            position 0;
            description "fin";
        }
        bit syn {
            position 1;
            description "syn";
        }
        bit rst {
            position 2;
            description "rst";
        }
        bit psh {
            position 3;
            description "psh";
        }
        bit ack {
            position 4;
            description "ack";
        }
        bit urg {
            position 5;
            description "urg";
        }
        bit established {
            position 6;
            description "established";
        }
    }
    description "type definition for CML_ACL_TCP_FLAGS_T";
}

typedef  CML_ACL_ANY_MAC_ADDR_T {
    type union {
        type CML_ACL_ANY_T {

        }
        type CML_MAC_ADDR_T {

        }
    }
    description "type definition for CML_ACL_ANY_MAC_ADDR_T";
}

typedef  CML_ACL_ETHER_TYPE_ENUM_T {
    type enumeration {
        enum ipv4 {
            value 2048;
            description "ipv4";
        }
        enum vines-echo {
            value 2991;
            description "vines-echo";
        }
        enum etype-6000 {
            value 24576;
            description "etype-6000";
        }
        enum mop-dump {
            value 24577;
            description "mop-dump";
        }
        enum mop-console {
            value 24578;
            description "mop-console";
        }
        enum decnet-iv {
            value 24579;
            description "decnet-iv";
        }
        enum lat {
            value 24580;
            description "lat";
        }
        enum diagnostic {
            value 24581;
            description "diagnostic";
        }
        enum lavc-sca {
            value 24583;
            description "lavc-sca";
        }
        enum etype-8042 {
            value 32834;
            description "etype-8042";
        }
        enum appletalk {
            value 32923;
            description "appletalk";
        }
        enum aarp {
            value 33011;
            description "aarp";
        }
        enum ipv6 {
            value 34525;
            description "ipv6";
        }
        enum mpls {
            value 34886;
            description "mpls";
        }
    }
    description "type definition for CML_ACL_ETHER_TYPE_ENUM_T";
}

typedef  CML_ACL_ETHER_TYPE_T {
    type union {
        type CML_ACL_ETHER_TYPE_ENUM_T {

        }
        type string {

        }
    }
    description "type definition for CML_ACL_ETHER_TYPE_T";
}

typedef  CML_ACL_TYPES_T {
    type enumeration {
        enum mac {
            value 1;
            description "Configure MAC parameters";
        }
        enum ip {
            value 3;
            description "Internet Protocol (IP)";
        }
        enum ipv6 {
            value 4;
            description "Internet Protocol version 6 (IPv6)";
        }
        enum arp {
            value 5;
            description "Configure ARP parameters";
        }
    }
    description "type definition for CML_ACL_TYPES_T";
}

typedef  CML_VTY_ACL_TYPES_T {
    type enumeration {
        enum ip {
            value 0;
            description "Internet Protocol (IP)";
        }
        enum ipv6 {
            value 1;
            description "Internet Protocol version 6 (IPv6)";
        }
    }
    description "type definition for CML_VTY_ACL_TYPES_T";
}

typedef  CML_ACL_PACKET_DIR_T {
    type enumeration {
        enum in {
            value 0;
            description "Specify to filter incoming packets";
        }
        enum out {
            value 1;
            description "Specify to filter outgoing packets";
        }
    }
    description "type definition for CML_ACL_PACKET_DIR_T";
}

typedef  CML_AUTH_PORT_SEC_MODE {
    type enumeration {
        enum filter {
            value 0;
            description "Set port to filter mode";
        }
        enum shutdown {
            value 1;
            description "Set port to disable mode";
        }
    }
    description "type definition for CML_AUTH_PORT_SEC_MODE";
}

typedef  CML_AUTH_CTRL_DIR_T {
    type enumeration {
        enum in {
            value 0;
            description "Discard receive packets from supplicant";
        }
        enum both {
            value 1;
            description "Discard receive and transmit packets from supplicant";
        }
    }
    description "type definition for CML_AUTH_CTRL_DIR_T";
}

typedef  CML_AUTH_PORT_CTRL {
    type enumeration {
        enum force-unauthorized {
            value 0;
            description "Force port state to unauthorized";
        }
        enum force-authorized {
            value 1;
            description "Force port state to authorized";
        }
        enum auto {
            value 2;
            description "Allow port client to negotiate authentication";
        }
    }
    description "type definition for CML_AUTH_PORT_CTRL";
}

typedef  CML_DOT1X_DEBUG_T {
    type bits {
        bit event {
            position 0;
            description "802.1X events";
        }
        bit timer {
            position 1;
            description "802.1X timer";
        }
        bit packet {
            position 2;
            description "802.1X packets";
        }
        bit nsm {
            position 3;
            description "802.1X NSM information";
        }
    }
    description "type definition for CML_DOT1X_DEBUG_T";
}

typedef  CML_RIP_DEBUG_T {
    type bits {
        bit events {
            position 1;
            description "RIP events";
        }
        bit packet {
            position 2;
            description "RIP packets";
        }
        bit packet-send {
            position 3;
            description "RIP packets,RIP send packets";
        }
        bit packet-recv {
            position 4;
            description "RIP packets, RIP receive packets";
        }
        bit packet-detail {
            position 5;
            description "RIP packets, Detailed information display";
        }
        bit packet-send-detail {
            position 6;
            description "RIP packets, RIP send packets, Detailed information display";
        }
        bit packet-recv-detail {
            position 7;
            description "RIP packets, RIP receive packets, Detailed information display";
        }
        bit nsm {
            position 8;
            description "RIP NSM information";
        }
        bit rib {
            position 9;
            description "RIP RIB information";
        }
        bit bfd {
            position 10;
            description "RIP BFD information";
        }
    }
    description "type definition for CML_RIP_DEBUG_T";
}

typedef  CML_RIP_ROUTE_T {
    type enumeration {
        enum kernel {
            value 1;
            description "Kernel routes";
        }
        enum connected {
            value 2;
            description "Connected";
        }
        enum static {
            value 3;
            description "Static routes";
        }
        enum isis {
            value 4;
            description "ISO IS-IS";
        }
        enum ospf {
            value 5;
            description "Open Shortest Path First (OSPF)";
        }
        enum bgp {
            value 6;
            description "Border Gateway Protocol (BGP)";
        }
        enum rip {
            value 7;
            description "Routing Information Protocol (RIP)";
        }
        enum all {
            value 8;
            description "all of the RIP routing tabl";
        }
    }
    description "type definition for CML_RIP_ROUTE_T";
}

typedef  CML_RIP_INSTANCE_T {
    type enumeration {
        enum rip {
            value 1;
            description "Routing Information Protocol (RIP)";
        }
    }
    description "type definition for CML_RIP_INSTANCE_T";
}

typedef  CML_RIP_DIRECTION_T {
    type enumeration {
        enum in {
            value 0;
            description "For incoming updates";
        }
        enum out {
            value 1;
            description "For outgoing updates";
        }
    }
    description "type definition for CML_RIP_DIRECTION_T";
}

typedef  CML_RIP_DIST_TYPE_T {
    type enumeration {
        enum in {
            value 0;
            description "Filter incoming routing updates";
        }
        enum out {
            value 1;
            description "Filter incoming routing updates";
        }
    }
    description "type definition for CML_RIP_DIST_TYPE_T";
}

typedef  CML_RIP_METRIC_T {
    type enumeration {
        enum disable {
            value 0;
            description "Disables updating metric consistent with Cisco";
        }
        enum enable {
            value 1;
            description "Enables updating metric consistent with Cisco";
        }
    }
    description "type definition for CML_RIP_METRIC_T";
}

typedef  CML_RIP_AUTH_MODE_T {
    type enumeration {
        enum text {
            value 2;
            description "Clear text authentication";
        }
        enum md5 {
            value 3;
            description "Keyed message digest";
        }
    }
    description "type definition for CML_RIP_AUTH_MODE_T";
}

typedef  CML_RIP_SPLIT_HORIZON_T {
    type enumeration {
        enum split-horizon {
            value 0;
            description "Perform split horizon";
        }
        enum split-horizon-poisoned {
            value 1;
            description "Perform split horizon,Perform poisoned reverse";
        }
    }
    description "type definition for CML_RIP_SPLIT_HORIZON_T";
}

typedef  CML_RIP_DEFAULT_ORIGINATE_T {
    type enumeration {
        enum originate {
            value 0;
            description "Distribute a default route";
        }
        enum originate-always {
            value 1;
            description "Distribute a default route,Always advertise default route";
        }
    }
    description "type definition for CML_RIP_DEFAULT_ORIGINATE_T";
}

typedef  CML_RIP_RECV_VERSION_TYPE_T {
    type enumeration {
        enum 1 {
            value 1;
            description "RIP version 1";
        }
        enum 2 {
            value 2;
            description "RIP version 2";
        }
        enum 1-2 {
            value 3;
            description "RIP version 1, RIP version 2";
        }
        enum 2-1 {
            value 5;
            description "RIP version 2, RIP version 1";
        }
    }
    description "type definition for CML_RIP_RECV_VERSION_TYPE_T";
}

typedef  CML_RIP_SEND_VERSION_TYPE_T {
    type enumeration {
        enum 1 {
            value 1;
            description "RIP version 1";
        }
        enum 2 {
            value 2;
            description "RIP version 2";
        }
        enum 1-2 {
            value 3;
            description "RIP version 1, RIP version 2";
        }
        enum 1-compatible {
            value 4;
            description "RIPv1-compatible";
        }
        enum 2-1 {
            value 5;
            description "RIP version 2, RIP version 1";
        }
    }
    description "type definition for CML_RIP_SEND_VERSION_TYPE_T";
}

typedef  CML_RIP_REDIST_PROTOS_T {
    type enumeration {
        enum kernel {
            value 0;
            description "Kernel routes";
        }
        enum connected {
            value 1;
            description "Connected";
        }
        enum static {
            value 2;
            description "Static routes";
        }
        enum ospf {
            value 3;
            description "Open Shortest Path First (OSPF)";
        }
        enum isis {
            value 4;
            description "ISO IS-IS";
        }
        enum bgp {
            value 5;
            description "Border Gateway Protocol (BGP)";
        }
    }
    description "type definition for CML_RIP_REDIST_PROTOS_T";
}

typedef  CML_RIP_VRF_REDIST_PROTOS_T {
    type enumeration {
        enum connected {
            value 1;
            description "Connected";
        }
        enum static {
            value 2;
            description "Static routes";
        }
        enum ospf {
            value 3;
            description "Open Shortest Path First (OSPF)";
        }
        enum bgp {
            value 5;
            description "Border Gateway Protocol (BGP)";
        }
    }
    description "type definition for CML_RIP_VRF_REDIST_PROTOS_T";
}

typedef  CML_NSM_LOAD_TRILL_T {
    type enumeration {
        enum outer-l2 {
            value 1;
            description "TRILL outer l2 header (outer SMAC, outer DMAC, outer VLAN)";
        }
        enum inner-l2 {
            value 2;
            description "TRILL inner l2 header (inner SMAC, inner DMAC, inner VLAN, trill tunnel)";
        }
        enum inner-l3 {
            value 3;
            description "TRILL inner l3 header (inner SIP, inner DIP, L4 srx/dest port)";
        }
    }
    description "type definition for CML_NSM_LOAD_TRILL_T";
}

typedef  CML_NSM_LOAD_HASH_T {
    type enumeration {
        enum crc16-bisync {
            value 0;
            description "16-bit CRC16 using the BISYNC Polynomial (DEFAULT)";
        }
        enum crc16-ccitt {
            value 1;
            description "16-bit CRC16 using the CCITT Polynomial";
        }
        enum crc32-lo {
            value 2;
            description "16 LSBs of computated CRC32";
        }
        enum crc32-hi {
            value 3;
            description "16 MSBs of computated CRC32";
        }
    }
    description "type definition for CML_NSM_LOAD_HASH_T";
}

typedef  CML_LACP_DEBUG_TYPE_T {
    type bits {
        bit event {
            position 0;
            description "event - do not echo events to console";
        }
        bit cli {
            position 1;
            description "cli - do not echo commands to console";
        }
        bit timer {
            position 2;
            description "timer - do not echo timer expiry to console";
        }
        bit sync {
            position 3;
            description "sync - do not echo synchronization to console";
        }
        bit packet {
            position 4;
            description "packet - do not echo packet contents to console";
        }
        bit tx {
            position 5;
            description "tx - do not echo transmission of lacpdus to console";
        }
        bit rx {
            position 6;
            description "rx - do not echo receving of lacpdus to console";
        }
        bit ha {
            position 7;
            description "ha - do not echo High availability events to console";
        }
    }
    description "type definition for CML_LACP_DEBUG_TYPE_T";
}

typedef  CML_ALLOWEDVLAN_T {
    type enumeration {
        enum none {
            value 1;
            description "Add a VLAN to Xmit/Tx through the Layer2 interface";
        }
        enum all {
            value 2;
            description "Allow no VLANs to Xmit/Rx through the Layer2 interface";
        }
    }
    description "type definition for CML_ALLOWEDVLAN_T";
}

typedef  CML_SWVLANOPER_T {
    type enumeration {
        enum remove {
            value 1;
            description "Remove a VLAN to Xmit/Rx through the Layer2 interface";
        }
        enum except {
            value 2;
            description "Allow all VLANs except VID to Xmit/Rx through the Layer2 interface";
        }
        enum all {
            value 3;
            description "Allow all VLANs to Xmit/Rx through the Layer2 interface";
        }
        enum add {
            value 4;
            description "Allow specified VLANs to Xmit/Rx through the Layer2 interface";
        }
        enum none {
            value 5;
            description "Allow none of the VLANs to Xmit/Rx through the Layer2 interface";
        }
    }
    description "type definition for CML_SWVLANOPER_T";
}

typedef  CML_DHCPSNOOP_DEBUG_T {
    type bits {
        bit event {
            position 0;
            description "enable event debugs";
        }
        bit rx {
            position 1;
            description "enable rx debugs";
        }
        bit tx {
            position 2;
            description "enable tx debugs";
        }
        bit packet {
            position 3;
            description "enable packet debug";
        }
    }
    description "type definition for CML_DHCPSNOOP_DEBUG_T";
}

typedef  CML_DHCP_VALIDATION_T {
    type enumeration {
        enum src-mac {
            value 0;
            description "source mac validation";
        }
        enum dst-mac {
            value 1;
            description "destination mac validation";
        }
        enum ip {
            value 2;
            description "arp ip address validation";
        }
    }
    description "type definition for CML_DHCP_VALIDATION_T";
}

typedef  CML_COMMON_ENABLE_DISABLE_T {
    type enumeration {
        enum Disabled {
            value 0;
            description "Disabled";
        }
        enum Enabled {
            value 1;
            description "Enabled";
        }
    }
    description "type definition for CML_COMMON_ENABLE_DISABLE_T";
}

typedef  CML_COMMON_FLAGS_T {
    type enumeration {
        enum False {
            value 0;
            description "None";
        }
        enum True {
            value 1;
            description "None";
        }
    }
    description "type definition for CML_COMMON_FLAGS_T";
}

typedef  CML_UNI_ENNI_T {
    type enumeration {
        enum uni {
            value 1;
            description "Configure UNI Parameter";
        }
        enum enni {
            value 2;
            description "Configure ENNI Parameter";
        }
    }
    description "type definition for CML_UNI_ENNI_T";
}

typedef  CML_UNI_ENNI_TYPE_T {
    type enumeration {
        enum leaf {
            value 1;
            description "Leaf";
        }
        enum root {
            value 2;
            description "Root";
        }
        enum trunk {
            value 3;
            description "Trunk";
        }
    }
    description "type definition for CML_UNI_ENNI_TYPE_T";
}

typedef  CML_UNI_SERVICE_T {
    type enumeration {
        enum bundle {
            value 1;
            description "UNI supports bundling without multiplexing";
        }
        enum all-to-one {
            value 2;
            description "UNI supports all to one bundling";
        }
        enum multiplex {
            value 3;
            description "UNI supports multiplexing without bundling";
        }
    }
    description "type definition for CML_UNI_SERVICE_T";
}

typedef  CML_UNI_ENABLE_DISABLE_T {
    type enumeration {
        enum disable {
            value 0;
            description "uni type disable will set the default uni type";
        }
        enum enable {
            value 1;
            description "uni type enable will update the uni type";
        }
    }
    description "type definition for CML_UNI_ENABLE_DISABLE_T";
}

typedef  CML_OEP_MAP_TYPE_T {
    type enumeration {
        enum uni-oep {
            value 2;
            description "Configure OVC endpoint map";
        }
        enum enni-oep {
            value 4;
            description "Configure OEP mapping table";
        }
    }
    description "type definition for CML_OEP_MAP_TYPE_T";
}

typedef  CML_BIND_T {
    type enumeration {
        enum delete {
            value 0;
            description "Command delete rule from a group";
        }
        enum add {
            value 1;
            description "Command add rule to a group";
        }
    }
    description "type definition for CML_BIND_T";
}

typedef  CML_ETHERTYPE_T {
    type enumeration {
        enum ETHERTYPE {
            value 0;
            description "Valid ethernet protocol number (0x600-0xFFFF)";
        }
        enum ip {
            value 2048;
            description "IP (0x0800)";
        }
        enum x25 {
            value 2053;
            description "CCITT X.25 (0x0805)";
        }
        enum arp {
            value 2054;
            description "Address Resolution Protocol (0x0806)";
        }
        enum g8bpqx25 {
            value 2303;
            description "G8BPQ AX.25 (0x08FF)";
        }
        enum ieeepup {
            value 2560;
            description "Xerox IEEE802.3 PUP (0x0a00)";
        }
        enum ieeeaddrtrans {
            value 2561;
            description "Xerox IEEE802.3 PUP Address Translation (0x0a01)";
        }
        enum dec {
            value 24576;
            description "DEC Assigned (0x6000)";
        }
        enum decdnadumpload {
            value 24577;
            description "DEC DNA Dump/Load (0x6001)";
        }
        enum decdnaremoteconsole {
            value 24578;
            description "DEC DNA Remote Console (0x6002)";
        }
        enum decdnarouting {
            value 24579;
            description "DEC DNA Routing (0x6003)";
        }
        enum declat {
            value 24580;
            description "DEC LAT (0x6004)";
        }
        enum decdiagnostics {
            value 24581;
            description "DEC Diagnostics (0x6005)";
        }
        enum rarp {
            value 32821;
            description "Reverse Address Resolution Protocol (0x8035)";
        }
        enum atalkddp {
            value 32923;
            description "Appletalk DDP (0x809B)";
        }
        enum atalkaarp {
            value 33011;
            description "Appletalk AARP (0x80F3)";
        }
        enum ipx {
            value 33079;
            description "IPX (0x8137)";
        }
        enum ipv6 {
            value 34525;
            description "IPv6 (0x86DD)";
        }
        enum atmmulti {
            value 34892;
            description "MultiProtocol Over ATM (0x884c)";
        }
        enum pppdiscovery {
            value 34915;
            description "PPPoE discovery (0x8863)";
        }
        enum pppsession {
            value 34916;
            description "PPPoE session (0x8864)";
        }
        enum atmtransport {
            value 34948;
            description "Frame-based ATM Transport (0x8884)";
        }
    }
    description "type definition for CML_ETHERTYPE_T";
}

typedef  CML_CE_SVLAN_T {
    type enumeration {
        enum ce-vlan {
            value 1;
            description "Preservation for Customer Edge VLAN";
        }
        enum svlan {
            value 2;
            description "Preservation for Service VLAN";
        }
    }
    description "type definition for CML_CE_SVLAN_T";
}

typedef  CML_OVC_TYPE_T {
    type enumeration {
        enum preserve-cos {
            value 1;
            description "Preserve Cos";
        }
        enum preserve-vlanid {
            value 2;
            description "Preserve vlan-id";
        }
    }
    description "type definition for CML_OVC_TYPE_T";
}

typedef  CML_MSTP_ENUM_T {
    type enumeration {
        enum te-msti {
            value 65;
            description "MSTI to be the traffic engineering MSTI instance";
        }
        enum instance-spbm {
            value 4092;
            description "instance,spbm instance";
        }
        enum instance-spbv {
            value 4093;
            description "instance,spbv instance";
        }
    }
    description "type definition for CML_MSTP_ENUM_T";
}

typedef  CML_MSTP_RANGE_T {

    type uint16{
     range 1..63;
    }
    description "type definition for CML_MSTP_RANGE_T";
}

typedef  CML_MSTP_INSTANCE_T {
    type union {
        type CML_MSTP_ENUM_T {

        }
        type CML_MSTP_RANGE_T {

        }
    }
    description "type definition for CML_MSTP_INSTANCE_T";
}

typedef  CML_VXLAN_PORT_T {
    type enumeration {
        enum port-only {
            value 1;
            description "Configures the port access interface";
        }
    }
    description "type definition for CML_VXLAN_PORT_T";
}

typedef  CML_VXLAN_HOST_T {
    type enumeration {
        enum Dynamic {
            value 0;
            description "Host type is Dynamic";
        }
        enum Static-Local {
            value 1;
            description "Host type is Static Local";
        }
        enum Remote-Dynamic {
            value 2;
            description "Host type is Evpn Dynamic";
        }
        enum Remote-Static {
            value 3;
            description "Host type is Evpn Static";
        }
        enum Static-Remote {
            value 4;
            description "Host type is Static Remote";
        }
    }
    description "type definition for CML_VXLAN_HOST_T";
}

typedef  CML_VXLAN_DF_STATUS_T {
    type enumeration {
        enum --- {
            value 0;
            description "Default DF status";
        }
        enum DF {
            value 1;
            description "Designated Forwarder";
        }
        enum NON-DF {
            value 2;
            description "Non Designated Forwarder";
        }
    }
    description "type definition for CML_VXLAN_DF_STATUS_T";
}

typedef  CML_VXLAN_STATIC_HOST_STATE_T {
    type enumeration {
        enum Inactive {
            value 1;
            description "static host state Inactive";
        }
        enum Active {
            value 2;
            description "static host state Active";
        }
        enum Conflict {
            value 4;
            description "static host state Conflict";
        }
        enum Learnt-Conflict {
            value 8;
            description "static host state Learnt Conflict";
        }
        enum Discard-Inactive {
            value 16;
            description "static host state Discard Inactive";
        }
    }
    description "type definition for CML_VXLAN_STATIC_HOST_STATE_T";
}

typedef  CML_CMM_CPU_TYPE_T {
    type enumeration {
        enum cpu-usage1 {
            value 1;
            description "Set CPU Usage for past 1 min";
        }
        enum cpu-usage5 {
            value 5;
            description "Set CPU Usage for past 5 min";
        }
        enum cpu-usage15 {
            value 15;
            description "Set CPU Usage for past 15 min";
        }
    }
    description "type definition for CML_CMM_CPU_TYPE_T";
}

typedef  CML_CMM_TRANS_TYPE_T {
    type enumeration {
        enum sfp {
            value 1;
            description "trans type sfp";
        }
        enum qsfp {
            value 2;
            description "trans type qsfp";
        }
        enum xfp {
            value 3;
            description "trans type xfp";
        }
        enum pon-xfp {
            value 4;
            description "trans type pon xfp";
        }
        enum unknown {
            value 5;
            description "trans type unknown";
        }
    }
    description "type definition for CML_CMM_TRANS_TYPE_T";
}

typedef  CML_CMM_TRANS_IDENTIFIER_T {
    type enumeration {
        enum unknown {
            value 1;
            description "trans identifier unknown";
        }
        enum gbic {
            value 2;
            description "trans identifier gbic";
        }
        enum soldered-to-motherboard {
            value 3;
            description "trans identifier soldered-to-motherboard";
        }
        enum sfp-or-sfpplus-or-sfp28 {
            value 4;
            description "trans identifier sfp-or-sfpplus-or-sfp28";
        }
        enum xbi-300pin {
            value 5;
            description "trans identifier xbi-300pin";
        }
        enum xenpak {
            value 6;
            description "trans identifier xenpak";
        }
        enum xfp {
            value 7;
            description "trans identifier xfp";
        }
        enum xff {
            value 8;
            description "trans identifier xff";
        }
        enum xfpe {
            value 9;
            description "trans identifier xfpe";
        }
        enum xpak {
            value 10;
            description "trans identifier xpak";
        }
        enum x2 {
            value 11;
            description "trans identifier x2";
        }
        enum dwdmsfp-or-dwdmsfpplus {
            value 12;
            description "trans identifier dwdmsfp-or-dwdmsfpplus";
        }
        enum qsfp {
            value 13;
            description "trans identifier qsfp";
        }
        enum qsfpplus-or-later {
            value 14;
            description "trans identifier qsfpplus-or-later";
        }
        enum cxp-or-later {
            value 15;
            description "trans identifier cxp-or-later";
        }
        enum shielded-mini-multilane-hd4x {
            value 16;
            description "trans identifier shielded-mini-multilane-hd4x";
        }
        enum shielded-mini-multilane-hd8x {
            value 17;
            description "trans identifier shielded-mini-multilane-hd8x";
        }
        enum qsfp28-or-later {
            value 18;
            description "trans identifier qsfp28-or-later";
        }
        enum cxp2-aka-cxp28-or-later {
            value 19;
            description "trans identifier cxp2-aka-cxp28-or-later";
        }
        enum cdfpstyle1-or-cdfpstyle2 {
            value 20;
            description "trans identifier cdfpstyle1-or-cdfpstyle2";
        }
        enum shielded-mini-multilane-hd4x-fanoutcable {
            value 21;
            description "trans identifier shielded-mini-multilane-hd4x-fanoutcable";
        }
        enum shielded-mini-multilane-hd8x-fanoutcable {
            value 22;
            description "trans identifier shielded-mini-multilane-hd8x-fanoutcable";
        }
        enum cdfpstyle3 {
            value 23;
            description "trans identifier cdfpstyle3";
        }
        enum microqsfp {
            value 24;
            description "trans identifier microqsfp";
        }
        enum qsfp-doubledensity-8x-pluggable-transceiver {
            value 25;
            description "trans identifier qsfp-doubledensity-8x-pluggable-transceiver";
        }
        enum reserved {
            value 26;
            description "trans identifier reserved";
        }
        enum vendor-specific {
            value 27;
            description "trans identifier vendor-specific";
        }
    }
    description "type definition for CML_CMM_TRANS_IDENTIFIER_T";
}

typedef  CML_CMM_TRANS_SFP_EXTENDED_IDENTIFIER_T {
    type enumeration {
        enum gbic-notspecified-or-compliant-with-moddef {
            value 1;
            description "sfp ext-identifier gbic-notspecified-or-compliant-with-moddef ";
        }
        enum gbic-compliant-with-moddef1 {
            value 2;
            description "sfp ext-identifier gbic-compliant-with-moddef1";
        }
        enum gbic-compliant-with-moddef2 {
            value 3;
            description "sfp ext-identifier gbic-compliant-with-moddef2";
        }
        enum gbic-compliant-with-moddef3 {
            value 4;
            description "sfp ext-identifier gbic-compliant-with-moddef3";
        }
        enum gbic-or-sfp-definedby-twowire-interfaceid-only {
            value 5;
            description "sfp ext-identifier gbic-or-sfp-definedby-twowire-interfaceid-only";
        }
        enum gbic-compliant-with-moddef5 {
            value 6;
            description "sfp ext-identifier gbic-compliant-with-moddef5";
        }
        enum gbic-compliant-with-moddef6 {
            value 7;
            description "sfp ext-identifier gbic-compliant-with-moddef6";
        }
        enum gbic-compliant-with-moddef7 {
            value 8;
            description "sfp ext-identifier gbic-compliant-with-moddef7";
        }
        enum unallocated {
            value 9;
            description "sfp ext-identifier unallocated";
        }
        enum unknown {
            value 10;
            description "sfp ext-identifier unknown";
        }
    }
    description "type definition for CML_CMM_TRANS_SFP_EXTENDED_IDENTIFIER_T";
}

typedef  CML_CMM_QSFP_EXTENDED_IDENTIFIER_T {
    type bits {
        bit powerclass1-1dot5wmax {
            position 0;
            description "qsfp ext-identifier powerclass1-1dot5wmax";
        }
        bit powerclass2-2wmax {
            position 1;
            description "qsfp ext-identifier powerclass2-2wmax";
        }
        bit powerclass3-2dot5wmax {
            position 2;
            description "qsfp ext-identifier powerclass3-2dot5wmax";
        }
        bit powerclass4-3dot5wmax {
            position 3;
            description "qsfp ext-identifier powerclass4-3dot5wmax";
        }
        bit cleicode-present {
            position 4;
            description "qsfp ext-identifier cleicode-present";
        }
        bit cdrpresent-in-tx {
            position 5;
            description "qsfp ext-identifier cdrpresent-in-tx";
        }
        bit cdrpresent-in-rx {
            position 6;
            description "qsfp ext-identifier cdrpresent-in-rx";
        }
        bit powerclass5-4wmax {
            position 7;
            description "qsfp ext-identifier powerclass5-4wmax";
        }
        bit powerclass6-4dot5wmax {
            position 8;
            description "qsfp ext-identifier powerclass6-4dot5wmax";
        }
        bit powerclass7-5wmax {
            position 9;
            description "qsfp ext-identifier powerclass7-5wmax";
        }
    }
    description "type definition for CML_CMM_QSFP_EXTENDED_IDENTIFIER_T";
}

typedef  CML_CMM_TRANS_CONNECTOR_TYPE_T {
    type enumeration {
        enum unknown {
            value 1;
            description "trans connector unknown";
        }
        enum subscriber-connector {
            value 2;
            description "trans connector subscriber-connector";
        }
        enum fibrechannel-style1-copperconnector {
            value 3;
            description "trans connector fibrechannel-style1-copperconnector";
        }
        enum fibrechannel-style2-copperconnector {
            value 4;
            description "trans connector fibrechannel-style2-copperconnector";
        }
        enum bayonet-or-threaded-neill-concelman {
            value 5;
            description "trans connector bayonet-or-threaded-neill-concelman";
        }
        enum fibrechannel-coaxheaders {
            value 6;
            description "trans connector fibrechannel-coaxheaders";
        }
        enum fiber-jack {
            value 7;
            description "trans connector fiber-jack";
        }
        enum lucent-connector {
            value 8;
            description "trans connector lucent-connector";
        }
        enum mechanical-transfer-registeredjack {
            value 9;
            description "trans connector mechanical-transfer-registeredjack";
        }
        enum multiple-optical {
            value 10;
            description "trans connector multiple-optical";
        }
        enum sg {
            value 11;
            description "trans connector sg";
        }
        enum optical-pigtail {
            value 12;
            description "trans connector optical-pigtail";
        }
        enum multifiber-paralleloptic-1x12 {
            value 13;
            description "trans connector multifiber-paralleloptic-1x12";
        }
        enum multifiber-paralleloptic-1x16 {
            value 14;
            description "trans connector multifiber-paralleloptic-1x16";
        }
        enum sfp-reserved {
            value 15;
            description "sfp trans connector reserved";
        }
        enum hssdcii {
            value 16;
            description "trans connector hssdcii";
        }
        enum copper-pigtail {
            value 17;
            description "trans connector copper-pigtail";
        }
        enum rj45 {
            value 18;
            description "trans connector rj45";
        }
        enum no-separable-connector {
            value 19;
            description "trans connector no-separable-connector";
        }
        enum mxc2-x16 {
            value 20;
            description "trans connector mxc2-x16";
        }
        enum qsfp-reserved {
            value 21;
            description "qsfp trans connector reserved";
        }
        enum vendor-specific {
            value 22;
            description "trans connector vendor-specific";
        }
    }
    description "type definition for CML_CMM_TRANS_CONNECTOR_TYPE_T";
}

typedef  CML_CMM_TRANS_ETH_COMPLIANCE_T {
    type enumeration {
        enum ec-unknown {
            value 1;
            description "trans compliance ec-unknown";
        }
        enum ec-10gbase-sr {
            value 2;
            description "trans compliance ec-10gbase-sr";
        }
        enum ec-10gbase-lr {
            value 3;
            description "trans compliance ec-10gbase-lr";
        }
        enum ec-10gbase-lrm {
            value 4;
            description "trans compliance ec-10gbase-lrm";
        }
        enum ec-10gbase-er {
            value 5;
            description "trans compliance ec-10gbase-er";
        }
        enum ec-1000base-sx {
            value 6;
            description "trans compliance ec-1000base-sx";
        }
        enum ec-1000base-lx {
            value 7;
            description "trans compliance ec-1000base-lx";
        }
        enum ec-1000base-cx {
            value 8;
            description "trans compliance ec-1000base-cx";
        }
        enum ec-1000base-t {
            value 9;
            description "trans compliance ec-1000base-t";
        }
        enum ec-100base-lx-or-lx10 {
            value 10;
            description "trans compliance ec-100base-lx-or-lx10";
        }
        enum ec-100base-fx {
            value 11;
            description "trans compliance ec-100base-fx";
        }
        enum ec-base-bx10 {
            value 12;
            description "trans compliance ec-base-bx10";
        }
        enum ec-base-px {
            value 13;
            description "trans compliance ec-base-px";
        }
        enum ec-40gbase-cr4 {
            value 14;
            description "trans compliance ec-40gbase-cr4";
        }
        enum ec-40gbase-sr4 {
            value 15;
            description "trans compliance ec-40gbase-sr4";
        }
        enum ec-40gbase-lr4 {
            value 16;
            description "trans compliance ec-40gbase-lr4";
        }
        enum ec-40g-activecable {
            value 17;
            description "trans compliance ec-40g-activecable";
        }
    }
    description "type definition for CML_CMM_TRANS_ETH_COMPLIANCE_T";
}

typedef  CML_CMM_TRANS_EXT_ETH_COMPLIANCE_T {
    type bits {
        bit eec-unspecified {
            position 0;
            description "trans ext compliance eec-unspecified";
        }
        bit eec-100g-activeopticalcable-or-25g-auic2maoc {
            position 1;
            description "trans ext compliance eec-100g-activeopticalcable-or-25g-auic2maoc";
        }
        bit eec-100gbase-sr4-or-25gbase-sr {
            position 2;
            description "trans ext compliance eec-100gbase-sr4-or-25gbase-sr";
        }
        bit eec-100gbase-lr4-or-25gbase-lr {
            position 3;
            description "trans ext compliance eec-100gbase-lr4-or-25gbase-lr";
        }
        bit eec-100gbase-er4-or-25gbase-er {
            position 4;
            description "trans ext compliance eec-100gbase-er4-or-25gbase-er";
        }
        bit eec-100gbase-sr10 {
            position 5;
            description "trans ext compliance eec-100gbase-sr10";
        }
        bit eec-100g-cwdm4 {
            position 6;
            description "trans ext compliance eec-100g-cwdm4";
        }
        bit eec-100g-psm4-parallelsmf {
            position 7;
            description "trans ext compliance eec-100g-psm4-parallelsmf";
        }
        bit eec-100g-activecoppercable-or-25g-auic2macc {
            position 8;
            description "trans ext compliance eec-100g-activecoppercable-or-25g-auic2macc";
        }
        bit eec-obsolete {
            position 9;
            description "trans ext compliance eec-obsolete";
        }
        bit eec-reserved {
            position 10;
            description "trans ext compliance eec-reserved";
        }
        bit eec-100gbase-cr4-or-25gbase-crca-l {
            position 11;
            description "trans ext compliance eec-100gbase-cr4-or-25gbase-crca-l";
        }
        bit eec-25gbase-crca-s {
            position 12;
            description "trans ext compliance eec-25gbase-crca-s";
        }
        bit eec-25gbase-crca-n {
            position 13;
            description "trans ext compliance eec-25gbase-crca-n";
        }
        bit eec-40gbase-er4 {
            position 14;
            description "trans ext compliance eec-40gbase-er4";
        }
        bit eec-4x10gbase-sr {
            position 15;
            description "trans ext compliance eec-4x10gbase-sr";
        }
        bit eec-40g-psm4-parallelsmf {
            position 16;
            description "trans ext compliance eec-40g-psm4-parallelsmf";
        }
        bit eec-g959-dot1-profilep1-i1-2d1 {
            position 17;
            description "trans ext compliance eec-g959-dot1-profilep1-i1-2d1";
        }
        bit eec-g959-dot1-profilep1-s1-2d2 {
            position 18;
            description "trans ext compliance eec-g959-dot1-profilep1-s1-2d2";
        }
        bit eec-g959-dot1-profilep1-l1-2d2 {
            position 19;
            description "trans ext compliance eec-g959-dot1-profilep1-l1-2d2";
        }
        bit eec-100gbase-t-with-sfi-electricalinterface {
            position 20;
            description "trans ext compliance eec-100gbase-t-with-sfi-electricalinterface";
        }
        bit eec-100g-clr4 {
            position 21;
            description "trans ext compliance eec-100g-clr4";
        }
        bit eec-100g-aoc-or-25g-auic2maoc {
            position 22;
            description "trans ext compliance eec-100g-aoc-or-25g-auic2maoc";
        }
        bit eec-100g-acc-or-25g-auic2macc {
            position 23;
            description "trans ext compliance eec-100g-acc-or-25g-auic2macc";
        }
        bit eec-100ge-dwdm2 {
            position 24;
            description "trans ext compliance eec-100ge-dwdm2";
        }
        bit null {
            position 31;
            description "NULL";
        }
    }
    description "type definition for CML_CMM_TRANS_EXT_ETH_COMPLIANCE_T";
}

typedef  CML_CMM_TRANS_SONET_COMPLIANCE_T {
    type bits {
        bit oc192-shortreach {
            position 0;
            description "oc192-shortreach";
        }
        bit sonet-reachspecifier-bit1 {
            position 1;
            description "sonet-reachspecifier-bit1";
        }
        bit sonet-reachspecifier-bit2 {
            position 2;
            description "sonet-reachspecifier-bit2";
        }
        bit oc48-longreach {
            position 3;
            description "oc48-longreach";
        }
        bit oc48-intermediatereach {
            position 4;
            description "oc48-intermediatereach";
        }
        bit oc48-shortreach {
            position 5;
            description "oc48-shortreach";
        }
        bit oc12-singlemode-longreach {
            position 6;
            description "oc12-singlemode-longreach";
        }
        bit oc12-singlemode-intermediatereach {
            position 7;
            description "oc12-singlemode-intermediatereach";
        }
        bit oc12-singlemode-shortreach {
            position 8;
            description "oc12-singlemode-shortreach";
        }
        bit oc3-singlemode-longreach {
            position 9;
            description "oc3-singlemode-longreach";
        }
        bit oc3-singlemode-intermediatereach {
            position 10;
            description "oc3-singlemode-intermediatereach";
        }
        bit oc3-singlemode-shortreach {
            position 11;
            description "oc3-singlemode-shortreach";
        }
        bit null {
            position 31;
            description "NULL";
        }
    }
    description "type definition for CML_CMM_TRANS_SONET_COMPLIANCE_T";
}

typedef  CML_CMM_TRANS_FIBER_CHANNEL_LINKLEN_T {
    type bits {
        bit short {
            position 0;
            description "short";
        }
        bit medium {
            position 1;
            description "medium";
        }
        bit intermediate {
            position 2;
            description "intermediate";
        }
        bit long {
            position 3;
            description "long";
        }
        bit verylong {
            position 4;
            description "very long";
        }
        bit null {
            position 31;
            description "NULL";
        }
    }
    description "type definition for CML_CMM_TRANS_FIBER_CHANNEL_LINKLEN_T";
}

typedef  CML_CMM_TRANS_FIBER_CHANNEL_TRANSMITTECH_T {
    type bits {
        bit shortwaveLaserLinearRx {
            position 0;
            description "shortwaveLaserLinearRx";
        }
        bit longwaveLaserLC {
            position 1;
            description "longwaveLaser LC";
        }
        bit electricalInter-Enclosure {
            position 2;
            description "electricalInter-Enclosure";
        }
        bit electricalIntra-Enclosure {
            position 3;
            description "electricalIntra-Enclosure";
        }
        bit shortwaveLaserWithOutOFC {
            position 4;
            description "shortwaveLaserWithOutOFC";
        }
        bit shortwaveLaserwithOFC {
            position 5;
            description "shortwaveLaserwithOFC";
        }
        bit longwaveLaserLL {
            position 6;
            description "longwaveLaser LL";
        }
        bit null {
            position 31;
            description "NULL";
        }
    }
    description "type definition for CML_CMM_TRANS_FIBER_CHANNEL_TRANSMITTECH_T";
}

typedef  CML_CMM_TRANS_FIBER_CHANNEL_TRANSMITMEDIA_T {
    type bits {
        bit twinaxial-pair {
            position 0;
            description "twinaxial-pair";
        }
        bit twisted-pair {
            position 1;
            description "twisted-pair";
        }
        bit miniature-coax {
            position 2;
            description "miniature-coax";
        }
        bit video-coax {
            position 3;
            description "video-coax";
        }
        bit multi-mode62dot5m {
            position 4;
            description "multi-mode62dot5m";
        }
        bit multi-mode50m {
            position 5;
            description "multi-mode50m";
        }
        bit multi-mode50um {
            position 6;
            description "multi-mode50um";
        }
        bit single-mode {
            position 7;
            description "single-mode";
        }
        bit null {
            position 31;
            description "NULL";
        }
    }
    description "type definition for CML_CMM_TRANS_FIBER_CHANNEL_TRANSMITMEDIA_T";
}

typedef  CML_CMM_TRANS_FIBER_CHANNEL_SPEED_T {
    type bits {
        bit fcs-3200mbps {
            position 0;
            description "fcs-3200mbps";
        }
        bit fcs-1600mbps {
            position 1;
            description "fcs-1600mbps";
        }
        bit fcs-1200mbps {
            position 2;
            description "fcs-1200mbps";
        }
        bit fcs-800mbps {
            position 3;
            description "fcs-800mbps";
        }
        bit fcs-400mbps {
            position 4;
            description "fcs-400mbps";
        }
        bit fcs-200mbps {
            position 5;
            description "fcs-200mbps";
        }
        bit fcs-100mbps {
            position 6;
            description "fcs-100mbps";
        }
        bit null {
            position 31;
            description "NULL";
        }
    }
    description "type definition for CML_CMM_TRANS_FIBER_CHANNEL_SPEED_T";
}

typedef  CML_CMM_TRANS_SFP_INIFINBAND_COMPLIANCE_T {
    type enumeration {
        enum ibc-1xsx {
            value 1;
            description "ibc-1xsx";
        }
        enum ibc-1xlx {
            value 2;
            description "ibc-1xlx";
        }
        enum ibc-1xcopperactive {
            value 3;
            description "ibc-1xcopperactive";
        }
        enum ibc-1xcopperpassive {
            value 4;
            description "ibc-1xcopperpassive";
        }
        enum ibc-unknown {
            value 5;
            description "ibc-unknown";
        }
        enum ibc-notapplicable {
            value 6;
            description "ibc-notapplicable";
        }
    }
    description "type definition for CML_CMM_TRANS_SFP_INIFINBAND_COMPLIANCE_T";
}

typedef  CML_CMM_TRANS_SFP_ESCON_COMPLIANCE_T {
    type enumeration {
        enum escon-mmf-1310nm-led {
            value 1;
            description "escon-mmf-1310nm-led";
        }
        enum escon-smf-1310nm-laser {
            value 2;
            description "escon-smf-1310nm-laser";
        }
        enum unknown {
            value 3;
            description "unknown";
        }
        enum notapplicable {
            value 4;
            description "notapplicable";
        }
    }
    description "type definition for CML_CMM_TRANS_SFP_ESCON_COMPLIANCE_T";
}

typedef  CML_CMM_TRANS_SFP_PLUS_CABLE_TECH_T {
    type enumeration {
        enum active {
            value 1;
            description "active";
        }
        enum passive {
            value 2;
            description "passive";
        }
        enum unknown {
            value 3;
            description "unknown";
        }
        enum notapplicable {
            value 4;
            description "notapplicable";
        }
    }
    description "type definition for CML_CMM_TRANS_SFP_PLUS_CABLE_TECH_T";
}

typedef  CML_CMM_TRANS_ENCODING_T {
    type enumeration {
        enum enc-unspecified {
            value 1;
            description "enc-unspecified";
        }
        enum enc-8b-or-10b {
            value 2;
            description "enc-8b-or-10b";
        }
        enum enc-4b-or-5b {
            value 3;
            description "enc-4b-or-5b";
        }
        enum enc-nrz {
            value 4;
            description "enc-nrz";
        }
        enum enc-manchester {
            value 5;
            description "enc-manchester";
        }
        enum enc-sonet-scrambled {
            value 6;
            description "enc-sonet-scrambled";
        }
        enum enc-64b-or-66b {
            value 7;
            description "enc-64b-or-66b";
        }
        enum enc-256b-or-257b {
            value 8;
            description "enc-256b-or-257b";
        }
        enum enc-pam4 {
            value 9;
            description "enc-pam4";
        }
        enum enc-reserved {
            value 10;
            description "enc-reserved";
        }
    }
    description "type definition for CML_CMM_TRANS_ENCODING_T";
}

typedef  CML_CMM_TRANS_DDM_SUPPORT_T {
    type enumeration {
        enum yes {
            value 1;
            description "DDM is supported";
        }
        enum no {
            value 2;
            description "DDM is not supported";
        }
        enum unknown {
            value 3;
            description "DDM support unknown";
        }
    }
    description "type definition for CML_CMM_TRANS_DDM_SUPPORT_T";
}

typedef  CML_CMM_TRANS_PRESENCE_T {
    type enumeration {
        enum present {
            value 1;
            description "transceiver present";
        }
        enum notpresent {
            value 2;
            description "transceiver not present";
        }
        enum unknown {
            value 3;
            description "unknown";
        }
    }
    description "type definition for CML_CMM_TRANS_PRESENCE_T";
}

typedef  CML_CMM_TRANS_TX_RX_STATE_T {
    type enumeration {
        enum enable {
            value 1;
            description "enabled";
        }
        enum disable {
            value 2;
            description "disabled";
        }
        enum unknown {
            value 3;
            description "state unknown";
        }
    }
    description "type definition for CML_CMM_TRANS_TX_RX_STATE_T";
}

typedef  CML_CMM_TRANS_RESET_STATE_T {
    type enumeration {
        enum normal {
            value 1;
            description "normal";
        }
        enum reset {
            value 2;
            description "reset";
        }
        enum unknown {
            value 3;
            description "State unknown";
        }
    }
    description "type definition for CML_CMM_TRANS_RESET_STATE_T";
}

typedef  CML_CMM_TRANS_POWER_MODE_T {
    type enumeration {
        enum low {
            value 1;
            description "trans power low";
        }
        enum high {
            value 2;
            description "trans power high";
        }
        enum unknown {
            value 3;
            description "trans power state unknown";
        }
    }
    description "type definition for CML_CMM_TRANS_POWER_MODE_T";
}

typedef  CML_CMM_TRANS_SFP_OPTIONS_IMPLEMENTED_T {
    type bits {
        bit reserved {
            position 0;
            description "reserved";
        }
        bit power-level3 {
            position 1;
            description "power-level3";
        }
        bit paging {
            position 2;
            description "paging";
        }
        bit internal-retimer-or-cdr {
            position 3;
            description "internal-retimer-or-cdr";
        }
        bit cooled-laser-transmitter {
            position 4;
            description "cooled-laser-transmitter";
        }
        bit power-level2 {
            position 5;
            description "power-level2";
        }
        bit power-level1 {
            position 6;
            description "power-level1";
        }
        bit linear-receiver-output {
            position 7;
            description "linear-receiver-output";
        }
        bit receiver-decision-threshold {
            position 8;
            description "receiver-decision-threshold";
        }
        bit transmitter-wavelength-or-tunable-frequency {
            position 9;
            description "transmitter-wavelength-or-tunable-frequency";
        }
        bit rate-select {
            position 10;
            description "rate-select";
        }
        bit tx-disable {
            position 11;
            description "tx-disable";
        }
        bit tx-fault {
            position 12;
            description "tx-fault";
        }
        bit rx-loss-of-signal {
            position 13;
            description "rx-loss-of-signal";
        }
        bit null {
            position 31;
            description "NULL";
        }
    }
    description "type definition for CML_CMM_TRANS_SFP_OPTIONS_IMPLEMENTED_T";
}

typedef  CML_CMM_TRANS_QSFP_OPTIONS_IMPLEMENTED_T {
    type bits {
        bit reserved {
            position 0;
            description "reserved";
        }
        bit tx-inputequalization-auto-adaptive {
            position 1;
            description "tx-inputequalization-auto-adaptive";
        }
        bit tx-inputequalization-fixed-programmable {
            position 2;
            description "tx-inputequalization-fixed-programmable";
        }
        bit tx-outputemphasis-fixed-programmable {
            position 3;
            description "tx-outputemphasis-fixed-programmable";
        }
        bit tx-outputamplitude-fixed-programmable {
            position 4;
            description "tx-outputamplitude-fixed-programmable";
        }
        bit tx-cdr-on-or-off-controllable {
            position 5;
            description "tx-cdr-on-or-off-controllable";
        }
        bit tx-cdr-on-or-off-fixed {
            position 6;
            description "tx-cdr-on-or-off-fixed";
        }
        bit rx-cdr-on-or-off-controllable {
            position 7;
            description "rx-cdr-on-or-off-controllable";
        }
        bit rx-cdr-on-or-off-fixed {
            position 8;
            description "rx-cdr-on-or-off-fixed";
        }
        bit tx-cdr-lossoflock {
            position 9;
            description "tx-cdr-lossoflock";
        }
        bit rx-cdr-lossoflock {
            position 10;
            description "rx-cdr-lossoflock";
        }
        bit rx-squelch-disable {
            position 11;
            description "rx-squelch-disable";
        }
        bit rx-output-disable {
            position 12;
            description "rx-output-disable";
        }
        bit tx-squelch-disable {
            position 13;
            description "tx-squelch-disable";
        }
        bit tx-squelch {
            position 14;
            description "tx-squelch";
        }
        bit page2-provided {
            position 15;
            description "page2-provided";
        }
        bit page1-provided {
            position 16;
            description "page1-provided";
        }
        bit rateselect-controllable {
            position 17;
            description "rateselect-controllable";
        }
        bit rateselect-fixed {
            position 18;
            description "rateselect-fixed";
        }
        bit tx-disable {
            position 19;
            description "tx-disable";
        }
        bit tx-fault {
            position 20;
            description "tx-fault";
        }
        bit tx-squelch-to-reduce-pave {
            position 21;
            description "tx-squelch-to-reduce-pave";
        }
        bit tx-squelch-to-reduce-oma {
            position 22;
            description "tx-squelch-to-reduce-oma";
        }
        bit tx-loss-of-signal {
            position 23;
            description "tx-loss-of-signal";
        }
        bit null {
            position 31;
            description "NULL";
        }
    }
    description "type definition for CML_CMM_TRANS_QSFP_OPTIONS_IMPLEMENTED_T";
}

typedef  CML_CMM_TRANS_TX_RX_POWER_SUPPORTED_T {
    type enumeration {
        enum supported {
            value 1;
            description "trans tx/rx power supported";
        }
        enum unsupported {
            value 2;
            description "trans tx/rx power not supported";
        }
        enum notapplicable {
            value 3;
            description "trans tx/rx power support notapplicable";
        }
        enum unknown {
            value 4;
            description "trans tx/rx power support unknown";
        }
    }
    description "type definition for CML_CMM_TRANS_TX_RX_POWER_SUPPORTED_T";
}

typedef  CML_CMM_TRANS_DDM_STATUS_T {
    type enumeration {
        enum active {
            value 1;
            description "ddm status is active";
        }
        enum activeunsupported {
            value 2;
            description "ddm status is active but transceiver is unsupported";
        }
        enum inactive {
            value 3;
            description "ddm status is inactive";
        }
        enum inactiveunsupported {
            value 4;
            description "ddm status is inactive and transceiver is unsupported";
        }
        enum notapplicable {
            value 5;
            description "ddm status is not applicable";
        }
        enum unknown {
            value 6;
            description "ddm status is unknown";
        }
    }
    description "type definition for CML_CMM_TRANS_DDM_STATUS_T";
}

typedef  CML_CMM_POWER_SUPPLY_OPERSTATUS_T {
    type enumeration {
        enum notpresent {
            value 1;
            description "psu not present";
        }
        enum running {
            value 2;
            description "psu running";
        }
        enum faulty {
            value 3;
            description "psu faulty";
        }
        enum unknown {
            value 4;
            description "psu status unknown";
        }
    }
    description "type definition for CML_CMM_POWER_SUPPLY_OPERSTATUS_T";
}

typedef  CML_CMM_POWER_SUPPLY_TYPE_T {
    type enumeration {
        enum ac-normal {
            value 1;
            description "psu type ac-normal";
        }
        enum ac-reverse {
            value 2;
            description "psu type ac-reverse";
        }
        enum dc-normal {
            value 3;
            description "psu type dc-normal";
        }
        enum dc-reverse {
            value 4;
            description "psu type dc-reverse";
        }
        enum unknown {
            value 5;
            description "psu type unknown";
        }
        enum notapplicable {
            value 6;
            description "psu type notapplicable";
        }
    }
    description "type definition for CML_CMM_POWER_SUPPLY_TYPE_T";
}

typedef  CML_CMM_POWER_RAIL_T {
    type enumeration {
        enum good {
            value 1;
            description "power rail good";
        }
        enum fail {
            value 2;
            description "power rail fail";
        }
        enum unknown {
            value 3;
            description "power rail status unknown";
        }
        enum notapplicable {
            value 4;
            description "power rail notapplicable";
        }
    }
    description "type definition for CML_CMM_POWER_RAIL_T";
}

typedef  CML_CMM_PSU_PMBUS_PARAM_SUPPORT_T {
    type bits {
        bit volt-in {
            position 0;
            description "input voltage supported";
        }
        bit volt-out {
            position 1;
            description "output voltage supported";
        }
        bit curr-in {
            position 2;
            description "input current supported";
        }
        bit curr-out {
            position 3;
            description "output current supported";
        }
        bit power-in {
            position 4;
            description "input power supported";
        }
        bit power-out {
            position 5;
            description "output power supported";
        }
        bit temp1 {
            position 6;
            description "PSU Temp senor 1 supported";
        }
        bit temp2 {
            position 7;
            description "PSU Temp sensor 2 supported";
        }
        bit fan1 {
            position 8;
            description "PSU Fan 1 supported";
        }
        bit fan2 {
            position 9;
            description "PSU Fan 2 supported";
        }
        bit null {
            position 31;
            description "NULL";
        }
    }
    description "type definition for CML_CMM_PSU_PMBUS_PARAM_SUPPORT_T";
}

typedef  CML_CMM_LED_COLOR_CODE_T {
    type enumeration {
        enum none {
            value 1;
            description "ino color";
        }
        enum green {
            value 2;
            description "green color";
        }
        enum blinking-green {
            value 3;
            description "blinking-green color";
        }
        enum solid-green {
            value 4;
            description "solid-green color";
        }
        enum amber {
            value 5;
            description "amber color";
        }
        enum blinking-amber {
            value 6;
            description "blinking-amber color";
        }
        enum solid-amber {
            value 7;
            description "solid-amber color";
        }
        enum red {
            value 8;
            description "red color";
        }
        enum blinking-red {
            value 9;
            description "blinking-red color";
        }
        enum solid-red {
            value 10;
            description "solid-red color";
        }
        enum blue {
            value 11;
            description "blue color";
        }
        enum blinking-blue {
            value 12;
            description "blinking-blue color";
        }
        enum yellow {
            value 13;
            description "yellow color";
        }
        enum blinking-yellow {
            value 14;
            description "blinking-yellow color";
        }
        enum orange {
            value 15;
            description "orange color";
        }
        enum slow-blinking-green {
            value 16;
            description "slow-blinking-green color";
        }
        enum fast-blinking-green {
            value 17;
            description "fast-blinking-green color";
        }
        enum unknown {
            value 30;
            description "color unknown";
        }
    }
    description "type definition for CML_CMM_LED_COLOR_CODE_T";
}

typedef  CML_CMM_FAN_TRAY_STATUS_T {
    type enumeration {
        enum notpresent {
            value 1;
            description "fan tray not present";
        }
        enum present {
            value 2;
            description "fan tray present";
        }
        enum unknown {
            value 3;
            description "fan tray status unknown";
        }
    }
    description "type definition for CML_CMM_FAN_TRAY_STATUS_T";
}

typedef  CML_CMM_FAN_STATUS_T {
    type enumeration {
        enum notpresent {
            value 1;
            description "fan not present";
        }
        enum running {
            value 2;
            description "fan running";
        }
        enum faulty {
            value 3;
            description "fan faulty";
        }
        enum stalled {
            value 4;
            description "fan stalled";
        }
        enum unknown {
            value 5;
            description "fan status unknown";
        }
    }
    description "type definition for CML_CMM_FAN_STATUS_T";
}

typedef  CML_CMM_FAN_LOCATION_T {
    type enumeration {
        enum front {
            value 1;
            description "fan located in front";
        }
        enum rear {
            value 2;
            description "fan located in rear";
        }
        enum unknown {
            value 3;
            description "fan location unknown";
        }
        enum notapplicable {
            value 4;
            description "fan location notapplicable";
        }
    }
    description "type definition for CML_CMM_FAN_LOCATION_T";
}

typedef  CML_CMM_FAN_TYPE_T {
    type enumeration {
        enum blow-outfan {
            value 1;
            description "fan type blow-out";
        }
        enum blow-infan {
            value 2;
            description "fan type blow-in";
        }
        enum fan-type-unknown {
            value 3;
            description "fan type unknown";
        }
    }
    description "type definition for CML_CMM_FAN_TYPE_T";
}

typedef  CML_CMM_SYS_AND_COMPONENT_STATUS_T {
    type enumeration {
        enum normal {
            value 1;
            description "system/component status normal";
        }
        enum minor-fault {
            value 2;
            description "system/component in minor-fault";
        }
        enum major-fault {
            value 3;
            description "system/component in major-fault";
        }
        enum unknown {
            value 4;
            description "system/component status unknown";
        }
    }
    description "type definition for CML_CMM_SYS_AND_COMPONENT_STATUS_T";
}

typedef  CML_CMM_MASTER_LOCATOR_STATUS_T {
    type enumeration {
        enum notpresent {
            value 1;
            description "component not present";
        }
        enum on {
            value 2;
            description "component led on";
        }
        enum off {
            value 3;
            description "component led off";
        }
        enum unknown {
            value 4;
            description "component status unknown";
        }
    }
    description "type definition for CML_CMM_MASTER_LOCATOR_STATUS_T";
}

typedef  CML_CMM_SYS_FAULT_STATUS_T {
    type bits {
        bit cpu {
            position 0;
            description "cpu fault";
        }
        bit ram {
            position 1;
            description "ram fault";
        }
        bit disk {
            position 2;
            description "disk fault";
        }
        bit low-temperature {
            position 3;
            description "temperature fault in low";
        }
        bit high-temperature {
            position 4;
            description "temperature fault in high";
        }
        bit fan {
            position 5;
            description "fan fault";
        }
        bit power {
            position 6;
            description "psu fault";
        }
        bit software {
            position 7;
            description "software fault";
        }
        bit null {
            position 31;
            description "NULL";
        }
    }
    description "type definition for CML_CMM_SYS_FAULT_STATUS_T";
}

typedef  CML_HOSTP_SNMP_KEY_TYPE_T {
    type enumeration {
        enum plain {
            value 0;
            description "To specify shared key in clear-text form";
        }
        enum encrypt {
            value 1;
            description "To specify shared key in encrypted form";
        }
    }
    description "type definition for CML_HOSTP_SNMP_KEY_TYPE_T";
}

typedef  CML_FORWARDING_PROFILE_T {
    type enumeration {
        enum l2-profile-one {
            value 0;
            description "Configures the L2 profile One";
        }
        enum l2-profile-two {
            value 1;
            description "Configures the L2 profile Two";
        }
        enum l2-profile-three {
            value 2;
            description "Configures the L2 profile Three (default)";
        }
        enum l3-profile {
            value 3;
            description "Configures the L3 profile";
        }
        enum l3-128bit-profile {
            value 4;
            description "Configures the L3 profile with 128 bit prefix support";
        }
        enum lpm-profile {
            value 5;
            description "Configures the LPM profile profile";
        }
        enum lpm-128bit-profile {
            value 6;
            description "Configures the LPM profile with 128 bit prefix support";
        }
    }
    description "type definition for CML_FORWARDING_PROFILE_T";
}

typedef  CML_FORWARDING_PROFILE_MH_T {
    type enumeration {
        enum l3-nvo-mh-profile {
            value 1;
            description "configures the Multihoming ecmp for nvo";
        }
    }
    description "type definition for CML_FORWARDING_PROFILE_MH_T";
}

typedef  CML_FORWARDING_CUSTOM_PROFILE_LPM_T {
    type enumeration {
        enum 2 {
            value 2;
            description "Two banks for lpm and Remaining banks can be used by any";
        }
    }
    description "type definition for CML_FORWARDING_CUSTOM_PROFILE_LPM_T";
}

typedef  CML_KAPS_PROFILE_T {
    type enumeration {
        enum profile-one {
            value 1;
            description "select kaps profile one";
        }
        enum profile-two {
            value 2;
            description "select kaps profile two";
        }
    }
    description "type definition for CML_KAPS_PROFILE_T";
}

typedef  CML_TCAM_PROFILE_T {
    type enumeration {
        enum profile-one {
            value 3;
            description "select elk-tcam profile one";
        }
        enum profile-two {
            value 4;
            description "select elk-tcam profile two";
        }
        enum profile-three {
            value 5;
            description "select elk-tcam profile three";
        }
    }
    description "type definition for CML_TCAM_PROFILE_T";
}

typedef  CML_TCAM_CUSTOM_PROFILE_T {
    type enumeration {
        enum custom-profile {
            value 6;
            description "define elk-tcam custom profile";
        }
    }
    description "type definition for CML_TCAM_CUSTOM_PROFILE_T";
}

typedef  CML_NSM_HW_PROFILE_T {
    type enumeration {
        enum qos-group {
            value 1;
            description "Configures the qos-group";
        }
        enum ingress-l2-group {
            value 2;
            description "Configures the ingress-l2-group";
        }
        enum ingress-ipv4 {
            value 4;
            description "Configures the ingress-ipv4";
        }
        enum egress-ipv4 {
            value 8;
            description "Configures the egress-ipv4";
        }
        enum egress-ipv6 {
            value 16;
            description "Configures the egress-ipv6";
        }
        enum egress-l2-group {
            value 64;
            description "Configures egress-l2-group";
        }
    }
    description "type definition for CML_NSM_HW_PROFILE_T";
}

typedef  CML_NSM_CONFIG_MODE_T {
    type bits {
        bit addressmonitor {
            position 1;
            description "Enable Monitor adddress netlink";
        }
        bit bfd {
            position 2;
            description "Bidirectional Forwarding Detection (BFD)";
        }
        bit events {
            position 3;
            description "NSM events";
        }
        bit hal-events {
            position 4;
            description " Hardware Abstraction Layer,NSM events";
        }
        bit hal-ipc {
            position 5;
            description "Hardware Abstraction Layer,Async Debugging";
        }
        bit linkmonitor {
            position 6;
            description "Enable Monitor link netlink";
        }
        bit packet {
            position 7;
            description "NSM packets";
        }
        bit packet-detail {
            position 8;
            description "NSM packets,Detailed information display";
        }
        bit packet-recv {
            position 9;
            description "NSM packets,NSM receive packets";
        }
        bit packet-recv-detail {
            position 10;
            description "NSM packets,NSM receive packets,Detailed information display";
        }
        bit packet-send {
            position 11;
            description "NSM packets,NSM receive packets";
        }
        bit packet-send-detail {
            position 12;
            description "NSM packets,NSM receive packets,Detailed information display";
        }
        bit vxlan {
            position 15;
            description "VXLAN";
        }
        bit mpls {
            position 19;
            description "NSM mpls";
        }
    }
    description "type definition for CML_NSM_CONFIG_MODE_T";
}

typedef  CML_NSM_EXEC_MODE_T {
    type bits {
        bit addressmonitor {
            position 1;
            description "Enable Monitor adddress netlink";
        }
        bit bfd {
            position 2;
            description "Bidirectional Forwarding Detection (BFD)";
        }
        bit events {
            position 3;
            description "NSM events";
        }
        bit hal-events {
            position 4;
            description " Hardware Abstraction Layer,NSM events";
        }
        bit hal-ipc {
            position 5;
            description "Hardware Abstraction Layer,Async Debugging";
        }
        bit linkmonitor {
            position 6;
            description "Enable Monitor link netlink";
        }
        bit packet {
            position 7;
            description "NSM packets";
        }
        bit packet-detail {
            position 8;
            description "NSM packets,Detailed information display";
        }
        bit packet-recv {
            position 9;
            description "NSM packets,NSM receive packets";
        }
        bit packet-recv-detail {
            position 10;
            description "NSM packets,NSM receive packets,Detailed information display";
        }
        bit packet-send {
            position 11;
            description "NSM packets,NSM receive packets";
        }
        bit packet-send-detail {
            position 12;
            description "NSM packets,NSM receive packets,Detailed information display";
        }
        bit vxlan {
            position 15;
            description "VXLAN";
        }
        bit mpls {
            position 19;
            description "NSM mpls";
        }
    }
    description "type definition for CML_NSM_EXEC_MODE_T";
}

typedef  CML_NSM_PKT_MGR_T {
    type bits {
        bit l2-protocol-cfm {
            position 2;
            description "debug pktmgr,layer2,protocol,cfm";
        }
        bit l2-protocol-eapol {
            position 3;
            description "debug pktmgr,layer2,protocol,eapol";
        }
        bit l2-protocol-efm {
            position 4;
            description "debug pktmgr,layer2,protocol,efm";
        }
        bit l2-protocol-igmp-snoop {
            position 5;
            description "debug pktmgr,layer2,protocol,igmp snoop";
        }
        bit l2-protocol-lacp {
            position 6;
            description "debug pktmgr,layer2,protocol,lacp";
        }
        bit l2-protocol-lldp {
            position 7;
            description "debug pktmgr,layer2,protocol,lldp";
        }
        bit l2-protocol-mldp-snoop {
            position 8;
            description "debug pktmgr,layer2,protocol,mldp snoop";
        }
        bit l2-protocol-mstp {
            position 9;
            description "debug pktmgr,layer2,protocol,mstp";
        }
        bit l2-protocol-ptp {
            position 10;
            description "debug pktmgr,layer2,protocol,ptp";
        }
    }
    description "type definition for CML_NSM_PKT_MGR_T";
}

typedef  CML_MSTP_DEBUG_T {
    type bits {
        bit mstp-protocol {
            position 1;
            description "debug mstp,mstp protocol";
        }
        bit mstp-protocol-detail {
            position 2;
            description "debug mstp,mstp protocol,display detailed information";
        }
        bit mstp-timer {
            position 3;
            description "debug mstp,mstp timer";
        }
        bit mstp-timer-detail {
            position 4;
            description "debug mstp,mstp timer,display detailed information";
        }
        bit mstp-packet-tx {
            position 5;
            description "debug mstp,mstp packet,tx";
        }
        bit mstp-packet-rx {
            position 6;
            description "debug mstp,mstp packet,rx";
        }
        bit mstp-cli {
            position 7;
            description "debug mstp,mstp cli";
        }
        bit mstp-bpdu {
            position 8;
            description "debug mstp,mstp bpdu";
        }
        bit mstp-mcec {
            position 9;
            description "debug mstp,mstp mcec";
        }
    }
    description "type definition for CML_MSTP_DEBUG_T";
}

typedef  CML_EXEC_MSTP_T {
    type enumeration {
        enum stats {
            value 1;
            description "STATISTICS";
        }
        enum pkt-errors {
            value 2;
            description "PACKET ERROR STATS";
        }
    }
    description "type definition for CML_EXEC_MSTP_T";
}

typedef  CML_SFLOW_DEBUG_TYPE_T {
    type bits {
        bit agent {
            position 0;
            description "debug sflow agent";
        }
        bit sampling {
            position 1;
            description "debug sflow sampling";
        }
        bit polling {
            position 2;
            description "debug sflow polling";
        }
    }
    description "type definition for CML_SFLOW_DEBUG_TYPE_T";
}

typedef  CML_URPF_MODE_T {
    type enumeration {
        enum any {
            value 1;
            description "Source is reachable via any interface";
        }
        enum rx {
            value 2;
            description "Source is reachable via interface on which packet was received";
        }
    }
    description "type definition for CML_URPF_MODE_T";
}

typedef  CML_MACTYPE_T {
    type enumeration {
        enum static {
            value 0;
            description "Clear all entries configured through management";
        }
        enum multicast {
            value 2;
            description "Clear all multicast entries";
        }
    }
    description "type definition for CML_MACTYPE_T";
}

typedef  CML_INT_TRACK_MATCH_TYPE_T {
    type enumeration {
        enum all {
            value 1;
            description "Match criteria all";
        }
        enum any {
            value 2;
            description "Match criteria any";
        }
    }
    description "type definition for CML_INT_TRACK_MATCH_TYPE_T";
}

typedef  CML_INT_TRACK_STATE_TYPE_T {
    type enumeration {
        enum down {
            value 1;
            description "Make interface DOWN";
        }
        enum up {
            value 2;
            description "Make interface UP";
        }
    }
    description "type definition for CML_INT_TRACK_STATE_TYPE_T";
}

typedef  CML_PMIRROR_SESS_TYPE_T {
    type enumeration {
        enum local {
            value 1;
            description "Create a local session";
        }
        enum remote {
            value 2;
            description "Create a remote source node session";
        }
    }
    description "type definition for CML_PMIRROR_SESS_TYPE_T";
}

typedef  CML_PMIRROR_STATE_T {
    type enumeration {
        enum shut {
            value 0;
            description "shut";
        }
        enum no-shut {
            value 1;
            description "unser, shut";
        }
    }
    description "type definition for CML_PMIRROR_STATE_T";
}

typedef  CML_PMIRROR_DIR_T {
    type bits {
        bit rx {
            position 0;
            description "Ingress";
        }
        bit tx {
            position 1;
            description "Engress";
        }
    }
    description "type definition for CML_PMIRROR_DIR_T";
}

typedef  CML_PMIRROR_ALT_DIR_T {
    type bits {
        bit receive {
            position 0;
            description "Mirror received traffic";
        }
        bit transmit {
            position 1;
            description "Mirror transmit traffic";
        }
    }
    description "type definition for CML_PMIRROR_ALT_DIR_T";
}

typedef  CML_PMIRROR_ALL_SESS_T {
    type enumeration {
        enum all {
            value 0;
            description "All sessions";
        }
    }
    description "type definition for CML_PMIRROR_ALL_SESS_T";
}

typedef  CML_PMIRROR_SESS_T {
    type union {
        type CML_PMIRROR_ALL_SESS_T {

        }
        type uint32 {
            range "1..18";

        }
    }
    description "type definition for CML_PMIRROR_SESS_T";
}

typedef  CML_TUNNEL_STATUS_T {
    type enumeration {
        enum Deleted {
            value 0;
            description "Tunnel is deleted";
        }
        enum Un-Resolved {
            value 1;
            description "Tunnel not established";
        }
        enum Resolved {
            value 2;
            description "Tunnel established but not in hardware";
        }
        enum Installed {
            value 3;
            description "Tunnel established succesfully in hardware";
        }
    }
    description "type definition for CML_TUNNEL_STATUS_T";
}

typedef  CML_RSVP_TRUNK_FAMILY_T {
    type enumeration {
        enum gmpls {
            value 1;
            description "GMPLS enabled trunk";
        }
        enum ipv4 {
            value 2;
            description "IPv4 address family trunk";
        }
        enum ipv6 {
            value 10;
            description "IPv6 address family trunk";
        }
    }
    description "type definition for CML_RSVP_TRUNK_FAMILY_T";
}

typedef  CML_RSVP_FRR_PROTECTION_T {
    type enumeration {
        enum one-to-one {
            value 1;
            description "One-to-One protection mechanism";
        }
        enum facility {
            value 2;
            description "Facility Backup (Bypass) protection";
        }
    }
    description "type definition for CML_RSVP_FRR_PROTECTION_T";
}

typedef  CML_RSVP_ADMIN_TYPE_T {
    type enumeration {
        enum exclude-any {
            value 0;
            description "Exclude-any attribute";
        }
        enum include-any {
            value 1;
            description "Include-any attribute";
        }
        enum include-all {
            value 2;
            description "Include-all attribute";
        }
    }
    description "type definition for CML_RSVP_ADMIN_TYPE_T";
}

typedef  CML_RSVP_IGP_T {
    type enumeration {
        enum disable-igp-shortcut {
            value 0;
            description "Disable RSVP LSP for IGP Shortcut use";
        }
        enum enable-igp-shortcut {
            value 1;
            description "Enable RSVP LSP for IGP Shortcut use";
        }
    }
    description "type definition for CML_RSVP_IGP_T";
}

typedef  CML_RSVP_EXCLUDE_PATH_TYPE_T {
    type enumeration {
        enum link {
            value 1;
            description "Enables a Link Protection - NHOP";
        }
        enum node {
            value 2;
            description "Enables a Node Protection - NNHOP";
        }
    }
    description "type definition for CML_RSVP_EXCLUDE_PATH_TYPE_T";
}

typedef  CML_RSVP_SESS_TYEP_T {
    type enumeration {
        enum secondary {
            value 0;
            description "Configure secondary LSP option";
        }
        enum primary {
            value 1;
            description "Configure primary LSP option";
        }
    }
    description "type definition for CML_RSVP_SESS_TYEP_T";
}

typedef  CML_RSVP_AFFINITY_T {
    type enumeration {
        enum no-affinity {
            value 0;
            description "Dont pack affinity info into session attribute object";
        }
        enum affinity {
            value 1;
            description "Pack affinity info into session attribute object";
        }
    }
    description "type definition for CML_RSVP_AFFINITY_T";
}

typedef  CML_RSVP_RECORD_T {
    type enumeration {
        enum no-record {
            value 0;
            description "Disable record of route taken by PATH message";
        }
        enum record {
            value 1;
            description "Record route taken by PATH message in order to reach tunnel egress";
        }
    }
    description "type definition for CML_RSVP_RECORD_T";
}

typedef  CML_BFD_MULTI_HOP_TYPE_T {
    type enumeration {
        enum multihop {
            value 1;
            description "Multihop Session";
        }
    }
    description "type definition for CML_BFD_MULTI_HOP_TYPE_T";
}

typedef  CML_RIPNG_DEBUG_T {
    type bits {
        bit events {
            position 1;
            description "RIP events";
        }
        bit packet-send {
            position 2;
            description "RIP packets,RIP send packets";
        }
        bit packet-recv {
            position 3;
            description "RIP packets, RIP receive packets";
        }
        bit nsm {
            position 5;
            description "RIP NSM information";
        }
        bit rib {
            position 6;
            description "RIP RIB information";
        }
    }
    description "type definition for CML_RIPNG_DEBUG_T";
}

typedef  CML_RIPNG_SPLIT_HORIZON_T {
    type enumeration {
        enum split-horizon {
            value 0;
            description "Perform split horizon";
        }
        enum split-horizon-poisoned {
            value 1;
            description "Perform split horizon,Perform poisoned reverse";
        }
    }
    description "type definition for CML_RIPNG_SPLIT_HORIZON_T";
}

typedef  CML_RIPNG_INSTANCE_T {
    type enumeration {
        enum rip {
            value 1;
            description "Routing Information Protocol (RIP)";
        }
    }
    description "type definition for CML_RIPNG_INSTANCE_T";
}

typedef  CML_RIPNG_REDIST_PROTOS_T {
    type enumeration {
        enum kernel {
            value 0;
            description "Kernel routes";
        }
        enum connected {
            value 1;
            description "Connected";
        }
        enum static {
            value 2;
            description "Static routes";
        }
        enum ospf6 {
            value 3;
            description "Open Shortest Path First (OSPF)";
        }
        enum isis {
            value 4;
            description "ISO IS-IS";
        }
        enum bgp {
            value 5;
            description "Border Gateway Protocol (BGP)";
        }
    }
    description "type definition for CML_RIPNG_REDIST_PROTOS_T";
}

typedef  CML_RIPNG_VRF_REDIST_PROTOS_T {
    type enumeration {
        enum connected {
            value 1;
            description "Connected";
        }
        enum static {
            value 2;
            description "Static routes";
        }
        enum ospf6 {
            value 3;
            description "Open Shortest Path First (OSPF)";
        }
        enum bgp {
            value 5;
            description "Border Gateway Protocol (BGP)";
        }
    }
    description "type definition for CML_RIPNG_VRF_REDIST_PROTOS_T";
}

typedef  CML_RIPNG_FILTERING_T {
    type enumeration {
        enum in {
            value 0;
            description "For incoming updates";
        }
        enum out {
            value 1;
            description "For outgoing updates";
        }
    }
    description "type definition for CML_RIPNG_FILTERING_T";
}

typedef  CML_RIPNG_ROUTE_T {
    type enumeration {
        enum kernel {
            value 1;
            description "Kernel routes";
        }
        enum connected {
            value 2;
            description "Connected";
        }
        enum static {
            value 3;
            description "Static routes";
        }
        enum isis {
            value 4;
            description "ISO IS-IS";
        }
        enum ospf6 {
            value 5;
            description "Open Shortest Path First (OSPF)";
        }
        enum bgp {
            value 6;
            description "Border Gateway Protocol (BGP)";
        }
        enum rip {
            value 7;
            description "Routing Information Protocol (RIP)";
        }
        enum all {
            value 8;
            description "all of the RIP routing tabl";
        }
    }
    description "type definition for CML_RIPNG_ROUTE_T";
}

typedef  CML_CONFIDENCETYPE_T {
    type enumeration {
        enum native {
            value 1;
            description "Confidence level associated with MAC learned after decapsulation of frames";
        }
        enum decap {
            value 2;
            description "Confidence level associated with MAC learned from native frames";
        }
        enum static {
            value 3;
            description "Confidence level associated with MAC that are statically configured";
        }
    }
    description "type definition for CML_CONFIDENCETYPE_T";
}

typedef  CML_ESADI_T {
    type enumeration {
        enum enable {
            value 1;
            description "Enable ESADI";
        }
        enum disable {
            value 2;
            description "Disable ESADI";
        }
    }
    description "type definition for CML_ESADI_T";
}

typedef  CML_TRILL_T {
    type enumeration {
        enum disable {
            value 0;
            description "Disable vlan pruningI";
        }
        enum enable {
            value 1;
            description "Enable vlan pruning";
        }
    }
    description "type definition for CML_TRILL_T";
}

typedef  CML_ISUNICAST_T {
    type enumeration {
        enum multicast {
            value 0;
            description "Enable Multipath for multicast";
        }
        enum unicast {
            value 1;
            description "Enable Multipath for unicast";
        }
    }
    description "type definition for CML_ISUNICAST_T";
}

typedef  CML_CONFIGTYPE_T {
    type enumeration {
        enum broadcast {
            value 1;
            description "Link is broadcast multi-access";
        }
        enum point-to-point {
            value 2;
            description "Link is point-to-point";
        }
    }
    description "type definition for CML_CONFIGTYPE_T";
}

typedef  CML_VLAN_ENUM_T {
    type enumeration {
        enum all {
            value 4095;
            description "All the vlan";
        }
    }
    description "type definition for CML_VLAN_ENUM_T";
}

typedef  CML_VLAN_RANGE_T {

    type uint16{
     range 1..4094;
    }
    description "type definition for CML_VLAN_RANGE_T";
}

typedef  CML_STARTVIDESADI_T {
    type union {
        type CML_VLAN_ENUM_T {

        }
        type CML_VLAN_RANGE_T {

        }
    }
    description "type definition for CML_STARTVIDESADI_T";
}

typedef  CML_NSM_DCB_QCN_MODE_T {
    type enumeration {
        enum admin {
            value 1;
            description "Admin-Mode";
        }
        enum auto {
            value 2;
            description "Automatic mode - LLDP should be enabled";
        }
        enum component {
            value 3;
            description "Defense mode same as the bridge level defense mode";
        }
    }
    description "type definition for CML_NSM_DCB_QCN_MODE_T";
}

typedef  CML_MAPPING_TYPE_T {
    type enumeration {
        enum admin {
            value 1;
            description "Admin-Mode";
        }
        enum auto {
            value 2;
            description "Automatic mode - LLDP should be enabled";
        }
        enum component {
            value 3;
            description "Defense mode same as the bridge level defense mode";
        }
    }
    description "type definition for CML_MAPPING_TYPE_T";
}

typedef  CML_ETS_MODE_T {
    type enumeration {
        enum on {
            value 1;
            description "ON to force enable Enhanced-trasnsmission-selection";
        }
        enum auto {
            value 2;
            description "AUTO to negotiate Enhanced-transmission-selection capabilities)";
        }
    }
    description "type definition for CML_ETS_MODE_T";
}

typedef  CML_DCBSTATE_T {
    type enumeration {
        enum off {
            value 0;
            description "disable";
        }
        enum on {
            value 1;
            description "enable";
        }
    }
    description "type definition for CML_DCBSTATE_T";
}

typedef  CML_PRIOFLAG_T {
    type enumeration {
        enum remove {
            value 0;
            description "remove";
        }
        enum add {
            value 1;
            description "add";
        }
    }
    description "type definition for CML_PRIOFLAG_T";
}

typedef  CML_PROTOID_T {
    type enumeration {
        enum tcp {
            value 2;
            description "Protocol Type tcp";
        }
        enum udp {
            value 3;
            description "Protocol Type udp";
        }
        enum both-tcp-udp {
            value 4;
            description "Protocol Type both-tcp-udp";
        }
        enum neither-tcp-udp {
            value 5;
            description "Protocol Type neither-tcp-udp";
        }
    }
    description "type definition for CML_PROTOID_T";
}

typedef  CML_DEFENSEMODE_T {
    type enumeration {
        enum disabled {
            value 1;
            description "Disabled Mode";
        }
        enum interior {
            value 2;
            description "Interior Mode";
        }
        enum interior-ready {
            value 3;
            description "Interior Ready Mode";
        }
        enum edge {
            value 4;
            description "Edge Mode";
        }
    }
    description "type definition for CML_DEFENSEMODE_T";
}

typedef  CML_LOADSHARE_T {

    type string;
    description "type definition for CML_LOADSHARE_T";
}

typedef  CML_PBR_LOADSHARE_T {
    type union {
        type inet:ipv4-address {

        }
        type CML_LOADSHARE_T {

        }
    }
    description "type definition for CML_PBR_LOADSHARE_T";
}

typedef  CML_PBR_V6_LOADSHARE_T {
    type union {
        type inet:ipv6-address {

        }
        type CML_LOADSHARE_T {

        }
    }
    description "type definition for CML_PBR_V6_LOADSHARE_T";
}

typedef  CML_DEBUG_EVENT_T {
    type bits {
        bit event {
            position 0;
            description "ARP related events";
        }
    }
    description "type definition for CML_DEBUG_EVENT_T";
}

typedef  CML_VRF_ENUM_T {
    type enumeration {
        enum all {
            value 1;
            description "All VRFs";
        }
        enum default {
            value 2;
            description "Default VRF";
        }
    }
    description "type definition for CML_VRF_ENUM_T";
}

typedef  CML_VRF_STRING_T {

    type string;
    description "type definition for CML_VRF_STRING_T";
}

typedef  CML_VRF_NAME_T {
    type union {
        type CML_VRF_ENUM_T {

        }
        type CML_VRF_STRING_T {

        }
    }
    description "type definition for CML_VRF_NAME_T";
}

typedef  CML_ADJNBR_T {
    type enumeration {
        enum adjacency {
            value 1;
            description "Clear adjacency";
        }
        enum neighbor {
            value 2;
            description "Clear neighbors";
        }
    }
    description "type definition for CML_ADJNBR_T";
}

typedef  CML_MPLS_VCLINKMODE_T {
    type enumeration {
        enum primary {
            value 0;
            description "Primary Link";
        }
        enum secondary {
            value 16;
            description "Secondary Link - Will not be activated unless primary fails";
        }
    }
    description "type definition for CML_MPLS_VCLINKMODE_T";
}

typedef  CML_VR_CONFIG_T {
    type enumeration {
        enum read {
            value 0;
            description "Read file";
        }
        enum write {
            value 1;
            description "Write file";
        }
    }
    description "type definition for CML_VR_CONFIG_T";
}

typedef  CML_STATIC_BFD_ENABLE_DISABLE_T {
    type enumeration {
        enum fall-over-bfd-disable {
            value 0;
            description "static fall-over, BFD, disable bfd";
        }
        enum fall-over-bfd {
            value 1;
            description "Enable static fall-over bfd,BFD";
        }
    }
    description "type definition for CML_STATIC_BFD_ENABLE_DISABLE_T";
}

typedef  CML_CMM_TRANSCEIVER_T {
    type enumeration {
        enum 1000base-sx {
            value 1;
            description "sfp 1000base-sx";
        }
        enum 1000base-lx {
            value 2;
            description "sfp 1000base-lx";
        }
        enum 1000base-ex {
            value 3;
            description "sfp 1000base-ex";
        }
        enum 1000base-cx {
            value 4;
            description "sfp 1000base-cx";
        }
        enum 10gbase-sr {
            value 5;
            description "sfp+ 10gbase-sr";
        }
        enum 10gbase-lr {
            value 6;
            description "sfp+ 10gbase-lr";
        }
        enum 10gbase-er {
            value 7;
            description "sfp+ 10gbase-er";
        }
        enum 10gbase-cr {
            value 8;
            description "sfp+ 10gbase-cr";
        }
        enum 40gbase-sr4 {
            value 9;
            description "qsfp 40gbase-sr4";
        }
        enum 40gbase-lr4 {
            value 10;
            description "qsfp 40gbase-lr4";
        }
        enum 40gbase-er4 {
            value 11;
            description "qsfp 40gbase-er4";
        }
        enum 40gbase-cr4 {
            value 12;
            description "qsfp 40gbase-cr4";
        }
        enum 100gbase-sr4 {
            value 13;
            description "qsfp28 100gbase-sr4";
        }
        enum 100gbase-lr4 {
            value 14;
            description "qsfp28 100gbase-lr4";
        }
        enum 100gbase-er4 {
            value 15;
            description "qsfp28 100gbase-er4";
        }
        enum 100gbase-cr4 {
            value 16;
            description "qsfp28 100gbase-cr4";
        }
    }
    description "type definition for CML_CMM_TRANSCEIVER_T";
}

typedef  CML_L2PROCESS_T {
    type enumeration {
        enum discard {
            value 1;
            description "Discard the protocol data unit";
        }
        enum peer {
            value 2;
            description "Act as peer to the customer Device instance of the protocol";
        }
        enum tunnel {
            value 3;
            description "Tunnel the Protocol data unit into the SVLAN";
        }
    }
    description "type definition for CML_L2PROCESS_T";
}

typedef  IF_L2PROCESS_CLEAR_T {
    type enumeration {
        enum peer {
            value 0;
            description "Clear stats for Peer protocol pkts";
        }
        enum tunnel {
            value 1;
            description "Clear stats for Tunnel protocol pkts";
        }
        enum discard {
            value 2;
            description "Clear stats for Discard protocol pkts";
        }
        enum tunnel-discard {
            value 3;
            description "Clear stats for Tunnel discard protocol pkts";
        }
        enum all {
            value 4;
            description "Clear stats for all protocol pkts";
        }
    }
    description "type definition for IF_L2PROCESS_CLEAR_T";
}

typedef  CML_NAT_PORT_TYPE_T {
    type enumeration {
        enum tcp {
            value 0;
            description "TCP";
        }
        enum udp {
            value 1;
            description "UDP";
        }
    }
    description "type definition for CML_NAT_PORT_TYPE_T";
}

typedef  CML_NAT_DIR_T {
    type enumeration {
        enum inside {
            value 0;
            description "Inside";
        }
        enum outside {
            value 1;
            description "Outside";
        }
    }
    description "type definition for CML_NAT_DIR_T";
}

typedef  CML_NAT_ADDR_TYPE_T {
    type enumeration {
        enum source {
            value 0;
            description "Source Address";
        }
        enum destination {
            value 1;
            description "Destination Address";
        }
    }
    description "type definition for CML_NAT_ADDR_TYPE_T";
}

typedef  CML_NAT_DIR_OUT_T {
    type enumeration {
        enum outside {
            value 1;
            description "Outside";
        }
    }
    description "type definition for CML_NAT_DIR_OUT_T";
}

typedef  CML_NAT_ADDR_TYPE_DEST_T {
    type enumeration {
        enum destination {
            value 1;
            description "Destination Address";
        }
    }
    description "type definition for CML_NAT_ADDR_TYPE_DEST_T";
}

typedef  CML_NAT_TRANS_DIR_T {
    type enumeration {
        enum src {
            value 0;
            description "Source address";
        }
        enum dest {
            value 1;
            description "Destination address";
        }
    }
    description "type definition for CML_NAT_TRANS_DIR_T";
}

typedef  CML_AGENTX_DEBUG_TYPE_T {
    type bits {
        bit snmp-send {
            position 0;
            description "SNMP  (AgentX or SMUX),Packet send";
        }
        bit snmp-receive {
            position 1;
            description "SNMP  (AgentX or SMUX),Packet receive";
        }
        bit snmp-process {
            position 2;
            description "SNMP  (AgentX or SMUX),Packet process";
        }
        bit snmp-xdump {
            position 3;
            description "SNMP  (AgentX or SMUX),Packet hexa dump";
        }
        bit snmp-error-string {
            position 4;
            description "SNMP  (AgentX or SMUX),Error string display";
        }
        bit snmp-detail {
            position 5;
            description "SNMP  (AgentX or SMUX),Detail debugging";
        }
    }
    description "type definition for CML_AGENTX_DEBUG_TYPE_T";
}

typedef  CML_PERMASTATE_T {
    type enumeration {
        enum permanent {
            value 1;
            description "permanent state";
        }
    }
    description "type definition for CML_PERMASTATE_T";
}

typedef  CML_IFSTATE_T {
    type enumeration {
        enum down {
            value 0;
            description "interface state down";
        }
        enum up {
            value 1;
            description "interface state up";
        }
    }
    description "type definition for CML_IFSTATE_T";
}

typedef  CML_GMPLS_LMPTYPE_T {
    type enumeration {
        enum static {
            value 0;
            description "static";
        }
        enum using-lmp {
            value 1;
            description "lmp";
        }
    }
    description "type definition for CML_GMPLS_LMPTYPE_T";
}

typedef  CML_GMPLS_TYPE_T {
    type enumeration {
        enum data-control {
            value 1;
            description "Data and Conrol";
        }
        enum data {
            value 2;
            description "Data";
        }
        enum control {
            value 3;
            description "Control";
        }
        enum data-numbered {
            value 4;
            description "Data, Numbered";
        }
    }
    description "type definition for CML_GMPLS_TYPE_T";
}

typedef  CML_MPLS_VPLS_OPCODE_T {
    type enumeration {
        enum swap {
            value 3;
            description "Swap incoming label";
        }
        enum vpnpop {
            value 4;
            description "Pop incoming label and forward VPN packet";
        }
    }
    description "type definition for CML_MPLS_VPLS_OPCODE_T";
}

typedef  CML_MPLS_VPLS_POPOPCODE_T {
    type enumeration {
        enum pop {
            value 2;
            description "pop incoming label";
        }
    }
    description "type definition for CML_MPLS_VPLS_POPOPCODE_T";
}

typedef  CML_MPLS_IPV6OPCODE_T {
    type enumeration {
        enum swap {
            value 3;
            description "Swap incoming label";
        }
    }
    description "type definition for CML_MPLS_IPV6OPCODE_T";
}

typedef  CML_GMPLS_BIDIRECTIONAL_FLAG_T {
    type enumeration {
        enum False {
            value 0;
            description "Bidirectional flag is not set";
        }
        enum True {
            value 1;
            description "Bidirectional flag is set";
        }
    }
    description "type definition for CML_GMPLS_BIDIRECTIONAL_FLAG_T";
}

typedef  CML_GMPLS_CAPABILITY_TYPE_T {
    type enumeration {
        enum psc1 {
            value 1;
            description "Packet Switch Capable-1 (PSC1)";
        }
        enum psc2 {
            value 2;
            description "Packet Switch Capable-2 (PSC2)";
        }
        enum psc3 {
            value 4;
            description "Packet Switch Capable-3 (PSC3)";
        }
        enum psc4 {
            value 8;
            description "Packet Switch Capable-4 (PSC4)";
        }
        enum pbb-te {
            value 256;
            description "Provider Backbone Bridging-Traffic Engineering (PBB-TE)";
        }
    }
    description "type definition for CML_GMPLS_CAPABILITY_TYPE_T";
}

typedef  CML_IP_VERSION_T {
    type enumeration {
        enum unknown {
            value 0;
            description "An unknown or unspecified version of the Internet protocol";
        }
        enum ipv4 {
            value 1;
            description "The IPv4 protocol as defined in RFC 2460.";
        }
        enum ipv6 {
            value 2;
            description "The IPv6 protocol as defined in RFC 2460.";
        }
    }
    description "This value represents the version of the IP protocol.";
    reference "RFC 6991: Common YANG data types";
}

typedef  CML_LACP_RCV_STATE_T {
    type enumeration {
        enum Invalid {
            value 0;
            description "";
        }
        enum Initialize {
            value 1;
            description "";
        }
        enum Port-disabled {
            value 2;
            description "";
        }
        enum LACP-disabled {
            value 3;
            description "";
        }
        enum Expired {
            value 4;
            description "";
        }
        enum Defaulted {
            value 5;
            description "";
        }
        enum Current {
            value 6;
            description "";
        }
    }
    description "type definition for CML_LACP_RCV_STATE_T";
}

typedef  CML_LACP_PERIODIC_TX_STATE_T {
    type enumeration {
        enum Invalid {
            value 0;
            description "";
        }
        enum No-periodic {
            value 1;
            description "";
        }
        enum Fast-periodic {
            value 2;
            description "";
        }
        enum Slow-periodic {
            value 3;
            description "";
        }
        enum Periodic {
            value 4;
            description "";
        }
    }
    description "type definition for CML_LACP_PERIODIC_TX_STATE_T";
}

typedef  CML_LACP_MUX_STATE_T {
    type enumeration {
        enum Detached {
            value 0;
            description "";
        }
        enum Waiting {
            value 1;
            description "";
        }
        enum Attached {
            value 2;
            description "";
        }
        enum Collecting {
            value 3;
            description "";
        }
        enum Distributing {
            value 4;
            description "";
        }
        enum Collecting-Distributing {
            value 5;
            description "";
        }
    }
    description "type definition for CML_LACP_MUX_STATE_T";
}

typedef  CML_PSSTATE_T {
    type enumeration {
        enum Not-Running {
            value 0;
            description "Stop the process";
        }
        enum Running {
            value 1;
            description "Start the process";
        }
    }
    description "type definition for CML_PSSTATE_T";
}

typedef  CML_GLOBAL_PSSTATE_T {
    type enumeration {
        enum False {
            value 0;
            description "one of the process not running";
        }
        enum True {
            value 1;
            description "All process are running";
        }
    }
    description "type definition for CML_GLOBAL_PSSTATE_T";
}

typedef  CML_WATCHDOGSTATUS_T {
    type enumeration {
        enum Disabled {
            value 0;
            description "Watchdog status is disabled globally";
        }
        enum Enabled {
            value 1;
            description "Watchdog status is enabled globally";
        }
    }
    description "type definition for CML_WATCHDOGSTATUS_T";
}

typedef  CML_MPLS_PORT_TYPE_T {
    type enumeration {
        enum access-port {
            value 1;
            description "Access interface statistics counters";
        }
        enum network-port {
            value 2;
            description "Network interface statistics counters";
        }
    }
    description "type definition for CML_MPLS_PORT_TYPE_T";
}

typedef  CML_MPLS_PORT_ACCESS_TYPE_T {
    type enumeration {
        enum access-port {
            value 1;
            description "Access interface statistics counters";
        }
    }
    description "type definition for CML_MPLS_PORT_ACCESS_TYPE_T";
}

typedef  CML_MPLS_PORT_NETWORK_TYPE_T {
    type enumeration {
        enum network-port {
            value 2;
            description "Network interface statistics counters";
        }
    }
    description "type definition for CML_MPLS_PORT_NETWORK_TYPE_T";
}

typedef  CML_VPLS_PEER_TYPE_T {

    type string;
    description "type definition for CML_VPLS_PEER_TYPE_T";
}

typedef  CML_VPLS_SPOKE_VC_TYPE_T {

    type string;
    description "type definition for CML_VPLS_SPOKE_VC_TYPE_T";
}

typedef  CML_NSM_MPLS_IF_ETHER_T {
    type enumeration {
        enum ethernet {
            value 0;
            description "Ethernet";
        }
    }
    description "type definition for CML_NSM_MPLS_IF_ETHER_T";
}

typedef  CML_NSM_MPLS_VLAN_INTERFACE_T {

    type string;
    description "type definition for CML_NSM_MPLS_VLAN_INTERFACE_T";
}

typedef  CML_MPLS_ACCESS_TYPE_T {
    type union {
        type CML_NSM_MPLS_VLAN_INTERFACE_T {

        }
        type CML_NSM_MPLS_IF_ETHER_T {

        }
    }
    description "type definition for CML_MPLS_ACCESS_TYPE_T";
}

typedef  CML_RAW_STRING_T {

    type string;
    description "type definition for CML_RAW_STRING_T";
}

typedef  CML_HW_TCAM_FILTER_T {
    type enumeration {
        enum ingress-l2-acl {
            value 1;
            description "Ingress ACL L2 filter profile";
        }
        enum ingress-qos {
            value 2;
            description "Ingress ACL QOS filter profile";
        }
        enum ingress-ipv4-acl {
            value 3;
            description "Ingress ACL IPV4 filter profile";
        }
        enum ingress-ipv6-acl {
            value 4;
            description "Ingress ACL IPV6 filter profile";
        }
        enum egress-l2-l3 {
            value 5;
            description "Egress ACL L2-L3 filter profile";
        }
        enum egress-ipv6-acl {
            value 6;
            description "Egress ACL IPV6 filter profile";
        }
    }
    description "type definition for CML_HW_TCAM_FILTER_T";
}

typedef  CML_KAPS_FORWADING_PROFILE_T {
    type enumeration {
        enum kaps-profile-one {
            value 9;
            description "kaps profile one";
        }
        enum kaps-profile-two {
            value 10;
            description "kaps profile two";
        }
    }
    description "type definition for CML_KAPS_FORWADING_PROFILE_T";
}

typedef  CML_ELK_TCAM_FORWADING_PROFILE_T {
    type enumeration {
        enum elk-tcam-profile-one {
            value 11;
            description "elk-tcam profile one";
        }
        enum elk-tcam-profile-two {
            value 12;
            description "elk-tcam profile two";
        }
        enum elk-tcam-profile-three {
            value 13;
            description "elk-tcam profile three";
        }
    }
    description "type definition for CML_ELK_TCAM_FORWADING_PROFILE_T";
}

typedef  CML_FRWD_PROFILE_T {
    type enumeration {
        enum l2-profile-one {
            value 0;
            description "L2 profile One";
        }
        enum l2-profile-two {
            value 1;
            description "L2 profile Two";
        }
        enum l2-profile-three {
            value 2;
            description "L2 profile Three (default)";
        }
        enum l3-profile {
            value 3;
            description "L3 profile";
        }
        enum l3-128bit-profile {
            value 4;
            description "L3 profile with 128 bit prefix support";
        }
        enum lpm-profile {
            value 5;
            description "LPM profile";
        }
        enum lpm-128bit-profile {
            value 6;
            description "LPM profile with 128 bit prefix support";
        }
        enum acl-profile {
            value 7;
            description "ACL profile";
        }
        enum custom-profile {
            value 8;
            description "custom profile";
        }
    }
    description "type definition for CML_FRWD_PROFILE_T";
}

typedef  CML_WATCHDOG_T {
    type enumeration {
        enum software-watchdog {
            value 1;
            description "Software Watchdog";
        }
    }
    description "type definition for CML_WATCHDOG_T";
}

typedef  CML_WATCHDOG_MODULE_NAME_T {
    type enumeration {
        enum nsm {
            value 1;
            description "Software watchdog for NSM module";
        }
        enum ripd {
            value 2;
            description "Software watchdog for RIP module";
        }
        enum ripngd {
            value 3;
            description "Software watchdog for RIPNG module";
        }
        enum ospfd {
            value 4;
            description "Software watchdog for OSPF module";
        }
        enum ospf6d {
            value 5;
            description "Software watchdog for OSPF6 module";
        }
        enum isisd {
            value 6;
            description "Software watchdog for ISIS module";
        }
        enum hostpd {
            value 7;
            description "Software watchdog for HOSTP module";
        }
        enum ldpd {
            value 8;
            description "Software watchdog for LDP module";
        }
        enum rsvpd {
            value 9;
            description "Software watchdog for RSVP module";
        }
        enum mribd {
            value 10;
            description "Software watchdog for MRIB module";
        }
        enum pimd {
            value 11;
            description "Software watchdog for PIM module";
        }
        enum authd {
            value 13;
            description "Software watchdog for AUTH module";
        }
        enum mstpd {
            value 17;
            description "Software watchdog for MSTP module";
        }
        enum imi {
            value 18;
            description "Software watchdog for IMI module";
        }
        enum onmd {
            value 24;
            description "Software watchdog for ONM module";
        }
        enum hsl {
            value 26;
            description "Software watchdog for HSL module";
        }
        enum oamd {
            value 28;
            description "Software watchdog for OAM module";
        }
        enum vlogd {
            value 30;
            description "Software watchdog for VLOG module";
        }
        enum vrrpd {
            value 39;
            description "Software watchdog for VRRP module";
        }
        enum ndd {
            value 40;
            description "Software watchdog for NDD module";
        }
        enum ribd {
            value 42;
            description "Software watchdog for RIB module";
        }
        enum bgpd {
            value 44;
            description "Software watchdog for BGP module";
        }
        enum l2mribd {
            value 46;
            description "Software watchdog for L2MRIB module";
        }
        enum lagd {
            value 49;
            description "Software watchdog for LAG module";
        }
        enum sflow {
            value 50;
            description "Software watchdog for SFLOW module";
        }
        enum cmld {
            value 52;
            description "Software watchdog for CML module";
        }
        enum cmmd {
            value 69;
            description "Software watchdog for CMM module";
        }
    }
    description "type definition for CML_WATCHDOG_MODULE_NAME_T";
}

typedef  CML_WATCHDOG_MODULE_STATUS_T {
    type enumeration {
        enum disabled {
            value 0;
            description "Disable software watchdog";
        }
        enum enabled {
            value 1;
            description "Enable software watchdog";
        }
    }
    description "type definition for CML_WATCHDOG_MODULE_STATUS_T";
}

typedef  CML_AGGREGATOR_TYPE_T {
    type enumeration {
        enum Layer3 {
            value 0;
            description "Layer3 aggregator";
        }
        enum Layer2 {
            value 1;
            description "Layer2 aggregator";
        }
    }
    description "type definition for CML_AGGREGATOR_TYPE_T";
}

typedef  CML_PROTOCOL_DEST_ADDR_TYPE_T {
    type enumeration {
        enum 01-80-c2-00-00-00 {
            value 0;
            description "LACP_NR_CUST_BR_ADDR";
        }
        enum 01-80-c2-00-00-02 {
            value 1;
            description "LACP_MCAST_GRP_ADDR";
        }
        enum 01-80-c2-00-00-03 {
            value 2;
            description "LACP_NR_NON_TPMR_BR_ADDR";
        }
    }
    description "type definition for CML_PROTOCOL_DEST_ADDR_TYPE_T";
}

typedef  CML_HQOS_MATCH_NOT_LAYER4_T {
    type enumeration {
        enum layer4 {
            value 0;
            description "Specify Layer4 Protocol";
        }
        enum ipv6-layer4 {
            value 2;
            description "Specify IPv6 values,Specify IPv6 Layer4 Protocol";
        }
    }
    description "type definition for CML_HQOS_MATCH_NOT_LAYER4_T";
}

typedef  CML_HQOS_LAYER4_PROTOCOL_T {
    type enumeration {
        enum any {
            value 0;
            description "Specify ANY protocol- TCP/UDP";
        }
        enum tcp {
            value 1;
            description "Specify TCP protocol";
        }
        enum udp {
            value 2;
            description "Specify UDP protocol";
        }
    }
    description "type definition for CML_HQOS_LAYER4_PROTOCOL_T";
}

typedef  CML_HQOS_LAYER4_PORT_T {
    type enumeration {
        enum source-port {
            value 1;
            description "Specify source TCP/UDP port";
        }
        enum destination-port {
            value 2;
            description "Specify destination TCP/UDP port";
        }
    }
    description "type definition for CML_HQOS_LAYER4_PORT_T";
}

typedef  CML_REDIRECT_MIRROR_PORT_T {
    type enumeration {
        enum redirect-to-port {
            value 5;
            description "Redirect packet to new interface";
        }
        enum mirror-to-port {
            value 6;
            description "Mirror packet to new interface";
        }
    }
    description "type definition for CML_REDIRECT_MIRROR_PORT_T";
}

typedef  CML_QOS_MODE_TYPE_T {
    type enumeration {
        enum allow {
            value 1;
            description "allow accept flow traffic";
        }
        enum deny {
            value 2;
            description "deny drop flow traffic";
        }
    }
    description "type definition for CML_QOS_MODE_TYPE_T";
}

typedef  CML_EXTERNAL_SYNCE_INTERFACE_T {
    type enumeration {
        enum gps {
            value 1;
            description "GPS interface as input-source";
        }
        enum 10mhz-in {
            value 2;
            description "10MHZ interface as input-source";
        }
        enum ptp {
            value 3;
            description "PTP interface as input-source";
        }
    }
    description "type definition for CML_EXTERNAL_SYNCE_INTERFACE_T";
}

typedef  CML_SYNCE_SYNC_OPTION_T {
    type enumeration {
        enum 1 {
            value 1;
            description "Set synchronization option to 1";
        }
        enum 2 {
            value 2;
            description "Set synchronization option to 2";
        }
    }
    description "type definition for CML_SYNCE_SYNC_OPTION_T";
}

typedef  CML_SYNCE_CLK_SELECTION_MODE_T {
    type enumeration {
        enum ql-enabled {
            value 1;
            description "Enable QL for clock selection";
        }
        enum ql-disabled {
            value 2;
            description "Disable QL for clock selection";
        }
    }
    description "type definition for CML_SYNCE_CLK_SELECTION_MODE_T";
}

typedef  CML_SYNCE_MODE_OPTION_T {
    type enumeration {
        enum synchronous {
            value 1;
            description "Configure the interface to synchronous mode";
        }
        enum non-synchronous {
            value 2;
            description "Configure the interface to non-synchronous mode";
        }
    }
    description "type definition for CML_SYNCE_MODE_OPTION_T";
}

typedef  CML_SYNCE_SOURCE_SELECT_T {
    type enumeration {
        enum force {
            value 1;
            description "Forcefully select a synchronization source";
        }
        enum manual {
            value 2;
            description "manually select a synchronization source";
        }
    }
    description "type definition for CML_SYNCE_SOURCE_SELECT_T";
}

typedef  CML_SYNCE_SIGNAL_FAIL_T {
    type enumeration {
        enum active {
            value 1;
            description "set to true";
        }
        enum non-active {
            value 2;
            description "set to false";
        }
    }
    description "type definition for CML_SYNCE_SIGNAL_FAIL_T";
}

typedef  CML_SYNCE_DEBUG_T {
    type enumeration {
        enum event {
            value 1;
            description "event debugs";
        }
        enum recvd {
            value 2;
            description "rx debugs";
        }
        enum trans {
            value 3;
            description "tx debugs";
        }
    }
    description "type definition for CML_SYNCE_DEBUG_T";
}

typedef  CML_SYNCE_ESMC_STATE_T {
    type enumeration {
        enum Idle {
            value 0;
            description "ESMC state is idle";
        }
        enum Start {
            value 1;
            description "ESMC state is Start";
        }
        enum OK {
            value 2;
            description "ESMC state is OK";
        }
        enum Failed {
            value 3;
            description "ESMC state is Failed";
        }
    }
    description "type definition for CML_SYNCE_ESMC_STATE_T";
}

typedef  CML_SYNCE_IS_SRC_SELECTED_T {
    type enumeration {
        enum No {
            value 0;
            description "Src is not seleceted";
        }
        enum Yes {
            value 1;
            description "Src is seleceted";
        }
    }
    description "type definition for CML_SYNCE_IS_SRC_SELECTED_T";
}

typedef  CML_SYNCE_IS_SF_T {
    type enumeration {
        enum No {
            value 0;
            description "Interface is not in Signal Fail condition";
        }
        enum Yes {
            value 1;
            description "Interface is in Signal Fail condition";
        }
    }
    description "type definition for CML_SYNCE_IS_SF_T";
}

typedef  CML_SYNCE_CLOCK_STATE_T {
    type enumeration {
        enum Free-run {
            value 1;
            description "Clk is in Free-run state";
        }
        enum Holdover {
            value 2;
            description "Clk is in Holdover state";
        }
        enum Locked {
            value 3;
            description "Clk is in Locked state";
        }
    }
    description "type definition for CML_SYNCE_CLOCK_STATE_T";
}

typedef  CML_SYNCE_EXTERNAL_CMDS_T {
    type enumeration {
        enum None {
            value 0;
            description "No external commands configured";
        }
        enum Lockout {
            value 1;
            description "Lockout external command configured";
        }
        enum Force {
            value 2;
            description "Force switch external command configured";
        }
        enum Manual {
            value 3;
            description "Manual switch external command configured";
        }
    }
    description "type definition for CML_SYNCE_EXTERNAL_CMDS_T";
}

typedef  ERPS_SWITCH_OPERATION_TYPE {
    type enumeration {
        enum force-switch {
            value 0;
            description "Trigger force switch. This operation overrides all other state of the ring.";
        }
        enum manual-switch {
            value 1;
            description "Trigger manual switch. This operation is allowed only when a ring instance is in idle or pending state. This action allows administrator to temporarily block another ring port and unblock RPL link to perform maintenance operation in the ring.";
        }
    }
    description "G.8032 administrative operation types.";
}

typedef  ERPS_PORT_ID_TYPE {
    type enumeration {
        enum east-interface {
            value 1;
            description "East-interface of the ring node.";
        }
        enum west-interface {
            value 2;
            description "West-interface of the ring node.";
        }
    }
    description "Each ring instance has maximum of two ports. This definition
                     labels these ports as east or west for identifications.";
}

typedef  CML_RMEP_ID_T {
    type union {
        type CML_MEP_ID_T {

        }
        type CML_RMEP_MAC_ADDR_T {

        }
    }
    description "type definition for CML_RMEP_ID_T";
}

typedef  CML_MEP_ID_T {

    type string;
    description "type definition for CML_MEP_ID_T";
}

typedef  CML_RMEP_MAC_ADDR_T {

    type string;
    description "type definition for CML_RMEP_MAC_ADDR_T";
}

typedef  CML_STARTTIME_T {
    type enumeration {
        enum immediate {
            value 1;
            description "Start the measurement session immediately";
        }
    }
    description "type definition for CML_STARTTIME_T";
}

typedef  CML_STOPTIME_T {
    type enumeration {
        enum none {
            value 0;
            description "Never end the measurement session";
        }
    }
    description "type definition for CML_STOPTIME_T";
}

typedef  CML_ABSOLUTE_T {
    type enumeration {
        enum absolute {
            value 3;
            description "This object specifies the scheduled start/stop date/time to perform the on-demand Performance Monitoring OAM operations";
        }
    }
    description "type definition for CML_ABSOLUTE_T";
}

typedef  CML_RELATIVE_T {
    type enumeration {
        enum relative {
            value 2;
            description "This object specifies the relative start/stop time from the current system time to perform on-demand Performance Monitoring OAM operations";
        }
    }
    description "type definition for CML_RELATIVE_T";
}

typedef  CML_PTP_ENCAP_TYPE_T {
    type enumeration {
        enum ipv4 {
            value 1;
            description "IPv4 Transport";
        }
        enum ipv6 {
            value 2;
            description "IPv6 Transport";
        }
    }
    description "type definition for CML_PTP_ENCAP_TYPE_T";
}

typedef  CML_NETWORK_INTERFACE_T {
    type union {
        type CML_IFNAME_T {

        }
        type CML_GPS_SMA_SMB_INTERFACE_T {

        }
    }
    description "type definition for CML_NETWORK_INTERFACE_T";
}

typedef  CML_GPS_SMA_SMB_INTERFACE_T {
    type enumeration {
        enum gps {
            value 0;
            description "GPS interface";
        }
        enum prc {
            value 1;
            description "SMA/SMB or external interfaces";
        }
    }
    description "type definition for CML_GPS_SMA_SMB_INTERFACE_T";
}

typedef  CML_PTP_CLOCK_TYPE_T {
    type enumeration {
        enum ordinary {
            value 1;
            description "The clock is an ordinary master or slave clock ";
        }
        enum boundary {
            value 2;
            description "The clock is a boundary clock";
        }
    }
    description "type definition for CML_PTP_CLOCK_TYPE_T";
}

typedef  CML_PTP_1PSS_IN_SMX_TOD_TYPE_T {
    type enumeration {
        enum smx {
            value 1;
            description "SMA Or SMB 1pps";
        }
        enum tod {
            value 2;
            description "TOD 1pps (default)";
        }
    }
    description "type definition for CML_PTP_1PSS_IN_SMX_TOD_TYPE_T";
}

typedef  CML_PTP_SERVO_STATE_T {
    type enumeration {
        enum Acquiring-lock {
            value 0;
            description "Servo state is Acquiring-lock";
        }
        enum Warmup {
            value 1;
            description "Servo state is Warmup";
        }
        enum Fast-loop {
            value 2;
            description "Servo state is Fast-loop";
        }
        enum Normal-loop {
            value 3;
            description "Servo state is Normal-loop";
        }
        enum Bridge {
            value 4;
            description "Servo state is Bridge";
        }
        enum Holdover {
            value 5;
            description "Servo state is Holdover";
        }
        enum Initial {
            value 6;
            description "Servo state is Initial";
        }
        enum Unqualified {
            value 7;
            description "Servo state is Unqualified";
        }
        enum Freq-Locked {
            value 8;
            description "Servo state is Freq-Locked";
        }
        enum Time-Locked {
            value 9;
            description "Servo state is Time-Locked";
        }
        enum Holdover-in-spec {
            value 10;
            description "Servo state is Holdover-in-spec";
        }
        enum Holdover-out-spec {
            value 11;
            description "Servo state is Holdover-out-spec";
        }
        enum Free-run {
            value 12;
            description "Servo state is Free-run";
        }
    }
    description "type definition for CML_PTP_SERVO_STATE_T";
}

typedef  CML_PTP_PORT_STATE_T {
    type enumeration {
        enum initializing {
            value 1;
            description "The port is initializing its data sets, hardware, and communication facilities";
        }
        enum faulty {
            value 2;
            description "The port is in the fault state";
        }
        enum disabled {
            value 3;
            description "The port is disabled, and is not communicating PTP messages";
        }
        enum listening {
            value 4;
            description "The port is listening for an Announce message";
        }
        enum pre-master {
            value 5;
            description "The port is in the pre-master state";
        }
        enum master {
            value 6;
            description "The port is behaving as a master port";
        }
        enum passive {
            value 7;
            description "The port is in the passive state";
        }
        enum uncalibrated {
            value 8;
            description "A master port has been selected, but the port is still in the uncalibrated state";
        }
        enum slave {
            value 9;
            description "The port is synchronizing to the selected master port";
        }
    }
    description "type definition for CML_PTP_PORT_STATE_T";
}

typedef  CML_PTP_DELAY_MECHANISM_T {
    type enumeration {
        enum E2E {
            value 1;
            description "The port is configured to use the delay request-response mechanism";
        }
        enum P2P {
            value 2;
            description "The port is configured to use the peer delay mechanism";
        }
        enum disabled {
            value 254;
            description "The port does not implement the delay mechanism";
        }
    }
    description "type definition for CML_PTP_DELAY_MECHANISM_T";
}

typedef  CML_PTP_TIME_INTERVAL_T {

    type int64;
    description "type definition for CML_PTP_TIME_INTERVAL_T";
}

typedef  CML_PTP_CLOCK_IDENTITY_T {

    type string{
    length 18..26;
    }
    description "type definition for CML_PTP_CLOCK_IDENTITY_T";
}

typedef  CML_PTP_INSTANCE_T {
    type enumeration {
        enum clock {
            value 0;
            description "Precision Time Protocol (PTP)";
        }
    }
    description "type definition for CML_PTP_INSTANCE_T";
}

typedef  CML_PTP_PROFILE_T {
    type enumeration {
        enum g8275.1 {
            value 1;
            description "PTP time/phase telecom profile";
        }
        enum g8275.2 {
            value 2;
            description "PTP time/phase telecom g8275.2 profile";
        }
    }
    description "type definition for CML_PTP_PROFILE_T";
}

typedef  CML_PTP_EXT_INTERFACE_T {
    type enumeration {
        enum 1pps {
            value 1;
            description "1PPS external interface";
        }
        enum 10mhz {
            value 2;
            description "10mhz external interface";
        }
        enum tod {
            value 3;
            description "ToD external interface";
        }
    }
    description "type definition for CML_PTP_EXT_INTERFACE_T";
}

typedef  CML_PTP_TOD_FORMAT_T {
    type enumeration {
        enum nmea {
            value 1;
            description "NMEA time of day format";
        }
        enum iso8601 {
            value 2;
            description "ISO 8601 time of day format";
        }
    }
    description "type definition for CML_PTP_TOD_FORMAT_T";
}

typedef  CML_PTP_CLOCK_IO_TYPE_T {
    type enumeration {
        enum input {
            value 1;
            description "Clock input";
        }
        enum output {
            value 2;
            description "Clock output";
        }
    }
    description "type definition for CML_PTP_CLOCK_IO_TYPE_T";
}

typedef  CML_PTP_TIME_SOURCE_T {
    type enumeration {
        enum Atomic-clock {
            value 16;
            description "None";
        }
        enum Global-positioning-system {
            value 32;
            description "None";
        }
        enum Terrestrial-radio {
            value 48;
            description "None";
        }
        enum PTP-based-source {
            value 64;
            description "None";
        }
        enum Network-Time-Protocol-source {
            value 80;
            description "None";
        }
        enum Handset {
            value 96;
            description "None";
        }
        enum Other-timesource {
            value 144;
            description "None";
        }
        enum Internal-Oscillator {
            value 160;
            description "None";
        }
    }
    description "type definition for CML_PTP_TIME_SOURCE_T";
}

typedef  CML_CMM_TIMESYNC_TYPE_T {
    type enumeration {
        enum 1pps {
            value 1;
            description "1 Pulse-per-Second clock";
        }
        enum 10mhz {
            value 2;
            description "10 Mhz clock";
        }
        enum tod {
            value 3;
            description "Time of Day interface";
        }
    }
    description "type definition for CML_CMM_TIMESYNC_TYPE_T";
}

typedef  CML_CMM_TIMESYNC_DIRECTION_T {
    type enumeration {
        enum input {
            value 1;
            description "Input clock interface";
        }
        enum output {
            value 2;
            description "Output clock interface";
        }
    }
    description "type definition for CML_CMM_TIMESYNC_DIRECTION_T";
}

typedef  CML_EVPN_SERVICE_TYPE_T {
    type enumeration {
        enum vlan-based {
            value 1;
            description "vlan-based EVPN-Service type";
        }
    }
    description "type definition for CML_EVPN_SERVICE_TYPE_T";
}

typedef  CML_EVPN_MPLS_ACC_IF_T {
    type enumeration {
        enum access-if {
            value 1;
            description "EVPN MPLS Access interface mode change";
        }
    }
    description "type definition for CML_EVPN_MPLS_ACC_IF_T";
}

typedef  CML_EVPN_TABLE_SHOW {
    type enumeration {
        enum mac-table {
            value 1;
            description "dynamic and static MAC table";
        }
        enum arp-cache {
            value 2;
            description "dynamic and static MAC-IPv4 table";
        }
        enum nd-cache {
            value 3;
            description "dynamic and static MAC-IPv6 table";
        }
    }
    description "type definition for CML_EVPN_TABLE_SHOW";
}

typedef  CML_LIBHWCONF_LOADBALANCE {
    type enumeration {
        enum enable {
            value 1;
            description "Command to enable/disable load-balance";
        }
    }
    description "type definition for CML_LIBHWCONF_LOADBALANCE";
}

typedef  CML_MACADD_MEPID_T {
    type union {
        type uint16 {

        }
        type CML_MAC_ADDR_T {

        }
    }
    description "type definition for CML_MACADD_MEPID_T";
}

typedef  CML_SUPPRESSRA_T {
    type enumeration {
        enum disable {
            value 0;
            description "Disable IPv6 Router Advertisements";
        }
        enum enable {
            value 1;
            description "Enable IPv6 Router Advertisements";
        }
    }
    description "type definition for CML_SUPPRESSRA_T";
}

typedef  CML_SUPPRESSRA_MTU_T {
    type enumeration {
        enum disable {
            value 0;
            description "Disable sending MTU in Router Advertisement messages";
        }
        enum enable {
            value 1;
            description "Enable sending MTU in Router Advertisement messages";
        }
    }
    description "type definition for CML_SUPPRESSRA_MTU_T";
}

typedef  CFM_BRIDGE_TYPE {
    type enumeration {
        enum vpws {
            value 1;
            description "Identifying string for VPWS instance";
        }
    }
    description "type definition for CFM_BRIDGE_TYPE";
}

typedef  CML_RMEPID_T {

    type string;
    description "type definition for CML_RMEPID_T";
}

typedef  CML_RMEP_TYPE_T {
    type union {
        type CML_RMEP_MAC_ADDR_T {

        }
        type CML_RMEPID_T {

        }
    }
    description "type definition for CML_RMEP_TYPE_T";
}

typedef  CML_HOSTP_RBAC_RULE_TYPE_T {
    type enumeration {
        enum deny {
            value 0;
            description "Remove rule from policy";
        }
        enum permit {
            value 1;
            description "Add rule to policy";
        }
    }
    description "type definition for CML_HOSTP_RBAC_RULE_TYPE_T";
}

typedef  CML_HOSTP_RBAC_DEFAULT_RULE_TYPE_T {
    type enumeration {
        enum deny-all {
            value 0;
            description "Set default rule as deny-all";
        }
        enum permit-all {
            value 1;
            description "Set default rule as permit-all";
        }
    }
    description "type definition for CML_HOSTP_RBAC_DEFAULT_RULE_TYPE_T";
}

typedef  CML_VM_STATUS_T {
    type enumeration {
        enum DOWN {
            value 0;
            description "DOWN";
        }
        enum UP {
            value 1;
            description "UP";
        }
    }
    description "type definition for CML_VM_STATUS_T";
}

typedef  CML_LIBHWCONF_CPU_QUEUE_MONITOR {
    type enumeration {
        enum no-monitor {
            value 0;
            description "do not monitor cpu queue usage";
        }
        enum monitor {
            value 1;
            description "monitor cpu queue usage";
        }
    }
    description "type definition for CML_LIBHWCONF_CPU_QUEUE_MONITOR";
}

typedef  CML_LIBHWCONF_CPU_QUEUE_NAME {
    type enumeration {
        enum cpu.q0 {
            value 0;
            description "cpu.q0";
        }
        enum cpu.q1 {
            value 1;
            description "cpu.q1";
        }
        enum cpu.q2 {
            value 2;
            description "cpu.q2";
        }
        enum cpu.q3 {
            value 3;
            description "cpu.q3";
        }
        enum cpu.q4 {
            value 4;
            description "cpu.q4";
        }
        enum cpu.q5 {
            value 5;
            description "cpu.q5";
        }
        enum cpu.q6 {
            value 6;
            description "cpu.q6";
        }
        enum cpu.q7 {
            value 7;
            description "cpu.q7";
        }
        enum igmp {
            value 16;
            description "IGMP queue parameters";
        }
        enum isis {
            value 17;
            description "ISIS queue parameters";
        }
        enum reserved-mc {
            value 18;
            description "reserved-mc queue parameters";
        }
        enum link-local {
            value 19;
            description "Link-local  queue parameters";
        }
        enum ospf {
            value 20;
            description "OSPF queue parameters";
        }
        enum bgp {
            value 21;
            description "BGP queue parameters";
        }
        enum rsvp-ldp {
            value 22;
            description "RSVP/LDP queue parameters";
        }
        enum vrrp-rip-dhcp {
            value 23;
            description "VRRP/RIP/DHCP queue parameters";
        }
        enum pim {
            value 24;
            description "PIM queue parameters";
        }
        enum icmp-mpls {
            value 25;
            description "ICMP/MPLS queue parameters";
        }
        enum arp {
            value 26;
            description "ARP queue parameters";
        }
        enum bpdu {
            value 27;
            description "BPDU queue parameters";
        }
        enum oamp {
            value 28;
            description "OAMP queue parameters";
        }
        enum sflow {
            value 29;
            description "sflow queue parameters";
        }
        enum dsp {
            value 30;
            description "DSP queue parameters";
        }
        enum vxlan {
            value 31;
            description "VXLAN queue parameters";
        }
        enum nhop {
            value 32;
            description "nhop queue parameters";
        }
        enum icmp-redirect {
            value 33;
            description "ICMP-redirect queue parameters";
        }
        enum bfd {
            value 35;
            description "BFD queue parameters";
        }
    }
    description "type definition for CML_LIBHWCONF_CPU_QUEUE_NAME";
}

typedef  CML_OLT_PORTS_TYPE_T {
    type enumeration {
        enum nni {
            value 0;
            description "nni ports";
        }
        enum pon {
            value 1;
            description "pon ports";
        }
    }
    description "type definition for CML_OLT_PORTS_TYPE_T";
}

typedef  CML_OLT_FLOW_PORT_TYPE_T {
    type enumeration {
        enum nni-port {
            value 0;
            description "nni port";
        }
        enum uni-port {
            value 1;
            description "uni port";
        }
    }
    description "type definition for CML_OLT_FLOW_PORT_TYPE_T";
}

typedef  CML_OLT_OLT_ID_TYPE_T {
    type enumeration {
        enum 0 {
            value 0;
            description "OLT ID 0 (only OLT ID 0 supported)";
        }
    }
    description "type definition for CML_OLT_OLT_ID_TYPE_T";
}

}
