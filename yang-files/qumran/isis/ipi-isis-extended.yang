/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-isis-extended.yang
*
*/

submodule ipi-isis-extended {

    yang-version 1.1;

    belongs-to  ipi-isis { prefix ipi-isis; }

    import feature-list {
        prefix feature-list;
    }

    import ipi-isis-types {
        prefix ipi-isis-types;
    }

    import cml-data-types {
        prefix cml-data-types;
    }

    import ietf-inet-types {
        prefix inet;
    }

    organization
        "IP Infusion Inc.";

    contact
        "Address: 3965 Freedom Circle, Suite 200, Santa Clara, CA 95054
         Phone: +1 408-400-1900
         E-mail: support@ipinfusion.com
         Web: http://www.ipinfusion.com/";

    description
        "Model for managing IS-IS Extended Parameters";


    revision "2020-12-15" {
        description "Change to have data-types in lower case instead of camel case";
        reference " 0.2.0.";
    }

    revision "2020-05-06" {
        description "Datamodel restructuring";
        reference " 0.1.0.";
    }



    grouping ipv4-lfa-route-grouping {
    description
        "This objectlist defines the ISIS LFA Route";
        list ipv4-lfa-route {
            key "destination-prefix";
            config false;
            description
                "This objectlist defines the ISIS LFA Route";
            leaf destination-prefix  {
                type  leafref {
                    path  "../state/destination-prefix";
                }
                description "Destination Prefix for the LFA route";
            } // END of destination-prefix definition.


            list route-nexthop {
                key "primary-nexthop";
                config false;
                description
                    "This objectlist defines the ISIS LFA Route Next Hop";
                leaf primary-nexthop  {
                    type  leafref {
                        path  "../state/primary-nexthop";
                    }
                    description "Primary Nexthop address of LFA route";
                } // END of primary-nexthop definition.

                container state {
                    config false;
                    description
                        "This container defines the ISIS LFA Route Next Hop State";
                    uses isis-lfa-route-nh-state;
                } // END of state-container definition.
            } // End of route-nexthop-list
            container state {
                config false;
                description
                    "This container defines the ISIS LFA Route State";
                uses isis-lfa-route-state;
            } // END of state-container definition.
        } // End of ipv4-lfa-route-list
    } // END of ipv4-lfa-route-grouping definition.


    grouping ipv6-lfa-route-grouping {
    description
        "This objectlist defines the ISIS IPv6 LFA Route";
        list ipv6-lfa-route {
            key "destination-prefix";
            config false;
            description
                "This objectlist defines the ISIS IPv6 LFA Route";
            leaf destination-prefix  {
                type  leafref {
                    path  "../state/destination-prefix";
                }
                description "Destination Prefix of LFA route";
            } // END of destination-prefix definition.


            list route-nexthop {
                key "primary-nexthop";
                config false;
                description
                    "This objectlist defines the ISIS IPv6 LFA Route Next Hop";
                leaf primary-nexthop  {
                    type  leafref {
                        path  "../state/primary-nexthop";
                    }
                    description "Primary Nexthop address of LFA route";
                } // END of primary-nexthop definition.

                container state {
                    config false;
                    description
                        "This container defines the ISIS IPv6 LFA Route Next Hop State";
                    uses isis-ipv6-lfa-route-nh-state;
                } // END of state-container definition.
            } // End of route-nexthop-list
            container state {
                config false;
                description
                    "This container defines the ISIS IPv6 LFA Route State";
                uses isis-ipv6-lfa-route-state;
            } // END of state-container definition.
        } // End of ipv6-lfa-route-list
    } // END of ipv6-lfa-route-grouping definition.


    grouping fast-reroute-grouping {
    description
        "This objectlist defines the Fast Reroute";
        list fast-reroute {
        when " /isis/isis-instance/fast-reroute/route-map/protocol  or /isis/isis-instance/fast-reroute/protocol/lfa-protocol  or /isis/isis-instance/fast-reroute/ti-lfa/protocol ";
            key "level-type";
            description
                "This objectlist defines the Fast Reroute";
            leaf level-type  {
                type  leafref {
                    path  "../config/level-type";
                }
                description "IS-IS instance level,(1|2)";
            } // END of level-type definition.


            list route-map {
                if-feature feature-list:HAVE_ISIS_LFA;
                key "protocol";
                description
                    "This objectlist defines the Fast Reroute list";
                leaf protocol  {
                    type  leafref {
                        path  "../config/protocol";
                    }
                    description "Protocol Address Family";
                } // END of protocol definition.

                container config {
                    description
                        "This container defines the ISIS FRR Routemap Configurations";
                    uses isis-frr-routemap-config;
                } // END of config-container definition.
                container state {
                    config false;
                    description
                        "This container defines the ISIS FRR Routemap state information";
                    uses isis-frr-routemap-config;
                } // END of state-container definition.
            } // End of route-map-list

            list ti-lfa {
                if-feature feature-list:HAVE_ISIS_TI_LFA;
                key "protocol";
                description
                    "Topology Independent LFA protocol information";
                leaf protocol  {
                    type  leafref {
                        path  "../config/protocol";
                    }
                    description "Protocol Address Family";
                } // END of protocol definition.

                container config {
                    description
                        "This container defines the ISIS TI-LFA Configurations";
                    uses isis-ti-lfa-config;
                } // END of config-container definition.
                container state {
                    config false;
                    description
                        "This container defines the ISIS TI-LFA State information";
                    uses isis-ti-lfa-config;
                } // END of state-container definition.
            } // End of ti-lfa-list

            list protocol {
                if-feature feature-list:HAVE_ISIS_LFA;
                key "lfa-protocol preference-value";
                description
                    "This objectlist defines the Fast Protocol List";
                leaf lfa-protocol  {
                    type  leafref {
                        path  "../config/lfa-protocol";
                    }
                    description "LFA Protocol (ipv4 | ipv6)";
                } // END of lfa-protocol definition.

                leaf preference-value  {
                    type  leafref {
                        path  "../config/preference-value";
                    }
                    description "Indicates which tie-break option to use.";
                } // END of preference-value definition.

                container config {
                    description
                        "This container defines the ISIS FRR Routemap Configurations";
                    uses isis-frr-proto-config;
                } // END of config-container definition.
                container state {
                    config false;
                    description
                        "This container defines the ISIS FRR Routemap state information";
                    uses isis-frr-proto-config;
                } // END of state-container definition.
            } // End of protocol-list
            container config {
                description
                    "This container defines the ISIS FRR level type Configurations";
                uses isis-frr-level-type-config;
            } // END of config-container definition.
            container state {
                config false;
                description
                    "This container defines the ISIS FRR level type State information";
                uses isis-frr-level-type-config;
            } // END of state-container definition.
        } // End of fast-reroute-list
    } // END of fast-reroute-grouping definition.
    grouping isis-lfa-route-state {
        description
            "State items for ISIS LFA Route";
        leaf destination-prefix  {
            type  inet:ipv4-prefix;
            description "Destination Prefix of LFA route";
        } // END of destination-prefix definition.

        leaf destination-path-type  {
            type  string {
                length "1..max";
                pattern "[^?' =,>|]+";
            }
            description "Destination Path Type of LFA route";
        } // END of destination-path-type definition.

    } // END of isis-lfa-route-state definition.
    grouping isis-lfa-route-nh-state {
        description
            "State items for ISIS LFA Route Next Hop";
        leaf primary-nexthop  {
            type  inet:ipv4-address;
            description "Primary Nexthop address of LFA route";
        } // END of primary-nexthop definition.

        leaf primary-nexthop-interface-name  {
            type  string {
                length "1..max";
                pattern "[^?' =,>|]+";
            }
            description "Primary Nexthop Interface Name of LFA route";
        } // END of primary-nexthop-interface-name definition.

        leaf lfa-nexthop  {
            type  inet:ipv4-address;
            description "LFA Nexthop Prefix of LFA route";
        } // END of lfa-nexthop definition.

        leaf lfa-nexthop-interface-name  {
            type  string {
                length "1..max";
                pattern "[^?' =,>|]+";
            }
            description "LFA Nexthop Interface Name of LFA route";
        } // END of lfa-nexthop-interface-name definition.

        leaf lfa-path-metric  {
            type  uint32;
            description "LFA Path Metric of LFA route";
        } // END of lfa-path-metric definition.

        leaf protection-provided  {
            type  cml-data-types:cml_line_t;
            description "Protection Provided for LFA route";
        } // END of protection-provided definition.

    } // END of isis-lfa-route-nh-state definition.
    grouping isis-ipv6-lfa-route-state {
        description
            "State items for ISIS IPv6 LFA Route";
        leaf destination-prefix  {
            type  inet:ipv6-prefix;
            description "Destination Prefix of LFA route";
        } // END of destination-prefix definition.

        leaf destination-path-type  {
            type  string {
                length "1..max";
                pattern "[^?' =,>|]+";
            }
            description "Destination Path Type of LFA route";
        } // END of destination-path-type definition.

    } // END of isis-ipv6-lfa-route-state definition.
    grouping isis-ipv6-lfa-route-nh-state {
        description
            "State items for ISIS IPv6 LFA Route Next Hop";
        leaf primary-nexthop  {
            type  inet:ipv6-address;
            description "Primary Nexthop address of LFA route";
        } // END of primary-nexthop definition.

        leaf primary-nexthop-interface-name  {
            type  string {
                length "1..max";
                pattern "[^?' =,>|]+";
            }
            description "Primary Nexthop Interface Name of LFA route";
        } // END of primary-nexthop-interface-name definition.

        leaf lfa-nexthop  {
            type  inet:ipv6-address;
            description "Nexthop Prefix of LFA route";
        } // END of lfa-nexthop definition.

        leaf lfa-nexthop-interface-name  {
            type  string {
                length "1..max";
                pattern "[^?' =,>|]+";
            }
            description "Nexthop Interface Name of LFA route";
        } // END of lfa-nexthop-interface-name definition.

        leaf lfa-path-metric  {
            type  uint32;
            description "Path Metric of LFA route";
        } // END of lfa-path-metric definition.

        leaf protection-provided  {
            type  string {
                length "1..max";
                pattern "[^?' =,>|]+";
            }
            description "Protection Provided for LFA route";
        } // END of protection-provided definition.

    } // END of isis-ipv6-lfa-route-nh-state definition.
    grouping isis-ti-lfa-config {
        description
            "Config items for ISIS TI-LFA";
        leaf protocol  {
            type  ipi-isis-types:isis_lfa_level_proto_t;
            description "Protocol Address Family";
        } // END of protocol definition.

    } // END of isis-ti-lfa-config definition.
    grouping isis-frr-level-type-config {
        description
            "Configuration items for ISIS FRR Routemap";
        leaf level-type  {
            type  ipi-isis-types:isis_level2_t;
            description "IS-IS instance level,(1|2)";
        } // END of level-type definition.

    } // END of isis-frr-level-type-config definition.
    grouping isis-frr-routemap-config {
        description
            "Configuration items for ISIS FRR Routemap";
        leaf protocol  {
            type  ipi-isis-types:isis_lfa_level_proto_t;
            description "Protocol Address Family";
        } // END of protocol definition.

        leaf name  {
            when " not(/isis/isis-instance/fast-reroute/route-map/config/enable-all-prefixes) ";
            type  string {
                length "1..max";
                pattern "[^?' =,>|]+";
            }
            description "Specific prefixex allowed using this route map";
        } // END of name definition.

        leaf enable-all-prefixes  {
            when " not(/isis/isis-instance/fast-reroute/route-map/config/name) ";
            type  ipi-isis-types:isis_frr_enum_t;
            description "Apply on all prefixes";
        } // END of enable-all-prefixes definition.

    } // END of isis-frr-routemap-config definition.
    grouping isis-frr-proto-config {
        description
            "Configuration items for ISIS FRR Protocol";
        leaf lfa-protocol  {
            type  ipi-isis-types:isis_lfa_level_proto_t;
            description "Protocol Address Family";
        } // END of lfa-protocol definition.

        leaf preference-value  {
            type  ipi-isis-types:isis_frr_tie_break_val_t;
            description "Indicates which tie-break option to use.";
        } // END of preference-value definition.

        leaf preference-index  {
            type  uint32 {
                 range "1..255"  {
                    description "Index";
                 }
            }
            mandatory true;
            description "this index indicates which tie-break option to be given preference";
        } // END of preference-index definition.

    } // END of isis-frr-proto-config definition.
    grouping isis-gr-config {
        description
            "Configuration items for ISIS  GR Configurations";
        leaf grace-period  {
            type  uint16 {
                 range "1..65535"  {
                    description "Seconds";
                 }
            }
            description "The period within which ISIS should come up";
        } // END of grace-period definition.

        leaf enable-helper-only  {
            type  empty;
            description "Attribute to configure helper mode";
        } // END of enable-helper-only definition.

        leaf suppress-adjacency  {
            type  empty;
            description "When set to true, adjacency is not advertised. The SA bit is used by a
                        starting router to  request that its neighbor suppress advertisement
                        of the adjacency  to the starting router in the neighbor's LSPs.";
        } // END of suppress-adjacency definition.

    } // END of isis-gr-config definition.

    grouping  graceful-restart-grouping {
    description
        "This container defines the ISIS Graceful Restart";
    container graceful-restart {
        description
            "This container defines the ISIS Graceful Restart";
        container config {
            description
                "This container defines the ISIS Graceful Restart config parameters";
            uses isis-gr-config;
        } // END of config-container definition.
        container state {
            config false;
            description
                "This container defines the ISIS Graceful Restart state information";
            uses isis-gr-config;
        } // END of state-container definition.
    } // END of graceful-restart-container definition.
    } // END of graceful-restart-grouping definition.


}
