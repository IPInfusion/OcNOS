/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-isis-sr.yang
*
*/

submodule ipi-isis-sr {

    yang-version 1.1;

    belongs-to  ipi-isis { prefix ipi-isis; }

    import feature-list {
        prefix feature-list;
        revision-date 2021-05-03;
    }

    import cml-data-types {
        prefix cml-data-types;
        revision-date 2021-05-03;
    }

    import ipi-isis-types {
        prefix ipi-isis-types;
        revision-date 2020-12-15;
    }

    import ietf-inet-types {
        prefix inet;
        revision-date 2013-07-15;
    }

    organization
        "IP Infusion Inc.";

    contact
        "Address: 3965 Freedom Circle, Suite 200, Santa Clara, CA 95054
         Phone: +1 408-400-1900
         E-mail: support@ipinfusion.com
         Web: http://www.ipinfusion.com/";

    description
        "Model for managing IS-IS SR Parameters";


    revision "2020-12-15" {
        description "Change to have data-types in lower case instead of camel case";
        reference " 0.2.0.";
    }

    revision "2020-05-06" {
        description "Datamodel restructuring";
        reference " 0.1.0.";
    }



    grouping segment-routing-capability-grouping {
    description
        "ISIS SR Capability Attributes";
        list segment-routing-capability {
            key "advertising-router-ip";
            config false;
            description
                "ISIS SR Capability Attributes";
            leaf advertising-router-ip  {
                type  leafref {
                    path  "../state/advertising-router-ip";
                }
                description "Advertising Router";
            } // END of advertising-router-ip definition.


            list range-info {
                key "index";
                config false;
                description
                    "ISIS SRCAP Range Information";
                leaf index  {
                    type  leafref {
                        path  "../state/index";
                    }
                    description "SID's Range Index";
                } // END of index definition.

                container state {
                    config false;
                    description
                        "State Attributes for SRCAP Range Information";
                    uses isis-srcap-range-state;
                } // END of state-container definition.
            } // End of range-info-list
            container state {
                config false;
                description
                    "State Attributes for ISIS SRCAP";
                uses isis-srcap-state;
            } // END of state-container definition.
        } // End of segment-routing-capability-list
    } // END of segment-routing-capability-grouping definition.


    grouping segment-routing-mapping-server-ipv4-grouping {
    description
        "ISIS IPv4 SR mapping table";
        list segment-routing-mapping-server-ipv4 {
            key "type";
            config false;
            description
                "ISIS IPv4 SR mapping table";
            leaf type  {
                type  leafref {
                    path  "../state/type";
                }
                description "ISIS Sr Mapping table type Active/Inactive";
            } // END of type definition.


            list ipv4-table {
                key "prefix-length";
                config false;
                description
                    "IPv4 SR Mapping Table Attributes";
                leaf prefix-length  {
                    type  leafref {
                        path  "../state/prefix-length";
                    }
                    description "ISIS Sr Mapping Table Prefix length";
                } // END of prefix-length definition.


                list entry {
                    key "index";
                    config false;
                    description
                        "State Attributes for ISIS SRMS IPv4 Table Entry";
                    leaf index  {
                        type  leafref {
                            path  "../state/index";
                        }
                        description "SR map table entry SID's Index";
                    } // END of index definition.

                    container state {
                        config false;
                        description
                            "ISIS SRMS IPv4 Table Entry";
                        uses isis-srms-ipv4-table-entry-state;
                    } // END of state-container definition.
                } // End of entry-list
                container state {
                    config false;
                    description
                        "IPv4 SR Mapping Table State";
                    uses isis-srms-ipv4-table-state;
                } // END of state-container definition.
            } // End of ipv4-table-list
            container state {
                config false;
                description
                    "IPv4 SR Mapping Table State";
                uses isis-srms-ipv4-state;
            } // END of state-container definition.
        } // End of segment-routing-mapping-server-ipv4-list
    } // END of segment-routing-mapping-server-ipv4-grouping definition.


    grouping segment-routing-mapping-server-ipv6-grouping {
    description
        "ISIS IPv6 SR mapping table";
        list segment-routing-mapping-server-ipv6 {
            key "type";
            config false;
            description
                "ISIS IPv6 SR mapping table";
            leaf type  {
                type  leafref {
                    path  "../state/type";
                }
                description "ISIS Sr Mapping table type Active/Inactive";
            } // END of type definition.


            list ipv6-table {
                key "prefix-length";
                config false;
                description
                    "SR Mapping Table Attributes";
                leaf prefix-length  {
                    type  leafref {
                        path  "../state/prefix-length";
                    }
                    description "ISIS Sr Mapping Table Prefix length";
                } // END of prefix-length definition.


                list entry {
                    key "index";
                    config false;
                    description
                        "State Attributes for ISIS SRMS IPv6 Table Entry";
                    leaf index  {
                        type  leafref {
                            path  "../state/index";
                        }
                        description "SR map table entry SID's Index";
                    } // END of index definition.

                    container state {
                        config false;
                        description
                            "ISIS SRMS IPv6 Table Entry";
                        uses isis-srms-ipv6-table-entry-state;
                    } // END of state-container definition.
                } // End of entry-list
                container state {
                    config false;
                    description
                        "IPv6 SR Mapping Table State";
                    uses isis-srms-ipv6-table-state;
                } // END of state-container definition.
            } // End of ipv6-table-list
            container state {
                config false;
                description
                    "IPv6 SR Mapping Table State";
                uses isis-srms-ipv6-state;
            } // END of state-container definition.
        } // End of segment-routing-mapping-server-ipv6-list
    } // END of segment-routing-mapping-server-ipv6-grouping definition.
    grouping isis-sr-path-config {
        description
            "SR Path Configurations";
        leaf name  {
            type  string {
                length "1..1965";
                pattern "[^?' =,>|]+";
            }
            description "Name of SR Path";
        } // END of name definition.

    } // END of isis-sr-path-config definition.
    grouping isis-sr-path-ero-config {
        description
            "SR Path ERO Configurations";
        leaf hop-address  {
            type  inet:ipv4-address;
            description "Path Constraint for SR";
        } // END of hop-address definition.

    } // END of isis-sr-path-ero-config definition.
    grouping isis-sr-path-ero-adjacent-config {
        description
            "SR Path ERO Adjacent Configurations";
        leaf adj-hop-address  {
            type  inet:ipv4-address;
            description "Hop Address";
        } // END of adj-hop-address definition.

    } // END of isis-sr-path-ero-adjacent-config definition.
    grouping isis-sr-path-ipv6-ero-config {
        description
            "IPv6 SR Path Ero Configurations";
        leaf hop-address6  {
            type  inet:ipv6-address;
            description "Path Constraint for SR Path";
        } // END of hop-address6 definition.

    } // END of isis-sr-path-ipv6-ero-config definition.
    grouping isis-sr-path-ipv6-ero-adjacent-config {
        description
            "IPv6 SR Path ERO Adjacent Configurations";
        leaf adj-hop-address6  {
            type  inet:ipv6-address;
            description "Use this attribute to configure path cosntraint for SR Path";
        } // END of adj-hop-address6 definition.

    } // END of isis-sr-path-ipv6-ero-adjacent-config definition.
    grouping isis-sr-config {
        description
            "Configuration items for ISIS SR";
        leaf enabled  {
            if-feature feature-list:HAVE_ISIS_SR;
            type  empty;
            mandatory true;
            description "Use this attribute to enable MPLS-based segment routing for an ISIS
                        process";
        } // END of enabled definition.

        leaf advertise-local  {
            if-feature feature-list:HAVE_ISIS_SR;
            type  empty;
            description "Use this attribute to advertise prefix-SID mapping";
        } // END of advertise-local definition.

        leaf receive-disable  {
            if-feature feature-list:HAVE_ISIS_SR;
            type  empty;
            description "Use this attribute to receive label binding TLVs";
        } // END of receive-disable definition.

    } // END of isis-sr-config definition.
    grouping isis-sr-global-block-config {
        description
            "Configuration items for ISIS SR Global Block";
        leaf global-block-base  {
            when " /isis/isis-instance/segment-routing/global-block/config/global-block-range ";
            type  int32 {
                 range "16000..1048575"  {
                    description "16000..1048575:SRGB Starting Range";
                 }
            }
            description "Segment Node Base Value";
        } // END of global-block-base definition.

        leaf global-block-range  {
            when " /isis/isis-instance/segment-routing/global-block/config/global-block-base ";
            if-feature feature-list:HAVE_ISIS_SR;
            type  int32 {
                 range "16000..1048575"  {
                    description "16000..1048575:SRGB End Range";
                 }
            }
            description "Use this attribute to set the SRGB range at each node. If you do not
                        specify a per-node range with the segmentrouting global block command,
                        this range will be used by that ISIS instance. IGP protocols must use
                        same SRGB range or use a different non-overlapping SRGB range. Note:
                        For a segment routing trunk, all nodes on the path of the trunk should
                        have same SRGB range for the trunk to be established.";
        } // END of global-block-range definition.

    } // END of isis-sr-global-block-config definition.
    grouping isis-srcap-state {
        description
            "State items for ISIS Srcap";
        leaf advertising-router-ip  {
            type  inet:ipv4-address;
            description "Advertising Router";
        } // END of advertising-router-ip definition.

        leaf algoritm  {
            type  ipi-isis-types:isis_spf_t;
            description "Segment Routing Algorithm";
        } // END of algoritm definition.

        leaf mapping-server-preference  {
            type  uint32;
            description "SRMS Preference";
        } // END of mapping-server-preference definition.

        leaf total-sid-count  {
            type  uint32;
            description "Index accumlated for total number of label published for that node";
        } // END of total-sid-count definition.

        leaf sid-range-list-count  {
            type  uint8;
            description "count for list of Ranges";
        } // END of sid-range-list-count definition.

    } // END of isis-srcap-state definition.
    grouping isis-srcap-range-state {
        description
            "State items for ISIS Scrap Range";
        leaf start  {
            type  uint32;
            description "SID's Range start";
        } // END of start definition.

        leaf end  {
            type  uint32;
            description "SID's Range End";
        } // END of end definition.

        leaf index  {
            type  uint32;
            description "SID's Range Index";
        } // END of index definition.

    } // END of isis-srcap-range-state definition.
    grouping isis-srms-ipv4-state {
        description
            "State items for ISIS SRMS IPv4";
        leaf type  {
            type  ipi-isis-types:isis_srms_type_t;
            description "ISIS Sr Mapping table type Active/Inactive";
        } // END of type definition.

        leaf entry-count  {
            type  uint32;
            description "ISIS Sr Mapping table entry count";
        } // END of entry-count definition.

        leaf conflict-resolution-policy  {
            type  string {
                length "1..1965";
                pattern "[^?' =,>|]+";
            }
            description "ISIS Sr Mapping table Conflict Resolution Policy";
        } // END of conflict-resolution-policy definition.

    } // END of isis-srms-ipv4-state definition.
    grouping isis-srms-ipv4-table-state {
        description
            "State items for ISIS SRMS IPv4 Table";
        leaf prefix-length  {
            type  uint32;
            description "ISIS Sr Mapping Table Prefix length";
        } // END of prefix-length definition.

    } // END of isis-srms-ipv4-table-state definition.
    grouping isis-srms-ipv4-table-entry-state {
        description
            "State items for ISIS SRMS IPv4 Table Entry";
        leaf index  {
            type  uint32;
            description "SR map table entry SID's Index";
        } // END of index definition.

        leaf label-options  {
            type  uint8;
            description "SR map table entry prefix flags";
        } // END of label-options definition.

        leaf system-id  {
            type  string {
                length "1..1965";
                pattern "[^?' =,>|]+";
            }
            description "SR map table entry system";
        } // END of system-id definition.

        leaf status  {
            type  string {
                length "1..1965";
                pattern "[^?' =,>|]+";
            }
            description "SR map table entry status";
        } // END of status definition.

        leaf preference  {
            type  uint8;
            description "SR map table entry SRMS pref";
        } // END of preference definition.

        leaf attached  {
            type  string {
                length "1..1965";
                pattern "[^?' =,>|]+";
            }
            description "SR map table entry Last Prefix";
        } // END of attached definition.

        leaf last-system-id-index  {
            type  uint32;
            description "SR map table entry LAST sid index";
        } // END of last-system-id-index definition.

        leaf last-prefix  {
            type  cml-data-types:cml_ip_prefix_addr_t;
            description "SR map table entry Last Prefix";
        } // END of last-prefix definition.

        leaf prefix-range  {
            type  uint32;
            description "SR map table entry Range";
        } // END of prefix-range definition.

        leaf entry-prefix  {
            type  cml-data-types:cml_ip_prefix_addr_t;
            description "SR map table entry Prefix";
        } // END of entry-prefix definition.

    } // END of isis-srms-ipv4-table-entry-state definition.
    grouping isis-srms-ipv6-state {
        description
            "State items for ISIS SRMS IPv6 Table";
        leaf type  {
            type  ipi-isis-types:isis_srms_type_t;
            description "ISIS Sr Mapping table type Active/Inactive";
        } // END of type definition.

        leaf entry-count  {
            type  uint32;
            description "ISIS Sr Mapping table entry count";
        } // END of entry-count definition.

        leaf conflict-resolution-policy  {
            type  string {
                length "1..1965";
                pattern "[^?' =,>|]+";
            }
            description "ISIS Sr Mapping table Conflict Resolution Policy";
        } // END of conflict-resolution-policy definition.

    } // END of isis-srms-ipv6-state definition.
    grouping isis-srms-ipv6-table-state {
        description
            "State items for ISIS SRMS IPv6 Table";
        leaf prefix-length  {
            type  uint32;
            description "ISIS Sr Mapping Table Prefix length";
        } // END of prefix-length definition.

    } // END of isis-srms-ipv6-table-state definition.
    grouping isis-srms-ipv6-table-entry-state {
        description
            "State items for ISIS SRMS IPv6 Table Entry";
        leaf index  {
            type  uint32;
            description "SR map table entry SID's Index";
        } // END of index definition.

        leaf label-options  {
            type  uint8;
            description "SR map table entry prefix flags";
        } // END of label-options definition.

        leaf system-id  {
            type  string {
                length "1..1965";
                pattern "[^?' =,>|]+";
            }
            description "SR map table entry system";
        } // END of system-id definition.

        leaf status  {
            type  string {
                length "1..1965";
                pattern "[^?' =,>|]+";
            }
            description "SR map table entry status";
        } // END of status definition.

        leaf preference  {
            type  uint8;
            description "SR map table entry SRMS pref";
        } // END of preference definition.

        leaf attached  {
            type  string {
                length "1..1965";
                pattern "[^?' =,>|]+";
            }
            description "SR map table entry Last Prefix";
        } // END of attached definition.

        leaf last-system-id-index  {
            type  uint32;
            description "SR map table entry LAST sid index";
        } // END of last-system-id-index definition.

        leaf last-prefix  {
            type  cml-data-types:cml_ip_prefix_addr_t;
            description "SR map table entry Last Prefix";
        } // END of last-prefix definition.

        leaf prefix-range  {
            type  uint32;
            description "SR map table entry Range";
        } // END of prefix-range definition.

        leaf entry-prefix  {
            type  cml-data-types:cml_ip_prefix_addr_t;
            description "SR map table entry Prefix";
        } // END of entry-prefix definition.

    } // END of isis-srms-ipv6-table-entry-state definition.

    grouping  segment-routing-grouping {
    description
        "This container defines the ISIS SR configurations.";
    container segment-routing {
        description
            "This container defines the ISIS SR configurations.";

        list global-block {
            key "global-block-base global-block-range";
            description
                "This objectlist defines the ISIS SR Global Block configurations.";
            leaf global-block-base  {
                type  leafref {
                    path  "../config/global-block-base";
                }
                description "Segment Node Base Value. Default value is 16000";
            } // END of global-block-base definition.

            leaf global-block-range  {
                type  leafref {
                    path  "../config/global-block-range";
                }
                description "Use this attribute to set the SRGB range at each node. If you do not
                            specify a per-node range with the segmentrouting global block command,
                            this range will be used by that ISIS instance. IGP protocols must use
                            same SRGB range or use a different non-overlapping SRGB range. Note:
                            For a segment routing trunk, all nodes on the path of the trunk should
                            have same SRGB range for the trunk to be established.Default value is
                            23999";
            } // END of global-block-range definition.

            container config {
                description
                    "This container defines the ISIS SR Global Block configurations.";
                uses isis-sr-global-block-config;
            } // END of config-container definition.
            container state {
                config false;
                description
                    "This container defines the ISIS SR state.";
                uses isis-sr-global-block-config;
            } // END of state-container definition.
        } // End of global-block-list
        container config {
            presence "To enable MPLS based segment routing";
            description
                "This container defines the ISIS SR configurations.";
            uses isis-sr-config;
        } // END of config-container definition.
        container state {
            config false;
            description
                "This container defines the ISIS SR state.";
            uses isis-sr-config;
        } // END of state-container definition.
    } // END of segment-routing-container definition.
    } // END of segment-routing-grouping definition.


}
