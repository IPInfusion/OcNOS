/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-dhcp-client.yang
*
*/

submodule ipi-dhcp-client {

    yang-version 1.1;

    belongs-to  ipi-dhcp { prefix ipi-dhcp; }

    import feature-list {
        prefix feature-list;
    }

    import ipi-interface {
        prefix ipi-interface;
    }

    organization
        "IP Infusion Inc.";

    contact
        "Address: 3965 Freedom Circle, Suite 200, Santa Clara, CA 95054
         Phone: +1 408-400-1900
         E-mail: support@ipinfusion.com
         Web: http://www.ipinfusion.com/";

    description
        "dhcp_client_configuration";


    revision "2020-12-15" {
        description "Change to have data-types in lower case instead of camel case";
        reference " 0.2.0.";
    }

    revision "2020-08-11" {
        description "Initial Version";
        reference " 0.1.0.";
    }

    grouping client-interface-config {
        description
            "Configuration data for dhcp-client on each interface";
        leaf request-ipv4-dns  {
            type  empty;
            description "Use this attribute to to add an option to a DHCP request.";
        } // END of request-ipv4-dns definition.

        leaf request-log-server  {
            type  empty;
            description "Use this attribute to to add an option to a DHCP request.";
        } // END of request-log-server definition.

        leaf request-host-name  {
            type  empty;
            description "Use this attribute to to add an option to a DHCP request.";
        } // END of request-host-name definition.

        leaf request-ntp-server  {
            type  empty;
            description "Use this attribute to to add an option to a DHCP request.";
        } // END of request-ntp-server definition.

        leaf request-ipv6-dns  {
            if-feature feature-list:HAVE_IPV6;
            type  empty;
            description "Use this attribute to to add an option to a DHCP request.";
        } // END of request-ipv6-dns definition.

    } // END of client-interface-config definition.
    grouping dhcp-interface-top {
        description
            "DHCP interface related operations";
        container interfaces {
            description
                "Top level container for dhcp-client on each interface";

            list interface {
                key "name";
                description
                    "List of interfaces mapped with dhcp-client";
                leaf name  {
                    type  leafref {
                        path  "/ipi-interface:interfaces/ipi-interface:interface/ipi-interface:name";
                    }
                    description "The textual name of the interface. The value of this object should be
                                the name of the interface as assigned by the local device and should
                                be suitable for use in commands entered at the device's `console'.
                                This might be a text name, such as `le0' or a simple port number, such
                                as `1', depending on the interface naming syntax of the device. If
                                several entries in the ifTable together represent a single interface
                                as named by the device, then each will have the same value of name.
                                Note that for an agent which responds to SNMP queries concerning an
                                interface on some other (proxied) device, then the value of name for
                                such an interface is the proxied device's local name for it. If there
                                is no local name, or this object is otherwise not applicable, then
                                this object contains a zero-length string.";
                } // END of name definition.

                container config {
                    description
                        "Configuration data for dhcp-client on each interface";
                    uses client-interface-config;
                } // END of config-container definition.
                container state {
                    config false;
                    description
                        "Operational state data";
                    uses client-interface-config;
                } // END of state-container definition.
            } // End of interface-list
        } // END of interfaces-container definition.
    } // END of dhcp-interface-top definition.

    grouping  client-grouping {
    description
        "DHCP client related operations";
    container client {
        when " /dhcp/global/config/disable-dhcp-feature != 1 ";
        description
            "DHCP client related operations";
        uses dhcp-interface-top;
    } // END of client-container definition.
    } // END of client-grouping definition.


}
