/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-dhcp.yang
*
*/

module ipi-dhcp {

    yang-version 1.1;

    namespace   "http://www.ipinfusion.com/yang/ocnos/ipi-dhcp";

    prefix "ipi-dhcp";

    include ipi-dhcp-relay;
    include ipi-dhcp-client;
    organization
        "IP Infusion Inc.";

    contact
        "Address: 3965 Freedom Circle, Suite 200, Santa Clara, CA 95054
         Phone: +1 408-400-1900
         E-mail: support@ipinfusion.com
         Web: http://www.ipinfusion.com/";

    description
        "feature_dhcp_configuration";


    revision "2020-12-15" {
        description "Change to have data-types in lower case instead of camel case";
        reference " 0.2.0.";
    }

    revision "2020-08-11" {
        description "Initial Version";
        reference " 0.1.0.";
    }

    grouping dhcp-feature-config {
        description
            "Configuration data for feature-dhcp for client and relay";
        leaf disable-dhcp-feature  {
            type  empty;
            description "Disable the DHCP client and DHCP relay on the device.";
        } // END of disable-dhcp-feature definition.

    } // END of dhcp-feature-config definition.
    grouping dhcp-global-top {
        description
            "DHCP global level information grouping";
        container global {
            description
                "DHCP global level information";
            container config {
                description
                    "Configurationd data for feature dhcp";
                uses dhcp-feature-config;
            } // END of config-container definition.
            container state {
                config false;
                description
                    "Operational state data";
                uses dhcp-feature-config;
            } // END of state-container definition.
        } // END of global-container definition.
    } // END of dhcp-global-top definition.

    grouping  dhcp-grouping {
    description
        "Enable feature dhcp";
    container dhcp {
        description
            "Enable feature dhcp";
        uses dhcp-global-top;
        uses relay-grouping;
        uses client-grouping;
    } // END of dhcp-container definition.
    } // END of dhcp-grouping definition.

    uses dhcp-grouping;

}
