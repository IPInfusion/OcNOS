/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-platform-transceiver.yang
*
*/

submodule ipi-platform-transceiver {

    yang-version 1.1;

    belongs-to  ipi-platform { prefix ipi-platform; }

    import feature-list {
        prefix feature-list;
        revision-date 2021-05-03;
    }

    import ipi-platform-transceiver-types {
        prefix ipi-platform-transceiver-types;
        revision-date 2020-12-15;
    }

    organization
        "IP Infusion Inc.";

    contact
        "Address: 3965 Freedom Circle, Suite 200, Santa Clara, CA 95054
         Phone: +1 408-4001900
         E-mail: support@ipinfusio.com
         Web: http://www.ipinfusion.com/";

    description
        "This module defines a schema for ram components in platform datamodel";


    revision "2020-12-15" {
        description "Change to have data-types in lower case instead of camel case";
        reference " 0.2.0.";
    }

    revision "2018-06-21" {
        description "Initial Version";
        reference " 0.1.0.";
    }

    grouping transceiver-state {
        description
            "Operational state data for transceiver components";
        leaf port-no  {
            type  uint8;
            description "Transceiver port number";
        } // END of port-no definition.

        leaf presence  {
            type  ipi-platform-transceiver-types:ddm_cmm_trans_presence_t;
            description "Transceiver presence status";
        } // END of presence definition.

    } // END of transceiver-state definition.
    grouping sfp-xfp-state {
        description
            "Operational state data for sfp and xfp components";
        leaf transmit-status  {
            type  ipi-platform-transceiver-types:ddm_tx_rx_state_t;
            description "Transceiver transmit status";
        } // END of transmit-status definition.

        leaf recieve-loss-status  {
            type  ipi-platform-transceiver-types:ddm_tx_rx_state_t;
            description "Transceiver recieve status";
        } // END of recieve-loss-status definition.

    } // END of sfp-xfp-state definition.
    grouping qsfp-state {
        description
            "Operational state data for qsfp components";
        leaf reset-status  {
            type  ipi-platform-transceiver-types:ddm_cmm_trans_reset_t;
            description "Transceiver reset status";
        } // END of reset-status definition.

        leaf power  {
            type  ipi-platform-transceiver-types:ddm_cmm_trans_power_t;
            description "Transceiver power status";
        } // END of power definition.

        leaf lane1-transmission  {
            type  ipi-platform-transceiver-types:ddm_tx_rx_state_t;
            description "Lane 1 Transmission";
        } // END of lane1-transmission definition.

        leaf lane1-transmission-loss  {
            type  ipi-platform-transceiver-types:ddm_tx_rx_state_t;
            description "Lane 1 Transmission Loss";
        } // END of lane1-transmission-loss definition.

        leaf lane1-recieve-loss  {
            type  ipi-platform-transceiver-types:ddm_tx_rx_state_t;
            description "Lane 1 recieve Loss";
        } // END of lane1-recieve-loss definition.

        leaf lane2-transmisssion  {
            type  ipi-platform-transceiver-types:ddm_tx_rx_state_t;
            description "Lane 2 Transmission";
        } // END of lane2-transmisssion definition.

        leaf lane2-transmission-loss  {
            type  ipi-platform-transceiver-types:ddm_tx_rx_state_t;
            description "Lane 2 Transmission Loss";
        } // END of lane2-transmission-loss definition.

        leaf lane2-recieve-loss  {
            type  ipi-platform-transceiver-types:ddm_tx_rx_state_t;
            description "Lane 2 recieve Loss";
        } // END of lane2-recieve-loss definition.

        leaf lane3-transmission  {
            type  ipi-platform-transceiver-types:ddm_tx_rx_state_t;
            description "Lane 3 transmission";
        } // END of lane3-transmission definition.

        leaf lane3-transmission-loss  {
            type  ipi-platform-transceiver-types:ddm_tx_rx_state_t;
            description "Lane 3 transmission Loss";
        } // END of lane3-transmission-loss definition.

        leaf lane3-recieve-loss  {
            type  ipi-platform-transceiver-types:ddm_tx_rx_state_t;
            description "Lane 3 recieve Loss";
        } // END of lane3-recieve-loss definition.

        leaf lane4-transmission  {
            type  ipi-platform-transceiver-types:ddm_tx_rx_state_t;
            description "Lane 4 transmission";
        } // END of lane4-transmission definition.

        leaf lane4-transmission-loss  {
            type  ipi-platform-transceiver-types:ddm_tx_rx_state_t;
            description "Lane 4 transmission Loss";
        } // END of lane4-transmission-loss definition.

        leaf lane4-recieve-loss  {
            type  ipi-platform-transceiver-types:ddm_tx_rx_state_t;
            description "Lane 4 recieve Loss";
        } // END of lane4-recieve-loss definition.

    } // END of qsfp-state definition.

    grouping  transceiver-grouping {
    description
        "Container for transceiver component";
    container transceiver {
        if-feature feature-list:NOT_HAVE_TIBIT;
        config false;
        description
            "Container for transceiver component";
        container state {
            config false;
            description
                "Operational state data for transceiver components";
            uses transceiver-state;
        } // END of state-container definition.
        container sfp {
            config false;
            description
                "Container for sfp type transceiver";
            container state {
                config false;
                description
                    "Operational state data for sfp type transcivers";
                uses sfp-xfp-state;
            } // END of state-container definition.
        } // END of sfp-container definition.
        container xfp {
            config false;
            description
                "Container for xfp type transceiver";
            container state {
                config false;
                description
                    "Operational state data for sfp type transceivers";
                uses sfp-xfp-state;
            } // END of state-container definition.
        } // END of xfp-container definition.
        container qsfp {
            config false;
            description
                "Container for qsfp type transceiver";
            container state {
                config false;
                description
                    "Operational state data for qsfp type transceivers";
                uses qsfp-state;
            } // END of state-container definition.
        } // END of qsfp-container definition.
    } // END of transceiver-container definition.
    } // END of transceiver-grouping definition.


}
