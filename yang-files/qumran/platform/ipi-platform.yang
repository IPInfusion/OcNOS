/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-platform.yang
*
*/

module ipi-platform {

    yang-version 1.1;

    namespace   "http://www.ipinfusion.com/yang/ocnos/ipi-platform";

    prefix "ipi-platform";

    import ipi-interface {
        prefix ipi-interface;
        revision-date 2021-06-14;
    }

    import ipi-platform-types {
        prefix ipi-platform-types;
        revision-date 2021-01-25;
    }

    import ipi-platform-transceiver-types {
        prefix ipi-platform-transceiver-types;
        revision-date 2020-12-15;
    }

    import ietf-yang-types {
        prefix yang;
        revision-date 2013-07-15;
    }

    import feature-list {
        prefix feature-list;
        revision-date 2021-05-03;
    }

    include ipi-platform-temperature { revision-date 2021-03-18;}
    include ipi-platform-cpu { revision-date 2021-04-28;}
    include ipi-platform-storage { revision-date 2021-05-31;}
    include ipi-platform-ram { revision-date 2020-12-15;}
    include ipi-platform-transceiver { revision-date 2020-12-15;}
    include ipi-platform-power-supply { revision-date 2021-03-18;}
    include ipi-platform-fan { revision-date 2021-03-18;}
    include ipi-platform-fan-tray { revision-date 2021-03-18;}
    include ipi-platform-chassis { revision-date 2021-03-18;}
    include ipi-platform-linecard { revision-date 2021-01-25;}
    include ipi-platform-power-rail { revision-date 2021-01-25;}
    include ipi-platform-profile { revision-date 2021-06-23;}
    organization
        "IP Infusion Inc.";

    contact
        "Address: 3965 Freedom Circle, Suite 200, Santa Clara, CA 95054
         Phone: +1 408-400-1900
         E-mail: support@ipinfusion.com
         Web: http://www.ipinfusion.com/";

    description
        "This module defines a data model for representing a system
                component inventory, which can include hardware or software
                elements arranged in an arbitrary structure. The primary
                relationship supported by the model is containment, e.g.,
                components containing subcomponents.";


    revision "2021-06-23" {
        description "Updated submodule ipi-platform-profile for attribute ingress-bfd datatype changed.";
        reference " 0.9.2.";
    }

    revision "2021-06-17" {
        description "Updated submodule ipi-platform-profile for non-DNX Broadcom platform.";
        reference " 0.9.1.";
    }

    revision "2021-06-11" {
        description "Some BMC sensor attributes had the type changes from two decimal places to three.";
        reference " 0.9.0.";
    }

    revision "2021-05-31" {
        description "New attributes added for submodule ipi-platform-storage";
        reference " 0.8.0.";
    }

    revision "2021-04-28" {
        description "Submodule ipi-platform-cpu changed.";
        reference " 0.7.0.";
    }

    revision "2021-03-30" {
        description "Introduced new sub-modules ipi-platform-profile.";
        reference " 0.6.0.";
    }

    revision "2021-03-18" {
        description "Updated ipi-platform-power-supply sub-module. Removed pattern from string attributes.";
        reference " 0.5.0.";
    }

    revision "2021-01-25" {
        description "Introduced new sub-modules ipi-platform-temperature, ipi-platform-power-supply, ipi-fan, ipi-fan-tray, ipi-chassis, ipi-linecard, and ipi-power-rail. Fixed attribute transceiver-code typo.";
        reference " 0.4.0.";
    }

    revision "2021-01-18" {
        description "Introduced new ipi-platform-cpu sub-module";
        reference " 0.3.0.";
    }

    revision "2020-12-15" {
        description "Change to have data-types in lower case instead of camel case";
        reference " 0.2.0.";
    }

    revision "2018-06-21" {
        description "Initial Version";
        reference " 0.1.0.";
    }

    grouping component-memory-state-detail {
        description
            "Per-component memory statistics detail";
        leaf available  {
            type  uint64;
            units "Mbytes";
            description "The available memory physically installed, or logically allocated to
                        the component.";
        } // END of available definition.

        leaf utilized  {
            type  uint64;
            units "Mbytes";
            description "utilized memory.";
        } // END of utilized definition.

    } // END of component-memory-state-detail definition.
    grouping component-board-state-detail {
        description
            "Per-component board detail";
        leaf board-name  {
            type  string {
                length "1..1965";
            }
            description "Name of the Board";
        } // END of board-name definition.

        leaf board-serial-no  {
            type  string {
                length "1..1965";
            }
            description "Serial No of the device";
        } // END of board-serial-no definition.

        leaf board-mfg-name  {
            type  string {
                length "1..1965";
            }
            description "Device's manufacturer name";
        } // END of board-mfg-name definition.

        leaf board-mfg-date  {
            type  yang:date-and-time {
                pattern "\\d{4}-\\d{2}-\\d{2}T\\d{2}:\\d{2}:\\d{2}(\\.\\d+)?(Z|[\\+\\-]\\d{2}:\\d{2})";
                }
                description "Device's manufacturing date.";
            } // END of board-mfg-date definition.

    } // END of component-board-state-detail definition.
    grouping system-load {
        description
            "System load group";
        leaf system-1min-load-avg-warning-threshold  {
            type  uint8 {
                 range "41..100"  {
                    description "41..100:41-100";
                 }
            }
            description "System 1min average load threshold for warning";
        } // END of system-1min-load-avg-warning-threshold definition.

        leaf system-1min-load-avg-alarm  {
            type  uint8 {
                 range "51..100"  {
                    description "51..100:51-100";
                 }
            }
            description "System 1min average load for alarm";
        } // END of system-1min-load-avg-alarm definition.

        leaf system-5min-load-avg-alarm  {
            type  uint8 {
                 range "51..100"  {
                    description "51..100:51-100";
                 }
            }
            description "System 5min average load for alarm";
        } // END of system-5min-load-avg-alarm definition.

        leaf system-15min-load-avg-alarm  {
            type  uint8 {
                 range "51..100"  {
                    description "51..100:51-100";
                 }
            }
            description "System 15min average load for alarm";
        } // END of system-15min-load-avg-alarm definition.

    } // END of system-load definition.
    grouping cpu-threshold {
        description
            "cpu threshold group";
        leaf warning-threshold  {
            type  uint8 {
                 range "51..100"  {
                    description "51..100:51-100";
                 }
            }
            description "Cpu threshold for warning";
        } // END of warning-threshold definition.

        leaf alarm-threshold  {
            type  uint8 {
                 range "91..100"  {
                    description "91..100:91-100";
                 }
            }
            description "Cpu threshold for alarm";
        } // END of alarm-threshold definition.

    } // END of cpu-threshold definition.
    grouping component-generic-global {
        description
            "Generic platform global configuration";
        leaf warning-repeat  {
            type  empty;
            description "To enable cmm warning level logs to repeat.";
        } // END of warning-repeat definition.

    } // END of component-generic-global definition.
    grouping system-load-cpu-usage-global {
        description
            "System load and CPU usage global group";

        list system-load-average-threshold {
            key "system-1min-load-avg-warning-threshold system-1min-load-avg-alarm system-5min-load-avg-alarm system-15min-load-avg-alarm";
            max-elements 1;
            description
                "Global system load average";
            leaf system-1min-load-avg-warning-threshold  {
                type  leafref {
                    path  "../config/system-1min-load-avg-warning-threshold";
                }
                description "System 1min average load threshold for warning";
            } // END of system-1min-load-avg-warning-threshold definition.

            leaf system-1min-load-avg-alarm  {
                type  leafref {
                    path  "../config/system-1min-load-avg-alarm";
                }
                description "System 1min average load for alarm";
            } // END of system-1min-load-avg-alarm definition.

            leaf system-5min-load-avg-alarm  {
                type  leafref {
                    path  "../config/system-5min-load-avg-alarm";
                }
                description "System 5min average load for alarm";
            } // END of system-5min-load-avg-alarm definition.

            leaf system-15min-load-avg-alarm  {
                type  leafref {
                    path  "../config/system-15min-load-avg-alarm";
                }
                description "System 15min average load for alarm";
            } // END of system-15min-load-avg-alarm definition.

            container config {
                description
                    "system level load configuration";
                uses system-load;
            } // END of config-container definition.
            container state {
                config false;
                description
                    "system level load operational data";
                uses system-load;
                uses temperature-grouping;
            } // END of state-container definition.
        } // End of system-load-average-threshold-list

        list cpu-core-usage-threshold {
            key "warning-threshold alarm-threshold";
            max-elements 1;
            description
                "Global level cpu usage threshold";
            leaf warning-threshold  {
                type  leafref {
                    path  "../config/warning-threshold";
                }
                description "Cpu threshold for warning";
            } // END of warning-threshold definition.

            leaf alarm-threshold  {
                type  leafref {
                    path  "../config/alarm-threshold";
                }
                description "Cpu threshold for alarm";
            } // END of alarm-threshold definition.

            container config {
                description
                    "Global level cpu threshold configuration";
                uses cpu-threshold;
            } // END of config-container definition.
            container state {
                config false;
                description
                    "system level load operational data";
                uses cpu-threshold;
                uses temperature-grouping;
            } // END of state-container definition.
        } // End of cpu-core-usage-threshold-list
    } // END of system-load-cpu-usage-global definition.
    grouping component-interface {
        description
            "interface configuration group";
        leaf monitor-port  {
            type  ipi-platform-types:cmm_monitor_state;
            description "To enable DDM monitor for current transceiver.";
        } // END of monitor-port definition.

        leaf videopiu-port  {
            if-feature feature-list:HAVE_VPIU_EMULATION;
            type  ipi-platform-types:cmm_videopiu_state;
            description "To enable VIDEO PIU for current transceiver.";
        } // END of videopiu-port definition.

        leaf transceiver-code  {
            type  ipi-platform-transceiver-types:ddm_transceiver_t;
            description "To set transceiver code for current transceiver.";
        } // END of transceiver-code definition.

        leaf wavelength  {
            type  ipi-platform-types:cml_wavelength_t;
            description "wavelength";
        } // END of wavelength definition.

        leaf tx-disable  {
            type  empty;
            description "To disable laser tx for current transceiver.";
        } // END of tx-disable definition.

    } // END of component-interface definition.
    grouping platform-component-interface-list {
        description
            "global interface configuration list group";

        list interface {
            key "interface-name";
            description
                "Platform interface related operations";
            leaf interface-name  {
                type  leafref {
                    path  "/ipi-interface:interfaces/ipi-interface:interface/ipi-interface:name";
                }
                description "Use this attribute to perform platform's interface related
                            configurations";
            } // END of interface-name definition.

            container config {
                description
                    "interface related configurations";
                uses component-interface;
            } // END of config-container definition.
            container state {
                config false;
                description
                    "Operational data for interface";
                uses component-interface;
                uses temperature-grouping;
            } // END of state-container definition.
        } // End of interface-list
    } // END of platform-component-interface-list definition.
    grouping component-generic-debug {
        description
            "Grouping debug info for generic platform";
        leaf cmm-debug-enable  {
            type  empty;
            description "Use this attribute to turn on debugging for chassis monitoring";
        } // END of cmm-debug-enable definition.

    } // END of component-generic-debug definition.
    grouping component-generic-terminal-debug {
        description
            "Grouping terminal debug info for generic platform";
        leaf cmm-terminal-debug  {
            type  empty;
            description "Use this attribute to see the terminal debugging state for chassis
                        monitoring";
        } // END of cmm-terminal-debug definition.

    } // END of component-generic-terminal-debug definition.
    grouping component-bmc-sensor-record-state {
        description
            "componentCMLSEPbmcCMLSEPsensorCMLSEPrecordCMLSEPstate";
        container state {
            config false;
            description
                "Operational data for bmc-sensor";
            leaf sensor-name  {
                type  string {
                    length "1..1965";
                }
                description "sensor name";
            } // END of sensor-name definition.

            leaf value  {
                type  ipi-platform-types:cmm_bmc_value_t;
                description "sensor record value.Value -100002 represents not applicable";
            } // END of value definition.

            leaf units  {
                type  string {
                    length "1..1965";
                }
                description "unit of sensor record";
            } // END of units definition.

            leaf lower-non-recoverable  {
                type  decimal64 {
                     fraction-digits 3;                }
                description "lower non recoverable sensor threshold.-100002 represents not
                            applicable";
            } // END of lower-non-recoverable definition.

            leaf lower-non-critical  {
                type  decimal64 {
                     fraction-digits 3;                }
                description "lower non critical sensor threshold.-100002 represents not applicable";
            } // END of lower-non-critical definition.

            leaf lower-critical  {
                type  decimal64 {
                     fraction-digits 3;                }
                description "lower non critical sensor threshold.-100002 represents not applicable";
            } // END of lower-critical definition.

            leaf upper-non-critical  {
                type  decimal64 {
                     fraction-digits 3;                }
                description "upper non critical sensor threshold.-100002 represents not applicable";
            } // END of upper-non-critical definition.

            leaf upper-critical  {
                type  decimal64 {
                     fraction-digits 3;                }
                description "upper critical sensor threshold.-100002 represents not applicable";
            } // END of upper-critical definition.

            leaf upper-non-recoverable  {
                type  decimal64 {
                     fraction-digits 3;                }
                description "upper critical sensor threshold.-100002 represents not applicable";
            } // END of upper-non-recoverable definition.

            leaf operational-status  {
                type  string {
                    length "1..1965";
                }
                description "Sensor's operational state";
            } // END of operational-status definition.

            leaf threshold  {
                type  decimal64 {
                     fraction-digits 3;                }
                description "threshold for sensor notification";
            } // END of threshold definition.

            leaf event-type  {
                type  ipi-platform-types:cmm_bmc_event_type_t;
                description "Type of event for sensor notification";
            } // END of event-type definition.

            uses temperature-grouping;
        } // END of state-container definition.
    } // END of component-bmc-sensor-record-state definition.
    grouping component-hardware-debug {
        description
            "Grouping debug info for hardware related debug";
        leaf ddm-debug-enable  {
            if-feature feature-list:NOT_HAVE_TIBIT;
            type  empty;
            description "Use this attribute to turn on debugging for digital diagnostic
                        monitoring";
        } // END of ddm-debug-enable definition.

    } // END of component-hardware-debug definition.
    grouping component-hardware-terminal-debug {
        description
            "Grouping terminal hardware related debug";
        leaf ddm-terminal-debug  {
            if-feature feature-list:NOT_HAVE_TIBIT;
            type  empty;
            description "Use this attribute to see the debugging state for digital diagnostic
                        monitoring";
        } // END of ddm-terminal-debug definition.

    } // END of component-hardware-terminal-debug definition.
    grouping platform-component-state {
        description
            "Operational state data for device components";
        leaf type  {
            if-feature feature-list:NOT_HAVE_TIBIT;
            type  ipi-platform-types:cmm_component_type_t;
            description "Type of component as identified by the system";
        } // END of type definition.

        leaf location  {
            if-feature feature-list:NOT_HAVE_TIBIT;
            type  string {
                length "1..1965";
            }
            description "System-supplied description of the location of the
                        component within the system. This could be a bay position,
                        slot number, socket location, etc. For component types that
                        have an explicit slot-id attribute, such as linecards, the
                        system should populate the more specific slot-id.";
        } // END of location definition.

        leaf mfg-name  {
            if-feature feature-list:NOT_HAVE_TIBIT;
            type  string {
                length "1..1965";
            }
            description "System-supplied identifier for the manufacturer of the component.This
                        data is particularly useful when a component manufacturer is different
                        than the overall device vendor.";
        } // END of mfg-name definition.

        leaf mfg-date  {
            if-feature feature-list:NOT_HAVE_TIBIT;
            type  yang:date-and-time {
                pattern "\\d{4}-\\d{2}-\\d{2}T\\d{2}:\\d{2}:\\d{2}(\\.\\d+)?(Z|[\\+\\-]\\d{2}:\\d{2})";
                }
                description "System-supplied representation of the component's manufacturing date.";
            } // END of mfg-date definition.

            leaf description  {
                if-feature feature-list:NOT_HAVE_TIBIT;
                type  string {
                    length "1..1965";
                }
                description "System-supplied description of the component.";
            } // END of description definition.

            leaf hardware-version  {
                if-feature feature-list:NOT_HAVE_TIBIT;
                type  string {
                    length "1..1965";
                }
                description "For hardware components, this is the hardware revision of the
                            component.";
            } // END of hardware-version definition.

            leaf firmware-version  {
                if-feature feature-list:NOT_HAVE_TIBIT;
                type  string {
                    length "1..1965";
                }
                description "For hardware components, this is the version of associated firmware
                            that is running on the component, if applicable.";
            } // END of firmware-version definition.

            leaf software-version  {
                if-feature feature-list:NOT_HAVE_TIBIT;
                type  string {
                    length "1..1965";
                }
                description "For software components such as operating system or other software
                            module,this is the version of the currently running software.";
            } // END of software-version definition.

            leaf serial-no  {
                if-feature feature-list:NOT_HAVE_TIBIT;
                type  string {
                    length "1..1965";
                }
                description "System-assigned serial number of the component.";
            } // END of serial-no definition.

            leaf part-no  {
                if-feature feature-list:NOT_HAVE_TIBIT;
                type  string {
                    length "1..1965";
                }
                description "System-assigned part number for the component.This should be present
                            in particular if the component is also an FRU(field replaceable unit).";
            } // END of part-no definition.

            leaf removable  {
                if-feature feature-list:NOT_HAVE_TIBIT;
                type  boolean;
                description "If true,this component is removable or is a field replaceable unit";
            } // END of removable definition.

            leaf oper-status  {
                if-feature feature-list:NOT_HAVE_TIBIT;
                type  ipi-platform-types:cmm_component_oper_status_t;
                description "If applicable,this reports the current operational status of the
                            component.";
            } // END of oper-status definition.

            leaf product-name  {
                if-feature feature-list:NOT_HAVE_TIBIT;
                type  string {
                    length "1..1965";
                }
                description "Component's product name";
            } // END of product-name definition.

            leaf asset-tag  {
                if-feature feature-list:NOT_HAVE_TIBIT;
                type  string {
                    length "1..1965";
                }
                description "Component's asset tag";
            } // END of asset-tag definition.

            leaf-list component-additional-details  {
                if-feature feature-list:NOT_HAVE_TIBIT;
                type  string {
                    length "1..1965";
                    pattern "[^?' =,>|]+";
                }
                description "Component's extra details";
            } // END of component-additional-details definition.

    } // END of platform-component-state definition.
    grouping platform-component-memory-state {
        description
            "Per-component memory statistics";
        container memory {
            if-feature feature-list:NOT_HAVE_TIBIT;
            config false;
            description
                "For components that have associated memory, these values
                        report information about available and utilized memory";
            uses component-memory-state-detail;
        } // END of memory-container definition.
    } // END of platform-component-memory-state definition.
    grouping platform-component-board-state {
        description
            "Per-component board state";
        container board-fru {
            if-feature feature-list:NOT_HAVE_TIBIT;
            config false;
            description
                "For components that have associated board fru details";
            uses component-board-state-detail;
        } // END of board-fru-container definition.
    } // END of platform-component-board-state definition.
    grouping component-hardware-global {
        description
            "Platform hardware global states";
        leaf locator-led-enable  {
            if-feature feature-list:NOT_HAVE_TIBIT;
            type  empty;
            description "To set the locator-led on or off.";
        } // END of locator-led-enable definition.

        leaf ddm-monitor-time-interval  {
            if-feature feature-list:NOT_HAVE_TIBIT;
            type  uint16 {
                 range "60..3600"  {
                    description "60..3600:60-3600 seconds";
                 }
            }
            default "60";
            description "To set DDM Monitor interval time.";
        } // END of ddm-monitor-time-interval definition.

        leaf vpiu-control-vlan  {
            if-feature feature-list:HAVE_VPIU_EMULATION;
            type  uint16 {
                 range "2..4094"  {
                    description "2..4094:VLAN ID 2 4094";
                 }
            }
            description "To set Video PIU Command VLAN.";
        } // END of vpiu-control-vlan definition.

        leaf service-unsupported-transceiver  {
            if-feature feature-list:NOT_HAVE_TIBIT;
            type  empty;
            description "To enable DDM Monitor for unsupported transceivers at user risk.";
        } // END of service-unsupported-transceiver definition.

        leaf enable-ddm-monitor  {
            if-feature feature-list:NOT_HAVE_TIBIT;
            type  empty;
            description "To enable DDM monitor for all transceivers.";
        } // END of enable-ddm-monitor definition.

        leaf nmea-monitor  {
            if-feature feature-list:HAVE_PTP_HW_OFFLOAD;
            if-feature feature-list:NOT_HAVE_TIBIT;
            type  ipi-platform-types:cmm_gps_monitor_type_t;
            description "gps monitor start and stop";
        } // END of nmea-monitor definition.

        leaf nmea-log  {
            if-feature feature-list:HAVE_PTP_HW_OFFLOAD;
            if-feature feature-list:NOT_HAVE_TIBIT;
            type  empty;
            description "gps nmea log";
        } // END of nmea-log definition.

    } // END of component-hardware-global definition.
    grouping platform-sensor-record {
        description
            "Grouping sensor states";
        container bmc-sensor-data-record {
            if-feature feature-list:NOT_HAVE_TIBIT;
            config false;
            description
                "container enclosing bmc sensor data";
            uses component-bmc-sensor-record-state;
        } // END of bmc-sensor-data-record-container definition.
    } // END of platform-sensor-record definition.
    grouping platform-component-interface {
        description
            "Global interface configuration group";
        container interfaces {
            if-feature feature-list:NOT_HAVE_TIBIT;
            description
                "platform interface properties";
            uses platform-component-interface-list;
        } // END of interfaces-container definition.
    } // END of platform-component-interface definition.
    grouping platform-component-global {
        description
            "Global configuration group for the platform";
        container global {
            description
                "container enclosing global configuration";
            container config {
                description
                    "configuration data for platform  global configuration";
                uses component-generic-global;
                uses component-hardware-global;
            } // END of config-container definition.
            container state {
                config false;
                description
                    "Global operational data";
                uses component-generic-global;
                uses component-hardware-global;
                uses temperature-grouping;
            } // END of state-container definition.
            uses system-load-cpu-usage-global;
        } // END of global-container definition.
    } // END of platform-component-global definition.
    grouping platform-component-debug {
        description
            "Global debug configuration group";
        container debug {
            description
                "configuration data for debug configuration";
            container config {
                description
                    "configuration data for cmm debug configuration";
                uses component-generic-debug;
                uses component-hardware-debug;
            } // END of config-container definition.
            container state {
                config false;
                description
                    "Operational data for debug";
                uses component-generic-debug;
                uses component-hardware-debug;
                uses component-generic-terminal-debug;
                uses component-hardware-terminal-debug;
                uses temperature-grouping;
            } // END of state-container definition.
        } // END of debug-container definition.
    } // END of platform-component-debug definition.

    grouping  components-grouping {
    description
        "Enclosing container for the components in the system.";
    container components {
        description
            "Enclosing container for the components in the system.";

        list component {
            key "name";
            config false;
            description
                "List of components, keyed by component name.";
            leaf name  {
                type  leafref {
                    path  "../state/name";
                }
                description "References the component name";
            } // END of name definition.

            container state {
                config false;
                description
                    "Operational state data for each component";
                leaf name  {
                    type  string {
                        length "1..1965";
                    }
                    description "References the component name";
                } // END of name definition.

                uses platform-component-state;
                uses platform-component-memory-state;
                uses platform-component-board-state;
                uses temperature-grouping;
            } // END of state-container definition.
            uses platform-sensor-record;
            uses cpu-grouping;
            uses storage-grouping;
            uses ram-grouping;
            uses transceiver-grouping;
            uses power-supply-grouping;
            uses fan-grouping;
            uses fan-tray-grouping;
            uses chassis-grouping;
            uses linecard-grouping;
            uses power-rail-grouping;
        } // End of component-list
        uses platform-component-debug;
        uses platform-component-global;
        uses platform-component-interface;
    } // END of components-container definition.
    } // END of components-grouping definition.

    uses components-grouping;
    uses profiles-grouping;

    rpc ddm-clear-transceiver-alarm-all {
        description "Use ddm-clear-transceiver-alarm-all to clear alarms from all
                    transceivers";
    }

    rpc ddm-clear-transceiver-alarm {
        description "Use ddm-clear-transceiver-alarm-all to clear alarm from transceiver";
        input  {
            leaf name  {
                type string;
                mandatory true;
                description "Use this rpc attribute to clear transceiver alarm";
            }
        }
    }

    rpc debug-ddm-on {
        description "Use debug-ddm-on to enable debug for digital diagnostic monitoring";
    }

    rpc debug-ddm-off {
        description "Use debug-ddm-off to disable debug for digital diagnostic monitoring";
    }

    rpc debug-cmm-on {
        description "Use debug-cmm-on to enable debug for chassis monitoring";
    }

    rpc debug-cmm-off {
        description "Use debug-cmm-off to disable debug for chassis monitoring";
    }

    notification bmc-lower-non-critical-low-threshold-notification {

        description "Notification for lower non critical low event.";

        // severity "WARNING";
        // eventClass "STATE";
        leaf name {
            type  string;
        description
            "References the component name";
        }

        leaf lower-non-critical {
            type  decimal64 {
                 fraction-digits 3;            }
        description
            "lower non critical sensor threshold.-100002 represents not applicable";
        }

        leaf threshold {
            type  decimal64 {
                 fraction-digits 3;            }
        description
            "threshold for sensor notification";
        }

        leaf units {
            type  string;
        description
            "unit of sensor record";
        }

        leaf event-type {
            type ipi-platform-types:cmm_bmc_event_type_t;
        description
            "Type of event for sensor notification";
        }
    }

    notification bmc-lower-non-critical-high-threshold-notification {

        description "Notification for lower non critical high event.";

        // severity "WARNING";
        // eventClass "STATE";
        leaf name {
            type  string;
        description
            "References the component name";
        }

        leaf lower-non-critical {
            type  decimal64 {
                 fraction-digits 3;            }
        description
            "lower non critical sensor threshold.-100002 represents not applicable";
        }

        leaf threshold {
            type  decimal64 {
                 fraction-digits 3;            }
        description
            "threshold for sensor notification";
        }

        leaf units {
            type  string;
        description
            "unit of sensor record";
        }

        leaf event-type {
            type ipi-platform-types:cmm_bmc_event_type_t;
        description
            "Type of event for sensor notification";
        }
    }

    notification bmc-lower-critical-low-threshold-notification {

        description "Notification for lower critical low event.";

        // severity "MAJOR";
        // eventClass "STATE";
        leaf name {
            type  string;
        description
            "References the component name";
        }

        leaf lower-critical {
            type  decimal64 {
                 fraction-digits 3;            }
        description
            "lower non critical sensor threshold.-100002 represents not applicable";
        }

        leaf threshold {
            type  decimal64 {
                 fraction-digits 3;            }
        description
            "threshold for sensor notification";
        }

        leaf units {
            type  string;
        description
            "unit of sensor record";
        }

        leaf event-type {
            type ipi-platform-types:cmm_bmc_event_type_t;
        description
            "Type of event for sensor notification";
        }
    }

    notification bmc-lower-critical-high-threshold-notification {

        description "Notification for lower critical high event.";

        // severity "WARNING";
        // eventClass "STATE";
        leaf name {
            type  string;
        description
            "References the component name";
        }

        leaf lower-critical {
            type  decimal64 {
                 fraction-digits 3;            }
        description
            "lower non critical sensor threshold.-100002 represents not applicable";
        }

        leaf threshold {
            type  decimal64 {
                 fraction-digits 3;            }
        description
            "threshold for sensor notification";
        }

        leaf units {
            type  string;
        description
            "unit of sensor record";
        }

        leaf event-type {
            type ipi-platform-types:cmm_bmc_event_type_t;
        description
            "Type of event for sensor notification";
        }
    }

    notification bmc-lower-non-recoverable-low-threshold-notification {

        description "Notification for lower non recoverable low event.";

        // severity "CRITICAL";
        // eventClass "STATE";
        leaf name {
            type  string;
        description
            "References the component name";
        }

        leaf lower-non-recoverable {
            type  decimal64 {
                 fraction-digits 3;            }
        description
            "lower non recoverable sensor threshold.-100002 represents not
                    applicable";
        }

        leaf threshold {
            type  decimal64 {
                 fraction-digits 3;            }
        description
            "threshold for sensor notification";
        }

        leaf units {
            type  string;
        description
            "unit of sensor record";
        }

        leaf event-type {
            type ipi-platform-types:cmm_bmc_event_type_t;
        description
            "Type of event for sensor notification";
        }
    }

    notification bmc-lower-non-recoverable-high-threshold-notification {

        description "Notification for lower non recoverable high event.";

        // severity "WARNING";
        // eventClass "STATE";
        leaf name {
            type  string;
        description
            "References the component name";
        }

        leaf lower-non-recoverable {
            type  decimal64 {
                 fraction-digits 3;            }
        description
            "lower non recoverable sensor threshold.-100002 represents not
                    applicable";
        }

        leaf threshold {
            type  decimal64 {
                 fraction-digits 3;            }
        description
            "threshold for sensor notification";
        }

        leaf units {
            type  string;
        description
            "unit of sensor record";
        }

        leaf event-type {
            type ipi-platform-types:cmm_bmc_event_type_t;
        description
            "Type of event for sensor notification";
        }
    }

    notification bmc-upper-non-critical-low-threshold-notification {

        description "Notification for upper non critical low event.";

        // severity "WARNING";
        // eventClass "STATE";
        leaf name {
            type  string;
        description
            "References the component name";
        }

        leaf upper-non-critical {
            type  decimal64 {
                 fraction-digits 3;            }
        description
            "upper non critical sensor threshold.-100002 represents not applicable";
        }

        leaf threshold {
            type  decimal64 {
                 fraction-digits 3;            }
        description
            "threshold for sensor notification";
        }

        leaf units {
            type  string;
        description
            "unit of sensor record";
        }

        leaf event-type {
            type ipi-platform-types:cmm_bmc_event_type_t;
        description
            "Type of event for sensor notification";
        }
    }

    notification bmc-upper-non-critical-high-threshold-notification {

        description "Notification for upper non critical high event.";

        // severity "WARNING";
        // eventClass "STATE";
        leaf name {
            type  string;
        description
            "References the component name";
        }

        leaf upper-non-critical {
            type  decimal64 {
                 fraction-digits 3;            }
        description
            "upper non critical sensor threshold.-100002 represents not applicable";
        }

        leaf threshold {
            type  decimal64 {
                 fraction-digits 3;            }
        description
            "threshold for sensor notification";
        }

        leaf units {
            type  string;
        description
            "unit of sensor record";
        }

        leaf event-type {
            type ipi-platform-types:cmm_bmc_event_type_t;
        description
            "Type of event for sensor notification";
        }
    }

    notification bmc-upper-critical-low-threshold-notification {

        description "Notification for upper critical low event.";

        // severity "WARNING";
        // eventClass "STATE";
        leaf name {
            type  string;
        description
            "References the component name";
        }

        leaf upper-critical {
            type  decimal64 {
                 fraction-digits 3;            }
        description
            "upper critical sensor threshold.-100002 represents not applicable";
        }

        leaf threshold {
            type  decimal64 {
                 fraction-digits 3;            }
        description
            "threshold for sensor notification";
        }

        leaf units {
            type  string;
        description
            "unit of sensor record";
        }

        leaf event-type {
            type ipi-platform-types:cmm_bmc_event_type_t;
        description
            "Type of event for sensor notification";
        }
    }

    notification bmc-upper-critical-high-threshold-notification {

        description "Notification for upper critical high event.";

        // severity "MAJOR";
        // eventClass "STATE";
        leaf name {
            type  string;
        description
            "References the component name";
        }

        leaf upper-critical {
            type  decimal64 {
                 fraction-digits 3;            }
        description
            "upper critical sensor threshold.-100002 represents not applicable";
        }

        leaf threshold {
            type  decimal64 {
                 fraction-digits 3;            }
        description
            "threshold for sensor notification";
        }

        leaf units {
            type  string;
        description
            "unit of sensor record";
        }

        leaf event-type {
            type ipi-platform-types:cmm_bmc_event_type_t;
        description
            "Type of event for sensor notification";
        }
    }

    notification bmc-upper-non-recoverable-low-threshold-notification {

        description "Notification for upper non recoverable low event.";

        // severity "WARNING";
        // eventClass "STATE";
        leaf name {
            type  string;
        description
            "References the component name";
        }

        leaf upper-non-recoverable {
            type  decimal64 {
                 fraction-digits 3;            }
        description
            "upper critical sensor threshold.-100002 represents not applicable";
        }

        leaf threshold {
            type  decimal64 {
                 fraction-digits 3;            }
        description
            "threshold for sensor notification";
        }

        leaf units {
            type  string;
        description
            "unit of sensor record";
        }

        leaf event-type {
            type ipi-platform-types:cmm_bmc_event_type_t;
        description
            "Type of event for sensor notification";
        }
    }

    notification bmc-upper-non-recoverable-high-threshold-notification {

        description "Notification for upper non recoverable high threshold high event.";

        // severity "CRITICAL";
        // eventClass "STATE";
        leaf name {
            type  string;
        description
            "References the component name";
        }

        leaf upper-non-recoverable {
            type  decimal64 {
                 fraction-digits 3;            }
        description
            "upper critical sensor threshold.-100002 represents not applicable";
        }

        leaf threshold {
            type  decimal64 {
                 fraction-digits 3;            }
        description
            "threshold for sensor notification";
        }

        leaf units {
            type  string;
        description
            "unit of sensor record";
        }

        leaf event-type {
            type ipi-platform-types:cmm_bmc_event_type_t;
        description
            "Type of event for sensor notification";
        }
    }

    notification bmc-device-state-notification {

        description "Notification for operational state of the device.";

        // severity "WARNING";
        // eventClass "STATE";
        leaf name {
            type  string;
        description
            "References the component name";
        }

        leaf operational-status {
            type  string;
        description
            "Sensor's operational state";
        }
    }

    notification cpu-load-15min-alert {

        description "This notification is sent when CPU utilization average during 15 minutes exceeds the alert threshold.";

        // severity "MAJOR";
        // eventClass "STATE";
        leaf name {
            type  string;
        description
            "References the component name";
        }

        leaf cpu-15min-load-percentage {
            type  decimal64 {
                 fraction-digits 2;            }
        description
            "The arithmetic mean value of the percentage measure of the CPU load
                    over 15 minutes interval";
        }

        leaf cpu-15min-alert-threshold {
            type  uint8;
        description
            "CPU load threshold during 15 minutes interval for alert level";
        }
    }

    notification cpu-load-15min-alert-recovery {

        description "This notification is sent when CPU utilization average during 15 minutes falls bellow the alert threshold.";

        // severity "INFO";
        // eventClass "STATE";
        leaf name {
            type  string;
        description
            "References the component name";
        }

        leaf cpu-15min-load-percentage {
            type  decimal64 {
                 fraction-digits 2;            }
        description
            "The arithmetic mean value of the percentage measure of the CPU load
                    over 15 minutes interval";
        }

        leaf cpu-15min-alert-threshold {
            type  uint8;
        description
            "CPU load threshold during 15 minutes interval for alert level";
        }
    }

    notification cpu-load-5min-alert {

        description "This notification is sent when CPU utilization average during 5 minutes exceeds the alert threshold.";

        // severity "MAJOR";
        // eventClass "STATE";
        leaf name {
            type  string;
        description
            "References the component name";
        }

        leaf cpu-5min-load-percentage {
            type  decimal64 {
                 fraction-digits 2;            }
        description
            "The arithmetic mean value of the percentage measure of the CPU load
                    over 5 minutes interval";
        }

        leaf cpu-5min-alert-threshold {
            type  uint8;
        description
            "CPU load threshold during 5 minutes interval for alert level";
        }
    }

    notification cpu-load-5min-alert-recovery {

        description "This notification is sent when CPU utilization average during 5 minutes falls bellow the alert threshold.";

        // severity "INFO";
        // eventClass "STATE";
        leaf name {
            type  string;
        description
            "References the component name";
        }

        leaf cpu-5min-load-percentage {
            type  decimal64 {
                 fraction-digits 2;            }
        description
            "The arithmetic mean value of the percentage measure of the CPU load
                    over 5 minutes interval";
        }

        leaf cpu-5min-alert-threshold {
            type  uint8;
        description
            "CPU load threshold during 5 minutes interval for alert level";
        }
    }

    notification cpu-load-1min-critical {

        description "This notification is sent when CPU utilization average during 1 minute exceeds the critical threshold.";

        // severity "CRITICAL";
        // eventClass "STATE";
        leaf name {
            type  string;
        description
            "References the component name";
        }

        leaf cpu-1min-load-percentage {
            type  decimal64 {
                 fraction-digits 2;            }
        description
            "The arithmetic mean value of the percentage measure of the CPU load
                    over 1 minute interval";
        }

        leaf cpu-1min-critical-threshold {
            type  uint8;
        description
            "CPU load threshold during 1 minute interval for critical level";
        }
    }

    notification cpu-load-1min-critical-recovery {

        description "This notification is sent when CPU utilization average during 1 minute falls bellow the critical threshold.";

        // severity "INFO";
        // eventClass "STATE";
        leaf name {
            type  string;
        description
            "References the component name";
        }

        leaf cpu-1min-load-percentage {
            type  decimal64 {
                 fraction-digits 2;            }
        description
            "The arithmetic mean value of the percentage measure of the CPU load
                    over 1 minute interval";
        }

        leaf cpu-1min-critical-threshold {
            type  uint8;
        description
            "CPU load threshold during 1 minute interval for critical level";
        }
    }

    notification cpu-load-1min-alert {

        description "This notification is sent when CPU utilization average during 1 minute falls bellow the alert threshold.";

        // severity "MAJOR";
        // eventClass "STATE";
        leaf name {
            type  string;
        description
            "References the component name";
        }

        leaf cpu-1min-load-percentage {
            type  decimal64 {
                 fraction-digits 2;            }
        description
            "The arithmetic mean value of the percentage measure of the CPU load
                    over 1 minute interval";
        }

        leaf cpu-1min-alert-threshold {
            type  uint8;
        description
            "CPU load threshold during 1 minute interval for alert level";
        }
    }

    notification cpu-load-1min-alert-recovery {

        description "This notification is sent when CPU utilization average during 1 minute falls bellow the alert threshold.";

        // severity "INFO";
        // eventClass "STATE";
        leaf name {
            type  string;
        description
            "References the component name";
        }

        leaf cpu-1min-load-percentage {
            type  decimal64 {
                 fraction-digits 2;            }
        description
            "The arithmetic mean value of the percentage measure of the CPU load
                    over 1 minute interval";
        }

        leaf cpu-1min-alert-threshold {
            type  uint8;
        description
            "CPU load threshold during 1 minute interval for alert level";
        }
    }

    notification storage-usage-rising-alert {

        description "Notification for storage when it exceeds alert threshold.";

        // severity "CRITICAL";
        // eventClass "STATE";
        leaf name {
            type  string;
        description
            "References the component name";
        }

        leaf used-memory {
            type  uint64;
        description
            "Used memory of the Hard storage.";
        }

        leaf usage-alert-threshold {
            type  int32;
        description
            "Hard disk's usage threshold %  for Alert Level.";
        }

        leaf mount-point {
            type  string;
        description
            "A unique value for each mounted filesystem.";
        }
    }

    notification storage-usage-critical-alert {

        description "Notification for storage when it exceeds critical threshold.";

        // severity "MAJOR";
        // eventClass "STATE";
        leaf name {
            type  string;
        description
            "References the component name";
        }

        leaf used-memory {
            type  uint64;
        description
            "Used memory of the Hard storage.";
        }

        leaf usage-critical-threshold {
            type  int32;
        description
            "Hard disk's usage threshold %  for critical level.";
        }

        leaf mount-point {
            type  string;
        description
            "A unique value for each mounted filesystem.";
        }
    }

    notification storage-usage-recovery-from-alert-level {

        description "Notification for storage usage recovery from alert level.";

        // severity "WARNING";
        // eventClass "STATE";
        leaf name {
            type  string;
        description
            "References the component name";
        }

        leaf used-memory {
            type  uint64;
        description
            "Used memory of the Hard storage.";
        }

        leaf usage-alert-threshold {
            type  int32;
        description
            "Hard disk's usage threshold %  for Alert Level.";
        }

        leaf mount-point {
            type  string;
        description
            "A unique value for each mounted filesystem.";
        }
    }

    notification storage-usage-recovery-from-critical-level {

        description "Notification for storage usage recovery from critical level.";

        // severity "WARNING";
        // eventClass "STATE";
        leaf name {
            type  string;
        description
            "References the component name";
        }

        leaf used-memory {
            type  uint64;
        description
            "Used memory of the Hard storage.";
        }

        leaf usage-critical-threshold {
            type  int32;
        description
            "Hard disk's usage threshold %  for critical level.";
        }

        leaf mount-point {
            type  string;
        description
            "A unique value for each mounted filesystem.";
        }
    }

    notification ram-usage-rising-critical {

        description "Notification for RAM usage rising critical threshold.";

        // severity "CRITICAL";
        // eventClass "STATE";
        leaf name {
            type  string;
        description
            "References the component name";
        }

        leaf used-memory {
            type  uint64;
        description
            "CPU RAM's used memory available for utilisation in MBytes.";
        }

        leaf usage-critical-threshold {
            type  uint32;
        description
            "RAM usage threshold % for critical level.";
        }
    }

    notification ram-usage-rising-alert {

        description "Notification for RAM usage rising alert threshold.";

        // severity "CRITICAL";
        // eventClass "STATE";
        leaf name {
            type  string;
        description
            "References the component name";
        }

        leaf used-memory {
            type  uint64;
        description
            "CPU RAM's used memory available for utilisation in MBytes.";
        }

        leaf usage-alert-threshold {
            type  uint32;
        description
            "RAM usage threshold % for alert level.";
        }
    }

    notification ram-usage-recovery-from-critical-level {

        description "Notification for RAM usage recovery from critical threshold.";

        // severity "WARNING";
        // eventClass "STATE";
        leaf name {
            type  string;
        description
            "References the component name";
        }

        leaf used-memory {
            type  uint64;
        description
            "CPU RAM's used memory available for utilisation in MBytes.";
        }

        leaf usage-critical-threshold {
            type  uint32;
        description
            "RAM usage threshold % for critical level.";
        }
    }

    notification ram-usage-recovery-from-alert-level {

        description "Notification for RAM usage recovery from alert threshold.";

        // severity "WARNING";
        // eventClass "STATE";
        leaf name {
            type  string;
        description
            "References the component name";
        }

        leaf used-memory {
            type  uint64;
        description
            "CPU RAM's used memory available for utilisation in MBytes.";
        }

        leaf usage-alert-threshold {
            type  uint32;
        description
            "RAM usage threshold % for alert level.";
        }
    }

    notification temperature-high {

        description "This notification is sent when temperature sensor exceeds a given threshold.";

        // eventClass "STATE";
        leaf name {
            type  string;
        description
            "References the component name";
        }

        leaf alarm-status {
            type  boolean;
        description
            "A value of true indicates the alarm has been raised or asserted. The
                    value should be false when the alarm is cleared.";
        }

        leaf alarm-threshold {
            type  decimal64 {
                 fraction-digits 2;            }
        description
            "The threshold value that was crossed for this alarm.";
        }

        leaf instant {
            type  decimal64 {
                 fraction-digits 2;            }
        description
            "The instantaneous temperature value.";
        }
    }

    notification temperature-low {

        description "This notification is sent when temperature sensor falls below a given threshold.";

        // eventClass "STATE";
        leaf name {
            type  string;
        description
            "References the component name";
        }

        leaf alarm-status {
            type  boolean;
        description
            "A value of true indicates the alarm has been raised or asserted. The
                    value should be false when the alarm is cleared.";
        }

        leaf alarm-threshold {
            type  decimal64 {
                 fraction-digits 2;            }
        description
            "The threshold value that was crossed for this alarm.";
        }

        leaf instant {
            type  decimal64 {
                 fraction-digits 2;            }
        description
            "The instantaneous temperature value.";
        }
    }

    notification power-supply-inserted {

        description "This notification is sent when power supply unit is inserted.";

        // severity "WARNING";
        // eventClass "STATE";
        leaf name {
            type  string;
        description
            "References the component name";
        }
    }

    notification power-supply-removed {

        description "This notification is sent when power supply unit is removed.";

        // severity "WARNING";
        // eventClass "STATE";
        leaf name {
            type  string;
        description
            "References the component name";
        }
    }

    notification power-supply-ac-failed {

        description "This notification is sent when power supply unit has no input power.";

        // severity "CRITICAL";
        // eventClass "STATE";
        leaf name {
            type  string;
        description
            "References the component name";
        }
    }

    notification power-supply-ac-recovery {

        description "This notification is sent when power supply unit input power is restored.";

        // severity "INFO";
        // eventClass "STATE";
        leaf name {
            type  string;
        description
            "References the component name";
        }
    }

    notification power-supply-12v-failed {

        description "This notification is sent when power supply unit has no output power.";

        // severity "CRITICAL";
        // eventClass "STATE";
        leaf name {
            type  string;
        description
            "References the component name";
        }
    }

    notification power-supply-12v-recovery {

        description "This notification is sent when power supply unit output power is restored..";

        // severity "INFO";
        // eventClass "STATE";
        leaf name {
            type  string;
        description
            "References the component name";
        }
    }

    notification fan-status-alarm {

        description "This notification is sent when fan is in alarm state.";

        // severity "CRITICAL";
        // eventClass "STATE";
        leaf name {
            type  string;
        description
            "References the component name";
        }

        leaf fan-index {
            type  uint8;
        description
            "Fan identifier index in the system";
        }

        leaf fan-status {
            type  cml_cmm_fan_status_t;
        description
            "The status of the fan";
        }
    }

    notification fan-status-alarm-recovery {

        description "This notification is sent when fan recovers from an alarm state.";

        // severity "INFO";
        // eventClass "STATE";
        leaf name {
            type  string;
        description
            "References the component name";
        }

        leaf fan-index {
            type  uint8;
        description
            "Fan identifier index in the system";
        }

        leaf fan-status {
            type  cml_cmm_fan_status_t;
        description
            "The status of the fan";
        }
    }

    notification fan-rpm-min-alert {

        description "This notification is sent when fan RPM set to its minimum value..";

        // severity "CRITICAL";
        // eventClass "STATE";
        leaf name {
            type  string;
        description
            "References the component name";
        }

        leaf minimum-rpm {
            type  uint32;
        description
            "Value represents the minimum supported RPM of fan";
        }
    }

    notification fan-rpm-max-alert {

        description "This notification is sent when fan RPM set to its maximum value..";

        // severity "CRITICAL";
        // eventClass "STATE";
        leaf name {
            type  string;
        description
            "References the component name";
        }

        leaf maximum-rpm {
            type  uint32;
        description
            "Value represents the maximum supported RPM of fan";
        }
    }

    notification fan-tray-inserted {

        description "This notification is sent when fan tray is inserted.";

        // severity "WARNING";
        // eventClass "STATE";
        leaf name {
            type  string;
        description
            "References the component name";
        }
    }

    notification fan-tray-removed {

        description "This notification is sent when fan tray is removed.";

        // severity "WARNING";
        // eventClass "STATE";
        leaf name {
            type  string;
        description
            "References the component name";
        }
    }

}
