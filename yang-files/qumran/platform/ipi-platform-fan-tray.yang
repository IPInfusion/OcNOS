/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-platform-fan-tray.yang
*
*/

submodule ipi-platform-fan-tray {

    yang-version 1.1;

    belongs-to  ipi-platform { prefix ipi-platform; }

    organization
        "IP Infusion Inc.";

    contact
        "Address: 3965 Freedom Circle, Suite 200, Santa Clara, CA 95054
         Phone: +1 408-400-1900
         E-mail: support@ipinfusio.com
         Web: http://www.ipinfusion.com/";

    description
        "This module defines a schema for fan tray components in platform
                datamodel";


    revision "2021-03-18" {
        description "Added notification for fan tray alarms";
        reference " 0.2.0.";
    }

    revision "2021-01-25" {
        description "Initial version adding support to fan tray components in ipi-platform module";
        reference " 0.1.0.";
    }



    typedef  cml_cmm_fan_tray_status_t {
        type enumeration {
            enum unknown {
                value 0;
                description "Fan tray status unknown";
            }
            enum not-present {
                value 1;
                description "Fan tray not present";
            }
            enum present {
                value 2;
                description "Fan tray present";
            }
        }
        description "type definition for CML_CMM_FAN_TRAY_STATUS_T";
    }

    typedef  cml_cmm_led_color_code_t {
        type enumeration {
            enum none {
                value 1;
                description "No color";
            }
            enum green {
                value 2;
                description "Green color";
            }
            enum blinking-green {
                value 3;
                description "Blinking-green color";
            }
            enum solid-green {
                value 4;
                description "Solid-green color";
            }
            enum amber {
                value 5;
                description "Amber color";
            }
            enum blinking-amber {
                value 6;
                description "Blinking-amber color";
            }
            enum solid-amber {
                value 7;
                description "Solid-amber color";
            }
            enum red {
                value 8;
                description "Red color";
            }
            enum blinking-red {
                value 9;
                description "Blinking-red color";
            }
            enum solid-red {
                value 10;
                description "Solid-red color";
            }
            enum blue {
                value 11;
                description "Blue color";
            }
            enum blinking-blue {
                value 12;
                description "Blinking-blue color";
            }
            enum yellow {
                value 13;
                description "Yellow color";
            }
            enum blinking-yellow {
                value 14;
                description "Blinking-yellow color";
            }
            enum orange {
                value 15;
                description "Orange color";
            }
            enum slow-blinking-green {
                value 16;
                description "Slow-blinking-green color";
            }
            enum fast-blinking-green {
                value 17;
                description "Fast-blinking-green color";
            }
            enum unknown {
                value 30;
                description "Color unknown";
            }
        }
        description "type definition for CML_CMM_LED_COLOR_CODE_T";
    }    grouping fan-tray-state {
        description
            "Fan tray data for platform components";
        leaf tray-number  {
            type  uint8;
            description "Fan identifier number in the system";
        } // END of tray-number definition.

        leaf status  {
            type  cml_cmm_fan_tray_status_t;
            description "Fan tray status";
        } // END of status definition.

        leaf led-color  {
            type  cml_cmm_led_color_code_t;
            description "The color of the fan led";
        } // END of led-color definition.

        leaf fan-count  {
            type  uint32;
            description "Number of fans in the tray";
        } // END of fan-count definition.

    } // END of fan-tray-state definition.

    grouping  fan-tray-grouping {
    description
        "Container for fan tray component";
    container fan-tray {
        config false;
        description
            "Container for fan tray component";
        container state {
            config false;
            description
                "Operational state data for fan tray components";
            uses fan-tray-state;
        } // END of state-container definition.
    } // END of fan-tray-container definition.
    } // END of fan-tray-grouping definition.


}
