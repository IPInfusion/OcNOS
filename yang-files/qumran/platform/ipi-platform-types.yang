/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-platform-types.yang
*
*/

module ipi-platform-types {

    yang-version 1.1;

    namespace   "http://www.ipinfusion.com/yang/ocnos/ipi-platform-types";

    prefix "ipi-platform-types";

    organization
        "IP Infusion Inc.";

    contact
        "Address: 3965 Freedom Circle, Suite 200, Santa Clara, CA 95054
         Phone: +1 408-400-1900
         E-mail: support@ipinfusion.com
         Web: http://www.ipinfusion.com/";

    description
        "YANG version of the ipi-platform-types";


    revision "2020-12-15" {
        description "Change to have data-types in lower case instead of camel case";
        reference " 0.2.0.";
    }

    revision "2018-06-21" {
        description "Initial Version";
        reference " 0.1.0.";
    }



    typedef  cmm_component_type_t {
        type enumeration {
            enum NA {
                value 0;
                description "Not applicable";
            }
            enum software {
                value 1;
                description "software-related components in a managed device";
            }
            enum chasis {
                value 2;
                description "Chassis component, typically with multiple slots / shelves";
            }
            enum backplane {
                value 3;
                description "Backplane component for aggregating traffic, typically contained in a chassis component";
            }
            enum fabric {
                value 4;
                description "Interconnect between ingress and egress ports on the device (e.g., a crossbar switch).";
            }
            enum power-supply {
                value 5;
                description "Component that is supplying power to the device";
            }
            enum power-rail {
                value 6;
                description "Power rail component";
            }
            enum fan {
                value 7;
                description "Cooling fan, or could be some other heat-reduction component";
            }
            enum sensor {
                value 8;
                description "Physical sensor, e.g., a temperature sensor in a chassis";
            }
            enum fan-tray {
                value 9;
                description "Fan tray";
            }
            enum transceiver {
                value 10;
                description "Pluggable module present in a port";
            }
            enum cpu {
                value 11;
                description "Processing unit, e.g., a management processor";
            }
            enum storage {
                value 12;
                description "A storage subsystem on the device (disk, SSD, etc.)";
            }
            enum integrated-circuit {
                value 13;
                description "A special purpose processing unit, typically for traffic           switching/forwarding (e.g., switching ASIC, NPU, forwarding           chip, etc.)";
            }
            enum ram {
                value 14;
                description "RAM unit";
            }
            enum ptp-clock {
                value 15;
                description "Ptp-clock unit";
            }
        }
        description "type definition for CMM_COMPONENT_TYPE_T";
    }

    typedef  cmm_bmc_event_type_t {
        type enumeration {
            enum Deasserted {
                value 1;
                description "Deasserted event";
            }
            enum Asserted {
                value 2;
                description "Asserted event";
            }
        }
        description "type definition for CMM_BMC_EVENT_TYPE_T";
    }

    typedef  cmm_component_oper_status_t {
        type enumeration {
            enum NA {
                value 0;
                description "Not Applicable";
            }
            enum active {
                value 1;
                description "Component is enabled and active (i.e., up)";
            }
            enum inactive {
                value 2;
                description "Component is enabled but inactive (i.e., down)";
            }
            enum disabled {
                value 3;
                description "Component is administratively disabled.";
            }
        }
        description "type definition for CMM_COMPONENT_OPER_STATUS_T";
    }

    typedef  cmm_bmc_value_t {
        type union {
            type decimal64 {

             fraction-digits 6;
            }
            type string {

            }
        }
        description "type definition for CMM_BMC_VALUE_T";
    }

    typedef  cmm_cpu_type_t {
        type enumeration {
            enum cpu-usage1 {
                value 1;
                description "Set CPU Usage for past 1 min";
            }
            enum cpu-usage5 {
                value 5;
                description "Set CPU Usage for past 5 min";
            }
            enum cpu-usage15 {
                value 15;
                description "Set CPU Usage for past 15 min";
            }
        }
        description "type definition for CMM_CPU_TYPE_T";
    }

    typedef  cmm_monitor_state {
        type enumeration {
            enum disable {
                value 1;
                description "Disable";
            }
            enum enable {
                value 2;
                description "Enable";
            }
        }
        description "type definition for CMM_MONITOR_STATE";
    }

    typedef  cmm_gps_monitor_type_t {
        type enumeration {
            enum stop {
                value 0;
                description "stop monitoring";
            }
            enum start {
                value 1;
                description "start monitoring";
            }
        }
        description "type definition for CMM_GPS_MONITOR_TYPE_T";
    }

    typedef  cml_wavelength_t {
        type union {
            type cml_wavelength_channel_t {

            }
            type cml_wavelength_update_t {

            }
        }
        description "type definition for CML_WAVELENGTH_T";
    }

    typedef  cml_wavelength_channel_t {
        type uint32 {
             range 1..96;
        }
        description "type definition for CML_WAVELENGTH_CHANNEL_T";
    }

    typedef  cml_wavelength_update_t {
        type uint32 {
             range 1528773..1566723;
        }
        description "type definition for CML_WAVELENGTH_UPDATE_T";
    }

}
