/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-platform-profile.yang
*
*/

submodule ipi-platform-profile {

    yang-version 1.1;

    belongs-to  ipi-platform { prefix ipi-platform; }

    import feature-list {
        prefix feature-list;
        revision-date 2021-05-03;
    }

    import cml-data-types {
        prefix cml-data-types;
        revision-date 2021-05-03;
    }

    import ipi-platform-types {
        prefix ipi-platform-types;
        revision-date 2021-01-25;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for Platform profile object";


    revision "2021-06-23" {
        description "Updated attribute ingress-bfd datatype from CML_EMPTY_T to CML_ENABLE_DISABLE_T";
        reference " 0.3.0.";
    }

    revision "2021-06-17" {
        description "Updated with changes for non-DNX Broadcom platform hardware profiles";
        reference " 0.2.0.";
    }

    revision "2021-03-29" {
        description "Initial Version";
        reference " 0.1.0.";
    }

    grouping hardware-profile-config {
        description
            "Grouping for hardware-profile config objects.";
        leaf flow-control  {
            if-feature feature-list:HAVE_DUNE;
            if-feature feature-list:HAVE_BCM_UFT;
            type  empty;
            description "Use this attribute to enable or disable hardware profile flowcontrol.";
        } // END of flow-control definition.

        leaf micro-bfd  {
            if-feature feature-list:HAVE_CUSTOM1_HW_BFD;
            type  empty;
            description "Use this attribute to enable or disable hardware profile micro-bfd.";
        } // END of micro-bfd definition.

        leaf custom-service-queue-profile  {
            if-feature feature-list:HAVE_DUNE;
            type  ipi-platform-types:platform_qos_queue_profile_type_t;
            default "profile1";
            description "Use this attribute to configure or unconfigure hardware profile
                        service-queue profile support.";
        } // END of custom-service-queue-profile definition.

    } // END of hardware-profile-config definition.
    grouping hardware-profile-filters-config {
        description
            "Grouping for hardware-profile filter config objects.";
        leaf egress-ipv6  {
            if-feature feature-list:HAVE_ACL;
            if-feature feature-list:NOT_HAVE_DUNE;
            type  empty;
            description "Use this attribute to enable or disable Egress IPv6 filter groups.
                        Disabling filter groups increases the configurable filter entries.";
        } // END of egress-ipv6 definition.

        leaf ingress-ipv6  {
            if-feature feature-list:HAVE_DUNE;
            if-feature feature-list:HAVE_ACL;
            type  empty;
            description "Use this attribute to enable or disable Ingress IPv6 filter groups.
                        Disabling filter groups increases the configurable filter entries.";
        } // END of ingress-ipv6 definition.

        leaf ingress-ipv4  {
            when " not(/profiles/hardware-profile/filters/config/ingress-ipv4-extended) ";
            if-feature feature-list:HAVE_ACL;
            type  empty;
            description "Use this attribute to enable or disable Ingress IPv4 filter groups.
                        Disabling filter groups increases the configurable filter entries.";
        } // END of ingress-ipv4 definition.

        leaf ingress-ipv4-extended  {
            when " not(/profiles/hardware-profile/filters/config/ingress-ipv4) ";
            if-feature feature-list:HAVE_DUNE;
            if-feature feature-list:HAVE_ACL;
            type  empty;
            description "Use this attribute to enable or disable Ingress IPv4 extended filter
                        groups. Disabling filter groups increases the configurable filter
                        entries.";
        } // END of ingress-ipv4-extended definition.

        leaf ingress-ipv4-qos  {
            if-feature feature-list:HAVE_DUNE;
            if-feature feature-list:HAVE_ACL;
            type  empty;
            description "Use this attribute to enable or disable Ingress IPv4 QoS filter
                        groups. Disabling filter groups increases the configurable filter
                        entries.";
        } // END of ingress-ipv4-qos definition.

        leaf ingress-arp  {
            if-feature feature-list:HAVE_ACL;
            type  empty;
            description "Use this attribute to enable or disable Ingress ARP filter groups.";
        } // END of ingress-arp definition.

        leaf ingress-ipv6-qos  {
            if-feature feature-list:HAVE_DUNE;
            if-feature feature-list:HAVE_ACL;
            type  empty;
            description "Use this attribute to enable or disable Ingress IPv6 QoS filter
                        groups. Disabling filter groups increases the configurable filter
                        entries.";
        } // END of ingress-ipv6-qos definition.

        leaf qos  {
            when " not(/profiles/hardware-profile/filters/config/qos-extended) + not(/profiles/hardware-profile/filters/config/qos-policer) ";
            if-feature feature-list:HAVE_DUNE;
            if-feature feature-list:HAVE_ACL;
            type  empty;
            description "Use this attribute to enable or disable QoS filter groups. Disabling
                        filter groups increases the configurable filter entries.";
        } // END of qos definition.

        leaf qos-extended  {
            when " not(/profiles/hardware-profile/filters/config/qos) + not(/profiles/hardware-profile/filters/config/qos-policer) ";
            if-feature feature-list:HAVE_DUNE;
            if-feature feature-list:HAVE_ACL;
            type  empty;
            description "Use this attribute to enable or disable QoS extended filter groups.
                        Disabling filter groups increases the configurable filter entries.";
        } // END of qos-extended definition.

        leaf qos-policer  {
            when " not(/profiles/hardware-profile/filters/config/qos) + not(/profiles/hardware-profile/filters/config/qos-extended) ";
            if-feature feature-list:HAVE_DUNE;
            if-feature feature-list:HAVE_ACL;
            type  empty;
            description "Use this attribute to enable or disable QoS policer filter groups.
                        Disabling filter groups increases the configurable filter entries.";
        } // END of qos-policer definition.

        leaf qos-ipv6  {
            if-feature feature-list:HAVE_DUNE;
            if-feature feature-list:HAVE_ACL;
            type  empty;
            description "Use this attribute to enable or disable QoS filter group for IPv6
                        traffic. Disabling filter groups increases the configurable filter
                        entries.";
        } // END of qos-ipv6 definition.

        leaf egress-ipv4  {
            if-feature feature-list:HAVE_DUNE;
            if-feature feature-list:HAVE_ACL;
            type  empty;
            description "Use this attribute to enable or disable Egress IPv4 filter groups.
                        Disabling filter groups increases the configurable filter entries.";
        } // END of egress-ipv4 definition.

        leaf egress-layer2  {
            if-feature feature-list:HAVE_DUNE;
            if-feature feature-list:HAVE_ACL;
            type  empty;
            description "Use this attribute to enable or disable Egress L2 filter groups.
                        Disabling filter groups increases the configurable filter entries.";
        } // END of egress-layer2 definition.

        leaf ingress-layer2  {
            when " not(/profiles/hardware-profile/filters/config/ingress-layer2-extended) ";
            if-feature feature-list:HAVE_DUNE;
            if-feature feature-list:HAVE_ACL;
            type  empty;
            description "Use this attribute to enable or disable Ingress L2 filter groups.
                        Disabling filter groups increases the configurable filter entries.";
        } // END of ingress-layer2 definition.

        leaf ingress-layer2-extended  {
            when " not(/profiles/hardware-profile/filters/config/ingress-layer2) ";
            if-feature feature-list:HAVE_DUNE;
            if-feature feature-list:HAVE_ACL;
            type  empty;
            description "Use this attribute to enable or disable Ingress L2 extended filter
                        groups. Disabling filter groups increases the configurable filter
                        entries.";
        } // END of ingress-layer2-extended definition.

        leaf forwarding-ipv4  {
            if-feature feature-list:HAVE_DUNE;
            if-feature feature-list:HAVE_ACL;
            type  empty;
            description "Use this attribute to enable or disable forwarding-ipv4 filter groups.
                        Disabling filter groups increases the configurable filter entries.";
        } // END of forwarding-ipv4 definition.

        leaf cfm-domain-name-string  {
            if-feature feature-list:HAVE_DUNE;
            if-feature feature-list:HAVE_CFM;
            type  empty;
            description "Use this attribute to enable or disable CFM domain name filter groups.
                        Disabling filter groups increases the configurable filter entries.";
        } // END of cfm-domain-name-string definition.

        leaf vxlan-arp-nd  {
            if-feature feature-list:HAVE_DUNE;
            if-feature feature-list:HAVE_VXLAN;
            type  empty;
            description "Use this attribute to enable or disable VxLAN Forwarding filter
                        groups. Disabling filter groups increases the configurable filter
                        entries.";
        } // END of vxlan-arp-nd definition.

        leaf vxlan-multi-homing  {
            if-feature feature-list:HAVE_DUNE;
            if-feature feature-list:HAVE_VXLAN;
            type  empty;
            description "Use this attribute to enable or disable VxLAN Multi Homing Forwarding
                        filter groups. Disabling filter groups increases the configurable
                        filter entries.";
        } // END of vxlan-multi-homing definition.

        leaf evpn-mpls-multi-homing  {
            if-feature feature-list:HAVE_DUNE;
            if-feature feature-list:HAVE_MPLS;
            if-feature feature-list:HAVE_NVO;
            type  empty;
            description "Use this attribute to enable or disable EVPN-MPLS Multi Homing
                        Forwarding filter groups. Disabling filter groups increases the
                        configurable filter entries.";
        } // END of evpn-mpls-multi-homing definition.

        leaf ingress-bfd  {
            if-feature feature-list:HAVE_BFD_HW_OFFLOAD;
            if-feature feature-list:NOT_HAVE_CUSTOM1_HW_BFD;
            type  cml-data-types:cml_enable_disable_t;
            description "Use this attribute to enable or disable Ingress BFD filter groups.
                        Disabling filter groups increases the configurable filter entries.";
        } // END of ingress-bfd definition.

    } // END of hardware-profile-filters-config definition.
    grouping hardware-profiles-statistics-config {
        description
            "Grouping for hardware-profile statistics config objects.";
        leaf ingress-acl  {
            if-feature feature-list:HAVE_DUNE;
            type  empty;
            description "Use this attribute to enable or disable Ingress ACL QoS and PBR filter
                        groups. Disabling filter groups increases the configurable filter
                        entries.";
        } // END of ingress-acl definition.

        leaf egress-acl  {
            if-feature feature-list:HAVE_DUNE;
            type  empty;
            description "Use this attribute to enable or disable Egress ACL filter groups.
                        Disabling filter groups increases the configurable filter entries.";
        } // END of egress-acl definition.

        leaf ingress-qos  {
            if-feature feature-list:HAVE_DUNE;
            type  empty;
            description "Use this attribute to enable or disable explicitly for QoS filter
                        groups. Disabling filter groups increases the configurable filter
                        entries.";
        } // END of ingress-qos definition.

        leaf attachment-circuit-logical-if  {
            if-feature feature-list:HAVE_DUNE;
            type  empty;
            description "Use this attribute to enable or disable attachment circuits logical
                        filter groups. Disabling filter groups increases the configurable
                        filter entries.";
        } // END of attachment-circuit-logical-if definition.

        leaf tunnel-logical-if  {
            if-feature feature-list:HAVE_DUNE;
            type  empty;
            description "Use this attribute to enable or disable tunnel logical filter groups.
                        Disabling filter groups increases the configurable filter entries.";
        } // END of tunnel-logical-if definition.

        leaf evpn-mpls-stats  {
            if-feature feature-list:HAVE_DUNE;
            if-feature feature-list:HAVE_MPLS;
            if-feature feature-list:HAVE_NVO;
            type  empty;
            description "Use this attribute to enable or disable hardware statistics for
                        evpn-mpls.";
        } // END of evpn-mpls-stats definition.

        leaf mpls-pseudowire  {
            if-feature feature-list:HAVE_MPLS_STATS;
            if-feature feature-list:HAVE_DUNE;
            type  empty;
            description "Use this attribute to enable or disable MPLS Pseudowire filter groups.
                        Disabling filter groups increases the configurable filter entries.";
        } // END of mpls-pseudowire definition.

        leaf cfm-frame-loss-measurements  {
            if-feature feature-list:HAVE_CFM;
            if-feature feature-list:HAVE_DUNE;
            type  empty;
            description "Use this attribute to enable or disable CFM Loss Measurements filter
                        groups. Disabling filter groups increases the configurable filter
                        entries.";
        } // END of cfm-frame-loss-measurements definition.

        leaf cfm-continuity-check-messages  {
            if-feature feature-list:CCM_HW_OFFLOAD;
            if-feature feature-list:HAVE_DUNE;
            type  empty;
            description "Use this attribute to enable or disable CFM Continuity Check Messages
                        filter groups. Disabling filter groups increases the configurable
                        filter entries.";
        } // END of cfm-continuity-check-messages definition.

        leaf virtual-output-queue-full-color  {
            when " not(/profiles/hardware-profile/statistics/config/virtual-output-queue-forward-drop) ";
            if-feature feature-list:HAVE_DUNE;
            type  empty;
            description "Use this attribute to enable or disable Virtual Output Queue Full
                        Color filter groups. Disabling filter groups increases the
                        configurable filter entries.";
        } // END of virtual-output-queue-full-color definition.

        leaf virtual-output-queue-forward-drop  {
            when " not(/profiles/hardware-profile/statistics/config/virtual-output-queue-full-color) ";
            if-feature feature-list:HAVE_DUNE;
            type  empty;
            description "Use this attribute to enable or disable Virtual Output Queue Forward
                        Drop filter groups. Disabling filter groups increases the configurable
                        filter entries.";
        } // END of virtual-output-queue-forward-drop definition.

    } // END of hardware-profiles-statistics-config definition.

    grouping  profiles-grouping {
    description
        "Top level container for platform profiles, including configuration and
                state data";
    container profiles {
        description
            "Top level container for platform profiles, including configuration and
                    state data";
        container hardware-profile {
            description
                "This container defines hardware-profile configuration and state
                        information.";
            container config {
                description
                    "This container defines hardware-profile configuration.";
                uses hardware-profile-config;
            } // END of config-container definition.
            container state {
                config false;
                description
                    "This container defines hardware-profile Operational states.";
                uses hardware-profile-config;
            } // END of state-container definition.
            container filters {
                description
                    "This container defines hardware-profile filter configuration and state
                            information.";
                container config {
                    description
                        "This container defines hardware-profile filter configuration.";
                    uses hardware-profile-filters-config;
                } // END of config-container definition.
                container state {
                    config false;
                    description
                        "This container defines hardware-profile filter Operational states.";
                    uses hardware-profile-filters-config;
                } // END of state-container definition.
            } // END of filters-container definition.
            container statistics {
                description
                    "This container defines hardware-profile statistics configuration and
                            state information.";
                container config {
                    description
                        "This container defines hardware-profile statistics configuration.";
                    uses hardware-profiles-statistics-config;
                } // END of config-container definition.
                container state {
                    config false;
                    description
                        "This container defines hardware-profile statistics Operational states.";
                    uses hardware-profiles-statistics-config;
                } // END of state-container definition.
            } // END of statistics-container definition.
        } // END of hardware-profile-container definition.
    } // END of profiles-container definition.
    } // END of profiles-grouping definition.


}
