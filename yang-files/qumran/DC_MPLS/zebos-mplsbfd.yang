/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-mplsbfd.yang
*
*/

submodule zebos-mplsbfd {

    belongs-to  zebos { prefix zebos; }

    import cml_data_types {
        prefix cml_data_types;
    }

    include zebos-interface;
    organization
        "IP Infusion Inc.";

    contact
        "Address: 3965 Freedom Circle, Suite 200, Santa Clara, CA 95054
        Phone: +1 408-400-1900
        E-mail: support@ipinfusion.com
        Web: http://www.ipinfusion.com/";


    revision "2016-06-10" {
        description "Revisied on 2016-06-10.";
    }

    revision "2016-02-25" {
        description "Added managed object level if-feature.";
    }



    grouping mplsBfdVccpState-grouping {
        list mplsBfdVccpState {
            key "vrId";
            description
                "mplsBfdVccpState";
            leaf vrId  {
                type  cml_data_types:CML_UINT32_T;
                description "";
            } // END of vrId definition.

            leaf mplsBfdVccp  {
                type  cml_data_types:CML_NSM_MPLS_VCCP_STATE_T;
                description "";
            } // END of mplsBfdVccp definition.

            leaf mplsBfdVcId  {
                type  cml_data_types:CML_INT32_T {
                     range "1..1000000";
                }
                description "";
            } // END of mplsBfdVcId definition.

        } // End of mplsBfdVccpState-list
    } // END of mplsBfdVccpState-grouping definition.


    grouping mplsBfd-grouping {
        list mplsBfd {
            key "mplsBfdLdpStatic";
            description
                "mplsBfd";
            leaf vrId  {
                type  cml_data_types:CML_UINT32_T;
                description "";
            } // END of vrId definition.

            leaf mplsBfdLdpStatic  {
                type  cml_data_types:CML_NSM_MPLS_BFD_T;
                description "";
            } // END of mplsBfdLdpStatic definition.


            list mplsAddr {
                key "mplsAddress";
                description
                    "mplsAddr";
                leaf mplsAddress  {
                    type  cml_data_types:CML_IPV4_PREFIX_T;
                    description "";
                } // END of mplsAddress definition.

                leaf mplsDisable  {
                    type  cml_data_types:CML_BOOL_T;
                    description "";
                } // END of mplsDisable definition.

                uses mpls_configurations;
            } // End of mplsAddr-list
        } // End of mplsBfd-list
    } // END of mplsBfd-grouping definition.


    grouping mplsRsvp-grouping {
        list mplsRsvp {
            key "mplsBfdRsvp";
            description
                "mplsRsvp";
            leaf vrId  {
                type  cml_data_types:CML_UINT32_T;
                description "";
            } // END of vrId definition.

            leaf mplsBfdRsvp  {
                type  cml_data_types:CML_BFD_RSVP_LSP_T;
                description "";
            } // END of mplsBfdRsvp definition.


            list mplsTunnelName {
                key "RsvpTunnelName";
                description
                    "mplsTunnelName";
                leaf RsvpTunnelName  {
                    type  cml_data_types:CML_STRING_T {
                        length "0..255";
                    }
                    description "";
                } // END of RsvpTunnelName definition.

                leaf mplsRsvpDisable  {
                    type  cml_data_types:CML_BOOL_T;
                    description "";
                } // END of mplsRsvpDisable definition.

                uses mpls_configurations;
            } // End of mplsTunnelName-list
        } // End of mplsRsvp-list
    } // END of mplsRsvp-grouping definition.


    grouping mplsAllBfd-grouping {
        list mplsAllBfd {
            key "mplsBfdLdpAllStatic";
            description
                "mplsAllBfd";
            leaf vrId  {
                type  cml_data_types:CML_UINT32_T;
                description "";
            } // END of vrId definition.

            leaf mplsBfdLdpAllStatic  {
                type  cml_data_types:CML_NSM_MPLS_BFD_TYPE_T;
                description "";
            } // END of mplsBfdLdpAllStatic definition.


            list mplsAll {
                key "mplsAllAddress";
                description
                    "mplsAll";
                leaf mplsAllAddress  {
                    type  cml_data_types:CML_BOOL_T;
                    description "";
                } // END of mplsAllAddress definition.

                uses mpls_configurations;
            } // End of mplsAll-list
        } // End of mplsAllBfd-list
    } // END of mplsAllBfd-grouping definition.
    grouping mpls_configurations {
        description
            "mplsCMLSEPconfigurations";
        container mplsAllelement {
            description
                "mplsAllelement";
            leaf lspPingIntvl  {
                type  cml_data_types:CML_INT32_T {
                     range "1..4294967";
                }
                default "5";
                description "";
            } // END of lspPingIntvl definition.

            leaf minTx  {
                type  cml_data_types:CML_INT32_T {
                     range "50..4294967";
                }
                default "50";
                description "";
            } // END of minTx definition.

            leaf minRx  {
                type  cml_data_types:CML_INT32_T {
                     range "50..4294967";
                }
                default "50";
                description "";
            } // END of minRx definition.

            leaf multiplier  {
                type  cml_data_types:CML_INT32_T {
                     range "1..255";
                }
                default "5";
                description "";
            } // END of multiplier definition.

            leaf forceExplicitNull  {
                type  cml_data_types:CML_BOOL_T;
                default false;
                description "";
            } // END of forceExplicitNull definition.

        } // END of mplsAllelement-container definition.
    } // END of mpls_configurations definition.


}
