/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : cml_data_types.yang
*
*/

module cml_data_types {

    namespace   "http://www.ipinfusion.com/CMLSchema/cml_data_types";

    prefix "cml_data_types";

    import ietf-inet-types {
        prefix inet;
    }

    organization
        "IP Infusion Inc.";

    contact
        "Address: 3965 Freedom Circle, Suite 200, Santa Clara, CA 95054
        Phone: +1 408-400-1900
        E-mail: support@ipinfusion.com
        Web: http://www.ipinfusion.com/";

    description
        "YANG version of the cml_data_types";


    revision "2017-12-14" {
        description "add vxlan for debuging nsm.";
    }

    revision "2017-12-04" {
        description "modified the cvlan type to bitmap.";
    }

    revision "2017-10-03" {
        description "added if-feature support for bridge.";
    }

    revision "2017-09-27" {
        description "added helpstring for nsm debug.";
    }

    revision "2017-08-28" {
        description "changes for mac address type.";
    }

    revision "2017-05-12" {
        description "ISIS circuit-type CLI input type change.";
    }

    revision "2016-09-29" {
        description "Initial version of datatypes.";
    }



    typedef  CML_INT32_T{
        type int32;
    }

    typedef  CML_UINT32_T{
        type uint32;
    }

    typedef  CML_STRING_T{
        type string
        {pattern "[^?' =,>|]*";}
    }

    typedef  CML_NONEMPTY_STRING_T{
        type string
        {pattern "[^?' =,>|]+";}
    }

    typedef  CML_LINE_T{
        type string
        {pattern "[^?'=,>|]*";}
    }

    typedef  CML_HOST_STRING_T{
        type string;
    }

    typedef  CML_RANGE_T{
        type string
        {pattern "[^?'=>|]*";}
    }

    typedef  CML_UINT8_T{
        type uint8;
    }

    typedef  CML_INT8_T{
        type int8;
    }

    typedef  CML_UINT16_T{
        type uint16;
    }

    typedef  CML_BITMAP_T{
        type uint32;
    }

    typedef  CML_INT16_T{
        type int16;
    }

    typedef  CML_UINT64_T{
        type uint64;
    }

    typedef  CML_INT64_T{
        type int64;
    }

    typedef  CML_BOOL_T{
        type boolean;
    }

    typedef  CML_IPV4_ADDR_T{
        type inet:ipv4-address;
    }

    typedef  CML_IPV6_ADDR_T{
        type inet:ipv6-address;
    }

    typedef  CML_SNMP_IPV6_ADDR_T{
        type inet:ipv6-address;
    }

    typedef  CML_IPV4_PREFIX_T{
        type inet:ipv4-prefix;
    }

    typedef  CML_IPV6_PREFIX_T{
        type inet:ipv6-prefix;
    }

    typedef  CML_MAC_ADDR_T{
        type string;
    }

    typedef  CML_EMPTY_T{
        type empty;
    }

    typedef  CML_QOS_NAME_T{
        type string;
    }

    typedef  CML_CMAP_MATCH_ANY_CRITERIA_T{
        type enumeration {
            enum match-any { value 2;    }
        }
    }

    typedef  CML_CMAP_MATCH_CRITERIA_T{
        type enumeration {
            enum match-all { value 1;    }
            enum match-any { value 2;    }
        }
    }

    typedef  CML_PMAP_TYPE_T{
        type enumeration {
            enum type-qos { value 1;    }
            enum type-queuing { value 2;    }
            enum type-queuing-default { value 3;    }
        }
    }

    typedef  CML_QOS_FILTER_TYPE_T{
        type enumeration {
            enum ingress-ipv4 { value 4;    }
            enum ingress-ipv6 { value 16;    }
            enum egress-ipv6 { value 32;    }
        }
    }

    typedef  CML_QOS_OPERATION_T{
        type enumeration {
            enum qos-noop { value 0;    }
            enum qos-equal { value 1;    }
            enum qos-not-equal { value 2;    }
            enum qos-less-than { value 3;    }
            enum qos-greater-than { value 4;    }
            enum qos-operation-max { value 5;    }
        }
    }

    typedef  CML_FILTER_TYPE_T{
        type enumeration {
            enum qos-filter-deny { value 0;    }
            enum qos-filter-permit { value 1;    }
            enum qos-filter-mirror { value 2;    }
            enum qos-filter-dynamic { value 3;    }
            enum qos-filter-source { value 4;    }
            enum qos-filter-destination { value 5;    }
            enum qos-filter-no-match { value 6;    }
        }
    }

    typedef  CML_CONFORM_ACTION_T{
        type enumeration {
            enum none { value 0;    }
            enum transmit { value 1;    }
            enum set-dscp-transmit { value 2;    }
            enum set-prec-transmit { value 3;    }
            enum set-cos-transmit { value 4;    }
            enum set-mpls-class { value 5;    }
            enum set-qos-transmit { value 6;    }
        }
    }

    typedef  CML_EXCEED_ACTION_T{
        type enumeration {
            enum none { value 0;    }
            enum drop { value 1;    }
            enum set-dscp-transmit { value 2;    }
            enum set-prec-transmit { value 3;    }
            enum set-cos-transmit { value 4;    }
            enum set-mpls-class { value 5;    }
            enum set-flow-control { value 6;    }
            enum set-axe-ret { value 7;    }
            enum transmit { value 8;    }
        }
    }

    typedef  CML_VIOLATE_ACTION_T{
        type enumeration {
            enum none { value 0;    }
            enum drop { value 1;    }
            enum set-dscp-transmit { value 2;    }
            enum set-cos-transmit { value 4;    }
            enum set-mpls-class { value 5;    }
            enum transmit { value 8;    }
        }
    }

    typedef  CML_BURST_TYPE_T{
        type enumeration {
            enum none { value 0;    }
            enum kbytes { value 2;    }
            enum mbytes { value 3;    }
            enum ms { value 4;    }
            enum us { value 5;    }
        }
    }

    typedef  CML_QOS_RATE_T{
        type enumeration {
            enum none { value 0;    }
            enum kbps { value 2;    }
            enum mbps { value 3;    }
            enum gbps { value 4;    }
        }
    }

    typedef  CML_FLOW_CONTROL_MODE_T{
        type enumeration {
            enum nsm-qos-flow-control { value 0;    }
            enum nsm-full-bucket-size { value 1;    }
            enum nsm-cbs-bucket-size { value 2;    }
        }
    }

    typedef  CML_QOS_DSCP_VAL_T{
        type union{

            type CML_QOS_DSCP_T {

            }
            type CML_DSCP_TYPE_T {

            }
        }
    }

    typedef  CML_QOS_DSCP_T{
        type string;
    }

    typedef  CML_QOS_SET_VAL_T{
        type union{

            type int32 {
                range "0..63";

            }
            type CML_DSCP_TYPE_T {

            }
        }
    }

    typedef  CML_DSCP_TYPE_T{
        type enumeration {
            enum default { value 0;    }
            enum cs1 { value 8;    }
            enum af11 { value 10;    }
            enum af12 { value 12;    }
            enum af13 { value 14;    }
            enum cs2 { value 16;    }
            enum af21 { value 18;    }
            enum af22 { value 20;    }
            enum af23 { value 22;    }
            enum cs3 { value 24;    }
            enum af31 { value 26;    }
            enum af32 { value 28;    }
            enum af33 { value 30;    }
            enum cs4 { value 32;    }
            enum af41 { value 34;    }
            enum af42 { value 36;    }
            enum af43 { value 38;    }
            enum cs5 { value 40;    }
            enum ef { value 46;    }
            enum cs6 { value 48;    }
            enum cs7 { value 56;    }
        }
    }

    typedef  CML_QOS_PREC_VAL_T{
        type union{

            type CML_QOS_PREC_T {

            }
            type CML_PREC_TYPE_T {

            }
        }
    }

    typedef  CML_QOS_PREC_T{
        type string;
    }

    typedef  CML_PREC_TYPE_T{
        type enumeration {
            enum routine { value 0;    }
            enum priority { value 1;    }
            enum immediate { value 2;    }
            enum flash { value 3;    }
            enum flashoverride { value 4;    }
            enum critical { value 5;    }
            enum internet { value 6;    }
            enum network { value 7;    }
        }
    }

    typedef  CML_PROTO_TYPE_T{
        type enumeration {
            enum arp { value 0;    }
            enum bridging { value 1;    }
            enum cdp { value 2;    }
            enum clns { value 3;    }
            enum clns-es { value 4;    }
            enum clns-is { value 5;    }
            enum dhcp { value 6;    }
            enum isis { value 7;    }
            enum ldp { value 8;    }
            enum netbios { value 9;    }
        }
    }

    typedef  CML_QOS_CLASS_DEFAULT_T{
        type enumeration {
            enum class-default { value 0;    }
        }
    }

    typedef  CML_QUEUING_CLASS_DEFAULT_T{
        type enumeration {
            enum queuing-class-default { value 0;    }
        }
    }

    typedef  CML_HQOS_ENABLE_DISABLE_T{
        type enumeration {
            enum disable { value 0;    }
            enum enable { value 1;    }
        }
    }

    typedef  CML_HQOS_CLASS_TYPE_T{
        type enumeration {
            enum q0 { value 0;    }
            enum q1 { value 1;    }
            enum q2 { value 2;    }
            enum q3 { value 3;    }
            enum q4 { value 4;    }
            enum q5 { value 5;    }
            enum q6 { value 6;    }
            enum q7 { value 7;    }
        }
    }

    typedef  CML_QOS_PMAPC_CLASS_NAME_T{
        type union{

            type CML_QOS_NAME_T {

            }
            type CML_QUEUING_CLASS_DEFAULT_T {

            }
        }
    }

    typedef  CML_QOS_PMAP_CLASS_NAME_T{
        type union{

            type CML_QOS_NAME_T {

            }
            type CML_QOS_CLASS_DEFAULT_T {

            }
        }
    }

    typedef  CML_HQOS_MAC_DIR_T{
        type enumeration {
            enum src { value 0;    }
            enum dest { value 1;    }
        }
    }

    typedef  CML_HQOS_TRAFFIC_TYPE_NOT_T{
        type enumeration {
            enum traffic-type { value 0;    }
            enum not-traffic-type { value 1;    }
        }
    }

    typedef  CML_HQOS_TRAFFIC_TYPE_T{
        type enumeration {
            enum l2-uc { value 1;    }
            enum l2-uc-unknown { value 2;    }
            enum default { value 6;    }
        }
    }

    typedef  CML_HQOS_MATCH_NOT_T{
        type enumeration {
            enum cos { value 0;    }
            enum not-cos { value 1;    }
        }
    }

    typedef  CML_HQOS_SHAPE_TYPE_T{
        type enumeration {
            enum bps { value 1;    }
            enum kbps { value 2;    }
            enum mbps { value 3;    }
            enum gbps { value 4;    }
            enum percent { value 6;    }
        }
    }

    typedef  CML_HQOS_SET_BRIDGE_T{
        type enumeration {
            enum set-bridge { value 0;    }
            enum set { value 1;    }
        }
    }

    typedef  CML_HQOS_SET_TYPE_T{
        type enumeration {
            enum cos { value 1;    }
            enum dscp { value 2;    }
            enum precedence { value 3;    }
            enum mpls-class { value 4;    }
            enum qos-group { value 14;    }
        }
    }

    typedef  CML_HQOS_MATCH_NOT_DSCP_T{
        type enumeration {
            enum not-dscp { value 0;    }
            enum dscp { value 1;    }
        }
    }

    typedef  CML_HQOS_MATCH_NOT_PRECEDENCE_T{
        type enumeration {
            enum not-precedence { value 0;    }
            enum precedence { value 1;    }
        }
    }

    typedef  CML_HQOS_MATCH_NOT_RTP_T{
        type enumeration {
            enum not-ip { value 0;    }
            enum ip { value 1;    }
        }
    }

    typedef  CML_QOS_SERVICE_TYPE_T{
        type enumeration {
            enum qos { value 1;    }
            enum queuing { value 2;    }
        }
    }

    typedef  CML_QOS_CMAPDEF_TYPE_T{
        type enumeration {
            enum type-queuing-default { value 3;    }
        }
    }

    typedef  CML_QOS_CMAPANY_TYPE_T{
        type enumeration {
            enum type-qos { value 1;    }
        }
    }

    typedef  CML_QOS_CMAP_TYPE_T{
        type enumeration {
            enum type-qos { value 1;    }
            enum type-queuing { value 2;    }
        }
    }

    typedef  CML_VXLAN_QOS_GLOBAL_MODE_T{
        type enumeration {
            enum cos-dscp { value 1;    }
            enum dscp-dscp { value 2;    }
        }
    }

    typedef  CML_VXLAN_QOS_DIR_T{
        type enumeration {
            enum ingress { value 0;    }
            enum egress { value 1;    }
        }
    }

    typedef  CML_VXLAN_QOS_EGRESS_DIR_T{
        type enumeration {
            enum egress { value 1;    }
        }
    }

    typedef  CML_VXLAN_QOS_INGRESS_DIR_T{
        type enumeration {
            enum ingress { value 0;    }
        }
    }

    typedef  CML_QOS_MATCH_TYPE_T{
        type enumeration {
            enum match-any { value 1;    }
            enum match-all { value 2;    }
        }
    }

    typedef  CML_HQOS_MATCH_NOT_PROTOCOL_T{
        type enumeration {
            enum not-protocol { value 0;    }
            enum protocol { value 1;    }
        }
    }

    typedef  CML_HQOS_MATCH_NOT_VLAN_T{
        type enumeration {
            enum not-vlan { value 0;    }
            enum vlan { value 1;    }
        }
    }

    typedef  CML_HQOS_MATCH_NOT_MPLS_EXP_T{
        type enumeration {
            enum not-mpls { value 0;    }
            enum mpls { value 1;    }
        }
    }

    typedef  CML_HQOS_SHAPE_AVG_T{
        type enumeration {
            enum shape-average { value 0;    }
            enum shape { value 1;    }
        }
    }

    typedef  CML_HQOS_SHAPE_AVG_UNITS_T{
        type enumeration {
            enum bps { value 0;    }
            enum kbps { value 1;    }
            enum mbps { value 2;    }
            enum gbps { value 3;    }
        }
    }

    typedef  CML_HQOS_THRESHOLD_TYPE_T{
        type enumeration {
            enum packets { value 0;    }
            enum bytes { value 1;    }
            enum kbytes { value 2;    }
        }
    }

    typedef  CML_HOSTNAME_T{
        type union{

            type CML_IP_ADDR_T {

            }
            type CML_STRING_T {

            }
        }
    }

    typedef  CML_HOSTPNAME_T{
        type union{

            type CML_IP_ADDR_T {

            }
            type CML_HOST_STRING_T {

            }
        }
    }

    typedef  CML_HOSTSNMPNAME_T{
        type union{

            type CML_SNMP_IP_ADDR_T {

            }
            type CML_HOST_T {

            }
        }
    }

    typedef  CML_HOST_T{
        type enumeration {
            enum hostname { value 1;    }
        }
    }

    typedef  CML_IP_ADDR_T{
        type union{

            type CML_IPV4_ADDR_T {

            }
            type CML_IPV6_ADDR_T {

            }
        }
    }

    typedef  CML_SNMP_IP_ADDR_T{
        type union{

            type CML_IPV4_ADDR_T {

            }
            type CML_SNMP_IPV6_ADDR_T {

            }
        }
    }

    typedef  CML_IPV4_ADDR_DESC_T{
        type inet:ipv4-address;
    }

    typedef  CML_IPV6_ADDR_DESC_T{
        type inet:ipv6-address;
    }

    typedef  CML_IP_PREFIX_ADDR_T{
        type union{

            type CML_IPV4_PREFIX_T {

            }
            type CML_IPV6_PREFIX_T {

            }
        }
    }

    typedef  CML_MAC_ETH_TYPE_T{
        type union{

            type CML_ETH_TYPE_T {

            }
            type CML_STRING_T {

            }
        }
    }

    typedef  CML_ETH_TYPE_T{
        type enumeration {
            enum ip4 { value 0;    }
            enum ip6 { value 1;    }
            enum mpls { value 2;    }
        }
    }

    typedef  CML_VLAN_TYPE_T{
        type bits {
            bit customer { position 2;  }
            bit service-point-point { position 4;  }
            bit service-multipoint-multipoint { position 5;  }
            bit backbone-point-point { position 7;  }
            bit backbone-multipoint-multipoint { position 8;  }
            bit service-rooted-multipoint { position 11;  }
            bit backbone-rooted-multipoint { position 12;  }
        }
    }

    typedef  CML_FACILITY_T{
        type enumeration {
            enum local0 { value 0;    }
            enum local1 { value 1;    }
            enum local2 { value 2;    }
            enum local3 { value 3;    }
            enum local4 { value 4;    }
            enum local5 { value 5;    }
            enum local6 { value 6;    }
            enum local7 { value 7;    }
            enum user { value 8;    }
        }
    }

    typedef  CML_HOSTT_T{
        type enumeration {
            enum emergencies { value 0;    }
            enum alerts { value 1;    }
            enum critical { value 2;    }
            enum errors { value 3;    }
            enum warnings { value 4;    }
            enum notifications { value 5;    }
            enum informational { value 6;    }
            enum debugging { value 7;    }
        }
    }

    typedef  CML_DISCARDFORWARD_T{
        type enumeration {
            enum discard { value 0;    }
            enum forward { value 1;    }
        }
    }

    typedef  CML_SWITCH_PORT_MODE_T{
        type enumeration {
            enum access { value 1;    }
            enum hybrid { value 2;    }
            enum trunk { value 3;    }
            enum customer-network { value 5;    }
            enum provider-network { value 6;    }
            enum customer-edge-access { value 41;    }
            enum customer-edge-hybrid { value 42;    }
            enum customer-edge-trunk { value 43;    }
        }
    }

    typedef  CML_VLAN_FRAME_TYPE_T{
        type enumeration {
            enum vlan-tagged { value 1;    }
            enum all { value 2;    }
        }
    }

    typedef  CML_OSPFV3_LINK_STATUS_T{
        type enumeration {
            enum up { value 1;    }
            enum down { value 2;    }
        }
    }

    typedef  CML_OSPF6_CSPF_TYPE_T{
        type enumeration {
            enum random { value 0;    }
            enum most-fill { value 1;    }
            enum least-fill { value 2;    }
        }
    }

    typedef  CML_OSPF6_ABR_TYPE_T{
        type enumeration {
            enum standard { value 1;    }
            enum cisco { value 2;    }
            enum ibm { value 3;    }
        }
    }

    typedef  CML_OSPF6_TRANSLATOR_ROLE_T{
        type enumeration {
            enum always { value 1;    }
            enum candidate { value 2;    }
        }
    }

    typedef  CML_OSPF6_NETWORK_T{
        type enumeration {
            enum point-to-point { value 1;    }
            enum broadcast { value 2;    }
            enum non-broadcast { value 3;    }
            enum point-to-multipoint { value 4;    }
            enum point-to-multipoint-non-broadcast { value 5;    }
        }
    }

    typedef  CML_OSPF6_LSA_SUPRESSION_STATE_T{
        type enumeration {
            enum disable { value 0;    }
            enum enable { value 1;    }
        }
    }

    typedef  CML_OSPF6_RESTART_HELPER_T{
        type enumeration {
            enum only-reload { value 4;    }
            enum only-upgrade { value 8;    }
        }
    }

    typedef  CML_OSPF6_ROUTE_SOURCE_TYPE_T{
        type enumeration {
            enum kernel { value 1;    }
            enum connected { value 2;    }
            enum static { value 3;    }
            enum rip { value 4;    }
            enum bgp { value 8;    }
            enum isis { value 9;    }
        }
    }

    typedef  CML_OSPF6_DIST_ROUTE_SOURCE_TYPE_T{
        type enumeration {
            enum kernel { value 1;    }
            enum connected { value 2;    }
            enum static { value 3;    }
            enum rip { value 4;    }
            enum bgp { value 8;    }
            enum isis { value 9;    }
        }
    }

    typedef  CML_OSPF6_AF_ROUTE_SOURCE_TYPE_T{
        type enumeration {
            enum kernel { value 1;    }
            enum connected { value 2;    }
            enum static { value 3;    }
            enum rip { value 4;    }
            enum ospf { value 6;    }
            enum bgp { value 8;    }
            enum isis { value 9;    }
        }
    }

    typedef  CML_OSPF6_AREA_RANGE_T{
        type enumeration {
            enum not-advertise { value 0;    }
            enum advertise { value 1;    }
        }
    }

    typedef  CML_OSPF_INTERFACE_STATE_MSG_T{
        type enumeration {
            enum DependUpon { value 0;    }
            enum Down { value 1;    }
            enum Loopback { value 2;    }
            enum Waiting { value 3;    }
            enum Point-To-Point { value 4;    }
            enum DROther { value 5;    }
            enum Backup { value 6;    }
            enum DR { value 7;    }
        }
    }

    typedef  CML_OSPF6_PATH_TYPE_T{
        type enumeration {
            enum Connected { value 0;    }
            enum IntraArea { value 1;    }
            enum InterArea { value 2;    }
            enum External { value 3;    }
            enum Discard { value 4;    }
        }
    }

    typedef  CML_OSPF6_PATH_FLAGS_T{
        type enumeration {
            enum Type2 { value 1;    }
            enum ABR { value 2;    }
            enum ASBR { value 3;    }
            enum RangeMatched { value 4;    }
        }
    }

    typedef  CML_OSPF_ACTION_TYPE_T{
        type enumeration {
            enum soft { value 1;    }
            enum hard { value 2;    }
        }
    }

    typedef  CML_OSPF_TELINK_LOCAL_T{
        type enumeration {
            enum disable-te-link-local { value 0;    }
            enum enable-te-link-local { value 1;    }
        }
    }

    typedef  CML_OSPF_ROUTE_SOURCE_TYPE_T{
        type enumeration {
            enum kernel { value 1;    }
            enum connected { value 2;    }
            enum static { value 3;    }
            enum rip { value 4;    }
            enum ospf { value 6;    }
            enum bgp { value 8;    }
            enum isis { value 9;    }
        }
    }

    typedef  CML_OSPF_DIST_ROUTE_SOURCE_TYPE_T{
        type enumeration {
            enum kernel { value 1;    }
            enum connected { value 2;    }
            enum static { value 3;    }
            enum rip { value 4;    }
            enum bgp { value 8;    }
            enum isis { value 9;    }
        }
    }

    typedef  CML_BRIDGE_PROTOCOL_T{
        type enumeration {
            enum ieee { value 1;    }
            enum ieee-vlan-bridge { value 2;    }
            enum rstp { value 3;    }
            enum rstp-vlan-bridge { value 4;    }
            enum mstp { value 5;    }
            enum provider-rstp { value 6;    }
            enum provider-mstp { value 7;    }
            enum rpvst+ { value 8;    }
            enum provider-rpvst+ { value 9;    }
            enum trill { value 20;    }
        }
    }

    typedef  CML_BRIDGE_TYPE_T{
        type enumeration {
            enum spanning-tree { value 1;    }
            enum rapid-spanning-tree { value 3;    }
            enum multiple-spanning-tree { value 5;    }
        }
    }

    typedef  CML_OVERMACTYPE_T{
        type enumeration {
            enum static { value 1;    }
            enum static-priority-override { value 2;    }
            enum static-mgmt { value 3;    }
            enum static-mgmt-priority-overide { value 4;    }
        }
    }

    typedef  CML_ENABLE_DISABLE_T{
        type enumeration {
            enum disable { value 0;    }
            enum enable { value 1;    }
        }
    }

    typedef  CML_VLANSTATE_T{
        type enumeration {
            enum disable { value 1;    }
            enum enable { value 2;    }
        }
    }

    typedef  CML_PBRINTERFACE_T{
        type enumeration {
            enum null0 { value 0;    }
            enum tunnel-te { value 1;    }
        }
    }

    typedef  CML_SPANNINGTREE_ENABLE_DISABLE_T{
        type enumeration {
            enum enable { value 0;    }
            enum disable { value 1;    }
        }
    }

    typedef  CML_PATHCOST_METHOD_T{
        type enumeration {
            enum short { value 0;    }
            enum long { value 1;    }
            enum default { value 2;    }
        }
    }

    typedef  CML_LINK_TYPE_T{
        type enumeration {
            enum shared { value 0;    }
            enum point-to-point { value 1;    }
            enum auto { value 2;    }
        }
    }

    typedef  CML_PORTEDGE_T{
        type enumeration {
            enum edgeport { value 0;    }
            enum portfast { value 1;    }
        }
    }

    typedef  CML_BPDU_T{
        type enumeration {
            enum enable { value 0;    }
            enum disable { value 1;    }
            enum default { value 2;    }
        }
    }

    typedef  CML_BRIDGE_TOPOLOGY_T{
        type enumeration {
            enum topology-none { value 0;    }
            enum ring { value 1;    }
        }
    }

    typedef  CML_BRIDGE_FORWARDING_SET_T{
        type enumeration {
            enum disable { value 0;    }
            enum enable { value 1;    }
        }
    }

    typedef  CML_BRIDGE_MSTPENABLE_T{
        type enumeration {
            enum enable { value 1;    }
        }
    }

    typedef  CML_BRIDGE_AGEING_STATE{
        type enumeration {
            enum disable { value 0;    }
        }
    }

    typedef  CML_OSPF_DOMAIN_TYPE_T{
        type enumeration {
            enum type-as { value 1;    }
            enum type-as4 { value 2;    }
            enum type-back-comp { value 3;    }
            enum type-ip { value 4;    }
        }
    }

    typedef  CML_OSPF_ABR_TYPE_T{
        type enumeration {
            enum standard { value 1;    }
            enum cisco { value 2;    }
            enum ibm { value 3;    }
            enum shortcut { value 4;    }
        }
    }

    typedef  CML_OSPF_AREA_AUTH_TYPE_T{
        type enumeration {
            enum simple { value 1;    }
            enum message-digest { value 2;    }
        }
    }

    typedef  CML_OSPF_AREA_SHORTCUT_TYPE_T{
        type enumeration {
            enum default { value 0;    }
            enum enable { value 1;    }
            enum disable { value 2;    }
        }
    }

    typedef  CML_OSPF_TRANSLATOR_ROLE_T{
        type enumeration {
            enum never { value 0;    }
            enum always { value 1;    }
            enum candidate { value 2;    }
        }
    }

    typedef  CML_OSPF_NSSA_TRANSLATOR_ROLE_T{
        type enumeration {
            enum translate-never { value 0;    }
            enum translate-always { value 1;    }
            enum translate-candidate { value 2;    }
        }
    }

    typedef  CML_OSPF_STUB_T{
        type enumeration {
            enum stub { value 1;    }
        }
    }

    typedef  CML_OSPF_NSSA_T{
        type enumeration {
            enum nssa { value 1;    }
        }
    }

    typedef  CML_OSPF_AREA_FILTER_TYPE_T{
        type enumeration {
            enum access { value 0;    }
            enum prefix { value 1;    }
        }
    }

    typedef  CML_OSPF_AREA_FILTER_LIST_PREFIX_T{
        type enumeration {
            enum in { value 0;    }
            enum out { value 1;    }
        }
    }

    typedef  CML_OSPF_VIRT_AUTH_KEY_T{
        type enumeration {
            enum null { value 0;    }
            enum PASSWORD { value 1;    }
        }
    }

    typedef  CML_OSPF_VIRT_AUTH_TYPE_T{
        type enumeration {
            enum null { value 0;    }
            enum simple { value 1;    }
            enum message-digest { value 2;    }
        }
    }

    typedef  CML_OSPF_RESTART_METHOD_T{
        type enumeration {
            enum graceful { value 1;    }
            enum signaling { value 2;    }
        }
    }

    typedef  CML_CSPF_TIE_BREAK_T{
        type enumeration {
            enum least-fill { value 1;    }
            enum most-fill { value 2;    }
            enum random { value 3;    }
        }
    }

    typedef  CML_OSPF_METRIC_TYPE_T{
        type enumeration {
            enum 1 { value 1;    }
            enum 2 { value 2;    }
        }
    }

    typedef  CML_OSPF_NETWORK_T{
        type enumeration {
            enum point-to-point { value 1;    }
            enum broadcast { value 2;    }
            enum non-broadcast { value 3;    }
            enum point-to-multipoint { value 4;    }
            enum point-to-multipoint-non-broadcast { value 5;    }
        }
    }

    typedef  CML_OSPF_AUTH_TYPE_T{
        type enumeration {
            enum null { value 0;    }
            enum simple { value 1;    }
            enum message-digest { value 2;    }
        }
    }

    typedef  CML_LDP_HELPER_MODE_T{
        type enumeration {
            enum disable { value 0;    }
            enum enable { value 1;    }
        }
    }

    typedef  CML_OSPF_FRR_TIE_BREAK_VAL_T{
        type enumeration {
            enum primary-path { value 1;    }
            enum interface-disjoint { value 2;    }
            enum node-protecting { value 3;    }
            enum broadcast-interface-disjoint { value 4;    }
        }
    }

    typedef  CML_LDP_ADVERTISE_MODE_T{
        type enumeration {
            enum downstream-unsolicited { value 0;    }
            enum downstream-on-demand { value 1;    }
        }
    }

    typedef  CML_LDP_CONTROLMODE_T{
        type enumeration {
            enum independent { value 0;    }
            enum ordered { value 1;    }
        }
    }

    typedef  CML_LDP_LABEL_T{
        type enumeration {
            enum liberal { value 0;    }
            enum conservative { value 1;    }
        }
    }

    typedef  CML_LDP_MERGE_CAPABLE_T{
        type enumeration {
            enum merge-capable { value 0;    }
            enum non-merge-capable { value 1;    }
        }
    }

    typedef  CML_PIM_MODE_TYPE_T{
        type enumeration {
            enum dense-mode { value 1;    }
            enum sparse-mode { value 2;    }
            enum sparse-dense-mode { value 3;    }
        }
    }

    typedef  CML_PIM_EXTENDED_ACCESS_LIST_T{
        type union{

            type CML_STRING_T {

            }
            type uint8 {
                range "1..99";

            }
            type uint16 {
                range "1300..1999";

            }
        }
    }

    typedef  CML_PIM_SSM_TYPE_T{
        type union{

            type CML_STRING_T {

            }
            type uint8 {
                range "1..99";

            }
        }
    }

    typedef  CML_SSM_DEFAULT_T{
        type enumeration {
            enum default { value 0;    }
        }
    }

    typedef  CML_SSM_RANGE_T{
        type string;
    }

    typedef  CML_PIM_SSM_ACL_TYPE_T{
        type union{

            type CML_SSM_RANGE_T {

            }
            type CML_SSM_DEFAULT_T {

            }
        }
    }

    typedef  CML_PIM_DEBUG_TYPE_T{
        type bits {
            bit events { position 0;  }
            bit packet-in { position 1;  }
            bit packet-out { position 2;  }
            bit state { position 3;  }
            bit mfc { position 4;  }
            bit timer-hello-ht { position 5;  }
            bit timer-hello-nlt { position 6;  }
            bit timer-hello-tht { position 7;  }
            bit timer-joinprune-jt { position 8;  }
            bit timer-joinprune-et { position 9;  }
            bit timer-joinprune-ppt { position 10;  }
            bit timer-joinprune-kat { position 11;  }
            bit timer-joinprune-ot { position 12;  }
            bit timer-assert { position 13;  }
            bit timer-register { position 14;  }
            bit timer-bsr-bst { position 15;  }
            bit timer-bsr-crp { position 16;  }
            bit mib { position 17;  }
            bit nsm { position 18;  }
            bit nexthop { position 19;  }
            bit mtrace { position 20;  }
        }
    }

    typedef  CML_MRIB_IP_TYPE_T{
        type enumeration {
            enum ip { value 1;    }
        }
    }

    typedef  CML_MRIB_IPV6_TYPE_T{
        type enumeration {
            enum ipv6 { value 0;    }
        }
    }

    typedef  CML_MRIB4_DEBUG_T{
        type bits {
            bit event { position 0;  }
            bit vif { position 1;  }
            bit mrt { position 2;  }
            bit stats { position 3;  }
            bit fib-msg { position 4;  }
            bit register-msg { position 5;  }
            bit nsm-msg { position 6;  }
            bit mrib-msg { position 7;  }
            bit mtrace { position 8;  }
            bit mtrace-detail { position 9;  }
        }
    }

    typedef  CML_MRIB6_DEBUG_T{
        type bits {
            bit event { position 0;  }
            bit vif { position 1;  }
            bit mrt { position 2;  }
            bit stats { position 3;  }
            bit fib-msg { position 4;  }
            bit register-msg { position 5;  }
            bit nsm-msg { position 6;  }
            bit mrib-msg { position 7;  }
            bit mtrace { position 8;  }
            bit mtrace-detail { position 9;  }
        }
    }

    typedef  CML_IGMP_DEBUG_T{
        type bits {
            bit encode { position 0;  }
            bit decode { position 1;  }
            bit events { position 2;  }
            bit fsm { position 3;  }
            bit tib { position 4;  }
        }
    }

    typedef  CML_MLD_DEBUG_T{
        type bits {
            bit encode { position 0;  }
            bit decode { position 1;  }
            bit events { position 2;  }
            bit fsm { position 3;  }
            bit tib { position 4;  }
        }
    }

    typedef  CML_MAUTYPE_T{
        type enumeration {
            enum dot3MauType10BaseTHD { value 10;    }
            enum dot3MauType10BaseTFD { value 11;    }
            enum dot3MauType100BaseTXHD { value 15;    }
            enum dot3MauType100BaseTXFD { value 16;    }
            enum dot3MauType1000BaseXHD { value 21;    }
            enum dot3MauType1000BaseXFD { value 22;    }
            enum dot3MauType10GigBaseCX4 { value 41;    }
            enum dot3MauType10GbaseKX4 { value 57;    }
            enum dot3MauType10GbaseKR { value 58;    }
            enum dot3MauType40GbaseCR4 { value 71;    }
        }
    }

    typedef  CML_DUPLEX_T{
        type enumeration {
            enum half { value 0;    }
            enum full { value 1;    }
        }
    }

    typedef  CML_INTF_FEC_T{
        type enumeration {
            enum off { value 0;    }
            enum on { value 1;    }
            enum auto { value 2;    }
        }
    }

    typedef  CML_INTERFACE_TYPE_T{
        type enumeration {
            enum Router { value 0;    }
            enum Switch { value 1;    }
            enum TDM { value 2;    }
        }
    }

    typedef  CML_BANDWIDTHCONSTRAINTMODE_T{
        type enumeration {
            enum MAM { value 0;    }
            enum RSDL { value 1;    }
            enum MAR { value 2;    }
        }
    }

    typedef  CML_AFI_TYPE_T{
        type enumeration {
            enum ipv4 { value 1;    }
            enum ipv6 { value 2;    }
            enum vpnv4 { value 3;    }
            enum vpnv6 { value 4;    }
            enum rtfilter { value 5;    }
            enum l2vpn { value 25;    }
        }
    }

    typedef  CML_VRF_AFI_TYPE_T{
        type enumeration {
            enum ipv4 { value 1;    }
            enum ipv6 { value 2;    }
        }
    }

    typedef  CML_VRF_SAFI_TYPE_T{
        type enumeration {
            enum unicast { value 1;    }
        }
    }

    typedef  CML_SAFI_TYPE_T{
        type enumeration {
            enum unicast { value 1;    }
            enum multicast { value 2;    }
            enum labeled-unicast { value 4;    }
            enum l2vpn-vpls { value 65;    }
            enum evpn { value 70;    }
            enum vpn-unicast { value 128;    }
            enum rtfilter-unicast { value 132;    }
        }
    }

    typedef  CML_BGP_ROUTE_TARGET_T{
        type enumeration {
            enum rt { value 0;    }
            enum soo { value 1;    }
        }
    }

    typedef  CML_BGP_CONFIG_T{
        type enumeration {
            enum standard { value 0;    }
            enum zebos { value 1;    }
        }
    }

    typedef  CML_BGP_MED_TYPE_T{
        type bits {
            bit confed { position 0;  }
            bit missing-as-worst { position 1;  }
            bit remove-recv-med { position 2;  }
            bit remove-send-med { position 3;  }
        }
    }

    typedef  CML_BGP_ORF_PREFIX_TYPE_T{
        type bits {
            bit receive { position 1;  }
            bit send { position 2;  }
        }
    }

    typedef  CML_BGP_COMMUNITY_LIST_ACTION_T{
        type enumeration {
            enum deny { value 1;    }
            enum permit { value 2;    }
        }
    }

    typedef  CML_RMAP_PERMIT_T{
        type enumeration {
            enum permit { value 0;    }
            enum deny { value 1;    }
        }
    }

    typedef  BGP_ADDITIONAL_PATH_TYPE_T{
        type enumeration {
            enum receive { value 1;    }
            enum send { value 2;    }
            enum send-receive { value 3;    }
        }
    }

    typedef  BGP_PEER_ADDITIONAL_PATH_TYPE_T{
        type enumeration {
            enum receive { value 1;    }
            enum send { value 2;    }
            enum send-receive { value 3;    }
            enum disable { value 4;    }
        }
    }

    typedef  CML_BGP_SEND_COMMU_TYPE_T{
        type bits {
            bit standard { position 1;  }
            bit extended { position 2;  }
        }
    }

    typedef  CML_BGP_UPDATE_DEBUG_TYPE_T{
        type bits {
            bit in { position 8;  }
            bit out { position 9;  }
        }
    }

    typedef  CML_ATTRIBUTE_UNCHANGED_TYPE_T{
        type bits {
            bit as-path { position 1;  }
            bit next-hop { position 2;  }
            bit med { position 3;  }
        }
    }

    typedef  CML_BGP_DEBUG_TYPE_T{
        type bits {
            bit nht { position 1;  }
            bit nsm { position 2;  }
            bit fsm { position 3;  }
            bit events { position 4;  }
            bit filters { position 5;  }
            bit keepalives { position 6;  }
            bit updates { position 7;  }
            bit dampening { position 10;  }
            bit bfd { position 11;  }
        }
    }

    typedef  CML_BGP_DISTRIBUTE_LIST_ACTION_T{
        type enumeration {
            enum in { value 0;    }
            enum out { value 1;    }
        }
    }

    typedef  CML_BGP_REDISTRIBUTE_TYPE_T{
        type enumeration {
            enum kernel { value 1;    }
            enum connected { value 2;    }
            enum static { value 3;    }
            enum rip { value 4;    }
            enum ospf { value 5;    }
            enum isis { value 6;    }
        }
    }

    typedef  CML_BGP_COMMUNITY_LIST_ENTRY_T{
        type enumeration {
            enum standard { value 0;    }
            enum expanded { value 1;    }
            enum default { value 2;    }
        }
    }

    typedef  CML_BGP_AGGREGATE_ADDR_TYPE_T{
        type enumeration {
            enum summary-only { value 1;    }
            enum as-set { value 2;    }
        }
    }

    typedef  CML_CLUSTER_ID_T{
        type union{

            type CML_IPV4_ADDR_T {

            }
            type uint32 {
                range "1..4294967295";

            }
        }
    }

    typedef  CML_MPLS_VLAN_ACTIONTYPE_T{
        type enumeration {
            enum pop { value 0;    }
        }
    }

    typedef  CML_MPLS_MODULE_T{
        type enumeration {
            enum rsvp { value 0;    }
            enum ldp { value 1;    }
            enum bgp { value 4;    }
        }
    }

    typedef  CML_MPLS_ADMN_STATUS_T{
        type enumeration {
            enum up { value 1;    }
            enum down { value 2;    }
            enum testing { value 3;    }
        }
    }

    typedef  CML_MPLS_OPR_STATUS_T{
        type enumeration {
            enum up { value 1;    }
            enum down { value 2;    }
            enum testing { value 3;    }
            enum dormant { value 4;    }
            enum not-persent { value 5;    }
            enum ll-down { value 6;    }
        }
    }

    typedef  CML_MPLS_ROW_STATUS_T{
        type enumeration {
            enum active { value 1;    }
            enum not-in-severice { value 2;    }
            enum not-ready { value 3;    }
            enum create-go { value 4;    }
            enum create-wait { value 5;    }
            enum destroy { value 6;    }
        }
    }

    typedef  CML_MPLS_BFD_FLAG_T{
        type enumeration {
            enum configured { value 0;    }
            enum enabled { value 1;    }
            enum disable { value 2;    }
        }
    }

    typedef  CML_NSM_MPLS_TPID_T{
        type enumeration {
            enum 88a8 { value 34984;    }
            enum 9100 { value 37120;    }
        }
    }

    typedef  CML_NSM_SVC_TPID_T{
        type enumeration {
            enum dot1.q { value 33024;    }
            enum dot1.ad { value 34984;    }
            enum 0x9100 { value 37120;    }
        }
    }

    typedef  CML_NSM_MPLS_ADMIN_STATUS_T{
        type enumeration {
            enum down { value 0;    }
            enum up { value 1;    }
        }
    }

    typedef  CML_NSM_MPLS_VPLS_LEARNING_T{
        type enumeration {
            enum reset { value 0;    }
            enum enable { value 1;    }
            enum disable { value 2;    }
        }
    }

    typedef  CML_NSM_MPLS_VCMODE_T{
        type enumeration {
            enum standby { value 2;    }
            enum revertive { value 4;    }
        }
    }

    typedef  CML_NSM_MPLS_VCLINKMODE_T{
        type enumeration {
            enum primary { value 0;    }
            enum secondary { value 16;    }
        }
    }

    typedef  CML_NSM_MPLS_IF_VCTYPE_T{
        type enumeration {
            enum hdlc { value 6;    }
            enum ppp { value 7;    }
            enum tdm-E1 { value 17;    }
            enum tdm-T1 { value 18;    }
            enum tdm-E3 { value 19;    }
            enum tdm-T3 { value 20;    }
        }
    }

    typedef  CML_NSM_MPLS_IF_ETHER_VCTYPE_T{
        type enumeration {
            enum ethernet { value 5;    }
        }
    }

    typedef  CML_NSM_MPLS_IF_VLAN_VCTYPE_T{
        type enumeration {
            enum vlan { value 4;    }
        }
    }

    typedef  CML_NSM_MPLS_BFD_T{
        type enumeration {
            enum ldp { value 0;    }
            enum static { value 2;    }
        }
    }

    typedef  CML_BFD_RSVP_LSP_T{
        type enumeration {
            enum rsvp { value 1;    }
        }
    }

    typedef  CML_NSM_MPLS_BFD_TYPE_T{
        type enumeration {
            enum ldp { value 0;    }
            enum rsvp { value 1;    }
            enum static { value 2;    }
        }
    }

    typedef  CML_NSM_MPLS_VCCP_STATE_T{
        type enumeration {
            enum start { value 1;    }
            enum stop { value 2;    }
        }
    }

    typedef  CML_OSPF_ROW_STATUS{
        type enumeration {
            enum row-status-active { value 1;    }
            enum row-status-notinservice { value 2;    }
            enum row-status-notready { value 3;    }
            enum row-status-createandgo { value 4;    }
            enum row-status-createandwait { value 5;    }
        }
    }

    typedef  CML_NSM_VPLS_TYPE_T{
        type enumeration {
            enum vlan { value 4;    }
            enum ethernet { value 5;    }
        }
    }

    typedef  NSM_VPLS_ETHER_ACTION_T{
        type enumeration {
            enum no-op { value 1;    }
            enum add { value 2;    }
        }
    }

    typedef  NSM_VPLS_VLAN_ACTION_T{
        type enumeration {
            enum no-op { value 1;    }
            enum remove { value 3;    }
            enum replace { value 4;    }
        }
    }

    typedef  CML_NSM_VPLS_VC_SPOKE_TYPE_T{
        type enumeration {
            enum vlan { value 4;    }
            enum ethernet { value 5;    }
        }
    }

    typedef  CML_NSM_VPLS_PEER_TUNNEL_DIR_T{
        type enumeration {
            enum forward { value 0;    }
            enum reverse { value 1;    }
        }
    }

    typedef  CML_NSM_VPLS_PEER_TYPE_T{
        type enumeration {
            enum manual { value 1;    }
        }
    }

    typedef  CML_NSM_VPLS_FTN_ENTRY_T{
        type enumeration {
            enum secondary { value 0;    }
            enum primary { value 1;    }
        }
    }

    typedef  CML_VPLS_REDUNDANCY_ROLE_T{
        type enumeration {
            enum primary { value 0;    }
            enum secondary { value 1;    }
        }
    }

    typedef  CML_NSM_VPLS_OPCODE_T{
        type enumeration {
            enum swap { value 3;    }
            enum vpnpop { value 4;    }
        }
    }

    typedef  CML_NSM_MPLS_IPV6OPCODE_T{
        type enumeration {
            enum swap { value 3;    }
        }
    }

    typedef  CML_NSM_VPLS_POPOPCODE_T{
        type enumeration {
            enum pop { value 2;    }
        }
    }

    typedef  CML_VPLS_VC_STYLE1_T{
        type enumeration {
            enum peer { value 2;    }
        }
    }

    typedef  CML_VPLS_VC_STYLE2_T{
        type enumeration {
            enum spoke-vc { value 3;    }
        }
    }

    typedef  CML_L2VPN_PROTOCOL_T{
        type enumeration {
            enum none { value 1;    }
            enum bgp { value 2;    }
            enum ldp { value 4;    }
            enum ldp-autodiscovery-bgp { value 8;    }
        }
    }

    typedef  CML_L2VPN_VC_TYPE_T{
        type enumeration {
            enum ethernet { value 5;    }
            enum hdlc { value 6;    }
            enum ppp { value 7;    }
            enum tdm-E1 { value 17;    }
            enum tdm-T1 { value 18;    }
            enum tdm-E3 { value 19;    }
            enum tdm-T3 { value 20;    }
        }
    }

    typedef  CML_RSVP_PATH_STATUS_T{
        type enumeration {
            enum loose { value 0;    }
            enum strict { value 1;    }
        }
    }

    typedef  CML_RSVP_PROT_STATUS_T{
        type enumeration {
            enum one-to-one { value 1;    }
            enum facility { value 2;    }
        }
    }

    typedef  CML_RSVP_IP_ADDR_T{
        type union{

            type CML_IPV4_ADDR_T {

            }
            type CML_IPV6_ADDR_T {

            }
        }
    }

    typedef  CML_RSVP_FRR_ADMIN_TYPE_T{
        type enumeration {
            enum exclude-any { value 0;    }
            enum include-any { value 1;    }
        }
    }

    typedef  CML_RSVP_TRAFFIC_TYPE_T{
        type enumeration {
            enum controlled-load { value 1;    }
            enum guaranteed { value 2;    }
        }
    }

    typedef  CML_RSVP_UPDATE_TYPE_T{
        type enumeration {
            enum break-before-make { value 1;    }
            enum make-before-break { value 2;    }
        }
    }

    typedef  CML_RSVP_CAPABILITY_TYPE_T{
        type enumeration {
            enum psc-1 { value 1;    }
            enum psc-2 { value 2;    }
            enum psc-3 { value 4;    }
            enum psc-4 { value 8;    }
        }
    }

    typedef  CML_RSVP_DIRECTION_TYPE_T{
        type enumeration {
            enum unidirectional { value 0;    }
            enum bidirectional { value 1;    }
        }
    }

    typedef  CML_RSVP_GPID_TYPE_T{
        type enumeration {
            enum ethernet { value 33;    }
            enum ipv4 { value 2048;    }
        }
    }

    typedef  CML_RSVP_EXPLICIT_FWD_DIR_T{
        type enumeration {
            enum forward { value 1;    }
            enum packet-forward { value 3;    }
        }
    }

    typedef  CML_RSVP_EXPLICIT_REV_DIR_T{
        type enumeration {
            enum reverse { value 2;    }
            enum packet-reverse { value 4;    }
        }
    }

    typedef  CML_RSVP_FILTER_TYPE_T{
        type enumeration {
            enum default { value 0;    }
            enum fixed { value 1;    }
            enum shared-explicit { value 2;    }
        }
    }

    typedef  CML_RSVP_PROTECTION_TYPE_T{
        type enumeration {
            enum extra-traffic { value 1;    }
            enum unprotected { value 2;    }
            enum shared { value 4;    }
            enum dedicated-one-to-one { value 8;    }
            enum dedicated-one-plus-one { value 16;    }
            enum enhanced { value 32;    }
        }
    }

    typedef  CML_RSVP_EXCLUDE_ADDR_TYPE_T{
        type enumeration {
            enum link { value 1;    }
            enum node { value 2;    }
        }
    }

    typedef  CML_IS_TYPE_T{
        type enumeration {
            enum level-1 { value 1;    }
            enum level-2-only { value 2;    }
            enum level-1-2 { value 3;    }
        }
    }

    typedef  CML_IS_TYPE2_T{
        type enumeration {
            enum level-1 { value 1;    }
            enum level-2 { value 2;    }
            enum level-1-2 { value 3;    }
        }
    }

    typedef  CML_ISIS_LEVEL_T{
        type enumeration {
            enum level-1 { value 1;    }
            enum level-2 { value 2;    }
            enum level-1-2 { value 3;    }
        }
    }

    typedef  CML_ISIS_LEVEL_PROTO_T{
        type enumeration {
            enum ipv4 { value 1;    }
            enum ipv6 { value 2;    }
        }
    }

    typedef  CML_ISIS_FRR_ENUM_T{
        type enumeration {
            enum all { value 1;    }
        }
    }

    typedef  CML_ISIS_FRR_TIE_BREAK_VAL_T{
        type enumeration {
            enum primary-path { value 1;    }
            enum interface-disjoint { value 2;    }
            enum node-protecting { value 3;    }
            enum broadcast-interface-disjoint { value 4;    }
            enum secondary-path { value 5;    }
            enum downstream-path { value 6;    }
        }
    }

    typedef  CML_ISIS_IFLEVEL_T{
        type enumeration {
            enum level-1 { value 1;    }
            enum level-2 { value 2;    }
            enum p2p { value 3;    }
        }
    }

    typedef  CML_ISIS_NBR_ADJ_T{
        type enumeration {
            enum Suppress { value 1;    }
            enum Advertise { value 2;    }
        }
    }

    typedef  CML_ISIS_ORIGIN_TYPE_T{
        type enumeration {
            enum originate { value 4;    }
            enum originate-always { value 32;    }
        }
    }

    typedef  CML_ISIS_NETWORK_T{
        type enumeration {
            enum broadcast { value 1;    }
            enum point-to-point { value 2;    }
        }
    }

    typedef  CML_ISIS_STATE_T{
        type enumeration {
            enum Down { value 0;    }
            enum Init { value 1;    }
            enum Up { value 2;    }
        }
    }

    typedef  CML_METRIC_STYLE_T{
        type enumeration {
            enum narrow { value 1;    }
            enum wide { value 2;    }
            enum transition { value 3;    }
            enum narrow-transition { value 4;    }
            enum wide-transition { value 5;    }
        }
    }

    typedef  CML_TRANSITION_METRIC_STYLE_T{
        type enumeration {
            enum narrow { value 1;    }
            enum wide { value 2;    }
        }
    }

    typedef  CML_ISIS_AUTH_MODE_T{
        type enumeration {
            enum md5 { value 1;    }
            enum text { value 2;    }
        }
    }

    typedef  CML_ISIS_ROUTE_T{
        type enumeration {
            enum redistribution { value 0;    }
            enum all { value 1;    }
        }
    }

    typedef  CML_ISIS_SNP_T{
        type enumeration {
            enum send-only { value 1;    }
            enum validate { value 2;    }
        }
    }

    typedef  CML_ISIS_LIFETIME_T{
        type enumeration {
            enum accept-lifetime { value 1;    }
            enum send-lifetime { value 2;    }
        }
    }

    typedef  CML_ISIS_REDISTRIBUTE_T{
        type enumeration {
            enum kernel { value 1;    }
            enum connected { value 2;    }
            enum static { value 3;    }
            enum rip { value 4;    }
            enum ospf { value 5;    }
            enum bgp { value 6;    }
        }
    }

    typedef  CML_ISIS_DEBUG_T{
        type bits {
            bit ifsm { position 0;  }
            bit nfsm { position 1;  }
            bit pdu { position 2;  }
            bit lsp { position 3;  }
            bit spf { position 4;  }
            bit events { position 5;  }
            bit nsm { position 6;  }
            bit checksum { position 7;  }
            bit authentication { position 8;  }
            bit local-updates { position 9;  }
            bit protocol-errors { position 10;  }
            bit bfd { position 12;  }
            bit mpls { position 13;  }
            bit rib { position 14;  }
            bit spf-trace { position 17;  }
        }
    }

    typedef  CML_ISIS_DEBUG_HELLO_T{
        type enumeration {
            enum hello { value 1;    }
        }
    }

    typedef  CML_ISIS_CSPF_DEBUG_T{
        type bits {
            bit events { position 0;  }
            bit hexdump { position 1;  }
        }
    }

    typedef  CML_PASSWORD_T{
        type string
        {pattern "[a-zA-Z0-9].*";}
    }

    typedef  CML_SYSTEM_HOSTNAME_T{
        type string
        {pattern "[a-zA-Z0-9\-].*";}
    }

    typedef  CML_USERNAME_T{
        type string
        {pattern "[\-a-zA-Z0-9].*";}
    }

    typedef  CML_WRAP_T{
        type enumeration {
            enum off { value 0;    }
            enum on { value 1;    }
        }
    }

    typedef  CML_LDP_TDP_PROTOCOL_T{
        type enumeration {
            enum both { value 0;    }
            enum ldp { value 1;    }
            enum tdp { value 2;    }
        }
    }

    typedef  CML_INTERFACE_T{
        type enumeration {
            enum interface { value 0;    }
        }
    }

    typedef  CML_LDP_DISCOVERY_ADDRESS_T{
        type union{

            type CML_INTERFACE_T {

            }
            type CML_IPV4_ADDR_T {

            }
        }
    }

    typedef  CML_MTU_T{
        type union{

            type CML_UINT16_T {

            }
            type CML_UINT16_T {

            }
            type CML_UINT16_T {

            }
        }
    }

    typedef  CML_AREA_T{
        type union{

            type uint32 {
                range "0..4294967295";

            }
            type CML_IPV4_ADDR_T {

            }
        }
    }

    typedef  CML_SELF_TEST_T{
        type enumeration {
            enum extended { value 0;    }
            enum fast { value 1;    }
            enum none { value 2;    }
        }
    }

    typedef  CML_BAUD_RATE_T{
        type enumeration {
            enum 9600 { value 9600;    }
            enum 19200 { value 19200;    }
            enum 38400 { value 38400;    }
            enum 115200 { value 115200;    }
        }
    }

    typedef  CML_OSPF6_INSTANCE_T{
        type union{

            type CML_UINT8_T {

            }
            type CML_UINT8_T {

            }
        }
    }

    typedef  CML_ACCESS_GROUP_DIRECTION_T{
        type enumeration {
            enum in { value 0;    }
            enum out { value 1;    }
        }
    }

    typedef  CML_VLAN_ID_T{
        type uint16;
    }

    typedef  CML_ADDR_OR_SCRIPT_T{
        type union{

            type CML_IPV4_ADDR_T {

            }
            type CML_STRING_T {

            }
        }
    }

    typedef  CML_GI_MEDIA_T{
        type enumeration {
            enum 10-full { value 0;    }
            enum 10-half { value 1;    }
            enum 100-auto { value 2;    }
            enum 100-full { value 3;    }
            enum 100-half { value 4;    }
            enum 1000-full { value 5;    }
            enum 1000-half { value 6;    }
            enum auto { value 7;    }
        }
    }

    typedef  CML_TE_MEDIA_T{
        type enumeration {
            enum 1000-full { value 0;    }
            enum 10000-full { value 1;    }
            enum auto { value 2;    }
        }
    }

    typedef  CML_PORT_TYPE_T{
        type enumeration {
            enum nni { value 0;    }
        }
    }

    typedef  CML_MODE_T{
        type enumeration {
            enum active { value 0;    }
            enum auto { value 1;    }
            enum desirable { value 2;    }
            enum on { value 3;    }
            enum passive { value 4;    }
        }
    }

    typedef  CML_CHANNEL_PROTOCOL_T{
        type enumeration {
            enum lacp { value 0;    }
            enum pagp { value 1;    }
        }
    }

    typedef  CML_ENCAPSULATION_T{
        type enumeration {
            enum mpls { value 0;    }
            enum l2tpv3 { value 1;    }
        }
    }

    typedef  CML_SEQUENCE_T{
        type enumeration {
            enum both { value 0;    }
            enum receive { value 1;    }
            enum transmit { value 2;    }
        }
    }

    typedef  CML_GROUP_ENUM_T{
        type enumeration {
            enum global { value 0;    }
        }
    }

    typedef  CML_GROUP_T{
        type union{

            type CML_GROUP_ENUM_T {

            }
            type CML_STRING_T {

            }
        }
    }

    typedef  CML_RATE_TYPE_T{
        type uint32;
    }

    typedef  CML_IP_RATE_T{
        type union{

            type CML_RATE_TYPE_T {

            }
            type CML_STRING_T {

            }
        }
    }

    typedef  CML_SPT_NAME_T{
        type enumeration {
            enum mst { value 0;    }
        }
    }

    typedef  CML_OSPF_ROUTE_T{
        type enumeration {
            enum connected { value 0;    }
            enum kernel { value 1;    }
            enum static { value 2;    }
        }
    }

    typedef  CML_POLICY_MAP_T{
        type enumeration {
            enum ether-type { value 0;    }
            enum port { value 1;    }
            enum snpa { value 2;    }
            enum vid { value 3;    }
        }
    }

    typedef  CML_POLICY_MAP_ID_T{
        type union{

            type CML_IP_PREFIX_ADDR_T {

            }
            type CML_POLICY_MAP_T {

            }
        }
    }

    typedef  CML_ETHER_VALS_T{
        type enumeration {
            enum ipv4 { value 0;    }
            enum ipv6 { value 1;    }
            enum mpls-unicast { value 2;    }
            enum mpls-multicast { value 3;    }
            enum arp { value 4;    }
            enum ppoe-discover { value 5;    }
            enum ppoe-session { value 6;    }
        }
    }

    typedef  CML_ENDIS_T{
        type enumeration {
            enum disable { value 0;    }
            enum enable { value 1;    }
        }
    }

    typedef  CML_ROUTE_MAP_TYPE_T{
        type enumeration {
            enum client { value 0;    }
            enum ip { value 1;    }
            enum tag { value 2;    }
        }
    }

    typedef  CML_MIRROR_DIRECTION_T{
        type enumeration {
            enum bidir { value 0;    }
            enum in { value 1;    }
            enum out { value 2;    }
        }
    }

    typedef  CML_ROUTE_MAP_ACTION_T{
        type enumeration {
            enum deny { value 0;    }
            enum permit { value 1;    }
        }
    }

    typedef  CML_QUEUES_COUNT_T{
        type enumeration {
            enum 256 { value 256;    }
            enum 512 { value 512;    }
            enum 1024 { value 1024;    }
            enum 2048 { value 2048;    }
        }
    }

    typedef  CML_RT_T{
        type enumeration {
            enum import { value 0;    }
            enum export { value 1;    }
            enum both { value 2;    }
        }
    }

    typedef  CML_RSVP_ADDR_T{
        type enumeration {
            enum p2mp { value 1;    }
        }
    }

    typedef  CML_HOSTP_KEY_TYPE_T{
        type enumeration {
            enum 0 { value 0;    }
            enum 7 { value 1;    }
        }
    }

    typedef  CML_HOSTP_LOCAL_TYPE_T{
        type enumeration {
            enum local { value 1;    }
        }
    }

    typedef  CML_HOSTP_LOCAL_NONE_TYPE_T{
        type enumeration {
            enum local { value 0;    }
            enum none { value 1;    }
        }
    }

    typedef  CML_HOSTP_NONE_TYPE_T{
        type enumeration {
            enum none { value 1;    }
        }
    }

    typedef  CML_SNMP_OID_TREE_T{
        type enumeration {
            enum included { value 1;    }
            enum excluded { value 2;    }
        }
    }

    typedef  CML_SNMP_LINK_TYPE_T{
        type enumeration {
            enum linkUp { value 1;    }
            enum linkDown { value 2;    }
        }
    }

    typedef  CML_SNMP_USER_T{
        type enumeration {
            enum network-operator { value 1;    }
            enum network-admin { value 2;    }
        }
    }

    typedef  CML_OSPF6_METRIC_TYPE_T{
        type enumeration {
            enum 1 { value 1;    }
            enum 2 { value 2;    }
        }
    }

    typedef  CML_UDLD_MODE_TYPE_T{
        type enumeration {
            enum normal { value 0;    }
            enum aggressive { value 1;    }
        }
    }

    typedef  CML_UDLD_STATE_TYPE_T{
        type enumeration {
            enum enable { value 0;    }
            enum disable { value 1;    }
        }
    }

    typedef  CML_UDLD_T{
        type enumeration {
            enum disable { value 0;    }
            enum enable { value 1;    }
        }
    }

    typedef  CML_SNMP_AUTH_T{
        type enumeration {
            enum md5 { value 1;    }
            enum sha { value 2;    }
        }
    }

    typedef  CML_SNMP_PRIV_T{
        type enumeration {
            enum des { value 1;    }
            enum aes { value 2;    }
        }
    }

    typedef  CML_SNMP_VERSION_T{
        type enumeration {
            enum 1 { value 1;    }
            enum 2c { value 2;    }
        }
    }

    typedef  CML_SNMP_INFORMS_VERSION_T{
        type enumeration {
            enum 2c { value 2;    }
        }
    }

    typedef  CML_SNMP_VIEW_VERSION_T{
        type enumeration {
            enum v1 { value 1;    }
            enum v2c { value 2;    }
        }
    }

    typedef  CML_SNMP_INFORMS_T{
        type enumeration {
            enum informs { value 2;    }
        }
    }

    typedef  CML_SNMP_TRAP_T{
        type enumeration {
            enum traps { value 1;    }
        }
    }

    typedef  CML_VERSION3_T{
        type enumeration {
            enum noauth { value 1;    }
            enum auth { value 2;    }
            enum priv { value 3;    }
        }
    }

    typedef  CML_SNMP_ACCESS_T{
        type enumeration {
            enum ro { value 1;    }
            enum rw { value 2;    }
        }
    }

    typedef  CML_BFD_GTSM_STATE_T{
        type enumeration {
            enum enable { value 1;    }
            enum disable { value 2;    }
        }
    }

    typedef  CML_BFD_MULTIHOP_AUTH_TYPE_T{
        type enumeration {
            enum simple { value 1;    }
            enum keyed-sha1 { value 4;    }
            enum meticulous-keyed-sha1 { value 5;    }
        }
    }

    typedef  CML_HW_BFD_MULTIHOP_AUTH_TYPE_T{
        type enumeration {
            enum simple { value 1;    }
            enum keyed-sha1 { value 4;    }
            enum meticulous-keyed-sha1 { value 5;    }
        }
    }

    typedef  CML_BFD_SESSION_STATE_T{
        type enumeration {
            enum disable { value 0;    }
            enum enable { value 1;    }
        }
    }

    typedef  CML_OAMBFD_SESSION_FLAGS_T{
        type bits {
            bit rem-heard-up { position 0;  }
            bit admin-down { position 1;  }
            bit Fate-Shared { position 2;  }
            bit remote-admin-down { position 3;  }
            bit Echo-Enabled { position 4;  }
            bit Demand-Enabled { position 5;  }
            bit Remote-Demand-Enabled { position 6;  }
            bit Poll-seq-Init { position 8;  }
        }
    }

    typedef  CML_OAMBFD_PERFORM_DIAG_T{
        type enumeration {
            enum Diagnostics--None { value 0;    }
            enum Diagnostics-Control-Detected-Expiry { value 1;    }
            enum Diagnostics-Echo-Failed { value 2;    }
            enum Diagnostics-Neighbor-Session-Down { value 3;    }
            enum Diagnostics-Forwarding-Plane-Reset { value 4;    }
            enum Diagnostics-Path-Down { value 5;    }
            enum Diagnostics-Concatenated-Path-Down { value 6;    }
            enum Diagnostics-Admin-Down { value 7;    }
            enum Diagnostics-Reverse-Concatenated-Path-Down { value 8;    }
            enum Diagnostics-Configuration-Error { value 9;    }
            enum Diagnostics--Not-forwarding { value 10;    }
        }
    }

    typedef  CML_OAMBFD_SESSION_STATE_T{
        type enumeration {
            enum Admin-Down { value 0;    }
            enum Down { value 1;    }
            enum Init { value 2;    }
            enum Up { value 3;    }
        }
    }

    typedef  CML_OAMBFD_IMAGE_TYPE_T{
        type enumeration {
            enum MONOLITHIC { value 1;    }
            enum DISTRIBUTED { value 2;    }
            enum DISTRIBUTE { value 3;    }
        }
    }

    typedef  CML_OAMBFD_ADMIN_STATE_T{
        type enumeration {
            enum Up { value 1;    }
            enum Down { value 2;    }
        }
    }

    typedef  CML_OAMBFD_SESSION_TYPE_T{
        type enumeration {
            enum Single-Hop { value 1;    }
            enum Multihop-Arbit-Path { value 2;    }
            enum Multihop-OOB-Signalled { value 3;    }
            enum Multihop-Unidirectional { value 4;    }
        }
    }

    typedef  CML_OAMBFD_SESS_LOWER_LAYER_T{
        type enumeration {
            enum UNKNOWN { value 0;    }
            enum IPv4 { value 1;    }
            enum IPv6 { value 2;    }
            enum MPLS-LSP { value 3;    }
            enum MPLS-VCCV { value 4;    }
            enum MPLS-TP { value 5;    }
        }
    }

    typedef  CML_OAMBFD_HW_MULTIHOP_VAL_T{
        type enumeration {
            enum multi-hop { value 4784;    }
            enum micro-bfd { value 6784;    }
        }
    }

    typedef  CML_VRRP_VMAC_T{
        type enumeration {
            enum enable { value 1;    }
            enum disable { value 2;    }
        }
    }

    typedef  CML_VRRP_ACCEPT_MODE_T{
        type enumeration {
            enum true { value 1;    }
            enum false { value 2;    }
        }
    }

    typedef  CML_VRRP_PREEMPT_MODE_T{
        type enumeration {
            enum true { value 1;    }
            enum false { value 2;    }
        }
    }

    typedef  CML_LLDP_ADMIN_STATUS_T{
        type enumeration {
            enum rxonly { value 2;    }
            enum txonly { value 4;    }
            enum txrx { value 8;    }
        }
    }

    typedef  CML_LLDP_MEDDEV_T{
        type enumeration {
            enum ep-class1 { value 1;    }
            enum ep-class2 { value 2;    }
            enum ep-class3 { value 3;    }
            enum net-connect { value 4;    }
        }
    }

    typedef  CML_LLDP_CHASSIS_ID_T{
        type enumeration {
            enum chassis-component { value 0;    }
            enum if-alias { value 1;    }
            enum port-component { value 2;    }
            enum mac-address { value 3;    }
            enum ip-address { value 4;    }
            enum if-name { value 5;    }
            enum local { value 6;    }
        }
    }

    typedef  CML_LLDP_PORT_ID_T{
        type enumeration {
            enum if-alias { value 0;    }
            enum port-component { value 1;    }
            enum mac-address { value 2;    }
            enum ip-address { value 3;    }
            enum if-name { value 4;    }
            enum agent-circuit-id { value 5;    }
            enum local { value 6;    }
        }
    }

    typedef  CML_LLDP_PORT_ADDR_T{
        type enumeration {
            enum mac-address { value 1;    }
            enum ip-address { value 2;    }
        }
    }

    typedef  CML_LLDP_SET_STATE_T{
        type enumeration {
            enum disable { value 0;    }
            enum enable { value 1;    }
        }
    }

    typedef  CML_LLDP_TLV_MODE_T{
        type enumeration {
            enum manual { value 1;    }
            enum auto { value 2;    }
        }
    }

    typedef  CML_LLDP_IEEE_8023_T{
        type enumeration {
            enum ieee-8023-org-specific-mac-phy { value 0;    }
            enum ieee-8023-org-specific-max-mtu-size { value 1;    }
        }
    }

    typedef  CML_LLDP_IEEE_8021_T{
        type enumeration {
            enum ieee-8021-org-specific-port-vlanid { value 0;    }
            enum ieee-8021-org-specific-port-ptcl-vlanid { value 1;    }
            enum ieee-8021-org-specific-vlan-name { value 2;    }
            enum ieee-8021-org-specific-ptcl-identity { value 3;    }
            enum ieee-8021-org-specific-vid-digest { value 4;    }
            enum ieee-8021-org-specific-mgmt-vid { value 5;    }
            enum ieee-8021-org-specific-link-agg { value 6;    }
        }
    }

    typedef  CML_LLDP_BASIC_T{
        type enumeration {
            enum basic-mgmt-port-description { value 0;    }
            enum basic-mgmt-system-name { value 1;    }
            enum basic-mgmt-system-description { value 2;    }
            enum basic-mgmt-system-capabilities { value 3;    }
            enum basic-mgmt-management-address { value 4;    }
        }
    }

    typedef  CML_LLDP_AGENT_T{
        type enumeration {
            enum non-tpmr-bridge { value 0;    }
            enum customer-bridge { value 1;    }
            enum default { value 2;    }
        }
    }

    typedef  CML_VXLAN_MODE_T{
        type enumeration {
            enum vxlan { value 1;    }
        }
    }

    typedef  CML_LLDP_MED_T{
        type enumeration {
            enum network-policy { value 0;    }
            enum location { value 1;    }
            enum inventory { value 3;    }
            enum media-capabilities { value 4;    }
        }
    }

    typedef  CML_LLDP_ENABLE_T{
        type enumeration {
            enum rxonly { value 2;    }
            enum txonly { value 4;    }
            enum txrx { value 8;    }
        }
    }

    typedef  CML_LLDP_MGMT_ADDR_T{
        type enumeration {
            enum mac-address { value 1;    }
            enum ip-address { value 2;    }
        }
    }

    typedef  CML_LLDP_CHASSIS_T{
        type enumeration {
            enum if-alias { value 0;    }
            enum ip-address { value 1;    }
            enum mac-address { value 2;    }
            enum if-name { value 3;    }
            enum locally-assigned { value 4;    }
        }
    }

    typedef  CML_LLDP_PORT_T{
        type enumeration {
            enum if-alias { value 1;    }
            enum mac-address { value 2;    }
            enum ip-address { value 3;    }
            enum if-name { value 4;    }
            enum agt-circuit-id { value 5;    }
            enum locally-assigned { value 6;    }
        }
    }

    typedef  CML_LACP_TIMEOUT_T{
        type enumeration {
            enum long { value 0;    }
            enum short { value 1;    }
        }
    }

    typedef  CML_LACP_MODE_T{
        type enumeration {
            enum passive { value 0;    }
            enum active { value 1;    }
        }
    }

    typedef  CML_LACP_PSC_T{
        type enumeration {
            enum port-flow { value 13;    }
            enum smooth-division { value 14;    }
            enum round-robin { value 15;    }
        }
    }

    typedef  CML_SSH_KEY_RSA_DSA_T{
        type enumeration {
            enum dsa { value 1;    }
            enum rsa { value 2;    }
        }
    }

    typedef  CML_LLDP_TVL_FLAG_T{
        type enumeration {
            enum ieee-8021-org-specific { value 32;    }
            enum ieee-8023-org-specific { value 64;    }
            enum basic-mgmt { value 128;    }
        }
    }

    typedef  CML_NSM_MPLS_LOG_T{
        type bits {
            bit error { position 0;  }
            bit warning { position 1;  }
            bit debug { position 2;  }
            bit notice { position 3;  }
        }
    }

    typedef  CML_LDP_ENABLE_TYPE_T{
        type enumeration {
            enum ipv4 { value 1;    }
            enum ipv6 { value 2;    }
            enum both { value 3;    }
        }
    }

    typedef  CML_NSM_CONTAINER_ETHERNET_TYPE_T{
        type enumeration {
            enum ethernet { value 0;    }
        }
    }

    typedef  CML_INTERFACE_ADMIN_STATE_T{
        type enumeration {
            enum up { value 0;    }
            enum down { value 1;    }
            enum administratively-down { value 2;    }
        }
    }

    typedef  CML_NSM_TUNNEL_DIRECTION_TYPE_T{
        type enumeration {
            enum forward { value 0;    }
            enum reverse { value 1;    }
        }
    }

    typedef  CML_LACP_BRIDGETYPE_T{
        type enumeration {
            enum customer-bridge-group-address { value 0;    }
            enum multicast-group-address { value 1;    }
            enum non-tmpr-group-address { value 2;    }
        }
    }

    typedef  CML_LACP_DISCARD_CONV_T{
        type enumeration {
            enum disable { value 0;    }
            enum enable { value 1;    }
        }
    }

    typedef  CML_VXLAN_INGRESS_T{
        type enumeration {
            enum ingress-replication { value 1;    }
        }
    }

    typedef  CML_FOG_IFCTYPE_T{
        type enumeration {
            enum mpg { value 1;    }
            enum cpg { value 2;    }
        }
    }

    typedef  CML_FOG_LINK_TYPE_T{
        type enumeration {
            enum uplink { value 1;    }
            enum downlink { value 2;    }
        }
    }

    typedef  CML_VXLAN_INNER_VID_T{
        type enumeration {
            enum inner-vid-disabled { value 1;    }
        }
    }

    typedef  CML_MROUTE_ROUTETYPE_T{
        type enumeration {
            enum static { value 3;    }
            enum rip { value 4;    }
            enum ospf { value 6;    }
            enum bgp { value 8;    }
            enum isis { value 9;    }
        }
    }

    typedef  CML_MROUTE_IFNAME_T{
        type string;
    }

    typedef  CML_MROUTE_GW_ADDR_T{
        type union{

            type CML_IPV6_ADDR_T {

            }
            type CML_MROUTE_IFNAME_T {

            }
        }
    }

    typedef  CML_FIB_RETAIN_T{
        type union{

            type CML_FIB_RETAIN_TIME_T {

            }
            type CML_FIB_RETAIN_FOREVER_T {

            }
        }
    }

    typedef  CML_FIB_RETAIN_FOREVER_T{
        type enumeration {
            enum forever { value 0;    }
        }
    }

    typedef  CML_FIB_RETAIN_TIME_T{
        type uint32;
    }

    typedef  CML_RIB_DEBUG_TYPE_T{
        type bits {
            bit all { position 0;  }
            bit events { position 1;  }
            bit packet { position 2;  }
            bit packet-send { position 3;  }
            bit packet-recv { position 4;  }
            bit packet-detail { position 5;  }
            bit packet-send-detail { position 6;  }
            bit packet-recv-detail { position 7;  }
            bit kernel { position 8;  }
            bit ha { position 9;  }
            bit ha-all { position 10;  }
            bit nsm { position 11;  }
            bit bfd { position 12;  }
            bit monitor { position 13;  }
            bit hal-events { position 18;  }
        }
    }

    typedef  CML_RIB_DEBUG_EXIT_TYPE_T{
        type bits {
            bit all { position 0;  }
            bit events { position 1;  }
            bit packet { position 2;  }
            bit packet-send { position 3;  }
            bit packet-recv { position 4;  }
            bit packet-detail { position 5;  }
            bit packet-send-detail { position 6;  }
            bit packet-recv-detail { position 7;  }
            bit kernel { position 8;  }
            bit ha { position 9;  }
            bit ha-all { position 10;  }
            bit nsm { position 11;  }
            bit bfd { position 12;  }
            bit monitor { position 13;  }
            bit hal-events { position 18;  }
            bit hal-ipc { position 19;  }
        }
    }

    typedef  CML_RIB_UNDEBUG_TYPE_T{
        type bits {
            bit all { position 0;  }
            bit events { position 1;  }
            bit packet { position 2;  }
            bit packet-send { position 3;  }
            bit packet-recv { position 4;  }
            bit packet-detail { position 5;  }
            bit packet-send-detail { position 6;  }
            bit packet-recv-detail { position 7;  }
            bit kernel { position 8;  }
            bit ha { position 9;  }
            bit ha-all { position 10;  }
            bit nsm { position 11;  }
            bit bfd { position 12;  }
            bit hal-events { position 18;  }
        }
    }

    typedef  CML_RIB_DEBUG_ROUTING_TYPE_T{
        type bits {
            bit routing { position 20;  }
            bit routing-add-route { position 21;  }
            bit routing-delete-route { position 22;  }
            bit routing-mod-route { position 23;  }
        }
    }

    typedef  CML_RIB_PACKET_DEBUG_TYPE_T{
        type enumeration {
            enum recv { value 1;    }
            enum send { value 2;    }
        }
    }

    typedef  CML_VRRP_INIT_MSG_CODE_T{
        type enumeration {
            enum admin-down { value 0;    }
            enum if-not-running { value 1;    }
            enum circuit-down { value 2;    }
            enum no-subnet { value 3;    }
            enum vip-unset { value 4;    }
            enum switch-back-delay { value 5;    }
        }
    }

    typedef  CML_VRRP_DEBUG_T{
        type bits {
            bit events { position 1;  }
            bit packet-send { position 2;  }
            bit packet-recv { position 3;  }
        }
    }

    typedef  CML_VRRP_STATE_T{
        type enumeration {
            enum init { value 1;    }
            enum backup { value 2;    }
            enum master { value 3;    }
        }
    }

    typedef  CML_VRRP_MEMEBER_STATE{
        type enumeration {
            enum joined { value 1;    }
            enum left { value 2;    }
        }
    }

    typedef  CML_MCEC_HELLO_T{
        type enumeration {
            enum long { value 0;    }
            enum short { value 1;    }
        }
    }

    typedef  MCEC_DEBUG_T{
        type bits {
            bit hello { position 0;  }
            bit info { position 1;  }
            bit timer { position 2;  }
            bit event { position 3;  }
            bit cli { position 4;  }
            bit mac-sync { position 5;  }
            bit stp { position 6;  }
        }
    }

    typedef  CML_OSPF_AREA_ID_T{
        type union{

            type CML_STRING_T {

            }
            type uint16 {
                range "1..65535";

            }
        }
    }

    typedef  CML_COMMON_DEBUG_TYPE_T{
        type bits {
            bit decode { position 0;  }
            bit encode { position 1;  }
            bit events { position 2;  }
            bit fsm { position 3;  }
            bit tib { position 4;  }
        }
    }

    typedef  CML_UNKNOWN_MCAST_T{
        type enumeration {
            enum flood { value 0;    }
            enum discard { value 1;    }
        }
    }

    typedef  CML_OSPF6_DEBUG_PACKET_TYPE_T{
        type bits {
            bit hello { position 1;  }
            bit dd { position 2;  }
            bit ls-request { position 3;  }
            bit ls-update { position 4;  }
            bit ls-ack { position 5;  }
            bit send { position 6;  }
            bit recv { position 7;  }
            bit detail { position 8;  }
        }
    }

    typedef  CML_OSPF6_DEBUG_IFSM_T{
        type bits {
            bit status { position 0;  }
            bit events { position 1;  }
            bit timers { position 2;  }
        }
    }

    typedef  CML_OSPF6_DEBUG_NFSM_T{
        type bits {
            bit status { position 0;  }
            bit events { position 1;  }
            bit timers { position 2;  }
        }
    }

    typedef  CML_OSPF6_DEBUG_LSA_T{
        type bits {
            bit generate { position 0;  }
            bit flooding { position 1;  }
            bit install { position 2;  }
            bit refresh { position 3;  }
            bit maxage { position 4;  }
        }
    }

    typedef  CML_OSPF6_DEBUG_NSM_T{
        type bits {
            bit interface { position 0;  }
            bit redistribute { position 1;  }
        }
    }

    typedef  CML_OSPF6_DEBUG_RIB_T{
        type bits {
            bit interface { position 0;  }
            bit redistribute { position 1;  }
        }
    }

    typedef  CML_OSPF6_DEBUG_ROUTE_T{
        type bits {
            bit spf { position 0;  }
            bit ia { position 1;  }
            bit ase { position 2;  }
            bit install { position 3;  }
        }
    }

    typedef  CML_OSPF6_DEBUG_EVENT_T{
        type bits {
            bit abr { position 0;  }
            bit asbr { position 1;  }
            bit vlink { position 2;  }
            bit os { position 3;  }
            bit router { position 4;  }
            bit nssa { position 5;  }
        }
    }

    typedef  CML_MODULE_NAME_T{
        type enumeration {
            enum auth { value 1;    }
            enum bgp { value 2;    }
            enum cmm { value 3;    }
            enum hostp { value 5;    }
            enum hsl { value 6;    }
            enum isis { value 7;    }
            enum ldp { value 8;    }
            enum lag { value 9;    }
            enum l2mrib { value 10;    }
            enum mstp { value 11;    }
            enum mrib { value 12;    }
            enum nsm { value 13;    }
            enum onm { value 14;    }
            enum oam { value 15;    }
            enum ospf { value 16;    }
            enum ospf6 { value 17;    }
            enum rip { value 19;    }
            enum pim { value 21;    }
            enum rib { value 22;    }
            enum vrrp { value 23;    }
            enum sflow { value 24;    }
            enum rsvp { value 26;    }
            enum pserv { value 27;    }
            enum cml { value 28;    }
            enum ndd { value 29;    }
            enum ripng { value 30;    }
            enum vlog { value 31;    }
        }
    }

    typedef  CML_TIMESTAMP_T{
        type enumeration {
            enum microseconds { value 1;    }
            enum milliseconds { value 2;    }
            enum seconds { value 3;    }
        }
    }

    typedef  CML_LEVEL_T{
        type enumeration {
            enum debuglogging { value 0;    }
            enum emergencies { value 1;    }
            enum alerts { value 2;    }
            enum critical { value 3;    }
            enum errors { value 4;    }
            enum warnings { value 5;    }
            enum notifications { value 6;    }
            enum informational { value 7;    }
            enum debugging { value 8;    }
        }
    }

    typedef  CML_CLEAR_NTP_STATISTICS_T{
        type enumeration {
            enum all-peers { value 0;    }
            enum io { value 1;    }
            enum local { value 2;    }
            enum memory { value 3;    }
        }
    }

    typedef  CML_NTP_MODE_T{
        type enumeration {
            enum peer { value 1;    }
            enum server { value 2;    }
        }
    }

    typedef  SFLOW_DEBUG_OPTIONS_T{
        type enumeration {
            enum agent { value 1;    }
            enum sampling { value 2;    }
            enum polling { value 3;    }
            enum all { value 4;    }
        }
    }

    typedef  SFLOW_DIRECTION_OPTION_T{
        type enumeration {
            enum ingress { value 1;    }
            enum egress { value 2;    }
            enum both { value 3;    }
        }
    }

    typedef  USER_MGMT_ROLE_OPTIONS_T{
        type enumeration {
            enum network-admin { value 1;    }
            enum network-engineer { value 2;    }
            enum network-operator { value 3;    }
            enum network-user { value 4;    }
        }
    }

    typedef  CML_ACCEPT_LIFETIME_T{
        type enumeration {
            enum accept-lifetime { value 1;    }
        }
    }

    typedef  CML_ISIS_ADDRESS_IPV6_T{
        type enumeration {
            enum ipv6 { value 1;    }
        }
    }

    typedef  CML_SEND_LIFETIME_T{
        type enumeration {
            enum send-lifetime { value 1;    }
        }
    }

    typedef  CML_PREFIX_LIST_TYPE{
        type enumeration {
            enum deny { value 1;    }
            enum permit { value 2;    }
        }
    }

    typedef  CML_PREFIX_LIST_ANY_T{
        type enumeration {
            enum any { value 1;    }
        }
    }

    typedef  CML_IPV4_ADDR_PREFIX_T{
        type inet:ipv4-prefix;
    }

    typedef  CML_ISIS_METRIC_T{
        type enumeration {
            enum internal { value 0;    }
            enum external { value 1;    }
        }
    }

    typedef  CML_OAM_BFD_FW_T{
        type enumeration {
            enum multi-hop { value 1;    }
            enum micro-bfd { value 2;    }
        }
    }

    typedef  CML_IS_TYPE3_T{
        type enumeration {
            enum level-1 { value 1;    }
            enum level-2 { value 2;    }
            enum level-1-2 { value 3;    }
        }
    }

    typedef  CML_ISIS_SUMMARY_LEVEL_T{
        type enumeration {
            enum level-1 { value 1;    }
            enum level-2 { value 2;    }
            enum level-1-2 { value 3;    }
        }
    }

    typedef  CML_ISIS_LEVEL3_T{
        type enumeration {
            enum level-1 { value 1;    }
            enum level-2 { value 2;    }
            enum level-1-2 { value 3;    }
        }
    }

    typedef  CML_ISIS_SYNC_TYPE_T{
        type enumeration {
            enum level-1 { value 1;    }
            enum level-2 { value 2;    }
            enum level-1-2 { value 3;    }
        }
    }

    typedef  CML_ISIS_CIRCUIT_TYPE_T{
        type enumeration {
            enum level-1 { value 1;    }
            enum level-2-only { value 2;    }
            enum level-1-2 { value 3;    }
        }
    }

    typedef  CML_ISIS_SUPPRESS_T{
        type enumeration {
            enum default { value 0;    }
            enum external { value 1;    }
            enum interlevel { value 2;    }
            enum external-interlevel { value 3;    }
            enum interlevel-external { value 4;    }
        }
    }

    typedef  CML_WAITFORBGP_T{
        type enumeration {
            enum default { value 0;    }
            enum wait-for-bgp { value 1;    }
        }
    }

    typedef  CML_ISIS_ONSTARTUP_T{
        type union{

            type CML_WAITFORBGP_T {

            }
            type uint32 {
                range "5..86400";

            }
        }
    }

    typedef  CML_MESH_BLOCKED_T{
        type enumeration {
            enum blocked { value 0;    }
        }
    }

    typedef  CML_ISIS_MESH_TYPE_T{
        type union{

            type CML_MESH_BLOCKED_T {

            }
            type uint32 {
                range "1..4294967295";

            }
        }
    }

    typedef  CML_OSPF_CAPABILITY_TE_T{
        type enumeration {
            enum te { value 1;    }
            enum traffic-engineering { value 2;    }
        }
    }

    typedef  CML_OSPF_AREA_AUTHENTICATION_TYPE_T{
        type enumeration {
            enum authentication { value 1;    }
            enum authentication-message-digest { value 2;    }
        }
    }

    typedef  CML_OSPF_VLINK_AUTH_TYPE_T{
        type enumeration {
            enum authentication-null { value 0;    }
            enum authentication { value 1;    }
            enum authentication-message-digest { value 2;    }
        }
    }

    typedef  CML_OSPF_VLINK_INTERFACE_STATE_T{
        type enumeration {
            enum DependUpon { value 0;    }
            enum Down { value 1;    }
            enum Loopback { value 2;    }
            enum Waiting { value 3;    }
            enum Point-To-Point { value 4;    }
            enum DROther { value 5;    }
            enum Backup { value 6;    }
            enum DR { value 7;    }
        }
    }

    typedef  CML_OSPF_VLINK_ADJ_STATE_T{
        type enumeration {
            enum DependUpon { value 0;    }
            enum Down { value 1;    }
            enum Attempt { value 2;    }
            enum Init { value 3;    }
            enum 2-Way { value 4;    }
            enum ExStart { value 5;    }
            enum Exchange { value 6;    }
            enum Loading { value 7;    }
            enum Full { value 8;    }
        }
    }

    typedef  CML_OSPF_VLINK_STATUS_T{
        type enumeration {
            enum Down { value 0;    }
            enum Up { value 1;    }
        }
    }

    typedef  CML_OSPF_AREA_RANGE_ADVERTISE_T{
        type enumeration {
            enum not-advertise { value 0;    }
            enum advertise { value 1;    }
        }
    }

    typedef  CML_OSPF_BFD_STATE{
        type enumeration {
            enum enable { value 0;    }
            enum disable { value 1;    }
        }
    }

    typedef  CML_OSPF_ALL_DEBUG_T{
        type enumeration {
            enum all { value 1;    }
        }
    }

    typedef  CML_OSPF_PACKET_TYPE_T{
        type bits {
            bit hello { position 0;  }
            bit dd { position 1;  }
            bit ls-request { position 2;  }
            bit ls-update { position 3;  }
            bit ls-ack { position 4;  }
            bit send { position 5;  }
            bit recv { position 6;  }
            bit detail { position 7;  }
        }
    }

    typedef  CML_OSPF_DEBUG_EVENT_TYPE_T{
        type bits {
            bit abr { position 0;  }
            bit nssa { position 1;  }
            bit asbr { position 2;  }
            bit vlink { position 3;  }
            bit lsa { position 4;  }
            bit os { position 5;  }
            bit router { position 6;  }
        }
    }

    typedef  CML_OSPF_DEBUG_IFSM_T{
        type bits {
            bit status { position 0;  }
            bit events { position 1;  }
            bit timers { position 2;  }
        }
    }

    typedef  CML_OSPF_DEBUG_NFSM_T{
        type bits {
            bit status { position 0;  }
            bit events { position 1;  }
            bit timers { position 2;  }
        }
    }

    typedef  CML_OSPF_DEBUG_LSA_T{
        type bits {
            bit generate { position 0;  }
            bit flooding { position 1;  }
            bit install { position 2;  }
            bit refresh { position 3;  }
            bit maxage { position 4;  }
        }
    }

    typedef  CML_OSPF_DEBUG_NSM_T{
        type bits {
            bit interface { position 0;  }
            bit redistribute { position 1;  }
        }
    }

    typedef  CML_OSPF_DEBUG_RIB_T{
        type bits {
            bit interface { position 0;  }
            bit redistribute { position 1;  }
        }
    }

    typedef  CML_OSPF_DEBUG_RIB_CLIENT_T{
        type bits {
            bit redistribute { position 1;  }
            bit client { position 2;  }
        }
    }

    typedef  CML_FLOWCTRL_T{
        type enumeration {
            enum off { value 0;    }
            enum on { value 1;    }
        }
    }

    typedef  CML_ERROR_SET_TYPE_T{
        type enumeration {
            enum packet-loss { value 0;    }
            enum stray-packets { value 1;    }
            enum malformed-packets { value 2;    }
            enum excessive-packet-loss-rate { value 3;    }
            enum buffer-overrun { value 4;    }
            enum remote-packet-loss { value 5;    }
        }
    }

    typedef  CML_ERROR_CLEAR_TYPE_T{
        type enumeration {
            enum packet-loss { value 6;    }
            enum stray-packets { value 7;    }
            enum malformed-packets { value 8;    }
            enum excessive-packet-loss-rate { value 9;    }
            enum buffer-overrun { value 10;    }
            enum remote-packet-loss { value 11;    }
        }
    }

    typedef  CML_SR_ABSOLUTE_T{
        type uint32;
    }

    typedef  CML_SR_INDEX_T{
        type uint32;
    }

    typedef  CML_SR_SID_T{
        type union{

            type CML_SR_ABSOLUTE_T {

            }
            type CML_SR_INDEX_T {

            }
        }
    }

    typedef  CML_SR_PREFIX_FLAG_T{
        type enumeration {
            enum explicit-null { value 1;    }
            enum no-php { value 2;    }
        }
    }

    typedef  CML_SR_N_FLAG_CLEAR_T{
        type enumeration {
            enum n-flag-clear { value 1;    }
        }
    }

    typedef  CML_NSM_ERR_REASON_T{
        type bits {
            bit lag-mismatch { position 0;  }
            bit stp-bpdu-guard { position 1;  }
            bit link-flap { position 2;  }
        }
    }

    typedef  CML_NSM_ERR_DISABLE_TIMEOUT_T{
        type enumeration {
            enum disable { value 0;    }
            enum enable { value 1;    }
        }
    }

    typedef  CML_ON_OFF_T{
        type enumeration {
            enum off { value 0;    }
            enum on { value 1;    }
        }
    }

    typedef  CML_OSPF_DEBUG_ROUTE_T{
        type bits {
            bit spf { position 0;  }
            bit ia { position 1;  }
            bit ase { position 2;  }
            bit install { position 3;  }
            bit terse { position 4;  }
        }
    }

    typedef  CML_OSPF_DEBUG_REDIST_T{
        type bits {
            bit detail { position 0;  }
            bit terse { position 1;  }
        }
    }

    typedef  CML_OSPF_DEBUG_GRACEFUL_T{
        type bits {
            bit detail { position 0;  }
            bit terse { position 1;  }
        }
    }

    typedef  CML_OSPF_MD5_T{
        type enumeration {
            enum 0 { value 1;    }
        }
    }

    typedef  CML_ROUTEMAP_LIST_T{
        type union{

            type int32 {
                range "1..199 | 1300..2699";

            }
            type CML_STRING_T {

            }
        }
    }

    typedef  CML_ROUTEMAP_EXTERNAL_TYPE_LIST{
        type enumeration {
            enum type-1 { value 1;    }
            enum type-2 { value 2;    }
        }
    }

    typedef  CML_ROUTEMAP_OSPF_METRIC_TYPE_LIST{
        type enumeration {
            enum type-1 { value 1;    }
            enum type-2 { value 2;    }
        }
    }

    typedef  CML_ROUTEMAP_ISIS_METRIC_TYPE_LIST{
        type enumeration {
            enum internal { value 1;    }
            enum external { value 2;    }
        }
    }

    typedef  CML_LEVEL_LIST_T{
        type enumeration {
            enum level-1 { value 1;    }
            enum level-2 { value 2;    }
            enum level-1-2 { value 3;    }
        }
    }

    typedef  CML_ROUTEMAP_ORIGIN_CODE{
        type enumeration {
            enum egp { value 1;    }
            enum igp { value 2;    }
            enum incomplete { value 3;    }
        }
    }

    typedef  CML_ROUTEMAP_COST_COMPARISION_T{
        type enumeration {
            enum igp { value 1;    }
            enum pre-bestpath { value 2;    }
        }
    }

    typedef  CML_FORWARDTYPE_T{
        type enumeration {
            enum null0 { value 0;    }
            enum tunnel-te { value 1;    }
        }
    }

    typedef  CML_ROUTEMAP_COMMUNITY_LIST_T{
        type union{

            type int32 {
                range "1..99 | 100..500";

            }
            type CML_STRING_T {

            }
        }
    }

    typedef  CML_ROUT_MAP_EXACT_MATCH_T{
        type enumeration {
            enum exact-match { value 1;    }
        }
    }

    typedef  CML_ROUTEMAP_MATCH_T{
        type union{

            type CML_IPV6_ADDR_T {

            }
            type CML_STRING_T {

            }
        }
    }

    typedef  CML_COMMUNITY_T{
        type string;
    }

    typedef  CML_ROUTEMAP_COMMUNITY_T{
        type union{

            type int32 {
                range "1..65535";

            }
            type CML_COMMUNITY_T {

            }
        }
    }

    typedef  CML_ROUTEMAP_ADDITIVE_LIST_T{
        type enumeration {
            enum additive { value 1;    }
        }
    }

    typedef  CML_AP_RMAP_ALL_T{
        type enumeration {
            enum all { value 1;    }
        }
    }

    typedef  CML_AP_RMAP_BEST_T{
        type uint8;
    }

    typedef  CML_ADDPATH_RMAP_T{
        type union{

            type CML_AP_RMAP_BEST_T {

            }
            type CML_AP_RMAP_ALL_T {

            }
        }
    }

    typedef  CML_BRIDGE_FORWARD_T{
        type enumeration {
            enum bridge-forward { value 1;    }
        }
    }

    typedef  CML_BCKBONE_BRIDGE_GRP_T{
        type enumeration {
            enum backbone { value 0;    }
        }
    }

    typedef  CML_BRIDGE_GRP_T{
        type uint8;
    }

    typedef  CML_BRIDGE_GRP_CMD_T{
        type union{

            type CML_BRIDGE_GRP_T {

            }
            type CML_BCKBONE_BRIDGE_GRP_T {

            }
        }
    }

    typedef  CML_BRIDGE_SPANMODE_T{
        type enumeration {
            enum stp { value 1;    }
            enum stp-vlan-bridge { value 2;    }
            enum rstp { value 3;    }
            enum rstp-vlan-bridge { value 4;    }
            enum mstp { value 5;    }
            enum provider-rstp { value 6;    }
            enum provider-mstp { value 7;    }
            enum rpvst+ { value 12;    }
        }
    }

    typedef  CML_ALLOWED_FORBIDDEN_T{
        type enumeration {
            enum forbidden { value 0;    }
            enum allowed { value 1;    }
        }
    }

    typedef  CML_ADD_REMOVE_T{
        type enumeration {
            enum remove { value 0;    }
            enum add { value 1;    }
        }
    }

    typedef  CML_VLANSTACK_T{
        type enumeration {
            enum customer-edge-port { value 4;    }
            enum provider-port { value 6;    }
        }
    }

    typedef  CML_ENABLEBPDURX_T{
        type enumeration {
            enum disableBPDUrx { value 0;    }
            enum enableBPDUrx { value 1;    }
        }
    }

    typedef  CML_ACLTYPE_T{
        type enumeration {
            enum mac { value 1;    }
            enum ip { value 3;    }
            enum ipv6 { value 4;    }
        }
    }

    typedef  CML_BRIDGE_T{
        type uint8;
    }

    typedef  CML_BRIDGE_ID_T{
        type union{

            type CML_BRIDGE_T {

            }
            type CML_SPANNING_TREE_T {

            }
        }
    }

    typedef  CML_BRIDGE_BACKBONE_ID_T{
        type union{

            type CML_BRIDGE_BCKBONE_T {

            }
            type CML_BACKBONE_T {

            }
        }
    }

    typedef  CML_BACKBONE_T{
        type enumeration {
            enum backbone { value 33;    }
        }
    }

    typedef  CML_BRIDGE_BCKBONE_T{
        type uint8;
    }

    typedef  CML_ACTIONTYPE_T{
        type enumeration {
            enum forward { value 101;    }
            enum drop { value 102;    }
            enum redirect { value 103;    }
        }
    }

    typedef  CML_VLAN_OPT_TYPE_T{
        type enumeration {
            enum add { value 1;    }
            enum delete { value 2;    }
        }
    }

    typedef  CML_TESI_MODE_T{
        type enumeration {
            enum passive { value 1;    }
            enum active { value 2;    }
        }
    }

    typedef  CML_TESI_TYPE_T{
        type enumeration {
            enum dynamic { value 1;    }
            enum static { value 2;    }
        }
    }

    typedef  CML_PNPADDDEL_T{
        type enumeration {
            enum add { value 1;    }
            enum delete { value 2;    }
        }
    }

    typedef  CML_NSMVLANPORT_MODE_T{
        type enumeration {
            enum pnp { value 6;    }
            enum cnp { value 8;    }
            enum pip { value 10;    }
            enum cbp { value 11;    }
        }
    }

    typedef  CML_CMBCKINSTANCE_T{
        type uint32;
    }

    typedef  CML_SPANNING_TREE_T{
        type enumeration {
            enum spanning-tree { value 0;    }
        }
    }

    typedef  CML_INSTANCE_NAME_T{
        type string;
    }

    typedef  CML_SVLAN_INSTANCE_NAME_T{
        type union{

            type CML_CMBCKINSTANCE_T {

            }
            type CML_INSTANCE_NAME_T {

            }
        }
    }

    typedef  CML_CMBCKBONE_INSTANCE_T{
        type union{

            type CML_CMBCKINSTANCE_T {

            }
            type CML_INSTANCE_IFNAME_T {

            }
        }
    }

    typedef  CML_INSTANCE_IFNAME_T{
        type string;
    }

    typedef  CML_VIP_TRAFFIC_T{
        type enumeration {
            enum all { value 0;    }
            enum ingress { value 1;    }
            enum egress { value 2;    }
        }
    }

    typedef  CML_BEB_MODE_T{
        type enumeration {
            enum tx { value 0;    }
            enum rx { value 1;    }
            enum rxtx { value 2;    }
            enum none { value 3;    }
        }
    }

    typedef  CML_BRIDGE_BACKBONE_T{
        type union{

            type CML_BACKBONE_T {

            }
            type uint8 {
                range "1..32";

            }
        }
    }

    typedef  CML_ASPTEISID_T{
        type enumeration {
            enum add { value 1;    }
            enum delete { value 2;    }
        }
    }

    typedef  CML_CNPINS_T{
        type uint32;
    }

    typedef  CML_OSPF_NBMA_ROW_STATUS{
        type enumeration {
            enum row-status-active { value 1;    }
            enum row-status-notinservice { value 2;    }
            enum row-status-notready { value 3;    }
            enum row-status-createandgo { value 4;    }
            enum row-status-createandwait { value 5;    }
            enum row-status-destroy { value 6;    }
        }
    }

    typedef  CML_OSPF_IF_STATE{
        type enumeration {
            enum enabled { value 1;    }
            enum disabled { value 2;    }
        }
    }

    typedef  CML_CNP_INSTANCE_T{
        type union{

            type CML_CNPINS_T {

            }
            type CML_CNP_INSTANCE_IFNAME_T {

            }
        }
    }

    typedef  CML_CNP_INSTANCE_IFNAME_T{
        type string;
    }

    typedef  SNMP_TRAP_OPTIONS_T{
        type enumeration {
            enum link { value 1;    }
            enum link-linkDown { value 2;    }
            enum link-linkUp { value 3;    }
            enum snmp { value 4;    }
            enum snmp-authentication { value 5;    }
            enum mpls { value 6;    }
            enum pw { value 7;    }
            enum pwdelete { value 8;    }
            enum rsvp { value 9;    }
        }
    }

    typedef  CML_VR_PROTOCOL_T{
        type bits {
            bit rip { position 1;  }
            bit ipv6-rip { position 2;  }
            bit ospf { position 3;  }
            bit ipv6-ospf { position 4;  }
            bit isis { position 5;  }
            bit pim { position 6;  }
            bit vrrp { position 7;  }
            bit bgp { position 9;  }
        }
    }

    typedef  CML_LDP_ENABLE_IPV4_TYPE_T{
        type enumeration {
            enum disable-ldp { value 0;    }
            enum enable-ldp { value 1;    }
        }
    }

    typedef  CML_LDP_ENABLE_IPV6_TYPE_T{
        type enumeration {
            enum disable-ldp { value 0;    }
            enum enable-ldp { value 1;    }
        }
    }

    typedef  CML_LDP_IGP_SYNC_T{
        type enumeration {
            enum igp-sync { value 0;    }
            enum no-igp-sync { value 1;    }
        }
    }

    typedef  CML_RSVP_INSTANCE_T{
        type enumeration {
            enum rsvp { value 1;    }
        }
    }

    typedef  CML_LDP_INSTANCE_T{
        type enumeration {
            enum ldp { value 1;    }
        }
    }

    typedef  CML_LDP_DEBUG_T{
        type bits {
            bit events { position 0;  }
            bit fsm { position 1;  }
            bit hexdump { position 2;  }
            bit dsm { position 3;  }
            bit usm { position 4;  }
            bit tsm { position 5;  }
            bit qos { position 6;  }
            bit nsm { position 7;  }
            bit advertise-labels { position 8;  }
            bit cspf { position 9;  }
            bit vc-usm { position 10;  }
            bit vc-dsm { position 11;  }
            bit graceful-restart { position 12;  }
            bit rib { position 13;  }
        }
    }

    typedef  CML_LDP_DEBUG_PACKET_T{
        type bits {
            bit notification { position 0;  }
            bit hello { position 1;  }
            bit initialization { position 2;  }
            bit keepalive { position 3;  }
            bit address { position 4;  }
            bit label { position 5;  }
        }
    }

    typedef  CML_LDP_FAILURE_T{
        type enumeration {
            enum restart { value 0;    }
        }
    }

    typedef  CML_LDP_CSPF_T{
        type enumeration {
            enum no-cspf { value 0;    }
            enum cspf { value 1;    }
        }
    }

    typedef  CML_LDP_LOOSE_T{
        type enumeration {
            enum strict { value 0;    }
            enum loose { value 1;    }
        }
    }

    typedef  CML_LDP_TRUNK_ADMIN_GROUP_T{
        type enumeration {
            enum exclude-any { value 0;    }
            enum include-any { value 1;    }
        }
    }

    typedef  CML_LDP_IP_ADDR_T{
        type union{

            type CML_IPV4_ADDR_DESC_T {

            }
            type CML_IPV6_ADDR_DESC_T {

            }
        }
    }

    typedef  CML_LDP_ICCP_DEBUG_T{
        type bits {
            bit events { position 0;  }
            bit fsm { position 1;  }
            bit hexdump { position 2;  }
            bit packet { position 3;  }
            bit bfd { position 4;  }
        }
    }

    typedef  CML_RSVP_PATH_TYPE_T{
        type enumeration {
            enum mpls { value 0;    }
            enum gmpls { value 1;    }
        }
    }

    typedef  CML_RSVP_TRUNK_ADDRFAMILY_T{
        type enumeration {
            enum ipv4 { value 0;    }
            enum ipv6 { value 1;    }
            enum gmpls { value 2;    }
        }
    }

    typedef  CML_PATH_SEL_TYPE_T{
        type enumeration {
            enum te { value 0;    }
            enum igp { value 1;    }
        }
    }

    typedef  CML_RSVP_RESTART_STATUS_T{
        type enumeration {
            enum disable { value 0;    }
            enum enable { value 1;    }
        }
    }

    typedef  CML_RSVP_DETOUR_IDEN_T{
        type enumeration {
            enum sender-template { value 1;    }
            enum path { value 2;    }
        }
    }

    typedef  CML_RSVP_P2MP_ADDR_T{
        type enumeration {
            enum ipv4 { value 1;    }
            enum ipv6 { value 2;    }
        }
    }

    typedef  CML_RSVP_CSPF_TYPE_T{
        type enumeration {
            enum no-cspf { value 0;    }
            enum cspf { value 1;    }
        }
    }

    typedef  CML_RSVP_TRUNK_METRIC_TYPE_T{
        type enumeration {
            enum igp-metric { value 1;    }
            enum te-metric { value 2;    }
            enum hop-count { value 3;    }
        }
    }

    typedef  CML_RSVP_CSPF_STATUS_T{
        type enumeration {
            enum no-cspf { value 0;    }
            enum cspf { value 1;    }
        }
    }

    typedef  CML_LOOP_DETECTION_T{
        type enumeration {
            enum no-loop-detection { value 0;    }
            enum loop-detection { value 1;    }
        }
    }

    typedef  CML_RSVP_PHP_T{
        type enumeration {
            enum no-php { value 0;    }
            enum php { value 1;    }
        }
    }

    typedef  CML_REFRESH_PATH_PARSING_T{
        type enumeration {
            enum no-refresh-path-parsing { value 0;    }
            enum refresh-path-parsing { value 1;    }
        }
    }

    typedef  CML_REFRESH_RESV_PARSING_T{
        type enumeration {
            enum no-refresh-resv-parsing { value 0;    }
            enum refresh-resv-parsing { value 1;    }
        }
    }

    typedef  CML_RSVP_DEBUG_T{
        type bits {
            bit events { position 0;  }
            bit packet { position 1;  }
            bit packet-in { position 2;  }
            bit packet-out { position 3;  }
            bit hexdump { position 4;  }
            bit nsm { position 5;  }
            bit cspf { position 6;  }
            bit fsm-egress { position 7;  }
            bit fsm-transit-downstream { position 8;  }
            bit fsm-transit-upstream { position 9;  }
            bit fsm-ingress { position 10;  }
            bit rib { position 11;  }
        }
    }

    typedef  CML_L2_PROTOCOL_T{
        type enumeration {
            enum stp { value 0;    }
            enum gmrp { value 3;    }
            enum gvrp { value 4;    }
            enum mmrp { value 5;    }
            enum mvrp { value 6;    }
            enum lacp { value 7;    }
            enum dot1x { value 8;    }
            enum lldp { value 9;    }
            enum pause { value 13;    }
            enum efm { value 14;    }
            enum elmi { value 15;    }
            enum ptp { value 16;    }
            enum synce { value 17;    }
        }
    }

    typedef  CML_DISCARD_L2_PROTOCOL_T{
        type enumeration {
            enum stp { value 0;    }
            enum lacp { value 7;    }
            enum dot1x { value 8;    }
            enum lldp { value 9;    }
            enum pause { value 13;    }
            enum efm { value 14;    }
            enum elmi { value 15;    }
            enum ptp { value 16;    }
            enum synce { value 17;    }
        }
    }

    typedef  CML_PVLAN_MODE_T{
        type enumeration {
            enum host { value 1;    }
            enum promiscuous { value 2;    }
        }
    }

    typedef  CML_PVLAN_TYPE_T{
        type enumeration {
            enum community { value 1;    }
            enum isolated { value 2;    }
            enum primary { value 3;    }
            enum association { value 4;    }
        }
    }

    typedef  CML_PVLAN_ADD_REMOVE_TYPE_T{
        type enumeration {
            enum add { value 1;    }
            enum remove { value 2;    }
        }
    }

    typedef  CML_CVLAN_CONFIG_T{
        type bits {
            bit default { position 0;  }
            bit untagged-pep { position 1;  }
            bit untagged-cep { position 2;  }
        }
    }

    typedef  CML_OEP_VLAN_TYPE_T{
        type enumeration {
            enum cvlan { value 1;    }
            enum svlan { value 2;    }
        }
    }

    typedef  CML_EGERSS_TAGGED_TYPE_T{
        type enumeration {
            enum disable { value 0;    }
            enum enable { value 1;    }
        }
    }

    typedef  CML_EDGE_VLAN_TYPE_T{
        type enumeration {
            enum allowed { value 1;    }
            enum default-svlan { value 2;    }
        }
    }

    typedef  CML_ACL_PORT_OPERATIONS_T{
        type enumeration {
            enum eq { value 1;    }
            enum neq { value 2;    }
            enum lt { value 3;    }
            enum gt { value 4;    }
            enum range { value 5;    }
        }
    }

    typedef  CML_ACL_FILTER_ACTION_T{
        type enumeration {
            enum deny { value 0;    }
            enum permit { value 1;    }
            enum dynamic { value 2;    }
            enum deny-all { value 3;    }
            enum permit-all { value 4;    }
            enum no-match { value 5;    }
        }
    }

    typedef  CML_ACL_ARP_TYPE_T{
        type enumeration {
            enum none { value 0;    }
            enum request { value 1;    }
            enum response { value 2;    }
        }
    }

    typedef  CML_ACL_ANY_T{
        type enumeration {
            enum any { value 0;    }
        }
    }

    typedef  CML_ACL_IPV4_HOST_T{
        type string;
    }

    typedef  CML_ACL_IPV4_PREFIX_T{
        type inet:ipv4-prefix;
    }

    typedef  CML_ACL_ANY_IPV4_ADDR_T{
        type union{

            type CML_ACL_ANY_T {

            }
            type CML_ACL_IPV4_HOST_T {

            }
            type CML_ACL_IPV4_PREFIX_T {

            }
        }
    }

    typedef  CML_ACL_IPV6_HOST_T{
        type string;
    }

    typedef  CML_ACL_IPV6_PREFIX_T{
        type inet:ipv6-prefix;
    }

    typedef  CML_ACL_ANY_IPV6_ADDR_T{
        type union{

            type CML_ACL_ANY_T {

            }
            type CML_ACL_IPV6_HOST_T {

            }
            type CML_ACL_IPV6_PREFIX_T {

            }
        }
    }

    typedef  CML_ACL_UDP_KEYWORD_ENUM_T{
        type enumeration {
            enum echo { value 7;    }
            enum discard { value 9;    }
            enum time { value 37;    }
            enum nameserver { value 42;    }
            enum tacacs { value 49;    }
            enum domain { value 53;    }
            enum bootps { value 67;    }
            enum bootpc { value 68;    }
            enum tftp { value 69;    }
            enum sunrpc { value 111;    }
            enum netbios_ns { value 137;    }
            enum netbios_dgm { value 138;    }
            enum netbios_ss { value 139;    }
            enum snmp { value 161;    }
            enum snmptrap { value 162;    }
            enum xdmcp { value 177;    }
            enum dnsix { value 195;    }
            enum mobile_ip { value 434;    }
            enum pim_auto_rp { value 496;    }
            enum isakmp { value 500;    }
            enum biff { value 512;    }
            enum who { value 513;    }
            enum syslog { value 514;    }
            enum talk { value 517;    }
            enum rip { value 520;    }
            enum non500_isakmp { value 4500;    }
        }
    }

    typedef  CML_ACL_UDP_KEYWORD_T{
        type union{

            type CML_ACL_UDP_KEYWORD_ENUM_T {

            }
            type uint32 {
                range "0..65535";

            }
        }
    }

    typedef  CML_ACL_TCP_KEYWORD_ENUM_T{
        type enumeration {
            enum echo { value 7;    }
            enum discard { value 9;    }
            enum daytime { value 13;    }
            enum chargen { value 19;    }
            enum ftp_data { value 20;    }
            enum ftp { value 21;    }
            enum ssh { value 22;    }
            enum telnet { value 23;    }
            enum smtp { value 25;    }
            enum time { value 37;    }
            enum whois { value 43;    }
            enum tacacs { value 49;    }
            enum domain { value 53;    }
            enum gopher { value 70;    }
            enum finger { value 79;    }
            enum www { value 80;    }
            enum hostname { value 101;    }
            enum pop2 { value 109;    }
            enum pop3 { value 110;    }
            enum sunrpc { value 111;    }
            enum ident { value 113;    }
            enum nntp { value 119;    }
            enum bgp { value 179;    }
            enum irc { value 194;    }
            enum pim_auto_rp { value 496;    }
            enum exec { value 512;    }
            enum login { value 513;    }
            enum cmd { value 514;    }
            enum lpd { value 515;    }
            enum talk { value 517;    }
            enum uucp { value 540;    }
            enum klogin { value 543;    }
            enum kshell { value 544;    }
            enum drip { value 3949;    }
        }
    }

    typedef  CML_ACL_TCP_KEYWORD_T{
        type union{

            type CML_ACL_TCP_KEYWORD_ENUM_T {

            }
            type uint32 {
                range "0..65535";

            }
        }
    }

    typedef  CML_ACL_IP_PROTO_ENUM_T{
        type enumeration {
            enum ipv6_hop { value 0;    }
            enum icmp { value 1;    }
            enum igmp { value 2;    }
            enum ipip { value 4;    }
            enum tcp { value 6;    }
            enum udp { value 17;    }
            enum ipv6ip { value 41;    }
            enum rsvp { value 46;    }
            enum gre { value 47;    }
            enum esp { value 50;    }
            enum ahp { value 51;    }
            enum eigrp { value 88;    }
            enum ospf { value 89;    }
            enum pim { value 103;    }
            enum ipcomp { value 108;    }
            enum vrrp { value 112;    }
            enum sctp { value 132;    }
            enum any { value 256;    }
        }
    }

    typedef  CML_ACL_IP_PROTO_T{
        type union{

            type CML_ACL_IP_PROTO_ENUM_T {

            }
            type uint16 {
                range "0..255";

            }
        }
    }

    typedef  CML_ACL_IPV6_PROTO_ENUM_T{
        type enumeration {
            enum ipv6_hop { value 0;    }
            enum igmp { value 2;    }
            enum ipv6ip { value 4;    }
            enum tcp { value 6;    }
            enum udp { value 17;    }
            enum ipv6ipv6 { value 41;    }
            enum rsvp { value 46;    }
            enum gre { value 47;    }
            enum esp { value 50;    }
            enum ahp { value 51;    }
            enum icmpv6 { value 58;    }
            enum ospf { value 89;    }
            enum pim { value 103;    }
            enum ipcomp { value 108;    }
            enum vrrp { value 112;    }
            enum sctp { value 132;    }
            enum any { value 256;    }
        }
    }

    typedef  CML_ACL_IPV6_PROTO_T{
        type union{

            type CML_ACL_IPV6_PROTO_ENUM_T {

            }
            type uint16 {
                range "0..255";

            }
        }
    }

    typedef  CML_ACL_DSCP_ENUM_T{
        type enumeration {
            enum default { value 0;    }
            enum cs1 { value 8;    }
            enum af11 { value 10;    }
            enum af12 { value 12;    }
            enum af13 { value 14;    }
            enum cs2 { value 16;    }
            enum af21 { value 18;    }
            enum af22 { value 20;    }
            enum af23 { value 22;    }
            enum cs3 { value 24;    }
            enum af31 { value 26;    }
            enum af32 { value 28;    }
            enum af33 { value 30;    }
            enum cs4 { value 32;    }
            enum af41 { value 34;    }
            enum af42 { value 36;    }
            enum af43 { value 38;    }
            enum cs5 { value 40;    }
            enum ef { value 46;    }
            enum cs6 { value 48;    }
            enum cs7 { value 56;    }
        }
    }

    typedef  CML_ACL_DSCP_T{
        type union{

            type CML_ACL_DSCP_ENUM_T {

            }
            type int8 {
                range "0..63";

            }
        }
    }

    typedef  CML_ACL_PRECEDENCE_ENUM_T{
        type enumeration {
            enum routine { value 0;    }
            enum priority { value 1;    }
            enum immediate { value 2;    }
            enum flash { value 3;    }
            enum flashoverride { value 4;    }
            enum critical { value 5;    }
            enum internet { value 6;    }
            enum network { value 7;    }
        }
    }

    typedef  CML_ACL_PRECEDENCE_T{
        type union{

            type CML_ACL_PRECEDENCE_ENUM_T {

            }
            type int8 {
                range "0..7";

            }
        }
    }

    typedef  CML_ACL_ICMP_OPTIONS_T{
        type enumeration {
            enum administratively-prohibited { value 1;    }
            enum alternate-address { value 2;    }
            enum conversion-error { value 3;    }
            enum dod-host-prohibited { value 4;    }
            enum dod-net-prohibited { value 5;    }
            enum echo { value 6;    }
            enum echo-reply { value 7;    }
            enum general-parameter-problem { value 8;    }
            enum host-isolated { value 9;    }
            enum host-precedence-unreachable { value 10;    }
            enum host-redirect { value 11;    }
            enum host-tos-redirect { value 12;    }
            enum host-tos-unreachable { value 13;    }
            enum host-unknown { value 14;    }
            enum host-unreachable { value 15;    }
            enum information-reply { value 16;    }
            enum information-request { value 17;    }
            enum mask-reply { value 18;    }
            enum mask-request { value 19;    }
            enum mobile-redirect { value 20;    }
            enum net-redirect { value 21;    }
            enum net-tos-redirect { value 22;    }
            enum net-tos-unreachable { value 23;    }
            enum net-unreachable { value 24;    }
            enum network-unknown { value 25;    }
            enum no-room-for-option { value 26;    }
            enum option-missing { value 27;    }
            enum packet-too-big { value 28;    }
            enum parameter-problem { value 29;    }
            enum port-unreachable { value 30;    }
            enum precedence-unreachable { value 31;    }
            enum protocol-unreachable { value 32;    }
            enum reassembly-timeout { value 33;    }
            enum redirect { value 34;    }
            enum router-advertisement { value 35;    }
            enum router-solicitation { value 36;    }
            enum source-quench { value 37;    }
            enum source-route-failed { value 38;    }
            enum time-exceeded { value 39;    }
            enum timestamp-reply { value 40;    }
            enum timestamp-request { value 41;    }
            enum traceroute { value 42;    }
            enum ttl-exceeded { value 43;    }
            enum unreachable { value 44;    }
        }
    }

    typedef  CML_ACL_ICMPV6_OPTIONS_T{
        type enumeration {
            enum beyond-scope { value 0;    }
            enum destination-unreachable { value 1;    }
            enum echo-reply { value 2;    }
            enum echo-request { value 3;    }
            enum header { value 4;    }
            enum hop-limit { value 5;    }
            enum mld-query { value 6;    }
            enum mld-reduction { value 7;    }
            enum mld-report { value 8;    }
            enum nd-na { value 9;    }
            enum nd-ns { value 10;    }
            enum next-header { value 11;    }
            enum no-admin { value 12;    }
            enum no-route { value 13;    }
            enum packet-too-big { value 14;    }
            enum parameter-option { value 15;    }
            enum parameter-problem { value 16;    }
            enum port-unreachable { value 17;    }
            enum reassembly-timeout { value 18;    }
            enum redirect { value 19;    }
            enum renum-command { value 20;    }
            enum renum-result { value 21;    }
            enum renum-seq-number { value 22;    }
            enum router-advertisement { value 23;    }
            enum router-renumbering { value 24;    }
            enum router-solicitation { value 25;    }
            enum time-exceeded { value 26;    }
            enum unreachable { value 27;    }
        }
    }

    typedef  CML_ACL_TCP_FLAGS_T{
        type bits {
            bit fin { position 0;  }
            bit syn { position 1;  }
            bit rst { position 2;  }
            bit psh { position 3;  }
            bit ack { position 4;  }
            bit urg { position 5;  }
            bit established { position 6;  }
        }
    }

    typedef  CML_ACL_ANY_MAC_ADDR_T{
        type union{

            type CML_ACL_ANY_T {

            }
            type CML_MAC_ADDR_T {

            }
        }
    }

    typedef  CML_ACL_ETHER_TYPE_ENUM_T{
        type enumeration {
            enum ipv4 { value 2048;    }
            enum arp { value 2054;    }
            enum vines-echo { value 2991;    }
            enum etype-6000 { value 24576;    }
            enum mop-dump { value 24577;    }
            enum mop-console { value 24578;    }
            enum decnet-iv { value 24579;    }
            enum lat { value 24580;    }
            enum diagnostic { value 24581;    }
            enum lavc-sca { value 24583;    }
            enum etype-8042 { value 32834;    }
            enum appletalk { value 32923;    }
            enum aarp { value 33011;    }
            enum ipv6 { value 34525;    }
            enum mpls { value 34886;    }
        }
    }

    typedef  CML_ACL_ETHER_TYPE_T{
        type union{

            type CML_ACL_ETHER_TYPE_ENUM_T {

            }
            type CML_STRING_T {

            }
        }
    }

    typedef  CML_ACL_TYPES_T{
        type enumeration {
            enum mac { value 1;    }
            enum ip { value 3;    }
            enum ipv6 { value 4;    }
        }
    }

    typedef  CML_ACL_PACKET_DIR_T{
        type enumeration {
            enum in { value 0;    }
            enum out { value 1;    }
        }
    }

    typedef  CML_AUTH_PORT_SEC_MODE{
        type enumeration {
            enum filter { value 0;    }
            enum shutdown { value 1;    }
        }
    }

    typedef  CML_AUTH_CTRL_DIR_T{
        type enumeration {
            enum in { value 0;    }
            enum both { value 1;    }
        }
    }

    typedef  CML_AUTH_PORT_CTRL{
        type enumeration {
            enum force-unauthorized { value 0;    }
            enum force-authorized { value 1;    }
            enum auto { value 2;    }
        }
    }

    typedef  CML_DOT1X_DEBUG_T{
        type bits {
            bit event { position 0;  }
            bit timer { position 1;  }
            bit packet { position 2;  }
            bit nsm { position 3;  }
        }
    }

    typedef  CML_RIP_DEBUG_T{
        type bits {
            bit events { position 1;  }
            bit packet { position 2;  }
            bit packet-send { position 3;  }
            bit packet-recv { position 4;  }
            bit packet-detail { position 5;  }
            bit packet-send-detail { position 6;  }
            bit packet-recv-detail { position 7;  }
            bit nsm { position 8;  }
            bit rib { position 9;  }
            bit bfd { position 10;  }
        }
    }

    typedef  CML_RIP_ROUTE_T{
        type enumeration {
            enum kernel { value 1;    }
            enum connected { value 2;    }
            enum static { value 3;    }
            enum isis { value 4;    }
            enum ospf { value 5;    }
            enum bgp { value 6;    }
            enum rip { value 7;    }
            enum all { value 8;    }
        }
    }

    typedef  CML_RIP_INSTANCE_T{
        type enumeration {
            enum rip { value 1;    }
        }
    }

    typedef  CML_RIP_DIRECTION_T{
        type enumeration {
            enum in { value 0;    }
            enum out { value 1;    }
        }
    }

    typedef  CML_RIP_DIST_TYPE_T{
        type enumeration {
            enum in { value 0;    }
            enum out { value 1;    }
        }
    }

    typedef  CML_RIP_METRIC_T{
        type enumeration {
            enum disable { value 0;    }
            enum enable { value 1;    }
        }
    }

    typedef  CML_RIP_AUTH_MODE_T{
        type enumeration {
            enum text { value 2;    }
            enum md5 { value 3;    }
        }
    }

    typedef  CML_RIP_SPLIT_HORIZON_T{
        type enumeration {
            enum split-horizon { value 0;    }
            enum split-horizon-poisoned { value 1;    }
        }
    }

    typedef  CML_RIP_DEFAULT_ORIGINATE_T{
        type enumeration {
            enum originate { value 0;    }
            enum originate-always { value 1;    }
        }
    }

    typedef  CML_RIP_RECV_VERSION_TYPE_T{
        type enumeration {
            enum 1 { value 1;    }
            enum 2 { value 2;    }
            enum 1-2 { value 3;    }
            enum 2-1 { value 5;    }
        }
    }

    typedef  CML_RIP_SEND_VERSION_TYPE_T{
        type enumeration {
            enum 1 { value 1;    }
            enum 2 { value 2;    }
            enum 1-2 { value 3;    }
            enum 1-compatible { value 4;    }
            enum 2-1 { value 5;    }
        }
    }

    typedef  CML_RIP_REDIST_PROTOS_T{
        type enumeration {
            enum kernel { value 0;    }
            enum connected { value 1;    }
            enum static { value 2;    }
            enum ospf { value 3;    }
            enum isis { value 4;    }
            enum bgp { value 5;    }
        }
    }

    typedef  CML_RIP_VRF_REDIST_PROTOS_T{
        type enumeration {
            enum connected { value 1;    }
            enum static { value 2;    }
            enum ospf { value 3;    }
            enum bgp { value 5;    }
        }
    }

    typedef  CML_NSM_LOAD_TRILL_T{
        type enumeration {
            enum outer-l2 { value 1;    }
            enum inner-l2 { value 2;    }
            enum inner-l3 { value 3;    }
        }
    }

    typedef  CML_NSM_LOAD_HASH_T{
        type enumeration {
            enum crc16-bisync { value 0;    }
            enum crc16-ccitt { value 1;    }
            enum crc32-lo { value 2;    }
            enum crc32-hi { value 3;    }
        }
    }

    typedef  CML_NSM_HARDWARE_PORTMODE_T{
        type enumeration {
            enum 4X10g { value 1;    }
            enum 4X25g { value 2;    }
            enum 2X50g { value 3;    }
            enum 40g { value 4;    }
            enum 100g { value 5;    }
        }
    }

    typedef  CML_NSM_BREAKOUT_TYPE_T{
        type enumeration {
            enum 4X10g { value 1;    }
            enum 4X25g { value 2;    }
            enum 2X50g { value 3;    }
        }
    }

    typedef  CML_NSM_HARDWARE_PROFILE_PORTMODE_BUNDLE_T{
        type enumeration {
            enum 4X10g { value 6;    }
            enum 40g { value 7;    }
        }
    }

    typedef  CML_LACP_DEBUG_TYPE_T{
        type bits {
            bit event { position 0;  }
            bit cli { position 1;  }
            bit timer { position 2;  }
            bit sync { position 3;  }
            bit packet { position 4;  }
            bit tx { position 5;  }
            bit rx { position 6;  }
            bit ha { position 7;  }
        }
    }

    typedef  CML_ALLOWEDVLAN_T{
        type enumeration {
            enum none { value 1;    }
            enum all { value 2;    }
        }
    }

    typedef  CML_SWVLANOPER_T{
        type enumeration {
            enum remove { value 1;    }
            enum except { value 2;    }
        }
    }

    typedef  CML_DHCPSNOOP_DEBUG_T{
        type bits {
            bit event { position 0;  }
            bit rx { position 1;  }
            bit tx { position 2;  }
            bit packet { position 3;  }
        }
    }

    typedef  CML_DHCP_VALIDATION_T{
        type enumeration {
            enum src-mac { value 0;    }
            enum dst-mac { value 1;    }
            enum ip { value 2;    }
        }
    }

    typedef  CML_COMMON_ENABLE_DISABLE_T{
        type enumeration {
            enum Disabled { value 0;    }
            enum Enabled { value 1;    }
        }
    }

    typedef  CML_COMMON_FLAGS_T{
        type enumeration {
            enum False { value 0;    }
            enum True { value 1;    }
        }
    }

    typedef  CML_UNI_ENNI_T{
        type enumeration {
            enum uni { value 1;    }
            enum enni { value 2;    }
        }
    }

    typedef  CML_UNI_ENNI_TYPE_T{
        type enumeration {
            enum leaf { value 1;    }
            enum root { value 2;    }
            enum trunk { value 3;    }
        }
    }

    typedef  CML_UNI_SERVICE_T{
        type enumeration {
            enum bundle { value 1;    }
            enum all-to-one { value 2;    }
            enum multiplex { value 3;    }
        }
    }

    typedef  CML_UNI_ENABLE_DISABLE_T{
        type enumeration {
            enum disable { value 0;    }
            enum enable { value 1;    }
        }
    }

    typedef  CML_OEP_MAP_TYPE_T{
        type enumeration {
            enum uni-oep { value 2;    }
            enum enni-oep { value 4;    }
        }
    }

    typedef  CML_BIND_T{
        type enumeration {
            enum delete { value 0;    }
            enum add { value 1;    }
        }
    }

    typedef  CML_ETHERTYPE_T{
        type enumeration {
            enum ETHERTYPE { value 0;    }
            enum ip { value 2048;    }
            enum x25 { value 2053;    }
            enum arp { value 2054;    }
            enum g8bpqx25 { value 2303;    }
            enum ieeepup { value 2560;    }
            enum ieeeaddrtrans { value 2561;    }
            enum dec { value 24576;    }
            enum decdnadumpload { value 24577;    }
            enum decdnaremoteconsole { value 24578;    }
            enum decdnarouting { value 24579;    }
            enum declat { value 24580;    }
            enum decdiagnostics { value 24581;    }
            enum rarp { value 32821;    }
            enum atalkddp { value 32923;    }
            enum atalkaarp { value 33011;    }
            enum ipx { value 33079;    }
            enum ipv6 { value 34525;    }
            enum atmmulti { value 34892;    }
            enum pppdiscovery { value 34915;    }
            enum pppsession { value 34916;    }
            enum atmtransport { value 34948;    }
        }
    }

    typedef  CML_CE_SVLAN_T{
        type enumeration {
            enum ce-vlan { value 1;    }
            enum svlan { value 2;    }
        }
    }

    typedef  CML_OVC_TYPE_T{
        type enumeration {
            enum preserve-cos { value 1;    }
            enum preserve-vlanid { value 2;    }
        }
    }

    typedef  CML_MSTP_ENUM_T{
        type enumeration {
            enum te-msti { value 65;    }
            enum instance-spbm { value 4092;    }
            enum instance-spbv { value 4093;    }
        }
    }

    typedef  CML_MSTP_RANGE_T{
        type uint16;
    }

    typedef  CML_MSTP_INSTANCE_T{
        type union{

            type CML_MSTP_ENUM_T {

            }
            type CML_MSTP_RANGE_T {

            }
        }
    }

    typedef  CML_VXLAN_PORT_T{
        type enumeration {
            enum port-only { value 1;    }
        }
    }

    typedef  CML_RATE_LIMIT_TYPE{
        type enumeration {
            enum kbps { value 1;    }
            enum mbps { value 2;    }
            enum gbps { value 3;    }
        }
    }

    typedef  CML_RATE_LIMIT_LEVEL_T{
        type string;
    }

    typedef  CML_RATE_LIMIT_T{
        type union{

            type uint32 {
                range "0..1000000000";

            }
            type CML_RATE_LIMIT_LEVEL_T {

            }
        }
    }

    typedef  CML_HOSTP_SNMP_KEY_TYPE_T{
        type enumeration {
            enum plain { value 0;    }
            enum encrypt { value 1;    }
        }
    }

    typedef  CML_FORWARDING_PROFILE_T{
        type enumeration {
            enum l2-profile-one { value 0;    }
            enum l2-profile-two { value 1;    }
            enum l2-profile-three { value 2;    }
            enum l3-profile { value 3;    }
            enum l3-128bit-profile { value 4;    }
        }
    }

    typedef  CML_FORWARDING_PROFILE_LPM_T{
        type enumeration {
            enum lpm-profile { value 5;    }
            enum lpm-128bit-profile { value 6;    }
        }
    }

    typedef  CML_PROFILE_T{
        type enumeration {
            enum kaps-profile-one { value 1;    }
            enum kaps-profile-two { value 2;    }
            enum elk-tcam-profile-one { value 3;    }
            enum elk-tcam-profile-two { value 4;    }
        }
    }

    typedef  CML_NSM_HW_PROFILE_T{
        type enumeration {
            enum qos-group { value 1;    }
            enum ingress-l2-group { value 2;    }
            enum ingress-ipv4 { value 4;    }
            enum egress-ipv4 { value 8;    }
            enum egress-ipv6 { value 16;    }
            enum egress-l2-group { value 64;    }
        }
    }

    typedef  CML_NSM_CONFIG_MODE_T{
        type bits {
            bit nsm-bfd { position 2;  }
            bit nsm-events { position 3;  }
            bit nsm-packet { position 7;  }
            bit nsm-packet-detail { position 8;  }
            bit nsm-packet-recv { position 9;  }
            bit nsm-packet-recv-detail { position 10;  }
            bit nsm-packet-send { position 11;  }
            bit nsm-packet-send-detail { position 12;  }
            bit nsm-vxlan { position 14;  }
        }
    }

    typedef  CML_NSM_EXEC_MODE_T{
        type bits {
            bit nsm-bfd { position 2;  }
            bit nsm-events { position 3;  }
            bit nsm-hal-ipc { position 5;  }
            bit nsm-packet { position 7;  }
            bit nsm-packet-detail { position 8;  }
            bit nsm-packet-recv { position 9;  }
            bit nsm-packet-recv-detail { position 10;  }
            bit nsm-packet-send { position 11;  }
            bit nsm-packet-send-detail { position 12;  }
            bit nsm-hal-0 { position 13;  }
            bit nsm-vxlan { position 14;  }
        }
    }

    typedef  CML_NSM_PKT_MGR_T{
        type bits {
            bit pktmgr { position 1;  }
            bit pktmgr-l2-protocol-cfm { position 2;  }
            bit pktmgr-l2-protocol-eapol { position 3;  }
            bit pktmgr-l2-protocol-efm { position 4;  }
            bit pktmgr-l2-protocol-igmp-snoop { position 5;  }
            bit pktmgr-l2-protocol-lacp { position 6;  }
            bit pktmgr-l2-protocol-lldp { position 7;  }
            bit pktmgr-l2-protocol-mldp-snoop { position 8;  }
            bit pktmgr-l2-protocol-mstp { position 9;  }
            bit pktmgr-l2-protocol-ptp { position 10;  }
        }
    }

    typedef  CML_MSTP_DEBUG_T{
        type bits {
            bit mstp-protocol { position 1;  }
            bit mstp-protocol-detail { position 2;  }
            bit mstp-timer { position 3;  }
            bit mstp-timer-detail { position 4;  }
            bit mstp-packet-tx { position 5;  }
            bit mstp-packet-rx { position 6;  }
            bit mstp-cli { position 7;  }
            bit mstp-bpdu { position 8;  }
            bit mstp-mcec { position 9;  }
        }
    }

    typedef  CML_EXEC_MSTP_T{
        type enumeration {
            enum stats { value 1;    }
            enum pkt-errors { value 2;    }
        }
    }

    typedef  CML_SFLOW_DEBUG_TYPE_T{
        type bits {
            bit agent { position 0;  }
            bit sampling { position 1;  }
            bit polling { position 2;  }
        }
    }

    typedef  CML_URPF_MODE_T{
        type enumeration {
            enum any { value 1;    }
            enum rx { value 2;    }
        }
    }

    typedef  CML_MACTYPE_T{
        type enumeration {
            enum static { value 0;    }
            enum multicast { value 2;    }
        }
    }

    typedef  CML_INT_TRACK_MATCH_TYPE_T{
        type enumeration {
            enum all { value 1;    }
            enum any { value 2;    }
        }
    }

    typedef  CML_INT_TRACK_STATE_TYPE_T{
        type enumeration {
            enum down { value 1;    }
            enum up { value 2;    }
        }
    }

    typedef  CML_PMIRROR_SESS_TYPE_T{
        type enumeration {
            enum local { value 1;    }
            enum remote { value 2;    }
        }
    }

    typedef  CML_PMIRROR_STATE_T{
        type enumeration {
            enum shut { value 0;    }
            enum no-shut { value 1;    }
        }
    }

    typedef  CML_PMIRROR_DIR_T{
        type bits {
            bit rx { position 0;  }
            bit tx { position 1;  }
        }
    }

    typedef  CML_PMIRROR_ALT_DIR_T{
        type bits {
            bit receive { position 0;  }
            bit transmit { position 1;  }
        }
    }

    typedef  CML_PMIRROR_ALL_SESS_T{
        type enumeration {
            enum all { value 0;    }
        }
    }

    typedef  CML_PMIRROR_SESS_T{
        type union{

            type CML_PMIRROR_ALL_SESS_T {

            }
            type uint32 {
                range "1..18";

            }
        }
    }

    typedef  CML_TUNNEL_STATUS_T{
        type enumeration {
            enum Un-Resolved { value 1;    }
            enum Installed { value 2;    }
            enum Resolved { value 3;    }
        }
    }

    typedef  CML_RSVP_TRUNK_FAMILY_T{
        type enumeration {
            enum gmpls { value 1;    }
            enum ipv4 { value 2;    }
            enum ipv6 { value 10;    }
        }
    }

    typedef  CML_RSVP_FRR_PROTECTION_T{
        type enumeration {
            enum one-to-one { value 1;    }
        }
    }

    typedef  CML_RSVP_ADMIN_TYPE_T{
        type enumeration {
            enum exclude-any { value 0;    }
            enum include-any { value 1;    }
        }
    }

    typedef  CML_RSVP_IGP_T{
        type enumeration {
            enum disable-igp-shortcut { value 0;    }
            enum enable-igp-shortcut { value 1;    }
        }
    }

    typedef  CML_RSVP_EXCLUDE_PATH_TYPE_T{
        type enumeration {
            enum link { value 1;    }
            enum node { value 2;    }
        }
    }

    typedef  CML_RSVP_SESS_TYEP_T{
        type enumeration {
            enum secondary { value 0;    }
            enum primary { value 1;    }
        }
    }

    typedef  CML_RSVP_AFFINITY_T{
        type enumeration {
            enum no-affinity { value 0;    }
            enum affinity { value 1;    }
        }
    }

    typedef  CML_RSVP_RECORD_T{
        type enumeration {
            enum no-record { value 0;    }
            enum record { value 1;    }
        }
    }

    typedef  CML_BFD_MULTI_HOP_TYPE_T{
        type enumeration {
            enum multihop { value 1;    }
        }
    }

    typedef  CML_RIPNG_DEBUG_T{
        type bits {
            bit events { position 1;  }
            bit packet-send { position 2;  }
            bit packet-recv { position 3;  }
            bit nsm { position 5;  }
            bit rib { position 6;  }
        }
    }

    typedef  CML_RIPNG_SPLIT_HORIZON_T{
        type enumeration {
            enum split-horizon { value 0;    }
            enum split-horizon-poisoned { value 1;    }
        }
    }

    typedef  CML_RIPNG_INSTANCE_T{
        type enumeration {
            enum rip { value 1;    }
        }
    }

    typedef  CML_RIPNG_REDIST_PROTOS_T{
        type enumeration {
            enum kernel { value 0;    }
            enum connected { value 1;    }
            enum static { value 2;    }
            enum ospf6 { value 3;    }
            enum isis { value 4;    }
            enum bgp { value 5;    }
        }
    }

    typedef  CML_RIPNG_VRF_REDIST_PROTOS_T{
        type enumeration {
            enum connected { value 1;    }
            enum static { value 2;    }
            enum ospf6 { value 3;    }
            enum bgp { value 5;    }
        }
    }

    typedef  CML_RIPNG_FILTERING_T{
        type enumeration {
            enum in { value 0;    }
            enum out { value 1;    }
        }
    }

    typedef  CML_RIPNG_ROUTE_T{
        type enumeration {
            enum kernel { value 1;    }
            enum connected { value 2;    }
            enum static { value 3;    }
            enum isis { value 4;    }
            enum ospf6 { value 5;    }
            enum bgp { value 6;    }
            enum rip { value 7;    }
            enum all { value 8;    }
        }
    }

    typedef  CML_CONFIDENCETYPE_T{
        type enumeration {
            enum native { value 1;    }
            enum decap { value 2;    }
            enum static { value 3;    }
        }
    }

    typedef  CML_ESADI_T{
        type enumeration {
            enum enable { value 1;    }
            enum disable { value 2;    }
        }
    }

    typedef  CML_TRILL_T{
        type enumeration {
            enum disable { value 0;    }
            enum enable { value 1;    }
        }
    }

    typedef  CML_ISUNICAST_T{
        type enumeration {
            enum multicast { value 0;    }
            enum unicast { value 1;    }
        }
    }

    typedef  CML_CONFIGTYPE_T{
        type enumeration {
            enum broadcast { value 1;    }
            enum point-to-point { value 2;    }
        }
    }

    typedef  CML_VLAN_ENUM_T{
        type enumeration {
            enum all { value 4095;    }
        }
    }

    typedef  CML_VLAN_RANGE_T{
        type uint16;
    }

    typedef  CML_STARTVIDESADI_T{
        type union{

            type CML_VLAN_ENUM_T {

            }
            type CML_VLAN_RANGE_T {

            }
        }
    }

    typedef  CML_NSM_DCB_QCN_MODE_T{
        type enumeration {
            enum admin { value 1;    }
            enum auto { value 2;    }
            enum component { value 3;    }
        }
    }

    typedef  CML_MAPPING_TYPE_T{
        type enumeration {
            enum admin { value 1;    }
            enum auto { value 2;    }
            enum component { value 3;    }
        }
    }

    typedef  CML_ETS_MODE_T{
        type enumeration {
            enum on { value 1;    }
            enum auto { value 2;    }
        }
    }

    typedef  CML_DCBSTATE_T{
        type enumeration {
            enum off { value 0;    }
            enum on { value 1;    }
        }
    }

    typedef  CML_PRIOFLAG_T{
        type enumeration {
            enum remove { value 0;    }
            enum add { value 1;    }
        }
    }

    typedef  CML_PROTOID_T{
        type enumeration {
            enum tcp { value 2;    }
            enum udp { value 3;    }
            enum both-tcp-udp { value 4;    }
            enum neither-tcp-udp { value 5;    }
        }
    }

    typedef  CML_DEFENSEMODE_T{
        type enumeration {
            enum disabled { value 1;    }
            enum interior { value 2;    }
            enum interior-ready { value 3;    }
            enum edge { value 4;    }
        }
    }

    typedef  CML_LOADSHARE_T{
        type string;
    }

    typedef  CML_PBR_LOADSHARE_T{
        type union{

            type CML_IPV4_ADDR_T {

            }
            type CML_LOADSHARE_T {

            }
        }
    }

    typedef  CML_PBR_V6_LOADSHARE_T{
        type union{

            type CML_IPV6_ADDR_T {

            }
            type CML_LOADSHARE_T {

            }
        }
    }

    typedef  CML_DEBUG_EVENT_T{
        type enumeration {
            enum event { value 1;    }
            enum packet { value 2;    }
        }
    }

    typedef  CML_VRF_ENUM_T{
        type enumeration {
            enum all { value 1;    }
            enum default { value 2;    }
        }
    }

    typedef  CML_VRF_STRING_T{
        type string;
    }

    typedef  CML_VRF_NAME_T{
        type union{

            type CML_VRF_ENUM_T {

            }
            type CML_VRF_STRING_T {

            }
        }
    }

    typedef  CML_ADJNBR_T{
        type enumeration {
            enum adjacency { value 1;    }
            enum neighbor { value 2;    }
        }
    }

    typedef  CML_MPLS_VCLINKMODE_T{
        type enumeration {
            enum primary { value 0;    }
            enum secondary { value 16;    }
        }
    }

    typedef  CML_VR_CONFIG_T{
        type enumeration {
            enum read { value 0;    }
            enum write { value 1;    }
        }
    }

    typedef  CML_STATIC_BFD_ENABLE_DISABLE_T{
        type enumeration {
            enum fall-over-bfd-disable { value 0;    }
            enum fall-over-bfd { value 1;    }
        }
    }

}
