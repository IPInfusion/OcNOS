/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-ldp.yang
*
*/

submodule zebos-ldp {

    belongs-to  zebos { prefix zebos; }

    import cml_data_types {
        prefix cml_data_types;
    }

    import feature_list {
        prefix feature_list;
    }

    include zebos-interface;
    organization
        "IP Infusion Inc.";

    contact
        "Address: 3965 Freedom Circle, Suite 200, Santa Clara, CA 95054
        Phone: +1 408-400-1900
        E-mail: support@ipinfusion.com
        Web: http://www.ipinfusion.com/";


    revision "2017-04-18" {
        description "restart command helpstring change.";
    }

    revision "2017-01-11" {
        description "Ported changes from XP-master.";
    }

    revision "2016-10-10" {
        description "Added config and runtime attributes of LDP module.";
    }



    grouping ldpInterface-grouping {
        list ldpInterface {
            key "ifName";
            description
                "LDP interface related operations";
            leaf vrId  {
                type  cml_data_types:CML_INT32_T;
                default "0";
                description "";
            } // END of vrId definition.

            leaf ifName  {
                type  cml_data_types:CML_STRING_T {
                    length "0..255";
                }
                description "";
            } // END of ifName definition.

            uses ldpInterfaceGrouping;
        } // End of ldpInterface-list
    } // END of ldpInterface-grouping definition.
    grouping ldpVcAttrGrouping {
        description
            "ldpVcAttrGrouping";
        container ldpVcAttr {
            config false;
            description
                "ldpVcAttr";
            leaf grpId  {
                type  cml_data_types:CML_UINT32_T;
                description "";
            } // END of grpId definition.

            leaf pwStatusCap  {
                type  cml_data_types:CML_BOOL_T;
                description "";
            } // END of pwStatusCap definition.

            leaf ifmtu  {
                type  cml_data_types:CML_UINT16_T;
                description "";
            } // END of ifmtu definition.

            leaf ifpayloadBytes  {
                if-feature feature_list:HAVE_TDM_VC;
                type  cml_data_types:CML_UINT16_T;
                description "";
            } // END of ifpayloadBytes definition.

            leaf ifbitRate  {
                if-feature feature_list:HAVE_TDM_VC;
                type  cml_data_types:CML_UINT32_T;
                description "";
            } // END of ifbitRate definition.

            leaf cWord  {
                type  cml_data_types:CML_STRING_T {
                    length "0..255";
                }
                description "";
            } // END of cWord definition.

            leaf configuredCWord  {
                type  cml_data_types:CML_STRING_T {
                    length "0..255";
                }
                description "";
            } // END of configuredCWord definition.

            leaf ccTypes  {
                type  cml_data_types:CML_STRING_T {
                    length "0..255";
                }
                description "";
            } // END of ccTypes definition.

            leaf cvTypes  {
                type  cml_data_types:CML_STRING_T {
                    length "0..255";
                }
                description "";
            } // END of cvTypes definition.

        } // END of ldpVcAttr-container definition.
    } // END of ldpVcAttrGrouping definition.
    grouping ldpVcGrouping {
        description
            "ldpVcGrouping";

        list ldpVc {
            key "vcId";
            config false;
            description
                "ldpVc";
            leaf vcId  {
                type  cml_data_types:CML_UINT32_T;
                description "";
            } // END of vcId definition.

            leaf vcIfIndex  {
                type  cml_data_types:CML_UINT32_T;
                description "";
            } // END of vcIfIndex definition.

            leaf nbrAddr  {
                type  cml_data_types:CML_STRING_T {
                    length "0..255";
                }
                description "";
            } // END of nbrAddr definition.

            leaf vcRefCount  {
                type  cml_data_types:CML_INT32_T;
                description "";
            } // END of vcRefCount definition.

            leaf agi  {
                type  cml_data_types:CML_STRING_T {
                    length "0..255";
                }
                description "";
            } // END of agi definition.

            leaf saii  {
                type  cml_data_types:CML_STRING_T {
                    length "0..255";
                }
                description "";
            } // END of saii definition.

            leaf taii  {
                type  cml_data_types:CML_STRING_T {
                    length "0..255";
                }
                description "";
            } // END of taii definition.

            leaf fecTypeVc  {
                type  cml_data_types:CML_UINT8_T;
                description "";
            } // END of fecTypeVc definition.

            leaf vplsId  {
                type  cml_data_types:CML_UINT32_T;
                description "";
            } // END of vplsId definition.

            leaf grpId  {
                type  cml_data_types:CML_UINT32_T;
                description "";
            } // END of grpId definition.

            leaf vlanId  {
                type  cml_data_types:CML_UINT16_T;
                description "";
            } // END of vlanId definition.

            leaf flag  {
                type  cml_data_types:CML_UINT8_T;
                description "";
            } // END of flag definition.

            leaf state  {
                type  cml_data_types:CML_UINT8_T;
                description "";
            } // END of state definition.

            leaf pwStatus  {
                type  cml_data_types:CML_UINT32_T;
                description "";
            } // END of pwStatus definition.

            leaf remotePwStatus  {
                type  cml_data_types:CML_UINT32_T;
                description "";
            } // END of remotePwStatus definition.

            leaf withdrawLabel  {
                type  cml_data_types:CML_UINT32_T;
                description "";
            } // END of withdrawLabel definition.

            leaf msPwRole  {
                type  cml_data_types:CML_UINT8_T;
                description "";
            } // END of msPwRole definition.

            leaf shutdown  {
                type  cml_data_types:CML_BOOL_T;
                description "";
            } // END of shutdown definition.


            list dcbList {
                key "dummy";
                config false;
                description
                    "dcbList";
                leaf dummy  {
                    type  cml_data_types:CML_INT32_T;
                    description "";
                } // END of dummy definition.

                leaf sessionPeerId  {
                    type  cml_data_types:CML_STRING_T {
                        length "0..255";
                    }
                    description "";
                } // END of sessionPeerId definition.

                leaf ifName  {
                    type  cml_data_types:CML_STRING_T {
                        length "0..255";
                    }
                    description "";
                } // END of ifName definition.

                leaf type  {
                    type  cml_data_types:CML_UINT8_T;
                    description "";
                } // END of type definition.

                leaf state  {
                    type  cml_data_types:CML_UINT8_T;
                    description "";
                } // END of state definition.

                leaf status  {
                    type  cml_data_types:CML_UINT8_T;
                    description "";
                } // END of status definition.

                leaf shutdown  {
                    type  cml_data_types:CML_UINT8_T;
                    description "";
                } // END of shutdown definition.

                leaf vplsId  {
                    type  cml_data_types:CML_UINT32_T;
                    description "";
                } // END of vplsId definition.

                leaf labelId  {
                    type  cml_data_types:CML_UINT32_T;
                    description "";
                } // END of labelId definition.

                leaf vcType  {
                    type  cml_data_types:CML_UINT16_T;
                    description "";
                } // END of vcType definition.

                uses ldpVcAttrGrouping;
            } // End of dcbList-list
            container ucb {
                config false;
                description
                    "ucb";
                leaf sessionPeerId  {
                    type  cml_data_types:CML_STRING_T {
                        length "0..255";
                    }
                    description "";
                } // END of sessionPeerId definition.

                leaf ifName  {
                    type  cml_data_types:CML_STRING_T {
                        length "0..255";
                    }
                    description "";
                } // END of ifName definition.

                leaf type  {
                    type  cml_data_types:CML_UINT8_T;
                    description "";
                } // END of type definition.

                leaf state  {
                    type  cml_data_types:CML_UINT8_T;
                    description "";
                } // END of state definition.

                leaf status  {
                    type  cml_data_types:CML_UINT8_T;
                    description "";
                } // END of status definition.

                leaf shutdown  {
                    type  cml_data_types:CML_UINT8_T;
                    description "";
                } // END of shutdown definition.

                leaf vplsId  {
                    type  cml_data_types:CML_UINT32_T;
                    description "";
                } // END of vplsId definition.

                leaf labelId  {
                    type  cml_data_types:CML_UINT32_T;
                    description "";
                } // END of labelId definition.

                leaf vcType  {
                    type  cml_data_types:CML_UINT16_T;
                    description "";
                } // END of vcType definition.

                leaf agi  {
                    type  cml_data_types:CML_STRING_T {
                        length "0..255";
                    }
                    description "";
                } // END of agi definition.

                leaf saii  {
                    type  cml_data_types:CML_STRING_T {
                        length "0..255";
                    }
                    description "";
                } // END of saii definition.

                leaf taii  {
                    type  cml_data_types:CML_STRING_T {
                        length "0..255";
                    }
                    description "";
                } // END of taii definition.

                uses ldpVcAttrGrouping;
            } // END of ucb-container definition.
        } // End of ldpVc-list
    } // END of ldpVcGrouping definition.
    grouping ldpFecCbGrouping {
        description
            "ldpFecCbGrouping";
        leaf family  {
            type  cml_data_types:CML_UINT8_T;
            config false;
            description "";
        } // END of family definition.


        list ldpRt {
            key "fecNextHopAddr";
            config false;
            description
                "ldpRt";
            leaf fecNextHopAddr  {
                type  cml_data_types:CML_STRING_T {
                    length "0..255";
                }
                description "";
            } // END of fecNextHopAddr definition.

            leaf family  {
                type  cml_data_types:CML_UINT8_T;
                description "";
            } // END of family definition.

            leaf type  {
                type  cml_data_types:CML_INT32_T;
                description "";
            } // END of type definition.

            leaf ifIndex  {
                type  cml_data_types:CML_UINT32_T;
                description "";
            } // END of ifIndex definition.

        } // End of ldpRt-list
        uses ldpFecGrouping;
        uses ldpCrAttrGrouping;
        uses dcbListGrouping;
    } // END of ldpFecCbGrouping definition.
    grouping ldpFecGrouping {
        description
            "ldpFecGrouping";
        container ldpFec {
            config false;
            description
                "ldpFec";
            leaf rowStatus  {
                type  cml_data_types:CML_UINT32_T;
                description "";
            } // END of rowStatus definition.

            leaf storType  {
                type  cml_data_types:CML_UINT32_T;
                description "";
            } // END of storType definition.

            leaf prefix  {
                type  cml_data_types:CML_STRING_T {
                    length "0..255";
                }
                description "";
            } // END of prefix definition.

            leaf mplsFecAddrPrefixLength  {
                type  cml_data_types:CML_UINT32_T;
                description "";
            } // END of mplsFecAddrPrefixLength definition.

            leaf mplsFecAddrType  {
                type  cml_data_types:CML_STRING_T {
                    length "0..255";
                }
                description "";
            } // END of mplsFecAddrType definition.

            leaf agi  {
                type  cml_data_types:CML_STRING_T {
                    length "0..255";
                }
                description "";
            } // END of agi definition.

            leaf saii  {
                type  cml_data_types:CML_STRING_T {
                    length "0..255";
                }
                description "";
            } // END of saii definition.

            leaf taii  {
                type  cml_data_types:CML_STRING_T {
                    length "0..255";
                }
                description "";
            } // END of taii definition.

            leaf fecType  {
                type  cml_data_types:CML_UINT8_T;
                description "";
            } // END of fecType definition.

        } // END of ldpFec-container definition.
    } // END of ldpFecGrouping definition.
    grouping ldpCrAttrGrouping {
        description
            "ldpCrAttrGrouping";
        container ldpCrAttr {
            config false;
            description
                "ldpCrAttr";
            leaf frequency  {
                type  cml_data_types:CML_UINT8_T;
                description "";
            } // END of frequency definition.

            leaf weight  {
                type  cml_data_types:CML_UINT8_T;
                description "";
            } // END of weight definition.

            leaf pdr  {
                type  cml_data_types:CML_INT32_T;
                description "";
            } // END of pdr definition.

            leaf pbs  {
                type  cml_data_types:CML_INT32_T;
                description "";
            } // END of pbs definition.

            leaf cdr  {
                type  cml_data_types:CML_INT32_T;
                description "";
            } // END of cdr definition.

            leaf cbs  {
                type  cml_data_types:CML_INT32_T;
                description "";
            } // END of cbs definition.

            leaf ebs  {
                type  cml_data_types:CML_INT32_T;
                description "";
            } // END of ebs definition.

            leaf setPrio  {
                type  cml_data_types:CML_UINT8_T;
                description "";
            } // END of setPrio definition.

            leaf holdPrio  {
                type  cml_data_types:CML_UINT8_T;
                description "";
            } // END of holdPrio definition.

            leaf resourceCLass  {
                type  cml_data_types:CML_UINT32_T;
                description "";
            } // END of resourceCLass definition.

            leaf routePinnig  {
                type  cml_data_types:CML_UINT8_T;
                description "";
            } // END of routePinnig definition.

            leaf attrFlag  {
                type  cml_data_types:CML_UINT8_T;
                description "";
            } // END of attrFlag definition.

            leaf egress  {
                type  cml_data_types:CML_STRING_T {
                    length "0..255";
                }
                description "";
            } // END of egress definition.


            list er {
                key "hopAddr";
                config false;
                description
                    "er";
                leaf hopAddr  {
                    type  cml_data_types:CML_STRING_T {
                        length "0..255";
                    }
                    description "";
                } // END of hopAddr definition.

                leaf erLoose  {
                    type  cml_data_types:CML_UINT8_T;
                    description "";
                } // END of erLoose definition.

            } // End of er-list
        } // END of ldpCrAttr-container definition.
    } // END of ldpCrAttrGrouping definition.
    grouping ldpAdjacencyGrouping {
        description
            "ldpAdjacencyGrouping";

        list adjacency {
            key "prefix";
            config false;
            description
                "adjacency";
            leaf prefix  {
                type  cml_data_types:CML_STRING_T {
                    length "0..255";
                }
                description "";
            } // END of prefix definition.

            leaf peer  {
                type  cml_data_types:CML_STRING_T {
                    length "0..255";
                }
                description "";
            } // END of peer definition.

            leaf peerTcp  {
                type  cml_data_types:CML_STRING_T {
                    length "0..255";
                }
                description "";
            } // END of peerTcp definition.

            leaf peerAddrType  {
                type  cml_data_types:CML_INT32_T;
                description "";
            } // END of peerAddrType definition.

            leaf ifName  {
                type  cml_data_types:CML_STRING_T {
                    length "0..255";
                }
                description "";
            } // END of ifName definition.

            leaf passwdType  {
                if-feature feature_list:HAVE_TCP_MD5SIG;
                type  cml_data_types:CML_UINT8_T;
                description "";
            } // END of passwdType definition.

            leaf passwd  {
                if-feature feature_list:HAVE_TCP_MD5SIG;
                type  cml_data_types:CML_STRING_T {
                    length "0..255";
                }
                description "";
            } // END of passwd definition.

            leaf lsrId  {
                type  cml_data_types:CML_UINT32_T;
                description "";
            } // END of lsrId definition.

            leaf labelSpace  {
                type  cml_data_types:CML_UINT16_T;
                description "";
            } // END of labelSpace definition.

            leaf helloReceived  {
                if-feature feature_list:HAVE_SNMP;
                type  cml_data_types:CML_STRING_T {
                    length "0..255";
                }
                description "";
            } // END of helloReceived definition.

            leaf holdTimeRem  {
                type  cml_data_types:CML_INT32_T;
                description "";
            } // END of holdTimeRem definition.

            leaf holdTime  {
                type  cml_data_types:CML_INT32_T;
                description "";
            } // END of holdTime definition.

            leaf adjType  {
                type  cml_data_types:CML_UINT32_T;
                description "";
            } // END of adjType definition.

            leaf targetedPeer  {
                type  cml_data_types:CML_UINT8_T;
                description "";
            } // END of targetedPeer definition.

            leaf family  {
                type  cml_data_types:CML_UINT8_T;
                description "";
            } // END of family definition.

        } // End of adjacency-list
    } // END of ldpAdjacencyGrouping definition.
    grouping ldpSessionGrouping {
        description
            "ldpSessionGrouping";

        list ldpSession {
            key "peerAddr";
            config false;
            description
                "ldpSession";
            leaf peerAddr  {
                type  cml_data_types:CML_STRING_T {
                    length "0..255";
                }
                description "";
            } // END of peerAddr definition.

            leaf reconnectTimeout  {
                type  cml_data_types:CML_UINT32_T;
                description "";
            } // END of reconnectTimeout definition.

            leaf recoveryTime  {
                type  cml_data_types:CML_UINT32_T;
                description "";
            } // END of recoveryTime definition.

            leaf reconnectInterval  {
                type  cml_data_types:CML_INT32_T;
                description "";
            } // END of reconnectInterval definition.

            leaf peerType  {
                type  cml_data_types:CML_UINT32_T;
                description "";
            } // END of peerType definition.

            leaf lastStateChange  {
                type  cml_data_types:CML_UINT32_T;
                description "";
            } // END of lastStateChange definition.

            leaf keepaliveHoldTime  {
                type  cml_data_types:CML_UINT32_T;
                description "";
            } // END of keepaliveHoldTime definition.

            leaf keepaliveTimeout  {
                type  cml_data_types:CML_UINT32_T;
                description "";
            } // END of keepaliveTimeout definition.

            leaf discontinuityTime  {
                type  cml_data_types:CML_UINT32_T;
                description "";
            } // END of discontinuityTime definition.

            leaf pduLength  {
                type  cml_data_types:CML_UINT32_T;
                description "";
            } // END of pduLength definition.

            leaf state  {
                type  cml_data_types:CML_UINT8_T;
                description "";
            } // END of state definition.

            leaf oldState  {
                type  cml_data_types:CML_UINT8_T;
                description "";
            } // END of oldState definition.

            leaf role  {
                type  cml_data_types:CML_UINT8_T;
                description "";
            } // END of role definition.

            leaf gracefulRestartCap  {
                if-feature feature_list:HAVE_RESTART;
                type  cml_data_types:CML_UINT8_T;
                description "";
            } // END of gracefulRestartCap definition.

            leaf grflags  {
                if-feature feature_list:HAVE_RESTART;
                type  cml_data_types:CML_UINT8_T;
                description "";
            } // END of grflags definition.

            leaf advMode  {
                type  cml_data_types:CML_UINT8_T;
                description "";
            } // END of advMode definition.

            leaf retentionMode  {
                type  cml_data_types:CML_UINT8_T;
                description "";
            } // END of retentionMode definition.

            leaf fecAdvEnabled  {
                type  cml_data_types:CML_UINT8_T;
                description "";
            } // END of fecAdvEnabled definition.

            leaf tcpEstablished  {
                type  cml_data_types:CML_UINT8_T;
                description "";
            } // END of tcpEstablished definition.

            leaf statusRecord  {
                type  cml_data_types:CML_UINT8_T;
                description "";
            } // END of statusRecord definition.

            leaf ldpifName  {
                type  cml_data_types:CML_STRING_T {
                    length "0..255";
                }
                description "";
            } // END of ldpifName definition.


            list remoteAddr {
                key "prefixAddr";
                config false;
                description
                    "remoteAddr";
                leaf prefixAddr  {
                    type  cml_data_types:CML_STRING_T {
                        length "0..255";
                    }
                    description "";
                } // END of prefixAddr definition.

            } // End of remoteAddr-list
            container id {
                config false;
                description
                    "id";
                leaf lsrId  {
                    type  cml_data_types:CML_UINT32_T;
                    description "";
                } // END of lsrId definition.

                leaf labelSpace  {
                    type  cml_data_types:CML_UINT16_T;
                    description "";
                } // END of labelSpace definition.

            } // END of id-container definition.
            uses ldpAdjacencyGrouping;
            uses ucbListGrouping;
            uses dcbListGrouping;
        } // End of ldpSession-list
    } // END of ldpSessionGrouping definition.
    grouping ucbListGrouping {
        description
            "ucbListGrouping";

        list ucbList {
            key "ucbLabelRequestId";
            config false;
            description
                "ucbList";
            leaf ucbLabelRequestId  {
                type  cml_data_types:CML_UINT32_T;
                description "";
            } // END of ucbLabelRequestId definition.

            leaf ucbLabel  {
                type  cml_data_types:CML_STRING_T {
                    length "0..255";
                }
                description "";
            } // END of ucbLabel definition.

            leaf requestAttr  {
                type  cml_data_types:CML_STRING_T {
                    length "0..255";
                }
                description "";
            } // END of requestAttr definition.

            leaf fecPrefix  {
                type  cml_data_types:CML_STRING_T {
                    length "0..255";
                }
                description "";
            } // END of fecPrefix definition.

            leaf state  {
                type  cml_data_types:CML_UINT8_T;
                description "";
            } // END of state definition.


            list dcbList {
                key "dcbLabelRequestId";
                config false;
                description
                    "dcbList";
                leaf dcbLabelRequestId  {
                    type  cml_data_types:CML_UINT32_T;
                    description "";
                } // END of dcbLabelRequestId definition.

                leaf dcbLabel  {
                    type  cml_data_types:CML_STRING_T {
                        length "0..255";
                    }
                    description "";
                } // END of dcbLabel definition.

            } // End of dcbList-list
        } // End of ucbList-list
    } // END of ucbListGrouping definition.
    grouping dcbListGrouping {
        description
            "dcbListGrouping";

        list dcbList {
            key "dcbLabelRequestId";
            config false;
            description
                "dcbList";
            leaf dcbLabelRequestId  {
                type  cml_data_types:CML_UINT32_T;
                description "";
            } // END of dcbLabelRequestId definition.

            leaf dcbLabel  {
                type  cml_data_types:CML_STRING_T {
                    length "0..255";
                }
                description "";
            } // END of dcbLabel definition.

            leaf mappingAttr  {
                type  cml_data_types:CML_STRING_T {
                    length "0..255";
                }
                description "";
            } // END of mappingAttr definition.

            leaf labelReleased  {
                type  cml_data_types:CML_UINT8_T;
                description "";
            } // END of labelReleased definition.

            leaf labelReleasedReceived  {
                type  cml_data_types:CML_UINT8_T;
                description "";
            } // END of labelReleasedReceived definition.

            leaf state  {
                type  cml_data_types:CML_UINT8_T;
                description "";
            } // END of state definition.


            list ucbList {
                key "ucbLabelRequestId";
                config false;
                description
                    "ucbList";
                leaf ucbLabelRequestId  {
                    type  cml_data_types:CML_UINT32_T;
                    description "";
                } // END of ucbLabelRequestId definition.

                leaf ucbLabel  {
                    type  cml_data_types:CML_STRING_T {
                        length "0..255";
                    }
                    description "";
                } // END of ucbLabel definition.

            } // End of ucbList-list

            list nexthop {
                key "nexthopAddr";
                config false;
                description
                    "nexthop";
                leaf nexthopAddr  {
                    type  cml_data_types:CML_STRING_T {
                        length "0..255";
                    }
                    description "";
                } // END of nexthopAddr definition.

                leaf ifindexNh  {
                    type  cml_data_types:CML_UINT32_T;
                    description "";
                } // END of ifindexNh definition.

            } // End of nexthop-list
        } // End of dcbList-list
    } // END of dcbListGrouping definition.
    grouping ldpInterfaceGrouping {
        description
            "ldpInterfaceGrouping";
        leaf primaryAddr  {
            type  cml_data_types:CML_STRING_T {
                length "0..255";
            }
            config false;
            description "";
        } // END of primaryAddr definition.

        leaf primaryAddr6  {
            type  cml_data_types:CML_STRING_T {
                length "0..255";
            }
            config false;
            description "";
        } // END of primaryAddr6 definition.

        leaf owner  {
            type  cml_data_types:CML_UINT8_T;
            config false;
            description "";
        } // END of owner definition.

        leaf pduLength  {
            type  cml_data_types:CML_UINT32_T {
                 range "256..65535";
            }
            default "4096";
            description "";
        } // END of pduLength definition.

        leaf interfaceType  {
            type  cml_data_types:CML_UINT16_T;
            config false;
            description "";
        } // END of interfaceType definition.

        leaf ifHelloInterval  {
            type  cml_data_types:CML_UINT16_T {
                 range "1..21845";
            }
            default "5";
            description "";
        } // END of ifHelloInterval definition.

        leaf ifHoldTime  {
            type  cml_data_types:CML_UINT16_T {
                 range "3..65535";
            }
            default "15";
            description "";
        } // END of ifHoldTime definition.

        leaf ifKeepaliveInterval  {
            type  cml_data_types:CML_UINT16_T {
                 range "10..21845";
            }
            description "";
        } // END of ifKeepaliveInterval definition.

        leaf ifKeepaliveTimeout  {
            type  cml_data_types:CML_UINT16_T {
                 range "30..65535";
            }
            description "";
        } // END of ifKeepaliveTimeout definition.

        leaf syncDelayInterval  {
            type  cml_data_types:CML_UINT32_T {
                 range "5..60";
            }
            description "";
        } // END of syncDelayInterval definition.

        leaf multicastHellosFlag  {
            type  cml_data_types:CML_BOOL_T;
            description "";
        } // END of multicastHellosFlag definition.

        leaf ifAdvMode  {
            type  cml_data_types:CML_LDP_ADVERTISE_MODE_T;
            description "";
        } // END of ifAdvMode definition.

        leaf ifRetentionMode  {
            type  cml_data_types:CML_LDP_LABEL_T;
            default "liberal";
            description "";
        } // END of ifRetentionMode definition.

        leaf labelMergeCap  {
            type  cml_data_types:CML_STRING_T {
                length "0..255";
            }
            config false;
            description "";
        } // END of labelMergeCap definition.

        leaf addrflag  {
            type  cml_data_types:CML_UINT8_T;
            config false;
            description "";
        } // END of addrflag definition.

        leaf addrflag6  {
            type  cml_data_types:CML_UINT8_T;
            config false;
            description "";
        } // END of addrflag6 definition.

        leaf enableInterfaceIpv4  {
            type  cml_data_types:CML_LDP_ENABLE_IPV4_TYPE_T;
            description "";
        } // END of enableInterfaceIpv4 definition.

        leaf enableInterfaceIpv6  {
            type  cml_data_types:CML_LDP_ENABLE_IPV6_TYPE_T;
            description "";
        } // END of enableInterfaceIpv6 definition.

        leaf igpSync  {
            type  cml_data_types:CML_LDP_IGP_SYNC_T;
            default "igp-sync";
            description "";
        } // END of igpSync definition.

        leaf enableFamily  {
            type  cml_data_types:CML_UINT8_T;
            config false;
            description "";
        } // END of enableFamily definition.

        container lAddr {
            config false;
            description
                "lAddr";
            leaf refcountLAddr  {
                type  cml_data_types:CML_INT32_T;
                description "";
            } // END of refcountLAddr definition.

            leaf labelSpace  {
                type  cml_data_types:CML_UINT16_T;
                description "";
            } // END of labelSpace definition.

            leaf addr4  {
                type  cml_data_types:CML_STRING_T {
                    length "0..255";
                }
                description "";
            } // END of addr4 definition.

            leaf addr6  {
                type  cml_data_types:CML_STRING_T {
                    length "0..255";
                }
                description "";
            } // END of addr6 definition.

            leaf rsrcAwaited  {
                type  cml_data_types:CML_UINT32_T;
                description "";
            } // END of rsrcAwaited definition.

        } // END of lAddr-container definition.
        container lspData {
            config false;
            description
                "lspData";
            leaf status  {
                type  cml_data_types:CML_UINT8_T;
                description "";
            } // END of status definition.

            leaf labelSpace  {
                type  cml_data_types:CML_UINT16_T;
                description "";
            } // END of labelSpace definition.

            leaf minLabelValue  {
                type  cml_data_types:CML_UINT32_T;
                description "";
            } // END of minLabelValue definition.

            leaf maxLabelValue  {
                type  cml_data_types:CML_UINT32_T;
                description "";
            } // END of maxLabelValue definition.

        } // END of lspData-container definition.
    } // END of ldpInterfaceGrouping definition.

    grouping  ldpMaster-grouping {
    container ldpMaster {
        description
            "ldpMaster";
        leaf termDebugLdp  {
            type  cml_data_types:CML_LDP_DEBUG_T;
            default "inter-area";
            description "";
        } // END of termDebugLdp definition.

        leaf termDebugLdpPacket  {
            type  cml_data_types:CML_LDP_DEBUG_PACKET_T;
            description "";
        } // END of termDebugLdpPacket definition.

        leaf confDebugLdp  {
            type  cml_data_types:CML_LDP_DEBUG_T;
            default "inter-area";
            description "";
        } // END of confDebugLdp definition.

        leaf confDebugLdpPacket  {
            type  cml_data_types:CML_LDP_DEBUG_PACKET_T;
            description "";
        } // END of confDebugLdpPacket definition.

        leaf rgId  {
            type  cml_data_types:CML_UINT32_T;
            config false;
            description "";
        } // END of rgId definition.

        leaf memberIp  {
            type  cml_data_types:CML_STRING_T {
                length "0..255";
            }
            config false;
            description "";
        } // END of memberIp definition.

        leaf sourceIp  {
            type  cml_data_types:CML_STRING_T {
                length "0..255";
            }
            config false;
            description "";
        } // END of sourceIp definition.

        leaf debugIccp  {
            type  cml_data_types:CML_UINT8_T;
            config false;
            description "";
        } // END of debugIccp definition.


        list adminGroupArray {
            if-feature feature_list:HAVE_CR_LDP;
            key "adminGrpName";
            config false;
            description
                "adminGroupArray";
            leaf adminGrpName  {
                type  cml_data_types:CML_STRING_T {
                    length "0..255";
                }
                description "";
            } // END of adminGrpName definition.

            leaf val  {
                type  cml_data_types:CML_INT32_T;
                description "";
            } // END of val definition.

        } // End of adminGroupArray-list

        list trunkList {
            if-feature feature_list:HAVE_CR_LDP;
            key "trunkName";
            description
                "trunkList";
            leaf trunkName  {
                type  cml_data_types:CML_STRING_T {
                    length "0..255";
                }
                description "";
            } // END of trunkName definition.

            leaf enableConfig  {
                type  cml_data_types:CML_UINT32_T;
                description "";
            } // END of enableConfig definition.

            leaf excludeAny  {
                type  cml_data_types:CML_UINT32_T;
                config false;
                description "";
            } // END of excludeAny definition.

            leaf includeAny  {
                type  cml_data_types:CML_UINT32_T;
                config false;
                description "";
            } // END of includeAny definition.

            leaf setupPriority  {
                type  cml_data_types:CML_INT32_T {
                     range "0..7";
                }
                description "";
            } // END of setupPriority definition.

            leaf holdPriority  {
                type  cml_data_types:CML_INT32_T {
                     range "0..7";
                }
                description "";
            } // END of holdPriority definition.

            leaf errVal  {
                type  cml_data_types:CML_STRING_T {
                    length "0..255";
                }
                config false;
                description "";
            } // END of errVal definition.

            leaf failures  {
                type  cml_data_types:CML_LDP_FAILURE_T;
                description "";
            } // END of failures definition.

            leaf bandwidth  {
                type  cml_data_types:CML_STRING_T {
                    length "0..255";
                }
                description "";
            } // END of bandwidth definition.

            leaf id  {
                type  cml_data_types:CML_UINT16_T;
                config false;
                description "";
            } // END of id definition.

            leaf cspfConf  {
                if-feature feature_list:HAVE_CSPF;
                type  cml_data_types:CML_LDP_CSPF_T;
                description "";
            } // END of cspfConf definition.

            leaf cspfRetryCount  {
                if-feature feature_list:HAVE_CSPF;
                type  cml_data_types:CML_UINT16_T {
                     range "1..65535";
                }
                description "";
            } // END of cspfRetryCount definition.

            leaf cspfRetryInterval  {
                if-feature feature_list:HAVE_CSPF;
                type  cml_data_types:CML_UINT16_T {
                     range "1..600";
                }
                description "";
            } // END of cspfRetryInterval definition.

            leaf labelReqRetryCount  {
                type  cml_data_types:CML_UINT16_T {
                     range "1..65535";
                }
                description "";
            } // END of labelReqRetryCount definition.

            leaf labelReqRetryInterval  {
                type  cml_data_types:CML_UINT16_T {
                     range "0..600";
                }
                description "";
            } // END of labelReqRetryInterval definition.

            leaf primaryPathName  {
                type  cml_data_types:CML_STRING_T {
                    length "0..255";
                }
                description "";
            } // END of primaryPathName definition.

            leaf secondaryPathName  {
                type  cml_data_types:CML_STRING_T {
                    length "0..255";
                }
                config false;
                description "";
            } // END of secondaryPathName definition.

            leaf state  {
                type  cml_data_types:CML_STRING_T {
                    length "0..255";
                }
                config false;
                description "";
            } // END of state definition.

            leaf ingress  {
                type  cml_data_types:CML_STRING_T {
                    length "0..255";
                }
                description "";
            } // END of ingress definition.

            leaf validIngress  {
                type  cml_data_types:CML_UINT8_T;
                config false;
                description "";
            } // END of validIngress definition.

            leaf nexthop  {
                type  cml_data_types:CML_STRING_T {
                    length "0..255";
                }
                config false;
                description "";
            } // END of nexthop definition.

            leaf egress  {
                type  cml_data_types:CML_STRING_T {
                    length "0..255";
                }
                description "";
            } // END of egress definition.

            leaf newCspfRequest  {
                type  cml_data_types:CML_UINT8_T;
                config false;
                description "";
            } // END of newCspfRequest definition.


            list adminGroupList {
                key "agname";
                description
                    "adminGroupList";
                leaf agname  {
                    type  cml_data_types:CML_STRING_T {
                        length "0..255";
                    }
                    description "";
                } // END of agname definition.

                leaf agtype  {
                    type  cml_data_types:CML_LDP_TRUNK_ADMIN_GROUP_T;
                    mandatory true;
                    description "";
                } // END of agtype definition.

                leaf enabled  {
                    type  cml_data_types:CML_STRING_T {
                        length "0..255";
                    }
                    config false;
                    description "";
                } // END of enabled definition.

            } // End of adminGroupList-list
            uses ldpFecGrouping;
            uses ldpCrAttrGrouping;
        } // End of trunkList-list

        list pathList {
            if-feature feature_list:HAVE_CR_LDP;
            key "pathName";
            description
                "pathList";
            leaf pathName  {
                type  cml_data_types:CML_STRING_T {
                    length "0..255";
                }
                description "";
            } // END of pathName definition.

            leaf lspId  {
                type  cml_data_types:CML_UINT16_T;
                config false;
                description "";
            } // END of lspId definition.


            list ldpEr {
                key "prefix";
                description
                    "ldpEr";
                leaf prefix  {
                    type  cml_data_types:CML_STRING_T {
                        length "0..255";
                    }
                    description "";
                } // END of prefix definition.

                leaf loose  {
                    type  cml_data_types:CML_LDP_LOOSE_T;
                    mandatory true;
                    description "";
                } // END of loose definition.

                leaf type  {
                    type  cml_data_types:CML_INT32_T;
                    config false;
                    description "";
                } // END of type definition.

            } // End of ldpEr-list
        } // End of pathList-list

        list nsmRt {
            key "prefix";
            config false;
            description
                "nsmRt";
            leaf prefix  {
                type  cml_data_types:CML_STRING_T {
                    length "0..255";
                }
                description "";
            } // END of prefix definition.


            list nextHop {
                key "nexthop";
                config false;
                description
                    "nextHop";
                leaf type  {
                    type  cml_data_types:CML_INT32_T;
                    description "";
                } // END of type definition.

                leaf family  {
                    type  cml_data_types:CML_UINT8_T;
                    description "";
                } // END of family definition.

                leaf nexthop  {
                    type  cml_data_types:CML_STRING_T {
                        length "0..255";
                    }
                    description "";
                } // END of nexthop definition.

                leaf ifindextype  {
                    type  cml_data_types:CML_UINT32_T;
                    description "";
                } // END of ifindextype definition.

            } // End of nextHop-list
        } // End of nsmRt-list

        list advm {
            key "prefixAcl";
            description
                "advm";
            leaf type  {
                type  cml_data_types:CML_UINT8_T;
                config false;
                description "";
            } // END of type definition.

            leaf prefixAcl  {
                type  cml_data_types:CML_STRING_T {
                    length "0..255";
                }
                description "";
            } // END of prefixAcl definition.


            list acl {
                key "peerAcl";
                description
                    "acl";
                leaf peerAcl  {
                    type  cml_data_types:CML_STRING_T {
                        length "0..255";
                    }
                    description "";
                } // END of peerAcl definition.

            } // End of acl-list
            container stats {
                config false;
                description
                    "stats";
                leaf denyReq  {
                    type  cml_data_types:CML_UINT32_T;
                    description "";
                } // END of denyReq definition.

                leaf denyMap  {
                    type  cml_data_types:CML_UINT32_T;
                    description "";
                } // END of denyMap definition.

            } // END of stats-container definition.
        } // End of advm-list
        container ldpInstance {
            presence "yes";
            description
                "ldpInstance";
            leaf ldpInstance  {
                type  cml_data_types:CML_LDP_INSTANCE_T;
                mandatory true;
                description "";
            } // END of ldpInstance definition.

            leaf routerId  {
                type  cml_data_types:CML_STRING_T {
                    length "0..255";
                }
                description "";
            } // END of routerId definition.

            leaf routerIdNsm  {
                type  cml_data_types:CML_UINT32_T;
                config false;
                description "";
            } // END of routerIdNsm definition.

            leaf pwStatusMode  {
                if-feature feature_list:HAVE_MPLS_VC;
                type  cml_data_types:CML_BOOL_T;
                description "";
            } // END of pwStatusMode definition.

            leaf messageId  {
                type  cml_data_types:CML_UINT32_T;
                config false;
                description "";
            } // END of messageId definition.

            leaf labelId  {
                type  cml_data_types:CML_UINT32_T;
                config false;
                description "";
            } // END of labelId definition.

            leaf udpRcvCount  {
                type  cml_data_types:CML_UINT32_T;
                config false;
                description "";
            } // END of udpRcvCount definition.

            leaf acceptSock  {
                type  cml_data_types:CML_INT32_T;
                config false;
                description "";
            } // END of acceptSock definition.

            leaf acceptCount  {
                type  cml_data_types:CML_INT32_T;
                config false;
                description "";
            } // END of acceptCount definition.

            leaf targetedHelloInterval  {
                type  cml_data_types:CML_UINT16_T {
                     range "1..21845";
                }
                default "15";
                description "";
            } // END of targetedHelloInterval definition.

            leaf targetedHoldTime  {
                type  cml_data_types:CML_UINT16_T {
                     range "3..65535";
                }
                default "45";
                description "";
            } // END of targetedHoldTime definition.

            leaf targetedHoldTimeForSync  {
                type  cml_data_types:CML_UINT16_T;
                config false;
                description "";
            } // END of targetedHoldTimeForSync definition.

            leaf helloInterval  {
                type  cml_data_types:CML_UINT16_T {
                     range "1..21845";
                }
                default "3";
                description "";
            } // END of helloInterval definition.

            leaf holdTime  {
                type  cml_data_types:CML_UINT16_T {
                     range "3..65535";
                }
                default "15";
                description "";
            } // END of holdTime definition.

            leaf holdTimeForSync  {
                type  cml_data_types:CML_UINT16_T;
                config false;
                description "";
            } // END of holdTimeForSync definition.

            leaf keepaliveTimeout  {
                type  cml_data_types:CML_UINT16_T {
                     range "3..65535";
                }
                description "";
            } // END of keepaliveTimeout definition.

            leaf keepaliveInterval  {
                type  cml_data_types:CML_UINT16_T {
                     range "1..21845";
                }
                description "";
            } // END of keepaliveInterval definition.

            leaf udpRcvCount6  {
                type  cml_data_types:CML_UINT32_T;
                config false;
                description "";
            } // END of udpRcvCount6 definition.

            leaf acceptCount6  {
                type  cml_data_types:CML_INT32_T;
                config false;
                description "";
            } // END of acceptCount6 definition.

            leaf uSock6  {
                type  cml_data_types:CML_INT32_T;
                config false;
                description "";
            } // END of uSock6 definition.

            leaf sSock6  {
                type  cml_data_types:CML_INT32_T;
                config false;
                description "";
            } // END of sSock6 definition.

            leaf config  {
                type  cml_data_types:CML_UINT32_T;
                config false;
                description "";
            } // END of config definition.

            leaf multicastHellos  {
                type  cml_data_types:CML_BOOL_T;
                description "";
            } // END of multicastHellos definition.

            leaf interAreaLsp  {
                if-feature feature_list:HAVE_LDP_INTER_AREA;
                type  cml_data_types:CML_STRING_T {
                    length "0..255";
                }
                default "NULL";
                description "";
            } // END of interAreaLsp definition.

            leaf interAreaAclName  {
                if-feature feature_list:HAVE_LDP_INTER_AREA;
                type  cml_data_types:CML_STRING_T {
                    length "0..255";
                }
                default "NULL";
                description "";
            } // END of interAreaAclName definition.

            leaf useBgpRoutes  {
                type  cml_data_types:CML_BOOL_T;
                description "";
            } // END of useBgpRoutes definition.

            leaf ldpOptimization  {
                type  cml_data_types:CML_BOOL_T;
                description "";
            } // END of ldpOptimization definition.

            leaf explicitNull  {
                type  cml_data_types:CML_BOOL_T;
                description "";
            } // END of explicitNull definition.

            leaf gracefulRestart  {
                if-feature feature_list:HAVE_RESTART;
                type  cml_data_types:CML_LDP_HELPER_MODE_T;
                description "";
            } // END of gracefulRestart definition.

            leaf helperMode  {
                if-feature feature_list:HAVE_RESTART;
                type  cml_data_types:CML_BOOL_T;
                default false;
                description "";
            } // END of helperMode definition.

            leaf restartReason  {
                if-feature feature_list:HAVE_RESTART;
                type  cml_data_types:CML_UINT8_T;
                config false;
                description "";
            } // END of restartReason definition.

            leaf nbrLivenessPeriod  {
                if-feature feature_list:HAVE_RESTART;
                type  cml_data_types:CML_INT32_T {
                     range "5..300";
                }
                default "120";
                description "";
            } // END of nbrLivenessPeriod definition.

            leaf maxRecoveryPeriod  {
                if-feature feature_list:HAVE_RESTART;
                type  cml_data_types:CML_INT32_T {
                     range "15..600";
                }
                default "120";
                description "";
            } // END of maxRecoveryPeriod definition.

            leaf restartCount  {
                type  cml_data_types:CML_INT32_T;
                config false;
                description "";
            } // END of restartCount definition.

            leaf ldpVersion  {
                type  cml_data_types:CML_UINT16_T;
                config false;
                description "";
            } // END of ldpVersion definition.

            leaf requestRetryTimeout  {
                type  cml_data_types:CML_UINT16_T {
                     range "1..65535";
                }
                default "5";
                description "";
            } // END of requestRetryTimeout definition.

            leaf globalMergeCap  {
                type  cml_data_types:CML_LDP_MERGE_CAPABLE_T;
                default "merge-capable";
                description "";
            } // END of globalMergeCap definition.

            leaf controlMode  {
                type  cml_data_types:CML_LDP_CONTROLMODE_T;
                description "";
            } // END of controlMode definition.

            leaf requestRetry  {
                type  cml_data_types:CML_BOOL_T;
                description "";
            } // END of requestRetry definition.

            leaf propagateRelease  {
                type  cml_data_types:CML_BOOL_T;
                description "";
            } // END of propagateRelease definition.

            leaf shutdown  {
                type  cml_data_types:CML_UINT8_T;
                config false;
                description "";
            } // END of shutdown definition.

            leaf retentionMode  {
                type  cml_data_types:CML_LDP_LABEL_T;
                description "";
            } // END of retentionMode definition.

            leaf advMode  {
                type  cml_data_types:CML_LDP_ADVERTISE_MODE_T;
                description "";
            } // END of advMode definition.

            leaf uSock  {
                type  cml_data_types:CML_INT32_T;
                config false;
                description "";
            } // END of uSock definition.

            leaf sSock  {
                type  cml_data_types:CML_INT32_T;
                config false;
                description "";
            } // END of sSock definition.

            leaf ldpEntityLastChange  {
                type  cml_data_types:CML_INT32_T;
                config false;
                description "";
            } // END of ldpEntityLastChange definition.

            leaf ldpLastPeerChange  {
                type  cml_data_types:CML_INT32_T;
                config false;
                description "";
            } // END of ldpLastPeerChange definition.

            leaf ldpFecLastChange  {
                type  cml_data_types:CML_INT32_T;
                config false;
                description "";
            } // END of ldpFecLastChange definition.

            leaf ldpLspFecChange  {
                type  cml_data_types:CML_STRING_T {
                    length "0..255";
                }
                config false;
                description "";
            } // END of ldpLspFecChange definition.

            leaf ldpEntityIndexNext  {
                type  cml_data_types:CML_UINT32_T;
                config false;
                description "";
            } // END of ldpEntityIndexNext definition.


            list ldpEntity {
                key "lsrId";
                config false;
                description
                    "ldpEntity";
                leaf lsrId  {
                    type  cml_data_types:CML_UINT32_T;
                    description "";
                } // END of lsrId definition.

                leaf labelSpace  {
                    type  cml_data_types:CML_UINT32_T;
                    description "";
                } // END of labelSpace definition.

                leaf targetedPeer  {
                    type  cml_data_types:CML_STRING_T {
                        length "0..255";
                    }
                    description "";
                } // END of targetedPeer definition.

                leaf targetedPeerType  {
                    type  cml_data_types:CML_UINT32_T;
                    description "";
                } // END of targetedPeerType definition.

                leaf transAddrKind  {
                    type  cml_data_types:CML_UINT8_T;
                    description "";
                } // END of transAddrKind definition.

                leaf advMode  {
                    type  cml_data_types:CML_UINT8_T;
                    description "";
                } // END of advMode definition.

                leaf retentionMode  {
                    type  cml_data_types:CML_UINT8_T;
                    description "";
                } // END of retentionMode definition.

                leaf controlMode  {
                    type  cml_data_types:CML_UINT8_T;
                    description "";
                } // END of controlMode definition.

                leaf holdTime  {
                    type  cml_data_types:CML_UINT16_T;
                    description "";
                } // END of holdTime definition.

                leaf keepaliveTimeout  {
                    type  cml_data_types:CML_UINT16_T;
                    description "";
                } // END of keepaliveTimeout definition.

                leaf helloInterval  {
                    type  cml_data_types:CML_UINT16_T;
                    description "";
                } // END of helloInterval definition.

                leaf targetedHelloInterval  {
                    type  cml_data_types:CML_UINT16_T;
                    description "";
                } // END of targetedHelloInterval definition.

                leaf targetedHoldTime  {
                    type  cml_data_types:CML_UINT16_T;
                    description "";
                } // END of targetedHoldTime definition.

                leaf targetedHoldTimeForSync  {
                    type  cml_data_types:CML_UINT16_T;
                    description "";
                } // END of targetedHoldTimeForSync definition.

                leaf keepaliveInterval  {
                    type  cml_data_types:CML_UINT16_T;
                    description "";
                } // END of keepaliveInterval definition.

                leaf pduLen  {
                    type  cml_data_types:CML_UINT16_T;
                    description "";
                } // END of pduLen definition.

                leaf reconnectTimeout  {
                    type  cml_data_types:CML_UINT32_T;
                    description "";
                } // END of reconnectTimeout definition.

                leaf loopDetectStatus  {
                    type  cml_data_types:CML_BOOL_T;
                    description "";
                } // END of loopDetectStatus definition.

                leaf initSessThreshold  {
                    type  cml_data_types:CML_UINT32_T;
                    description "";
                } // END of initSessThreshold definition.

                leaf pathVecLimit  {
                    type  cml_data_types:CML_UINT32_T;
                    description "";
                } // END of pathVecLimit definition.

                leaf hopCountLimit  {
                    type  cml_data_types:CML_UINT32_T;
                    description "";
                } // END of hopCountLimit definition.

                leaf rowStatus  {
                    type  cml_data_types:CML_UINT8_T;
                    description "";
                } // END of rowStatus definition.

                leaf adminStatus  {
                    type  cml_data_types:CML_UINT32_T;
                    description "";
                } // END of adminStatus definition.

                leaf operStatus  {
                    type  cml_data_types:CML_UINT32_T;
                    description "";
                } // END of operStatus definition.

                leaf tcpPort  {
                    type  cml_data_types:CML_UINT32_T;
                    description "";
                } // END of tcpPort definition.

                leaf udpDscPort  {
                    type  cml_data_types:CML_UINT32_T;
                    description "";
                } // END of udpDscPort definition.

                leaf notificationSend  {
                    type  cml_data_types:CML_UINT32_T;
                    description "";
                } // END of notificationSend definition.

                leaf notificationRecv  {
                    type  cml_data_types:CML_UINT32_T;
                    description "";
                } // END of notificationRecv definition.

                leaf helloSend  {
                    type  cml_data_types:CML_UINT32_T;
                    description "";
                } // END of helloSend definition.

                leaf helloRecv  {
                    type  cml_data_types:CML_UINT32_T;
                    description "";
                } // END of helloRecv definition.

                leaf initializationSend  {
                    type  cml_data_types:CML_UINT32_T;
                    description "";
                } // END of initializationSend definition.

                leaf initializationRecv  {
                    type  cml_data_types:CML_UINT32_T;
                    description "";
                } // END of initializationRecv definition.

                leaf keepaliveSend  {
                    type  cml_data_types:CML_UINT32_T;
                    description "";
                } // END of keepaliveSend definition.

                leaf keepaliveRecv  {
                    type  cml_data_types:CML_UINT32_T;
                    description "";
                } // END of keepaliveRecv definition.

                leaf addressSend  {
                    type  cml_data_types:CML_UINT32_T;
                    description "";
                } // END of addressSend definition.

                leaf addressRecv  {
                    type  cml_data_types:CML_UINT32_T;
                    description "";
                } // END of addressRecv definition.

                leaf addressWithdrawSend  {
                    type  cml_data_types:CML_UINT32_T;
                    description "";
                } // END of addressWithdrawSend definition.

                leaf addressWithdrawRecv  {
                    type  cml_data_types:CML_UINT32_T;
                    description "";
                } // END of addressWithdrawRecv definition.

                leaf labelMappingSend  {
                    type  cml_data_types:CML_UINT32_T;
                    description "";
                } // END of labelMappingSend definition.

                leaf rebelMappingRecv  {
                    type  cml_data_types:CML_UINT32_T;
                    description "";
                } // END of rebelMappingRecv definition.

                leaf labelRequestSend  {
                    type  cml_data_types:CML_UINT32_T;
                    description "";
                } // END of labelRequestSend definition.

                leaf labelRequestRecv  {
                    type  cml_data_types:CML_UINT32_T;
                    description "";
                } // END of labelRequestRecv definition.

                leaf labelWithdrawSend  {
                    type  cml_data_types:CML_UINT32_T;
                    description "";
                } // END of labelWithdrawSend definition.

                leaf labelWithdrawRecv  {
                    type  cml_data_types:CML_UINT32_T;
                    description "";
                } // END of labelWithdrawRecv definition.

                leaf labelReleaseSend  {
                    type  cml_data_types:CML_UINT32_T;
                    description "";
                } // END of labelReleaseSend definition.

                leaf labelReleaseRecv  {
                    type  cml_data_types:CML_UINT32_T;
                    description "";
                } // END of labelReleaseRecv definition.

                leaf requestAbortSend  {
                    type  cml_data_types:CML_UINT32_T;
                    description "";
                } // END of requestAbortSend definition.

                leaf requestAbortRecv  {
                    type  cml_data_types:CML_UINT32_T;
                    description "";
                } // END of requestAbortRecv definition.

                container stats {
                    config false;
                    description
                        "stats";
                    leaf mplsLdpAttemptedSessions  {
                        type  cml_data_types:CML_UINT32_T;
                        description "";
                    } // END of mplsLdpAttemptedSessions definition.

                    leaf mplsLdpSesRejectedNoHelloErrors  {
                        type  cml_data_types:CML_UINT32_T;
                        description "";
                    } // END of mplsLdpSesRejectedNoHelloErrors definition.

                    leaf mplsLdpSesRejectedAdErrors  {
                        type  cml_data_types:CML_UINT32_T;
                        description "";
                    } // END of mplsLdpSesRejectedAdErrors definition.

                    leaf mplsLdpSesRejectedMaxPduErrors  {
                        type  cml_data_types:CML_UINT32_T;
                        description "";
                    } // END of mplsLdpSesRejectedMaxPduErrors definition.

                    leaf mplsLdpSesRejectedLRErrors  {
                        type  cml_data_types:CML_UINT32_T;
                        description "";
                    } // END of mplsLdpSesRejectedLRErrors definition.

                    leaf mplsLdpBadLdpIdentifierErrors  {
                        type  cml_data_types:CML_UINT32_T;
                        description "";
                    } // END of mplsLdpBadLdpIdentifierErrors definition.

                    leaf mplsLdpBadPduLengthErrors  {
                        type  cml_data_types:CML_UINT32_T;
                        description "";
                    } // END of mplsLdpBadPduLengthErrors definition.

                    leaf mplsLdpBadMessageLengthErrors  {
                        type  cml_data_types:CML_UINT32_T;
                        description "";
                    } // END of mplsLdpBadMessageLengthErrors definition.

                    leaf mplsLdpBadTlvLengthErrors  {
                        type  cml_data_types:CML_UINT32_T;
                        description "";
                    } // END of mplsLdpBadTlvLengthErrors definition.

                    leaf mplsLdpMalformedTlvValueErrors  {
                        type  cml_data_types:CML_UINT32_T;
                        description "";
                    } // END of mplsLdpMalformedTlvValueErrors definition.

                    leaf mplsLdpKeepAliveTimerExpErrors  {
                        type  cml_data_types:CML_UINT32_T;
                        description "";
                    } // END of mplsLdpKeepAliveTimerExpErrors definition.

                    leaf mplsLdpShutdownNotifReceived  {
                        type  cml_data_types:CML_UINT32_T;
                        description "";
                    } // END of mplsLdpShutdownNotifReceived definition.

                    leaf mplsLdpShutdownNotifSent  {
                        type  cml_data_types:CML_UINT32_T;
                        description "";
                    } // END of mplsLdpShutdownNotifSent definition.

                } // END of stats-container definition.
                uses ldpAdjacencyGrouping;
                uses ldpSessionGrouping;
            } // End of ldpEntity-list

            list ipv4PrefixFecTable {
                key "prefixAddr4";
                config false;
                description
                    "ipv4PrefixFecTable";
                leaf prefixAddr4  {
                    type  cml_data_types:CML_STRING_T {
                        length "0..255";
                    }
                    description "";
                } // END of prefixAddr4 definition.

                uses ldpFecCbGrouping;
            } // End of ipv4PrefixFecTable-list

            list crLspFecTable {
                if-feature feature_list:HAVE_CR_LDP;
                key "crPrefixAddr";
                config false;
                description
                    "crLspFecTable";
                leaf crPrefixAddr  {
                    type  cml_data_types:CML_STRING_T {
                        length "0..255";
                    }
                    description "";
                } // END of crPrefixAddr definition.

                uses ldpFecCbGrouping;
            } // End of crLspFecTable-list

            list lsToAddr {
                key "transportLabelSpace";
                description
                    "lsToAddr";
                leaf refcount  {
                    type  cml_data_types:CML_INT32_T;
                    config false;
                    description "";
                } // END of refcount definition.

                leaf transportLabelSpace  {
                    type  cml_data_types:CML_UINT16_T;
                    description "";
                } // END of transportLabelSpace definition.

                leaf transportAddr4  {
                    type  cml_data_types:CML_STRING_T {
                        length "0..255";
                    }
                    description "";
                } // END of transportAddr4 definition.

                leaf transportAddr6  {
                    if-feature feature_list:HAVE_IPV6;
                    type  cml_data_types:CML_STRING_T {
                        length "0..255";
                    }
                    description "";
                } // END of transportAddr6 definition.

                leaf rsrcAwaited  {
                    type  cml_data_types:CML_UINT32_T;
                    config false;
                    description "";
                } // END of rsrcAwaited definition.

            } // End of lsToAddr-list

            list confIpv4Fec {
                key "prefixAddr";
                config false;
                description
                    "confIpv4Fec";
                leaf prefixAddr  {
                    type  cml_data_types:CML_STRING_T {
                        length "0..255";
                    }
                    description "";
                } // END of prefixAddr definition.

                leaf type  {
                    type  cml_data_types:CML_INT32_T;
                    description "";
                } // END of type definition.

                leaf family  {
                    type  cml_data_types:CML_UINT8_T;
                    description "";
                } // END of family definition.

                leaf nexthopAddr  {
                    type  cml_data_types:CML_STRING_T {
                        length "0..255";
                    }
                    description "";
                } // END of nexthopAddr definition.

                leaf ifIndexIpv4  {
                    type  cml_data_types:CML_UINT32_T;
                    description "";
                } // END of ifIndexIpv4 definition.

            } // End of confIpv4Fec-list

            list targetedPeers {
                key "targetAddress";
                description
                    "targetedPeers";
                leaf targetAddress  {
                    type  cml_data_types:CML_LDP_IP_ADDR_T;
                    description "";
                } // END of targetAddress definition.

                container ldpEntity {
                    description
                        "ldpEntity";
                    leaf lsrId  {
                        type  cml_data_types:CML_UINT32_T;
                        config false;
                        description "";
                    } // END of lsrId definition.

                    leaf labelSpace  {
                        type  cml_data_types:CML_UINT32_T;
                        config false;
                        description "";
                    } // END of labelSpace definition.

                    leaf targetHelloInterval  {
                        type  cml_data_types:CML_UINT16_T {
                             range "1..21845";
                        }
                        description "";
                    } // END of targetHelloInterval definition.

                    leaf targetHoldTime  {
                        type  cml_data_types:CML_UINT16_T {
                             range "3..65535";
                        }
                        description "";
                    } // END of targetHoldTime definition.

                    leaf initSessThreshold  {
                        type  cml_data_types:CML_UINT32_T;
                        config false;
                        description "";
                    } // END of initSessThreshold definition.

                    leaf pathVecLimit  {
                        type  cml_data_types:CML_UINT32_T;
                        config false;
                        description "";
                    } // END of pathVecLimit definition.

                    leaf hopCountLimit  {
                        type  cml_data_types:CML_UINT32_T;
                        config false;
                        description "";
                    } // END of hopCountLimit definition.

                    leaf rowStatus  {
                        type  cml_data_types:CML_UINT8_T;
                        config false;
                        description "";
                    } // END of rowStatus definition.

                    leaf adminStatus  {
                        type  cml_data_types:CML_UINT32_T;
                        config false;
                        description "";
                    } // END of adminStatus definition.

                    leaf notificationSend  {
                        type  cml_data_types:CML_UINT32_T;
                        config false;
                        description "";
                    } // END of notificationSend definition.

                    leaf notificationRecv  {
                        type  cml_data_types:CML_UINT32_T;
                        config false;
                        description "";
                    } // END of notificationRecv definition.

                    leaf helloSend  {
                        type  cml_data_types:CML_UINT32_T;
                        config false;
                        description "";
                    } // END of helloSend definition.

                    leaf helloRecv  {
                        type  cml_data_types:CML_UINT32_T;
                        config false;
                        description "";
                    } // END of helloRecv definition.

                    leaf initializationSend  {
                        type  cml_data_types:CML_UINT32_T;
                        config false;
                        description "";
                    } // END of initializationSend definition.

                    leaf initializationRecv  {
                        type  cml_data_types:CML_UINT32_T;
                        config false;
                        description "";
                    } // END of initializationRecv definition.

                    leaf keepaliveSend  {
                        type  cml_data_types:CML_UINT32_T;
                        config false;
                        description "";
                    } // END of keepaliveSend definition.

                    leaf keepaliveRecv  {
                        type  cml_data_types:CML_UINT32_T;
                        config false;
                        description "";
                    } // END of keepaliveRecv definition.

                    leaf addressSend  {
                        type  cml_data_types:CML_UINT32_T;
                        config false;
                        description "";
                    } // END of addressSend definition.

                    leaf addressRecv  {
                        type  cml_data_types:CML_UINT32_T;
                        config false;
                        description "";
                    } // END of addressRecv definition.

                    leaf addressWithdrawSend  {
                        type  cml_data_types:CML_UINT32_T;
                        config false;
                        description "";
                    } // END of addressWithdrawSend definition.

                    leaf addressWithdrawRecv  {
                        type  cml_data_types:CML_UINT32_T;
                        config false;
                        description "";
                    } // END of addressWithdrawRecv definition.

                    leaf labelMappingSend  {
                        type  cml_data_types:CML_UINT32_T;
                        config false;
                        description "";
                    } // END of labelMappingSend definition.

                    leaf rebelMappingRecv  {
                        type  cml_data_types:CML_UINT32_T;
                        config false;
                        description "";
                    } // END of rebelMappingRecv definition.

                    leaf labelRequestSend  {
                        type  cml_data_types:CML_UINT32_T;
                        config false;
                        description "";
                    } // END of labelRequestSend definition.

                    leaf labelRequestRecv  {
                        type  cml_data_types:CML_UINT32_T;
                        config false;
                        description "";
                    } // END of labelRequestRecv definition.

                    leaf labelWithdrawSend  {
                        type  cml_data_types:CML_UINT32_T;
                        config false;
                        description "";
                    } // END of labelWithdrawSend definition.

                    leaf labelWithdrawRecv  {
                        type  cml_data_types:CML_UINT32_T;
                        config false;
                        description "";
                    } // END of labelWithdrawRecv definition.

                    leaf labelReleaseSend  {
                        type  cml_data_types:CML_UINT32_T;
                        config false;
                        description "";
                    } // END of labelReleaseSend definition.

                    leaf labelReleaseRecv  {
                        type  cml_data_types:CML_UINT32_T;
                        config false;
                        description "";
                    } // END of labelReleaseRecv definition.

                    leaf requestAbortSend  {
                        type  cml_data_types:CML_UINT32_T;
                        config false;
                        description "";
                    } // END of requestAbortSend definition.

                    leaf requestAbortRecv  {
                        type  cml_data_types:CML_UINT32_T;
                        config false;
                        description "";
                    } // END of requestAbortRecv definition.

                } // END of ldpEntity-container definition.
            } // End of targetedPeers-list

            list vplsTable {
                key "vplsId";
                config false;
                description
                    "vplsTable";
                leaf vplsId  {
                    type  cml_data_types:CML_UINT32_T;
                    description "";
                } // END of vplsId definition.

                leaf mvcCount  {
                    type  cml_data_types:CML_UINT32_T;
                    description "";
                } // END of mvcCount definition.

                uses ldpVcGrouping;
                uses ldpVcAttrGrouping;
            } // End of vplsTable-list

            list ipv6PrefixFecTable {
                key "prefixAddr6";
                config false;
                description
                    "ipv6PrefixFecTable";
                leaf prefixAddr6  {
                    type  cml_data_types:CML_STRING_T {
                        length "0..255";
                    }
                    description "";
                } // END of prefixAddr6 definition.

                uses ldpFecCbGrouping;
            } // End of ipv6PrefixFecTable-list

            list confIpv6Fec {
                key "prefixAddr";
                config false;
                description
                    "confIpv6Fec";
                leaf prefixAddr  {
                    type  cml_data_types:CML_STRING_T {
                        length "0..255";
                    }
                    description "";
                } // END of prefixAddr definition.

                leaf type  {
                    type  cml_data_types:CML_INT32_T;
                    description "";
                } // END of type definition.

                leaf family  {
                    type  cml_data_types:CML_UINT8_T;
                    description "";
                } // END of family definition.

                leaf nexthopAddr  {
                    type  cml_data_types:CML_STRING_T {
                        length "0..255";
                    }
                    description "";
                } // END of nexthopAddr definition.

                leaf ifIndexIpv6  {
                    type  cml_data_types:CML_UINT32_T;
                    description "";
                } // END of ifIndexIpv6 definition.

            } // End of confIpv6Fec-list

            list nbrToPasswdTable {
                if-feature feature_list:HAVE_TCP_MD5SIG;
                key "nbrAddr";
                description
                    "nbrToPasswdTable";
                leaf nbrAddr  {
                    type  cml_data_types:CML_HOSTNAME_T;
                    description "";
                } // END of nbrAddr definition.

                leaf authType  {
                    type  cml_data_types:CML_STRING_T {
                        length "0..255";
                    }
                    mandatory true;
                    description "";
                } // END of authType definition.

                leaf type  {
                    type  cml_data_types:CML_UINT8_T {
                         range "0..7";
                    }
                    mandatory true;
                    description "";
                } // END of type definition.

                leaf password  {
                    type  cml_data_types:CML_STRING_T {
                        length "0..255";
                    }
                    mandatory true;
                    description "";
                } // END of password definition.

            } // End of nbrToPasswdTable-list

            list fecMatchedLpmRibTable4 {
                if-feature feature_list:HAVE_LDP_INTER_AREA;
                key "prefixAddr4";
                config false;
                description
                    "fecMatchedLpmRibTable4";
                leaf prefixAddr4  {
                    type  cml_data_types:CML_STRING_T {
                        length "0..255";
                    }
                    description "";
                } // END of prefixAddr4 definition.

                uses ldpFecCbGrouping;
            } // End of fecMatchedLpmRibTable4-list

            list fecMatchedLpmRibTable6 {
                if-feature feature_list:HAVE_LDP_INTER_AREA;
                key "prefixAddr6";
                config false;
                description
                    "fecMatchedLpmRibTable6";
                leaf prefixAddr6  {
                    type  cml_data_types:CML_STRING_T {
                        length "0..255";
                    }
                    description "";
                } // END of prefixAddr6 definition.

                uses ldpFecCbGrouping;
            } // End of fecMatchedLpmRibTable6-list
            container loopDetection {
                presence "yes";
                description
                    "loopDetection";
                leaf loopDetection  {
                    type  cml_data_types:CML_BOOL_T;
                    mandatory true;
                    description "";
                } // END of loopDetection definition.

                leaf globalPathVecLimit  {
                    type  cml_data_types:CML_UINT32_T {
                         range "1..255";
                    }
                    default "255";
                    description "";
                } // END of globalPathVecLimit definition.

                leaf globalHopCountLimit  {
                    type  cml_data_types:CML_UINT32_T {
                         range "1..255";
                    }
                    default "255";
                    description "";
                } // END of globalHopCountLimit definition.

            } // END of loopDetection-container definition.
            uses ldpVcGrouping;
        } // END of ldpInstance-container definition.
    } // END of ldpMaster-container definition.
    } // END of ldpMaster-container definition.


}
