/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-ntp.yang
*
*/

submodule zebos-ntp {

    belongs-to  zebos { prefix zebos; }

    import cml_data_types {
        prefix cml_data_types;
    }

    import feature_list {
        prefix feature_list;
    }

    include zebos-vrf;
    organization
        "IP Infusion Inc.";

    contact
        "Address: 3965 Freedom Circle, Suite 200, Santa Clara, CA 95054
        Phone: +1 408-400-1900
        E-mail: support@ipinfusion.com
        Web: http://www.ipinfusion.com/";

    description
        "ntp configurations";


    revision "2017-12-11" {
        description "Added autoPopulate custom  tag.";
    }

    revision "2016-12-27" {
        description "Added snmp oid and documentation tag.";
    }

    revision "2016-10-28" {
        description "Initial version of NTP datamodel.";
    }


    grouping  ntp-grouping {
    container ntp {
        description
            "ntp";
        leaf vrfName  {
            type  cml_data_types:CML_STRING_T {
                length "0..255";
            }
            description "";
        } // END of vrfName definition.

        leaf featurentp  {
            if-feature feature_list:HAVE_HOSTP_NTP;
            type  cml_data_types:CML_BOOL_T;
            description "";
        } // END of featurentp definition.

        leaf enableNTP  {
            if-feature feature_list:HAVE_HOSTP_NTP;
            type  cml_data_types:CML_BOOL_T;
            description "";
        } // END of enableNTP definition.

        leaf sourceInterface  {
            if-feature feature_list:HAVE_HOSTP_NTP;
            type  cml_data_types:CML_STRING_T {
                length "0..255";
            }
            description "";
        } // END of sourceInterface definition.

        leaf loggingNTP  {
            if-feature feature_list:HAVE_HOSTP_NTP;
            type  cml_data_types:CML_BOOL_T;
            default false;
            description "";
        } // END of loggingNTP definition.

        leaf authenticateNTP  {
            if-feature feature_list:HAVE_HOSTP_NTP;
            type  cml_data_types:CML_BOOL_T;
            default false;
            description "";
        } // END of authenticateNTP definition.

        leaf debugntp  {
            type  cml_data_types:CML_BOOL_T;
            default false;
            description "";
        } // END of debugntp definition.


        list ntpKey {
            key "keyAuthenticate";
            description
                "ntpKey";
            leaf vrfName  {
                type  cml_data_types:CML_STRING_T {
                    length "0..255";
                }
                description "";
            } // END of vrfName definition.

            leaf keyAuthenticate  {
                type  cml_data_types:CML_INT32_T {
                     range "1..65535";
                }
                description "";
            } // END of keyAuthenticate definition.

            leaf authenticateScheme  {
                type  cml_data_types:CML_STRING_T {
                    length "0..255";
                }
                mandatory true;
                description "";
            } // END of authenticateScheme definition.

            leaf keyEncrytion  {
                type  cml_data_types:CML_HOSTP_KEY_TYPE_T;
                mandatory true;
                description "";
            } // END of keyEncrytion definition.

        } // End of ntpKey-list

        list trustedKey {
            key "trustedkeyNTP";
            description
                "trustedKey";
            leaf vrfName  {
                type  cml_data_types:CML_STRING_T {
                    length "0..255";
                }
                description "";
            } // END of vrfName definition.

            leaf trustedkeyNTP  {
                type  cml_data_types:CML_INT32_T {
                     range "1..65535";
                }
                description "";
            } // END of trustedkeyNTP definition.

        } // End of trustedKey-list

        list PeerOptions {
            key "Address";
            description
                "PeerOptions";
            leaf vrfName  {
                type  cml_data_types:CML_STRING_T {
                    length "0..255";
                }
                description "";
            } // END of vrfName definition.

            leaf mode  {
                type  cml_data_types:CML_NTP_MODE_T;
                mandatory true;
                description "";
            } // END of mode definition.

            leaf Address  {
                type  cml_data_types:CML_HOSTPNAME_T;
                description "";
            } // END of Address definition.

            leaf prefer  {
                type  cml_data_types:CML_BOOL_T;
                description "";
            } // END of prefer definition.

            leaf key  {
                type  cml_data_types:CML_UINT32_T {
                     range "1..65535";
                }
                default "65535";
                description "";
            } // END of key definition.

            leaf minpoll  {
                type  cml_data_types:CML_UINT16_T {
                     range "4..16";
                }
                default "4";
                description "";
            } // END of minpoll definition.

            leaf maxpoll  {
                type  cml_data_types:CML_UINT16_T {
                     range "4..16";
                }
                default "6";
                description "";
            } // END of maxpoll definition.

        } // End of PeerOptions-list
    } // END of ntp-container definition.
    } // END of ntp-container definition.


}
