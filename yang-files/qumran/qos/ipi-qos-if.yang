/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-qos-if.yang
*
*/

module ipi-qos-if {

    yang-version 1.1;

    namespace   "http://www.ipinfusion.com/yang/ocnos/ipi-qos-if";

    prefix "ipi-qos-if";

    import ietf-yang-types {
        prefix yang;
        revision-date 2013-07-15;
    }

    import ipi-qos {
        prefix ipi-qos;
        revision-date 2021-06-10;
    }

    import ipi-qos-types {
        prefix ipi-qos-types;
        revision-date 2021-06-09;
    }

    import ipi-if-aggregate {
        prefix ipi-if-aggregate;
        revision-date 2020-12-15;
    }

    import ipi-interface {
        prefix ipi-interface;
        revision-date 2021-06-14;
    }

    import ipi-mpls {
        prefix ipi-mpls;
        revision-date 2021-05-13;
    }

    import feature-list {
        prefix feature-list;
        revision-date 2021-05-03;
    }

    organization
        "IP Infusion Inc.";

    contact
        "Address: 3965 Freedom Circle, Suite 200, Santa Clara, CA 95054
         Phone: +1 408-400-1900
         E-mail: support@ipinfusion.com
         Web: http://www.ipinfusion.com/";

    description
        "Quality of Service (QoS) interface information";


    revision "2021-06-09" {
        description "Merged 'type-qos' and 'type-queuing' with 'policy-map-name'.";
        reference "Initial Version";
    }

    revision "2021-06-05" {
        description "Added dscp-encap and exp-to-queue profiles.";
        reference "Initial Version";
    }

    revision "2021-06-04" {
        description "Changed notification type to ALARM";
        reference "Initial Version";
    }

    revision "2021-05-06" {
        description "Added type attr in service-policy";
        reference "Initial Version";
    }

    revision "2021-05-05" {
        description "Added length in policies names";
        reference "Initial Version";
    }

    revision "2021-03-23" {
        description "Removed mutation-map related objects";
        reference "Initial Version";
    }

    revision "2020-12-04" {
        description "Restructured module as per open-config style";
        reference "Initial Version";
    }

    revision "2018-06-21" {
        description "Initial Version";
        reference "Initial Version";
    }

    grouping qos-interface-config {
        description
            "Grouping for interface QoS configuration";
        leaf untagged-priority  {
            when " /ipi-interface:interfaces/ipi-interface:interface/ipi-interface:config/ipi-interface:switchport-status = 'true' ";
            type  uint8 {
                 range "0..7"  {
                    description "0..7:Untagged priority values";
                 }
            }
            description "Use this attribute to set internal priority for untagged traffic on L2
                        interface";
        } // END of untagged-priority definition.

        leaf trust-dscp  {
            when " /ipi-interface:interfaces/ipi-interface:interface/ipi-interface:config/ipi-interface:switchport-status ";
            type  empty;
            description "Use this command to classify the ingress traffic based on DSCP map on
                        L2 interface";
        } // END of trust-dscp definition.

    } // END of qos-interface-config definition.
    grouping qos-traffic-shape-config {
        description
            "Grouping for QoS traffic shape configuration";
        leaf rate  {
            when " ../rate-unit ";
            type  uint64 {
                 range "1..1000000000"  {
                    description "1..1000000000:Specify egress traffic rate limit from 52 Kbps to 1000
                            Gbps";
                 }
            }
            mandatory true;
            description "Use this attribute to configure shaping on an egress queue to impose a
                        maximum rate on it";
        } // END of rate definition.

        leaf rate-unit  {
            when " ../rate ";
            type  ipi-qos-types:qos_shape_rate_unit_t;
            mandatory true;
            description "Use this attribute to set the shape rate unit";
        } // END of rate-unit definition.

        leaf burst-rate  {
            when " ../rate ";
            if-feature feature-list:NOT_HAVE_CUSTOM2_QOS;
            type  uint64 {
                 range "1..1000000"  {
                    description "1..1000000:Specify egress traffic rate burst size from 1 Kbits to
                            1000000 kbits (1 Gbits)";
                 }
            }
            mandatory true;
            description "Use this attribute to set a shape rate burst";
        } // END of burst-rate definition.

    } // END of qos-traffic-shape-config definition.
    grouping qos-traffic-shape-top {
        description
            "Grouping for QoS traffic shape";
        container traffic-shape {
            description
                "Configuration data for QoS traffic shape";
            container config {
                presence "true";
                description
                    "Configuration data for QoS traffic shape";
                uses qos-traffic-shape-config;
            } // END of config-container definition.
            container state {
                config false;
                description
                    "Operational state data for QoS traffic shape";
                uses qos-traffic-shape-config;
            } // END of state-container definition.
        } // END of traffic-shape-container definition.
    } // END of qos-traffic-shape-top definition.
    grouping qos-interface-remark-top {
        description
            "Grouping for QoS remark";
        container remark {
            when " /ipi-qos:qos/ipi-qos:global/ipi-qos:config/ipi-qos:enable-qos ";
            description
                "Configuration data for QoS remark";
            container config {
                description
                    "Configuration data for QoS remark";
                uses qos-interface-remark-config;
            } // END of config-container definition.
            container state {
                config false;
                description
                    "Operational state data for QoS remark";
                uses qos-interface-remark-config;
            } // END of state-container definition.
        } // END of remark-container definition.
    } // END of qos-interface-remark-top definition.
    grouping qos-interface-remark-config {
        description
            "Grouping for QoS remark configuration";
        leaf cos  {
            when " /ipi-interface:interfaces/ipi-interface:interface/ipi-interface:config/ipi-interface:switchport-status = 'true' ";
            type  ipi-qos-types:cml_remark_state_t;
            description "Use this command to enable/disable remarking of CoS set by the egress
                        map";
        } // END of cos definition.

        leaf dei  {
            when " /ipi-interface:interfaces/ipi-interface:interface/ipi-interface:config/ipi-interface:switchport-status ";
            if-feature feature-list:NOT_HAVE_CUSTOM2_QOS;
            type  ipi-qos-types:cml_remark_state_t;
            description "Use this command to enable/disable remarking of DEI set by the egress
                        map";
        } // END of dei definition.

        leaf dscp  {
            type  ipi-qos-types:cml_remark_state_t;
            description "Use this command to enable/disable remarking of DSCP set by the egress
                        map";
        } // END of dscp definition.

    } // END of qos-interface-remark-config definition.
    grouping qos-map-profile-ref-config {
        description
            "Grouping for QoS map profile reference configuration";
        leaf cos-to-queue  {
            when " /ipi-interface:interfaces/ipi-interface:interface/ipi-interface:config/ipi-interface:switchport-status = 'true' ";
            type  string {
                length "1..1965";
                pattern "[^?' =,>|]+";
            }
            description "Use this attibute to attach a CoS to queue profile to the interface";
        } // END of cos-to-queue definition.

        leaf dscp-to-dscp  {
            when " /ipi-interface:interfaces/ipi-interface:interface/ipi-interface:config/ipi-interface:switchport-status != 'true' ";
            if-feature feature-list:HAVE_CUSTOM2_QOS;
            type  string {
                length "1..1965";
                pattern "[^?' =,>|]+";
            }
            description "Use this attibute to attach a DSCP to DSCP profile to the interface";
        } // END of dscp-to-dscp definition.

        leaf dscp-to-queue  {
            when " /ipi-interface:interfaces/ipi-interface:interface/ipi-interface:config/ipi-interface:switchport-status != 'true' ";
            type  string {
                length "1..1965";
                pattern "[^?' =,>|]+";
            }
            description "Use this attibute to attach a DSCP to queue profile to the interface";
        } // END of dscp-to-queue definition.

        leaf exp-encapsulation  {
            when " /ipi-interface:interfaces/ipi-interface:interface/ipi-interface:config/ipi-interface:switchport-status != 'true' ";
            if-feature feature-list:HAVE_DIFFSERV;
            if-feature feature-list:HAVE_CUSTOM2_QOS;
            type  string {
                length "1..1965";
                pattern "[^?' =,>|]+";
            }
            description "Use this attibute to attach a MPLS experimental encapsulation profile
                        to the interface";
        } // END of exp-encapsulation definition.

        leaf dscp-encapsulation  {
            when " /ipi-interface:interfaces/ipi-interface:interface/ipi-interface:config/ipi-interface:switchport-status != 'true' ";
            if-feature feature-list:HAVE_CUSTOM2_QOS;
            type  string {
                length "1..1965";
                pattern "[^?' =,>|]+";
            }
            description "Use this attibute to attach a MPLS dscp encapsulation profile to the
                        interface";
        } // END of dscp-encapsulation definition.

        leaf queue-color-to-cos  {
            when " /ipi-interface:interfaces/ipi-interface:interface/ipi-interface:config/ipi-interface:switchport-status = 'true' ";
            type  string {
                length "1..1965";
                pattern "[^?' =,>|]+";
            }
            description "Use this attibute to attach a queue color to CoS profile to the
                        interface";
        } // END of queue-color-to-cos definition.

        leaf queue-color-to-dscp  {
            if-feature feature-list:HAVE_CUSTOM1_QOS;
            type  string {
                length "1..1965";
                pattern "[^?' =,>|]+";
            }
            description "Use this attibute to attach a queue color to DSCP profile to the
                        interface";
        } // END of queue-color-to-dscp definition.

        leaf queue-to-exp  {
            if-feature feature-list:HAVE_DIFFSERV;
            if-feature feature-list:HAVE_CUSTOM1_QOS;
            type  string {
                length "1..1965";
                pattern "[^?' =,>|]+";
            }
            description "Use this attibute to attach a queue to exp profile to the interface";
        } // END of queue-to-exp definition.

    } // END of qos-map-profile-ref-config definition.
    grouping qos-map-profile-ref-top {
        description
            "Grouping for QoS map profile reference";
        container map-profile {
            if-feature feature-list:HAVE_QOS_MAPPING_PROFILE;
            description
                "Configuration data for QoS map profile reference";
            container config {
                description
                    "Configuration data for QoS map profile reference";
                uses qos-map-profile-ref-config;
            } // END of config-container definition.
            container state {
                config false;
                description
                    "Operational state data for QoS map profile reference";
                uses qos-map-profile-ref-config;
            } // END of state-container definition.
        } // END of map-profile-container definition.
    } // END of qos-map-profile-ref-top definition.
    grouping qos-qos-statistics-state {
        description
            "Grouping for QoS qos statistics state";
        leaf matched-packets  {
            type  yang:counter64;
            description "The number of packets that matched the rules of class-map attached to
                        the interface";
        } // END of matched-packets definition.

        leaf matched-octets  {
            type  yang:counter64;
            description "The number of bytes that matched the rules of class-map attached to
                        the interface";
        } // END of matched-octets definition.

        leaf transmitted-packets  {
            type  yang:counter64;
            description "The number of packets that were transmitted that matched the rules of
                        class-map attached to the interface";
        } // END of transmitted-packets definition.

        leaf transmitted-octets  {
            type  yang:counter64;
            description "The number of bytes that were transmitted that matched the rules of
                        class-map attached to the interface";
        } // END of transmitted-octets definition.

        leaf dropped-packets  {
            type  yang:counter64;
            description "The number of packets that were dropped due to policer action on the
                        class-map attached to the interface";
        } // END of dropped-packets definition.

        leaf dropped-octets  {
            type  yang:counter64;
            description "The number of bytes that were dropped due to policer action on the
                        class-map attached to the interface";
        } // END of dropped-octets definition.

    } // END of qos-qos-statistics-state definition.
    grouping qos-queue-statistics-state {
        description
            "Grouping for QoS queue statistics state";

        list queue {
            key "id";
            config false;
            description
                "Operational state data list for QoS queue statistics";
            leaf id  {
                type  uint8;
                description "An unique number associated with the queue";
            } // END of id definition.

            container counters {
                config false;
                description
                    "Operational state data for QoS queue statistics counters";
                leaf total-transmitted-packets  {
                    type  yang:counter64;
                    description "Total number of packets transmitted out of the queue";
                } // END of total-transmitted-packets definition.

                leaf total-transmitted-octets  {
                    type  yang:counter64;
                    description "Total number of octets transmitted out of the queue";
                } // END of total-transmitted-octets definition.

                leaf total-dropped-packets  {
                    type  yang:counter64;
                    description "Total number of packets dropped in the queue";
                } // END of total-dropped-packets definition.

                leaf total-dropped-octets  {
                    type  yang:counter64;
                    description "Total number of octets dropped in the queue";
                } // END of total-dropped-octets definition.

                leaf green-transmitted-packets  {
                    type  yang:counter64;
                    description "Number of green packets transmitted out of the queue";
                } // END of green-transmitted-packets definition.

                leaf non-green-transmitted-packets  {
                    type  yang:counter64;
                    description "Number of yellow and red (when applicable) packets transmitted out of
                                the queue";
                } // END of non-green-transmitted-packets definition.

                leaf green-dropped-packets  {
                    type  yang:counter64;
                    description "Number of green packets dropped in the queue";
                } // END of green-dropped-packets definition.

                leaf yellow-dropped-packets  {
                    type  yang:counter64;
                    description "Number of yellow packets dropped in the queue";
                } // END of yellow-dropped-packets definition.

                leaf red-dropped-packets  {
                    type  yang:counter64;
                    description "Number of red packets dropped in the queue";
                } // END of red-dropped-packets definition.

                leaf rate-kbps  {
                    type  decimal64 {
                         fraction-digits 6;                    }
                    description "Queue rate in Kbps";
                } // END of rate-kbps definition.

                leaf rate-mbps  {
                    type  decimal64 {
                         fraction-digits 6;                    }
                    description "Queue rate in Mbps";
                } // END of rate-mbps definition.

                leaf rate-gbps  {
                    type  decimal64 {
                         fraction-digits 6;                    }
                    description "Queue rate in Gbps";
                } // END of rate-gbps definition.

            } // END of counters-container definition.
        } // End of queue-list
    } // END of qos-queue-statistics-state definition.
    grouping qos-service-policy-ingress-state {
        description
            "Grouping for QoS input service policy state";
        container class-maps-level-1 {
            config false;
            description
                "Operational state data for QoS input service policy";

            list class-map-level-1 {
                key "class-map-name-level-1";
                config false;
                description
                    "Operational state data list for QoS input service policy";
                leaf class-map-name-level-1  {
                    type  leafref {
                        path  "../state/class-map-name-level-1";
                    }
                    description "Name of the class-map attached to the interface";
                } // END of class-map-name-level-1 definition.

                container state {
                    config false;
                    description
                        "Operational state data for QoS statistics level 1";
                    leaf class-map-name-level-1  {
                        type  string {
                            length "1..1965";
                            pattern "[^?' =,>|]+";
                        }
                        description "Name of the class-map attached to the interface";
                    } // END of class-map-name-level-1 definition.

                    container counters {
                        config false;
                        description
                            "Operational state data for QoS statistics counters";
                        uses qos-qos-statistics-state;
                    } // END of counters-container definition.
                } // END of state-container definition.
                container class-maps-level-2 {
                    config false;
                    description
                        "Operational state data for QoS input service policy";

                    list class-map-level-2 {
                        key "class-map-name-level-2";
                        config false;
                        description
                            "Operational state data list for QoS input service policy";
                        leaf class-map-name-level-2  {
                            type  leafref {
                                path  "../state/class-map-name-level-2";
                            }
                            description "Name of the class-map attached to the interface";
                        } // END of class-map-name-level-2 definition.

                        container state {
                            config false;
                            description
                                "Operational state data for QoS statistics level 2";
                            leaf class-map-name-level-2  {
                                type  string {
                                    length "1..1965";
                                    pattern "[^?' =,>|]+";
                                }
                                description "Name of the class-map attached to the interface";
                            } // END of class-map-name-level-2 definition.

                            container counters {
                                config false;
                                description
                                    "Operational state data for QoS statistics counters";
                                uses qos-qos-statistics-state;
                            } // END of counters-container definition.
                        } // END of state-container definition.
                        container class-maps-level-3 {
                            config false;
                            description
                                "Operational state data for QoS input service policy";

                            list class-map-level-3 {
                                key "class-map-name-level-3";
                                config false;
                                description
                                    "Operational state data list for QoS input service policy";
                                leaf class-map-name-level-3  {
                                    type  leafref {
                                        path  "../state/class-map-name-level-3";
                                    }
                                    description "Name of the class-map attached to the interface";
                                } // END of class-map-name-level-3 definition.

                                container state {
                                    config false;
                                    description
                                        "Operational state data for QoS statistics level 3";
                                    leaf class-map-name-level-3  {
                                        type  string {
                                            length "1..1965";
                                            pattern "[^?' =,>|]+";
                                        }
                                        description "Name of the class-map attached to the interface";
                                    } // END of class-map-name-level-3 definition.

                                    container counters {
                                        config false;
                                        description
                                            "Operational state data for QoS statistics counters";
                                        uses qos-qos-statistics-state;
                                    } // END of counters-container definition.
                                } // END of state-container definition.
                            } // End of class-map-level-3-list
                        } // END of class-maps-level-3-container definition.
                    } // End of class-map-level-2-list
                } // END of class-maps-level-2-container definition.
            } // End of class-map-level-1-list
        } // END of class-maps-level-1-container definition.
    } // END of qos-service-policy-ingress-state definition.
    grouping qos-service-policy-egress-state {
        description
            "Grouping for QoS output service policy state";
        container class-maps-level-1 {
            config false;
            description
                "Operational state data for QoS output service policy";

            list class-map-level-1 {
                key "class-map-name-level-1";
                config false;
                description
                    "Operational state data list for QoS output service policy";
                leaf class-map-name-level-1  {
                    type  leafref {
                        path  "../state/class-map-name-level-1";
                    }
                    description "Name of the class-map attached to the interface";
                } // END of class-map-name-level-1 definition.

                container state {
                    config false;
                    description
                        "Operational state data for QoS statistics level one";
                    leaf class-map-name-level-1  {
                        type  string {
                            length "1..1965";
                            pattern "[^?' =,>|]+";
                        }
                        description "Name of the class-map attached to the interface";
                    } // END of class-map-name-level-1 definition.

                    container queues {
                        config false;
                        description
                            "Operational state data for QoS queue statistics";
                        uses qos-queue-statistics-state;
                    } // END of queues-container definition.
                } // END of state-container definition.
                container class-maps-level-2 {
                    config false;
                    description
                        "Operational state data for QoS input service policy";

                    list class-map-level-2 {
                        key "class-map-name-level-2";
                        config false;
                        description
                            "Operational state data list for QoS input service policy";
                        leaf class-map-name-level-2  {
                            type  leafref {
                                path  "../state/class-map-name-level-2";
                            }
                            description "Name of the class-map attached to the interface";
                        } // END of class-map-name-level-2 definition.

                        container state {
                            config false;
                            description
                                "Operational state data for QoS statistics level two";
                            leaf class-map-name-level-2  {
                                type  string {
                                    length "1..1965";
                                    pattern "[^?' =,>|]+";
                                }
                                description "Name of the class-map attached to the interface";
                            } // END of class-map-name-level-2 definition.

                            container queues {
                                config false;
                                description
                                    "Operational state data for QoS queue statistics";
                                uses qos-queue-statistics-state;
                            } // END of queues-container definition.
                        } // END of state-container definition.
                        container class-maps-level-3 {
                            config false;
                            description
                                "Operational state data for QoS input service policy";

                            list class-map-level-3 {
                                key "class-map-name-level-3";
                                config false;
                                description
                                    "Operational state data list for QoS input service policy";
                                leaf class-map-name-level-3  {
                                    type  leafref {
                                        path  "../state/class-map-name-level-3";
                                    }
                                    description "Name of the class-map attached to the interface";
                                } // END of class-map-name-level-3 definition.

                                container state {
                                    config false;
                                    description
                                        "Operational state data for QoS statistics level three";
                                    leaf class-map-name-level-3  {
                                        type  string {
                                            length "1..1965";
                                            pattern "[^?' =,>|]+";
                                        }
                                        description "Name of the class-map attached to the interface";
                                    } // END of class-map-name-level-3 definition.

                                    container queues {
                                        config false;
                                        description
                                            "Operational state data for QoS queue statistics";
                                        uses qos-queue-statistics-state;
                                    } // END of queues-container definition.
                                } // END of state-container definition.
                            } // End of class-map-level-3-list
                        } // END of class-maps-level-3-container definition.
                    } // End of class-map-level-2-list
                } // END of class-maps-level-2-container definition.
            } // End of class-map-level-1-list
        } // END of class-maps-level-1-container definition.
    } // END of qos-service-policy-egress-state definition.
    grouping qos-service-policy-config {
        description
            "Grouping for QoS service policy configuration";
        leaf type-qos-policy-map-name  {
            type  string {
                length "1..32";
                pattern "[^?' =,>|]+";
            }
            description "Use this attribute to attach a service-policy of type qos to the
                        interface";
        } // END of type-qos-policy-map-name definition.

    } // END of qos-service-policy-config definition.
    grouping qos-service-policy-egress-config {
        description
            "Grouping for QoS service policy egress configuration";
        leaf type-qos-policy-map-name  {
            if-feature feature-list:HAVE_CUSTOM1_QOS;
            type  string {
                length "1..32";
                pattern "[^?' =,>|]+";
            }
            description "Use this attribute to attach a service-policy of type qos to the
                        interface";
        } // END of type-qos-policy-map-name definition.

        leaf type-queuing-policy-map-name  {
            type  string {
                length "1..32";
                pattern "[^?' =,>|]+";
            }
            description "Use this attribute to attach a service-policy of type queue to the
                        interface";
        } // END of type-queuing-policy-map-name definition.

    } // END of qos-service-policy-egress-config definition.
    grouping qos-service-policy-ingress-top {
        description
            "Grouping for QoS input service policy";
        container ingress {
            description
                "Configuration data for QoS input service policy";
            container config {
                description
                    "Configuration data for QoS input service policy";
                uses qos-service-policy-config;
            } // END of config-container definition.
            container state {
                config false;
                description
                    "Operational state data for QoS input service policy";
                uses qos-service-policy-config;
            } // END of state-container definition.
            uses qos-service-policy-ingress-state;
        } // END of ingress-container definition.
    } // END of qos-service-policy-ingress-top definition.
    grouping qos-service-policy-egress-top {
        description
            "Grouping for QoS output service policy";
        container egress {
            description
                "Configuration data for QoS output service policy";
            container config {
                description
                    "Configuration data for QoS output service policy";
                uses qos-service-policy-egress-config;
            } // END of config-container definition.
            container state {
                config false;
                description
                    "Operational state data for QoS output service policy";
                uses qos-service-policy-egress-config;
            } // END of state-container definition.
            uses qos-service-policy-egress-state;
        } // END of egress-container definition.
    } // END of qos-service-policy-egress-top definition.
    grouping qos-service-policy-top {
        description
            "Grouping for QoS service policy";
        container service-policy {
            description
                "Configuration data for QoS service policy";
            uses qos-service-policy-ingress-top;
            uses qos-service-policy-egress-top;
        } // END of service-policy-container definition.
    } // END of qos-service-policy-top definition.

    grouping  interfaces-grouping {
    description
        "Configuration data for interface QoS";
    container interfaces {
        description
            "Configuration data for interface QoS";

        list interface {
        when " not(/ipi-interface:interfaces/ipi-interface:interface/ipi-if-aggregate:member-aggregation) ";
            key "name";
            description
                "Configuration data list for interface QoS";
            leaf name  {
                type  leafref {
                    path  "/ipi-interface:interfaces/ipi-interface:interface/ipi-interface:name";
                }
                description "Interface name for which QoS is being configured";
            } // END of name definition.

            container config {
                description
                    "Configuration data for interface QoS";
                uses qos-interface-config;
            } // END of config-container definition.
            container state {
                config false;
                description
                    "Operational state data for interface QoS";
                uses qos-interface-config;
            } // END of state-container definition.
            uses qos-interface-remark-top;
            uses qos-traffic-shape-top;
            uses qos-map-profile-ref-top;
            uses qos-service-policy-top;
        } // End of interface-list
    } // END of interfaces-container definition.
    } // END of interfaces-grouping definition.

    augment /ipi-qos:qos {
    when " /ipi-qos:qos/ipi-qos:global/ipi-qos:config/ipi-qos:enable-qos ";
        description
            "Configuration data for interface QoS";
        uses interfaces-grouping;
    }


    notification qos-subinterface-default-policy-add-notification {

        description "Add default policy on subif in DB.";

        // severity "INFO";
        // eventClass "MESSAGE";
        leaf message {
            type string;
            description " alarm message notification";
        }
    }

    notification qos-subinterface-default-policy-delete-notification {

        description "Delete default policy on subif in DB.";

        // severity "INFO";
        // eventClass "MESSAGE";
        leaf message {
            type string;
            description " alarm message notification";
        }
    }

    notification qos-subinterface-traffic-shape-add-notification {

        description "Add port shaper from subif in DB.";

        // severity "INFO";
        // eventClass "MESSAGE";
        leaf message {
            type string;
            description " alarm message notification";
        }
    }

    notification qos-subinterface-traffic-shape-delete-notification {

        description "Delete port shaper from subif in DB.";

        // severity "INFO";
        // eventClass "MESSAGE";
        leaf message {
            type string;
            description " alarm message notification";
        }
    }

}
