/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-qos-types.yang
*
*/

module ipi-qos-types {

    yang-version 1.1;

    namespace   "http://www.ipinfusion.com/yang/ocnos/ipi-qos-types";

    prefix "ipi-qos-types";

    import cml-data-types {
        prefix cml-data-types;
    }

    organization
        "IP Infusion Inc.";

    contact
        "Address: 3965 Freedom Circle, Suite 200, Santa Clara, CA 95054
         Phone: +1 408-400-1900
         E-mail: support@ipinfusion.com
         Web: http://www.ipinfusion.com/";

    description
        "Quality of Service (QoS) types";


    revision "2021-03-15" {
        description "Removed qos-default and match-default options from its enum";
        reference "Initial Version";
    }

    revision "2020-12-04" {
        description "Restructured module as per open-config style";
        reference "Initial Version";
    }

    revision "2018-06-21" {
        description "Initial Version";
        reference "Initial Version";
    }



    typedef  qos_dscp_range_t {
        type uint8 {
             range 0..63;
        }
        description "type definition for QOS_DSCP_RANGE_T";
    }

    typedef  qos_precedence_range_t {
        type uint8 {
             range 0..7;
        }
        description "type definition for QOS_PRECEDENCE_RANGE_T";
    }

    typedef  qos_service_direction_t {
        type enumeration {
            enum input {
                value 0;
                description "inbound packets";
            }
        }
        description "type definition for QOS_SERVICE_DIRECTION_T";
    }

    typedef  qos_rate_unit_t {
        type enumeration {
            enum none {
                value 0;
                description "default value";
            }
            enum kbps {
                value 2;
                description "Specifies the unit of kilobits per second";
            }
            enum mbps {
                value 3;
                description "Specifies the unit of megabits per second";
            }
            enum gbps {
                value 4;
                description "Specifies the unit of gigabits per second";
            }
            enum percent {
                value 6;
                description "Specifies the unit in percentage";
            }
        }
        description "type definition for QOS_RATE_UNIT_T";
    }

    typedef  qos_burst_rate_unit_t {
        type enumeration {
            enum none {
                value 0;
                description "default value";
            }
            enum kbytes {
                value 2;
                description "Specifies the units of kilobytes per second";
            }
            enum mbytes {
                value 3;
                description "Specifies the units of megabytes per second";
            }
            enum ms {
                value 4;
                description "Specifies the units of milliseconds";
            }
            enum us {
                value 5;
                description "Specifies the units of microseconds";
            }
        }
        description "type definition for QOS_BURST_RATE_UNIT_T";
    }

    typedef  qos_shape_rate_unit_t {
        type enumeration {
            enum kbps {
                value 2;
                description "Specifies the unit of kilobits per second";
            }
            enum mbps {
                value 3;
                description "Specifies the unit of megabits per second";
            }
            enum gbps {
                value 4;
                description "Specifies the unit of gigabits per second";
            }
        }
        description "type definition for QOS_SHAPE_RATE_UNIT_T";
    }

    typedef  qos_shape_rate_unit_extended_t {
        type enumeration {
            enum bps {
                value 1;
                description "Specifies the unit of bits per second";
            }
            enum kbps {
                value 2;
                description "Specifies the unit of kilobits per second";
            }
            enum mbps {
                value 3;
                description "Specifies the unit of megabits per second";
            }
            enum gbps {
                value 4;
                description "Specifies the unit of gigabits per second";
            }
            enum percent {
                value 6;
                description "Specifies the unit in percentage";
            }
        }
        description "type definition for QOS_SHAPE_RATE_UNIT_EXTENDED_T";
    }

    typedef  qos_policy_map_t {
        type enumeration {
            enum qos {
                value 1;
                description "QoS is ingress/egress policy-map";
            }
            enum queuing {
                value 2;
                description "Queuing is egress policy-map";
            }
            enum queuing-default {
                value 3;
                description "Queuing is egress policy-map,Default queue of port";
            }
        }
        description "type definition for QOS_POLICY_MAP_T";
    }

    typedef  qos_policy_map_class_queuing_default_t {
        type enumeration {
            enum q0 {
                value 0;
                description "Queue 0 and priority 0 lowest";
            }
            enum q1 {
                value 1;
                description "Queue 1 and priority 1";
            }
            enum q2 {
                value 2;
                description "Queue 2 and priority 2";
            }
            enum q3 {
                value 3;
                description "Queue 3 and priority 3";
            }
            enum q4 {
                value 4;
                description "Queue 4 and priority 4";
            }
            enum q5 {
                value 5;
                description "Queue 5 and priority 5";
            }
            enum q6 {
                value 6;
                description "Queue 6 and priority 6";
            }
            enum q7 {
                value 7;
                description "Queue 7 and priority 7 highest";
            }
        }
        description "type definition for QOS_POLICY_MAP_CLASS_QUEUING_DEFAULT_T";
    }

    typedef  qos_policy_map_class_default_t {
        type string;
        description "type definition for QOS_POLICY_MAP_CLASS_DEFAULT_T";
    }

    typedef  qos_policy_map_class_t {
        type union {
            type string {

            }
            type qos_policy_map_class_default_t {

            }
        }
        description "type definition for QOS_POLICY_MAP_CLASS_T";
    }

    typedef  qos_class_mode_t {
        type enumeration {
            enum allow {
                value 1;
                description "Accept flow traffic";
            }
            enum deny {
                value 2;
                description "Drop flow traffic";
            }
        }
        description "type definition for QOS_CLASS_MODE_T";
    }

    typedef  qos_police_t {
        type enumeration {
            enum none {
                value 0;
                description "No policer. Default to colour blind policer";
            }
            enum colour-blind {
                value 1;
                description "Colour blind policer";
            }
            enum colour-aware {
                value 2;
                description "Colour aware policer";
            }
        }
        description "type definition for QOS_POLICE_T";
    }

    typedef  qos_port_action_t {
        type enumeration {
            enum redirect-to-port {
                value 5;
                description "Redirect packet to new interface";
            }
            enum mirror-to-port {
                value 6;
                description "Mirror packet to new interface";
            }
        }
        description "type definition for QOS_PORT_ACTION_T";
    }

    typedef  qos_precedence_t {
        type enumeration {
            enum routine {
                value 0;
                description "Routine precedence(0)";
            }
            enum priority {
                value 1;
                description "Priority precedence(1)";
            }
            enum immediate {
                value 2;
                description "Immediate precedence(2)";
            }
            enum flash {
                value 3;
                description "Flash precedence(3)";
            }
            enum flashoverride {
                value 4;
                description "Flash override precedence(4)";
            }
            enum critical {
                value 5;
                description "Critical precedence(5)";
            }
            enum internet {
                value 6;
                description "Internetwork control precedence(6)";
            }
            enum network {
                value 7;
                description "Network control precedence(7)";
            }
        }
        description "type definition for QOS_PRECEDENCE_T";
    }

    typedef  qos_precedence_extended_t {
        type union {
            type uint8 {
                range "0..7";

            }
            type qos_precedence_t {

            }
        }
        description "type definition for QOS_PRECEDENCE_EXTENDED_T";
    }

    typedef  qos_precedence_val_t {
        type union {
            type cml-data-types:cml_range_t {

            }
            type qos_precedence_t {

            }
        }
        description "type definition for QOS_PRECEDENCE_VAL_T";
    }

    typedef  qos_dscp_t {
        type enumeration {
            enum default {
                value 0;
                description "Default dscp (000000)";
            }
            enum cs1 {
                value 8;
                description "CS1(precedence 1) dscp (001000)";
            }
            enum af11 {
                value 10;
                description "AF11 dscp (001010)";
            }
            enum af12 {
                value 12;
                description "AF12 dscp (001100)";
            }
            enum af13 {
                value 14;
                description "AF13 dscp (001110)";
            }
            enum cs2 {
                value 16;
                description "CS2(precedence 2) dscp (010000)";
            }
            enum af21 {
                value 18;
                description "AF21 dscp (010010)";
            }
            enum af22 {
                value 20;
                description "AF22 dscp (010100)";
            }
            enum af23 {
                value 22;
                description "AF23 dscp (010110)";
            }
            enum cs3 {
                value 24;
                description "CS3(precedence 3) dscp (011000)";
            }
            enum af31 {
                value 26;
                description "AF31 dscp (011010)";
            }
            enum af32 {
                value 28;
                description "AF32 dscp (011100)";
            }
            enum af33 {
                value 30;
                description "AF33 dscp (011110)";
            }
            enum cs4 {
                value 32;
                description "CS4(precedence 4) dscp (100000)";
            }
            enum af41 {
                value 34;
                description "AF41 dscp (100010)";
            }
            enum af42 {
                value 36;
                description "AF42 dscp (100100)";
            }
            enum af43 {
                value 38;
                description "AF43 dscp (100110)";
            }
            enum cs5 {
                value 40;
                description "CS5(precedence 5) dscp (101000)";
            }
            enum ef {
                value 46;
                description "EF dscp (101110)";
            }
            enum cs6 {
                value 48;
                description "CS6(precedence 6) dscp (110000)";
            }
            enum cs7 {
                value 56;
                description "CS7(precedence 7) dscp (111000)";
            }
        }
        description "type definition for QOS_DSCP_T";
    }

    typedef  qos_dscp_extended_t {
        type union {
            type uint8 {
                range "0..63";

            }
            type qos_dscp_t {

            }
        }
        description "type definition for QOS_DSCP_EXTENDED_T";
    }

    typedef  qos_dscp_val_t {
        type union {
            type cml-data-types:cml_range_t {

            }
            type qos_dscp_t {

            }
        }
        description "type definition for QOS_DSCP_VAL_T";
    }

    typedef  qos_dei_t {
        type enumeration {
            enum 0 {
                value 0;
                description "Reset DEI";
            }
            enum 1 {
                value 1;
                description "Set DEI";
            }
            enum all {
                value 2;
                description "all DEI";
            }
        }
        description "type definition for QOS_DEI_T";
    }

    typedef  qos_color_t {
        type enumeration {
            enum green {
                value 0;
                description "Set mapping for green packets";
            }
            enum yellow {
                value 1;
                description "Set mapping for yellow packets";
            }
            enum red {
                value 2;
                description "Set mapping for red packets";
            }
            enum all {
                value 3;
                description "Set mapping for all packets";
            }
        }
        description "type definition for QOS_COLOR_T";
    }

    typedef  qos_clear_stats_t {
        type enumeration {
            enum type-qos {
                value 0;
                description "Type of qos,QoS statistics";
            }
            enum type-qos-input {
                value 1;
                description "Type of qos,QoS statistics,Input direction";
            }
            enum type-qos-output {
                value 2;
                description "Type of qos,QoS statistics,Output direction";
            }
            enum type-queuing {
                value 3;
                description "Type of qos,Queuing statistics";
            }
            enum type-qos-default {
                value 255;
                description "Type of qos,QoS statistics,default";
            }
        }
        description "type definition for QOS_CLEAR_STATS_T";
    }

    typedef  qos_class_map_t {
        type enumeration {
            enum qos {
                value 1;
                description "qos is ingress/egress class-map";
            }
            enum queuing {
                value 2;
                description "Match on Egress Queuing class";
            }
            enum queuing-default {
                value 3;
                description "Default queuing";
            }
        }
        description "type definition for QOS_CLASS_MAP_T";
    }

    typedef  qos_threshold_t {
        type enumeration {
            enum packets {
                value 1;
                description "Number of Packets (max 614400)";
            }
            enum bytes {
                value 2;
                description "bytes (max 629145600)";
            }
            enum kbytes {
                value 3;
                description "kilo-bytes (max 614400)";
            }
            enum mbytes {
                value 4;
                description "mega-bytes (max 600)";
            }
            enum ms {
                value 6;
                description "milli-seconds (max 50)";
            }
            enum us {
                value 7;
                description "micro-seconds (max 50000)";
            }
        }
        description "type definition for QOS_THRESHOLD_T";
    }

    typedef  qos_profile_name_default_t {
        type enumeration {
            enum default {
                value 0;
                description "default";
            }
        }
        description "type definition for QOS_PROFILE_NAME_DEFAULT_T";
    }

    typedef  qos_conform_action_t {
        type enumeration {
            enum none {
                value 0;
                description "Sets the action to take when the data rate is within bounds";
            }
            enum transmit {
                value 1;
                description "Specifies the action of transmitting packets";
            }
            enum set-dscp-transmit {
                value 2;
                description "Specify the IP DSCP value 0 to 63";
            }
            enum set-prec-transmit {
                value 3;
                description "Specify the IP Precedence value 0 to 7";
            }
            enum set-cos-transmit {
                value 4;
                description "Specify the cos value 0 to 7";
            }
            enum set-mpls-class {
                value 5;
                description "Set the mpls class filed to the give value and tx the packet";
            }
            enum set-qos-transmit {
                value 6;
                description "Specify the qos value";
            }
        }
        description "type definition for QOS_CONFORM_ACTION_T";
    }

    typedef  qos_exceed_action_t {
        type enumeration {
            enum none {
                value 0;
                description "default value";
            }
            enum drop {
                value 1;
                description "Sets the action to take when the data rate is exceeded. Default is drop";
            }
            enum set-dscp-transmit {
                value 2;
                description "Specify the IP DSCP value 0 to 63";
            }
            enum set-prec-transmit {
                value 3;
                description "Specify the IP Precedence value 0 to 7";
            }
            enum set-cos-transmit {
                value 4;
                description "Specify the cos value 0 to 7";
            }
            enum set-mpls-class {
                value 5;
                description "Set the mpls class filed to the give value and tx the packet";
            }
            enum set-flow-control {
                value 6;
                description "Send a pause frame on the ingress port and pass the packet";
            }
            enum set-axe-ret {
                value 7;
                description "Send a pause frame on the ingress port and pass the packet";
            }
            enum transmit {
                value 8;
                description "Pass the packet by setting DEI";
            }
        }
        description "type definition for QOS_EXCEED_ACTION_T";
    }

    typedef  qos_violate_action_t {
        type enumeration {
            enum none {
                value 0;
                description "default value";
            }
            enum drop {
                value 1;
                description "Sets the action to take when the data rate is exceeded. Default is drop";
            }
            enum set-dscp-transmit {
                value 2;
                description "Specify the IP DSCP value 0 to 63";
            }
            enum set-cos-transmit {
                value 4;
                description "Specify the cos value 0 to 7";
            }
            enum set-mpls-class {
                value 5;
                description "Set the mpls class filed to the give value and tx the packet";
            }
            enum transmit {
                value 8;
                description "Pass the packet by setting DEI";
            }
        }
        description "type definition for QOS_VIOLATE_ACTION_T";
    }

    typedef  qos_match_criteria_t {
        type enumeration {
            enum match-all {
                value 1;
                description "match all";
            }
            enum match-any {
                value 2;
                description "match any";
            }
        }
        description "type definition for QOS_MATCH_CRITERIA_T";
    }

    typedef  qos_service_police_type_t {
        type enumeration {
            enum qos-default {
                value 0;
                description "type default value";
            }
            enum qos {
                value 1;
                description "type qos";
            }
            enum queue {
                value 2;
                description "type queue";
            }
        }
        description "type definition for QOS_SERVICE_POLICE_TYPE_T";
    }

    typedef  qos_set_remark_t {
        type enumeration {
            enum port {
                value 1;
                description "port";
            }
            enum interface {
                value 2;
                description "interface";
            }
            enum precedence {
                value 3;
                description "precedence";
            }
            enum cos {
                value 4;
                description "cos";
            }
            enum dscp {
                value 5;
                description "dscp";
            }
            enum queue {
                value 6;
                description "queue";
            }
            enum vlan {
                value 7;
                description "vlan";
            }
        }
        description "type definition for QOS_SET_REMARK_T";
    }

    typedef  qos_vxlan_dir_t {
        type enumeration {
            enum ingress {
                value 0;
                description "Apply ingress direction";
            }
            enum egress {
                value 1;
                description "Apply Egress direction";
            }
        }
        description "type definition for QOS_VXLAN_DIR_T";
    }

    typedef  qos_traffic_type_t {
        type enumeration {
            enum l2-mc {
                value 3;
                description "L2 Multicast";
            }
            enum l2-bc {
                value 5;
                description "L2 Broadcast";
            }
            enum default {
                value 6;
                description "L2 traffic-type all";
            }
            enum l2-unknown {
                value 7;
                description "Unknown L2 traffic";
            }
        }
        description "type definition for QOS_TRAFFIC_TYPE_T";
    }

    typedef  qos_layer4_protocol_t {
        type enumeration {
            enum any {
                value 0;
                description "Specify ANY protocol- TCP/UDP";
            }
            enum tcp {
                value 1;
                description "Specify TCP protocol";
            }
            enum udp {
                value 2;
                description "Specify UDP protocol";
            }
        }
        description "type definition for QOS_LAYER4_PROTOCOL_T";
    }

    typedef  qos_layer4_port_t {
        type enumeration {
            enum source-port {
                value 1;
                description "Specify source TCP/UDP port";
            }
            enum destination-port {
                value 2;
                description "Specify destination TCP/UDP port";
            }
        }
        description "type definition for QOS_LAYER4_PORT_T";
    }

    typedef  cml_remark_state_t {
        type enumeration {
            enum disable {
                value 1;
                description "Disable remarking";
            }
            enum enable {
                value 2;
                description "Enable remarking";
            }
        }
        description "type definition for CML_REMARK_STATE_T";
    }

    typedef  qos_scheduler_queue_t {
        type enumeration {
            enum strict-priority-or-default-wrr-weight {
                value 1;
                description "Strict priority or default WRR weight";
            }
            enum wrr {
                value 2;
                description "WRR";
            }
        }
        description "type definition for QOS_SCHEDULER_QUEUE_T";
    }

    typedef  qos_type_queue_t {
        type enumeration {
            enum cos-list-wred {
                value 0;
                description "Cos list wred";
            }
            enum cos-based-wred {
                value 1;
                description "Cos based wred";
            }
            enum tail-drop {
                value 2;
                description "Tail drop";
            }
            enum bandwich {
                value 3;
                description "Bandwich";
            }
            enum shape {
                value 4;
                description "Shape";
            }
            enum priority-set {
                value 5;
                description "Priority set";
            }
            enum bandwich-set {
                value 6;
                description "Bandwich set";
            }
            enum shaping-set {
                value 7;
                description "Shaping set";
            }
            enum service-policy-set {
                value 8;
                description "Service policy set";
            }
            enum wrr-set {
                value 9;
                description "WRR set";
            }
            enum attach {
                value 10;
                description "Attach";
            }
            enum detach {
                value 11;
                description "Detach";
            }
            enum class-default {
                value 12;
                description "Class default";
            }
            enum compensation {
                value 13;
                description "Compensation";
            }
            enum delay-profile {
                value 14;
                description "Delay profile";
            }
        }
        description "type definition for QOS_TYPE_QUEUE_T";
    }

}
