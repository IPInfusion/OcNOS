/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-lldp-types.yang
*
*/

module ipi-lldp-types {

    namespace   "http://www.ipinfusion.com/yang/ocnos/ipi-lldp-types";

    prefix "ipi-lldp-types";

    organization
        "IP Infusion Inc.";

    contact
        "Address: 3965 Freedom Circle, Suite 200, Santa Clara, CA 95054
         Phone: +1 408-400-1900
         E-mail: support@ipinfusion.com
         Web: http://www.ip    infusion.com/";

    description
        "YANG version of the ipi-lldp-types";


    revision "2018-06-21" {
        description " Initial Version.";
        reference "Initial Version";
    }



typedef  LLDP_PROTOID_T {
    type bits {
        bit Spanning-Tree-Protocol {
            position 0;
            description "None";
        }
        bit Rapid-Spanning-Tree-Protocol {
            position 1;
            description "None";
        }
        bit Multiple-Spanning-Tree-Protocol {
            position 2;
            description "None";
        }
        bit GARP-Multicast-Registration-Protocol {
            position 3;
            description "None";
        }
        bit MRP-Multicast-Registration-Protocol {
            position 4;
            description "None";
        }
        bit GARP-VLAN-Registration-Protocol {
            position 5;
            description "None";
        }
        bit MRP-VLAN-Registration-Protocol {
            position 6;
            description "None";
        }
        bit Link-Aggregation {
            position 7;
            description "None";
        }
        bit Port-Authentication {
            position 8;
            description "None";
        }
        bit Ethernet-OAM {
            position 9;
            description "None";
        }
        bit Unknown {
            position 10;
            description "None";
        }
    }
    description "type definition for LLDP_PROTOID_T";
}

typedef  LLDP_MEDDEV_T {
    type enumeration {
        enum ep-class1 {
            value 1;
            description "ep-class1";
        }
        enum ep-class2 {
            value 2;
            description "ep-class2";
        }
        enum ep-class3 {
            value 3;
            description "ep-class3";
        }
        enum net-connect {
            value 4;
            description "net-connect";
        }
    }
    description "type definition for LLDP_MEDDEV_T";
}

typedef  LLDP_AGENT_T {
    type enumeration {
        enum non-tpmr-bridge {
            value 0;
            description "Non-TPMR-bridge";
        }
        enum customer-bridge {
            value 1;
            description "Customer-bridge";
        }
        enum default {
            value 2;
            description "default-bridge";
        }
    }
    description "type definition for LLDP_AGENT_T";
}

typedef  LLDP_ENABLE_T {
    type enumeration {
        enum rxonly {
            value 2;
            description "LLDP Recieve Only Mode";
        }
        enum txonly {
            value 4;
            description "LLDP Transmit Only Mode";
        }
        enum txrx {
            value 8;
            description "LLDP Transmit and Recieve Mode";
        }
    }
    description "type definition for LLDP_ENABLE_T";
}

typedef  LLDP_MGMT_ADDR_T {
    type enumeration {
        enum mac-address {
            value 1;
            description "Use the MAC address as the Management Address";
        }
        enum ip-address {
            value 2;
            description "Use the ip address as the Management Address";
        }
    }
    description "type definition for LLDP_MGMT_ADDR_T";
}

typedef  LLDP_CHASSIS_T {
    type enumeration {
        enum if-alias {
            value 0;
            description "Use the Interface Alias as the chassis-id";
        }
        enum ip-address {
            value 1;
            description "Use the ip-address as the chassis-id";
        }
        enum mac-address {
            value 2;
            description "Use the mac-address as the chassis-id";
        }
        enum if-name {
            value 3;
            description "Use the if-name as the chassis-id";
        }
        enum locally-assigned {
            value 4;
            description "Use the locally-assigned as the chassis-id";
        }
    }
    description "type definition for LLDP_CHASSIS_T";
}

typedef  LLDP_PORT_T {
    type enumeration {
        enum if-alias {
            value 1;
            description "Use the Interface Alias as the port-id-TLV";
        }
        enum mac-address {
            value 2;
            description "Use the mac-address as the port-id-TLV";
        }
        enum ip-address {
            value 3;
            description "Use the ip-address as the port-id-TLV";
        }
        enum if-name {
            value 4;
            description "Use the if-name as the port-id-TLV";
        }
        enum agt-circuit-id {
            value 5;
            description "Use the agt-circuit-id as the port-id-TLV";
        }
        enum locally-assigned {
            value 6;
            description "Use the locally-assigned as the port-id-TLV";
        }
    }
    description "type definition for LLDP_PORT_T";
}

typedef  LLDP_MED_T {
    type enumeration {
        enum media-capabilities {
            value 1;
            description "media-capabilties";
        }
        enum network-policy {
            value 2;
            description "network-policy";
        }
        enum location {
            value 3;
            description "location";
        }
        enum inventory {
            value 5;
            description "inventory";
        }
    }
    description "type definition for LLDP_MED_T";
}

typedef  LLDP_DEBUG_T {
    type bits {
        bit event {
            position 0;
            description "enable event debugs";
        }
        bit rx {
            position 1;
            description "enable rx debugs";
        }
        bit tx {
            position 2;
            description "enable tx debugs";
        }
        bit message {
            position 3;
            description "enable nsm-message debugs";
        }
        bit ha {
            position 4;
            description "enable ha debugs";
        }
    }
    description "type definition for LLDP_DEBUG_T";
}

typedef  LLDP_DCB_TLV_MODE_T {
    type enumeration {
        enum manual {
            value 1;
            description "Disable";
        }
        enum auto {
            value 2;
            description "Enable";
        }
    }
    description "type definition for LLDP_DCB_TLV_MODE_T";
}

typedef  LLDP_TLV_SELECT_TYPE {
    type enumeration {
        enum not-set {
            value 0;
            description "lldp tlv option not set";
        }
        enum select {
            value 1;
            description "Select lldp tlv to send";
        }
        enum unselect {
            value 2;
            description "Unselect lldp tlv not to send";
        }
    }
    description "type definition for LLDP_TLV_SELECT_TYPE";
}

}
