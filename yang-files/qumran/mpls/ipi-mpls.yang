/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-mpls.yang
*
*/

module ipi-mpls {

    yang-version 1.1;

    namespace   "http://www.ipinfusion.com/yang/ocnos/ipi-mpls";

    prefix "ipi-mpls";

    import cml-data-types {
        prefix cml-data-types;
    }

    import ipi-mpls-types {
        prefix ipi-mpls-types;
    }

    import ipi-interface {
        prefix ipi-interface;
    }

    import feature-list {
        prefix feature-list;
    }

    organization
        "IP Infusion Inc.";

    contact
        "Address: 3965 Freedom Circle, Suite 200, Santa Clara, CA 95054
         Phone: +1 408-400-1900
         E-mail: support@ipinfusion.com
         Web: http://www.ipinfusion.com/";

    description
        "Data model for MPLS";


    revision "2021-01-27" {
        description "Change for restructuring Label Management and admin group CLIs";
        reference " 0.3.0.";
    }

    revision "2020-12-15" {
        description "Change to have data-types in lower case instead of camel case";
        reference " 0.2.0.";
    }

    revision "2020-11-03" {
        description "Initial Version";
        reference " 0.1.0.";
    }

    grouping mpls-global-config {
        description
            "MPLS global configuration";
        leaf local-packet-handling  {
            type  empty;
            description "Use this attribute to enable the labeling of locally generated TCP
                        packets. All other locally generated packets are not looked at by the
                        MPLS Forwarder";
        } // END of local-packet-handling definition.

        leaf lsp-stitching  {
            type  empty;
            description "Use this attribute to enable lsp stitching for ILM and installed FTM";
        } // END of lsp-stitching definition.

        leaf propagate-ttl  {
            type  empty;
            description "Use this attribute to enable TTL propagation. Enabling TTL propagation
                        causes the TTL value in the IP header to be copied onto the TTL field
                        in the shim header, at the LSP ingress";
        } // END of propagate-ttl definition.

        leaf ingress-ttl-value  {
            type  uint8 {
                 range "0..255"  {
                    description "TTL value to be used";
                 }
            }
            description "Use this attribute to set a Time to Live (TTL) value for LSPs for
                        which this LSR is the ingress.";
        } // END of ingress-ttl-value definition.

        leaf diffserv-te-enable  {
            if-feature feature-list:HAVE_DSTE;
            type  empty;
            description "Use this attribute to enable Differentiated Services globally.";
        } // END of diffserv-te-enable definition.

        leaf egress-ttl-value  {
            if-feature feature-list:NOT_HAVE_USER_HSL;
            type  uint8 {
                 range "0..255"  {
                    description "TTL value to be used";
                 }
            }
            description "mpls egress-ttl . Use this attribute to set a custom Time to Live
                        (TTL) value for LSPs for which this LSR is the egress";
        } // END of egress-ttl-value definition.

        leaf lsp-model-uniform  {
            type  empty;
            description "Use this attribute to configure the MPLS LSP model as Uniform.";
        } // END of lsp-model-uniform definition.

    } // END of mpls-global-config definition.
    grouping mpls-debug-config {
        description
            "Grouping for MPLS Debug Level Configurations";
        leaf mpls-log-options  {
            type  cml-data-types:cml_nsm_mpls_log_t;
            description "Use this attribute to exercise logging control. This command interacts
                        with the Linux kernel. When using the kernel logging utility - klogd -
                        it needs to be enabled to a logging level that allows for the
                        requested log messages to be printed.";
        } // END of mpls-log-options definition.

    } // END of mpls-debug-config definition.
    grouping mpls-interface-label-switching-config {
        description
            "interface label switching configuration";
        leaf enable  {
            type  empty;
            mandatory true;
            description "Use this attribute to enable label-switching on a TE link";
        } // END of enable definition.

        leaf label-space  {
            type  uint16 {
                 range "0..60000"  {
                    description "label space value";
                 }
            }
            description "Use this attribute to specify label-space for the interface, at
                        present only label space 0 is supported";
        } // END of label-space definition.

    } // END of mpls-interface-label-switching-config definition.
    grouping mpls-admin-group-config {
        description
            "MPLS Administrative Group Configurations";
        leaf name  {
            type  string {
                length "1..max";
                pattern "[^?' =,>|]+";
            }
            description "Use this attribute to create a name-to-value binding for an
                        administrative group";
        } // END of name definition.

        leaf id  {
            type  uint8 {
                 range "0..31"  {
                    description "Value of administrative group to be added";
                 }
            }
            description "identifier value for the administrative group";
        } // END of id definition.

    } // END of mpls-admin-group-config definition.
    grouping mpls-interface-bandwidth-config {
        description
            "MPLS Interface Bandwidth Configurations";
        leaf-list admin-group-name  {
            if-feature feature-list:HAVE_TE;
            type  string {
                length "1..max";
                pattern "[^?' =,>|]+";
            }
            description "Use this attribute to create an administrative group to be used for
                        links. Each link can be a member of one or more, or no administrative
                        groups.this attribute adds link between an interface and a group. The
                        name is the name of the group previously configured. There can be
                        multiple groups per interface.";
        } // END of admin-group-name definition.

    } // END of mpls-interface-bandwidth-config definition.
    grouping label-space-config {
        description
            "Label space configuration";
        leaf label-space-name  {
            type  uint16 {
                 range "0..60000"  {
                    description "Label-space value";
                 }
            }
            description "This attribute identifies the label space";
        } // END of label-space-name definition.

    } // END of label-space-config definition.
    grouping label-range-config {
        description
            "Label Range configuration";
        leaf min-label  {
            type  uint32 {
                 range "16..1048575"  {
                    description "Minimum size to be used for label pools or protocol range";
                 }
            }
            mandatory true;
            description "Use this attribute to configure a minimum label value for a label
                        space. After setting a minimum label value for a label space, make
                        sure to bind the label space to an interface.";
        } // END of min-label definition.

        leaf max-label  {
            type  uint32 {
                 range "16..1048575"  {
                    description "Maximum size to be used for label pools or protocol range";
                 }
            }
            mandatory true;
            description "Use this attribute to configure a maximum label value for a label
                        space. After setting a maximum label value for a label space, make
                        sure to bind the label space to an interface";
        } // END of max-label definition.

    } // END of label-range-config definition.
    grouping module-label-range-config {
        description
            "Module Label Range configurations";
        leaf module-name  {
            type  ipi-mpls-types:mpls_module_t;
            description "Use this attribute to specify the protocol module for which label
                        range is specified";
        } // END of module-name definition.

        uses label-range-config;
    } // END of module-label-range-config definition.
    grouping l2vpn-customer-service-map-state {
        description
            "Grouping for Operational attributes for service-template mapping list";
        leaf vpls-name  {
            type  string {
                length "1..max";
                pattern "[^?' =,>|]+";
            }
            description "Use this attribute to retrieve confgiured VPLS instance details";
        } // END of vpls-name definition.

        leaf error-status  {
            type  ipi-mpls-types:mpls_l2vpn_serv_temp_error_status_t;
            description "Use this attribute to retrieve error status";
        } // END of error-status definition.

        leaf binding-interface-name  {
            type  string {
                length "1..max";
                pattern "[^?' =,>|]+";
            }
            description "Use this attribute to retrieve binded interface details for a
                        confgiured VPLS instance";
        } // END of binding-interface-name definition.

    } // END of l2vpn-customer-service-map-state definition.
    grouping l2vpn-access-circuit-group-config {
        description
            "Grouping for Configuration attributes for access-circuit-group";
        leaf group-name  {
            type  string {
                length "1..max";
                pattern "[^?' =,>|]+";
            }
            description "Use this attribute to create a new access circuit group for MPLS";
        } // END of group-name definition.

        leaf group-identifier  {
            type  uint32 {
                 range "1..4294967295"  {
                    description "Identifier for the group (group-id to be used in LDP)";
                 }
            }
            mandatory true;
            description "Specify group identifier for access circuit group";
        } // END of group-identifier definition.

    } // END of l2vpn-access-circuit-group-config definition.
    grouping l2vpn-access-circuit-group-top {
        description
            "Top level Grouping for access-circuit-group";

        list access-circuit-group {
            key "group-name";
            description
                "List for config data for access-circuit-group";
            leaf group-name  {
                type  leafref {
                    path  "../config/group-name";
                }
                description "Use this attribute to create a new access circuit group for MPLS";
            } // END of group-name definition.

            container config {
                description
                    "Configuration container for access circuit group";
                uses l2vpn-access-circuit-group-config;
            } // END of config-container definition.
            container state {
                config false;
                description
                    "Container for Operationa attributes for access circuit group";
                uses l2vpn-access-circuit-group-config;
            } // END of state-container definition.
        } // End of access-circuit-group-list
    } // END of l2vpn-access-circuit-group-top definition.
    grouping customer-service-map-top {
        description
            "Grouping for Operational attributes for service-template mapping";

        list map-list {
            key "vpls-name";
            config false;
            description
                "List for Operational data for Customer Service mapping";
            leaf vpls-name  {
                type  leafref {
                    path  "../state/vpls-name";
                }
                description "Use this attribute to retrieve confgiured VPLS instance details";
            } // END of vpls-name definition.

            container state {
                config false;
                description
                    "Operation state data for map-list";
                uses l2vpn-customer-service-map-state;
            } // END of state-container definition.
        } // End of map-list-list
    } // END of customer-service-map-top definition.
    grouping customer-service-template-config {
        description
            "Configuration attributes for customer-service-template";
        leaf name  {
            type  string {
                length "1..32";
                pattern "[a-zA-Z0-9_-]*";
            }
            description "Specify service template name";
        } // END of name definition.

        leaf match-all  {
            when " not(/ipi-mpls:mpls/ipi-mpls:l2vpn/ipi-mpls:customer-service-template/ipi-mpls:config/ipi-mpls:match-single-tag-outer-vlan-range) + not(/ipi-mpls:mpls/ipi-mpls:l2vpn/ipi-mpls:customer-service-template/ipi-mpls:config/ipi-mpls:match-untagged) + not(/ipi-mpls:mpls/ipi-mpls:l2vpn/ipi-mpls:customer-service-template/ipi-mpls:double-tag/ipi-mpls:match-outer-vlan-id) ";
            type  empty;
            description "Use this attribute to specify match criteria as match all";
        } // END of match-all definition.

        leaf-list match-single-tag-outer-vlan-range  {
            type  cml-data-types:cml_range_t;
            description "Use this attribute to set match type with outer vlan value";
        } // END of match-single-tag-outer-vlan-range definition.

        leaf match-untagged  {
            when " not(/ipi-mpls:mpls/ipi-mpls:l2vpn/ipi-mpls:customer-service-template/ipi-mpls:config/ipi-mpls:match-all) + not(/ipi-mpls:mpls/ipi-mpls:l2vpn/ipi-mpls:customer-service-template/ipi-mpls:config/ipi-mpls:match-single-tag-outer-vlan-range) + not(/ipi-mpls:mpls/ipi-mpls:l2vpn/ipi-mpls:customer-service-template/ipi-mpls:double-tag/ipi-mpls:match-outer-vlan-id) ";
            type  empty;
            description "Use this attribute to specify match criteria as match untagged";
        } // END of match-untagged definition.

    } // END of customer-service-template-config definition.
    grouping customer-service-template-double-tag-top {
        description
            "Top level groupig for customer-service-template double-tag attributes";

        list double-tag {
        when " not(/ipi-mpls:mpls/ipi-mpls:l2vpn/ipi-mpls:customer-service-template/ipi-mpls:config/ipi-mpls:match-all) + not(/ipi-mpls:mpls/ipi-mpls:l2vpn/ipi-mpls:customer-service-template/ipi-mpls:config/ipi-mpls:match-untagged) + not(/ipi-mpls:mpls/ipi-mpls:l2vpn/ipi-mpls:customer-service-template/ipi-mpls:config/ipi-mpls:match-single-tag-outer-vlan-range) ";
            key "match-outer-vlan-id match-inner-vlan-id";
            description
                "Configuration for double-tag configurations";
            leaf match-outer-vlan-id  {
                type  leafref {
                    path  "../config/match-outer-vlan-id";
                }
                description "Specify outer vlan id for match double tag";
            } // END of match-outer-vlan-id definition.

            leaf match-inner-vlan-id  {
                type  leafref {
                    path  "../config/match-inner-vlan-id";
                }
                description "Specify inner vlan id for match double tag";
            } // END of match-inner-vlan-id definition.

            container config {
                description
                    "Configuration container for double-tag configurations";
                uses customer-service-template-double-tag-config;
            } // END of config-container definition.
            container state {
                config false;
                description
                    "Container for Operationa attributes for double-tag";
                uses customer-service-template-double-tag-config;
            } // END of state-container definition.
        } // End of double-tag-list
    } // END of customer-service-template-double-tag-top definition.
    grouping customer-service-template-double-tag-config {
        description
            "Grouping for double-tag attributes";
        leaf match-outer-vlan-id  {
            type  uint16 {
                 range "1..4094"  {
                    description "Outer vid value";
                 }
            }
            description "Specify outer vlan id for match double tag";
        } // END of match-outer-vlan-id definition.

        leaf match-inner-vlan-id  {
            type  uint16 {
                 range "1..4094"  {
                    description "Inner vid value";
                 }
            }
            description "Specify inner vlan id for match double tag";
        } // END of match-inner-vlan-id definition.

    } // END of customer-service-template-double-tag-config definition.
    grouping customer-service-template-action-type-top {
        description
            "Top level groupig for customer-service-template action-type attributes";

        list action-type {
            key "vlan-action-type";
            description
                "Configuration for action-type configurations";
            leaf vlan-action-type  {
                type  leafref {
                    path  "../config/vlan-action-type";
                }
                description "Specify rewrite ingress action type";
            } // END of vlan-action-type definition.

            container config {
                description
                    "Configuration container for action-type configurations";
                uses customer-service-template-action-type-config;
            } // END of config-container definition.
            container state {
                config false;
                description
                    "Container for Operationa attributes for action-type";
                uses customer-service-template-action-type-config;
            } // END of state-container definition.
        } // End of action-type-list
    } // END of customer-service-template-action-type-top definition.
    grouping customer-service-template-action-type-config {
        description
            "Grouping for action-type attributes";
        leaf vlan-action-type  {
            type  ipi-mpls-types:mpls_l2vpn_vlan_action_type_t;
            description "Specify rewrite ingress action type";
        } // END of vlan-action-type definition.

        leaf outer-vlan-identifier  {
            when " /ipi-mpls:mpls/ipi-mpls:l2vpn/ipi-mpls:customer-service-template/ipi-mpls:action-type/ipi-mpls:config/ipi-mpls:vlan-action-type != '1' ";
            type  uint16 {
                 range "1..4094"  {
                    description "Vid range";
                 }
            }
            description "Spefiy vlan identifier for action types push and translate`";
        } // END of outer-vlan-identifier definition.

        leaf tag-protocol-identifier  {
            when " /ipi-mpls:mpls/ipi-mpls:l2vpn/ipi-mpls:customer-service-template/ipi-mpls:action-type/ipi-mpls:config/ipi-mpls:vlan-action-type != '2' ";
            type  ipi-mpls-types:mpls_svc_tpid_t;
            default "dot1.q";
            description "Specify tag protocol identofier for action types pop and translate";
        } // END of tag-protocol-identifier definition.

    } // END of customer-service-template-action-type-config definition.
    grouping l2vpn-service-template-top {
        description
            "Top level Grouping for service template";

        list customer-service-template {
            key "name";
            description
                "List for config data for Customer Service Templat";
            leaf name  {
                type  leafref {
                    path  "../config/name";
                }
                description "Specify service template name";
            } // END of name definition.

            container config {
                description
                    "Configuration container for Service-template configurations";
                uses customer-service-template-config;
            } // END of config-container definition.
            container state {
                config false;
                description
                    "Container for Operationa attributes for Service-template";
                uses customer-service-template-config;
            } // END of state-container definition.
            uses customer-service-template-double-tag-top;
            uses customer-service-template-action-type-top;
            uses customer-service-map-top;
        } // End of customer-service-template-list
    } // END of l2vpn-service-template-top definition.

    grouping  mpls-grouping {
    description
        "Top level container for MPLS, including configuration and state data";
    container mpls {
        description
            "Top level container for MPLS, including configuration and state data";

        list label-space {
        when " /ipi-mpls:mpls/ipi-mpls:label-space/ipi-mpls:module-label-range/ipi-mpls:config  or /ipi-mpls:mpls/ipi-mpls:label-space/ipi-mpls:global-label-range ";
            key "label-space-name";
            description
                "MPLS Label-Space Configurations";
            leaf label-space-name  {
                type  leafref {
                    path  "../config/label-space-name";
                }
                description "This attribute identifies the label space";
            } // END of label-space-name definition.


            list module-label-range {
                key "module-name";
                description
                    "MPLS Module Label Range Configurations";
                leaf module-name  {
                    type  leafref {
                        path  "../config/module-name";
                    }
                    description "Use this attribute to specify the protocol module for which label
                                range is specified";
                } // END of module-name definition.

                container config {
                    description
                        "Config container for MPLS Module Label Range configuration";
                    uses module-label-range-config;
                } // END of config-container definition.
                container state {
                    config false;
                    description
                        "Operational state data for MPLS Module Label Range";
                    uses module-label-range-config;
                } // END of state-container definition.
            } // End of module-label-range-list
            container config {
                description
                    "Config container for MPLS Label Space Configurations";
                uses label-space-config;
            } // END of config-container definition.
            container state {
                config false;
                description
                    "Operational state container for MPLS Label Space";
                uses label-space-config;
            } // END of state-container definition.
            container global-label-range {
                description
                    "MPLS Global Label Range Configurations";
                container config {
                    presence "Global Label Range is configured for the label space";
                    description
                        "Config Container for MPLS Global Label Range Configurations";
                    uses label-range-config;
                } // END of config-container definition.
                container state {
                    config false;
                    description
                        "Operational state container for MPLS Global Label Range";
                    uses label-range-config;
                } // END of state-container definition.
            } // END of global-label-range-container definition.
        } // End of label-space-list

        list admin-group {
            if-feature feature-list:HAVE_TE;
            key "name id";
            description
                "MPLS Administrative Group Configurations";
            leaf name  {
                type  leafref {
                    path  "../config/name";
                }
                description "Use this attribute to create a name-to-value binding for an
                            administrative group";
            } // END of name definition.

            leaf id  {
                type  leafref {
                    path  "../config/id";
                }
                description "identifier value for the administrative group";
            } // END of id definition.

            container config {
                description
                    "Config Container for MPLS Administrative Groups";
                uses mpls-admin-group-config;
            } // END of config-container definition.
            container state {
                config false;
                description
                    "State Contatiner for MPLS Administrative Groups";
                uses mpls-admin-group-config;
            } // END of state-container definition.
        } // End of admin-group-list
        container l2vpn {
            description
                "Top Level container for l2vpn objects";
            uses l2vpn-service-template-top;
            uses l2vpn-access-circuit-group-top;
        } // END of l2vpn-container definition.
        container global {
            description
                "MPLS global configuration";
            container config {
                description
                    "MPLS global configuration";
                uses mpls-global-config;
            } // END of config-container definition.
            container state {
                config false;
                description
                    "Global MPLS Operational state data";
                uses mpls-global-config;
            } // END of state-container definition.
        } // END of global-container definition.
        container interfaces {
            description
                "mpls interface level configuration and state data";

            list interface {
            when " /ipi-mpls:mpls/ipi-mpls:interfaces/ipi-mpls:interface/ipi-mpls:label-switching/ipi-mpls:config/ipi-mpls:enable  or /ipi-mpls:mpls/ipi-mpls:interfaces/ipi-mpls:interface/ipi-mpls:mpls-interface-bandwidth/ipi-mpls:config/ipi-mpls:admin-group-name ";
                key "name";
                description
                    "List of MPLS enabled interfaces on the device.";
                leaf name  {
                    type  leafref {
                        path  "/ipi-interface:interfaces/ipi-interface:interface/ipi-interface:config/ipi-interface:name";
                    }
                    description "The textual name of the interface.";
                } // END of name definition.

                container label-switching {
                    when " /ipi-interface:interfaces/ipi-interface:interface/ipi-interface:config/ipi-interface:switchport-status != 'true' ";
                    description
                        "Label switching configuration";
                    container config {
                        presence "Enable label switching for interface";
                        description
                            "Label switching configuration";
                        uses mpls-interface-label-switching-config;
                    } // END of config-container definition.
                    container state {
                        config false;
                        description
                            "Operational state for Label switching configuration";
                        uses mpls-interface-label-switching-config;
                    } // END of state-container definition.
                } // END of label-switching-container definition.
                container mpls-interface-bandwidth {
                    description
                        "MPLS Interface Bandwidth Configurations";
                    container config {
                        description
                            "Configurations for MPLS Interface Bandwidth";
                        uses mpls-interface-bandwidth-config;
                    } // END of config-container definition.
                    container state {
                        config false;
                        description
                            "Operational state for MPLS Interface Bandwidth";
                        uses mpls-interface-bandwidth-config;
                    } // END of state-container definition.
                } // END of mpls-interface-bandwidth-container definition.
            } // End of interface-list
        } // END of interfaces-container definition.
        container debug {
            if-feature feature-list:HAVE_MPLS_FWD;
            description
                "mpls debug level configuration and state data";
            container config {
                description
                    "mpls debug level configuration";
                uses mpls-debug-config;
            } // END of config-container definition.
            container state {
                config false;
                description
                    "Operational state data for MPLS Debug";
                uses mpls-debug-config;
            } // END of state-container definition.
        } // END of debug-container definition.
    } // END of mpls-container definition.
    } // END of mpls-grouping definition.

    uses mpls-grouping;

    rpc mpls-snmp-traps {
        description "Use this RPC to enable/disable SNMP trap notifications for MPLS";
        input  {
            leaf trap-notify  {
                type cml-data-types:cml_enable_disable_t;
                mandatory true;
                description "SNMP Trap Notification";
            }
        }
    }

}
