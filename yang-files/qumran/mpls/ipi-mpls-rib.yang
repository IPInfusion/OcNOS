/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-mpls-rib.yang
*
*/

module ipi-mpls-rib {

    yang-version 1.1;

    namespace   "http://www.ipinfusion.com/yang/ocnos/ipi-mpls-rib";

    prefix "ipi-mpls-rib";

    import ietf-inet-types {
        prefix inet;
    }

    import ipi-interface {
        prefix ipi-interface;
    }

    import ipi-network-instance {
        prefix ipi-network-instance;
    }

    import ipi-vrf {
        prefix ipi-vrf;
    }

    import ipi-mpls {
        prefix ipi-mpls;
    }

    import ipi-mpls-types {
        prefix ipi-mpls-types;
    }

    import feature-list {
        prefix feature-list;
    }

    organization
        "IP Infusion Inc.";

    contact
        "Address: 3965 Freedom Circle, Suite 200, Santa Clara, CA 95054
         Phone: +1 408-400-1900
         E-mail: support@ipinfusion.com
         Web: http://www.ipinfusion.com/";

    description
        "Data model for MPLS RIB";


    revision "2021-03-04" {
        description "Added attribute pseudowire-id";
        reference " 0.4.0.";
    }

    revision "2020-12-15" {
        description "Change to have data-types in lower case instead of camel case";
        reference " 0.3.0.";
    }

    revision "2020-12-07" {
        description "MPLS-RIB-DROP2";
        reference " 0.2.0.";
    }

    revision "2020-11-03" {
        description "Initial Version";
        reference " 0.1.0.";
    }



    grouping vrf-grouping {
    description
        "mpls VRF";
        list vrf {
            if-feature feature-list:HAVE_VRF;
            key "vrf-name";
            config false;
            description
                "mpls VRF";
            leaf vrf-name  {
                type  leafref {
                    path  "../rib/vrf-name";
                }
                description "VRF instance name";
            } // END of vrf-name definition.

            container rib {
                config false;
                description
                    "MPLS rib parameters for VRF";
                container ftn-table {
                    config false;
                    description
                        "Per VRF IPv4 FTN entries";

                    list ipv4-ftn-entry {
                        key "fec-prefix owner lsp-type";
                        config false;
                        description
                            "IPv4 FTN entry";
                        leaf fec-prefix  {
                            type  leafref {
                                path  "../state/fec-prefix";
                            }
                            description "Forwarding Equivalence Class";
                        } // END of fec-prefix definition.

                        leaf owner  {
                            type  leafref {
                                path  "../state/owner";
                            }
                            description "The protocol module which installed this entry";
                        } // END of owner definition.

                        leaf lsp-type  {
                            type  leafref {
                                path  "../state/lsp-type";
                            }
                            description "Type of Label Switched Path";
                        } // END of lsp-type definition.


                        list nhlfe-entry {
                            key "out-interface out-label";
                            config false;
                            description
                                "NHLFE entry";
                            leaf out-interface  {
                                type  leafref {
                                    path  "../state/out-interface";
                                }
                                description "Interface through which the packet should be forwarded";
                            } // END of out-interface definition.

                            leaf out-label  {
                                type  leafref {
                                    path  "../state/out-label";
                                }
                                description "Label value that is pushed to the outgoing MPLS header";
                            } // END of out-label definition.

                            container state {
                                config false;
                                description
                                    "Container for FTN NHLFE operational state";
                                uses mpls-rib-ipv4-ftn-nhlfe-entry-state;
                                uses mpls-rib-ip-ftn-nhlfe-entry-state;
                            } // END of state-container definition.
                        } // End of nhlfe-entry-list
                        container state {
                            config false;
                            description
                                "Container for FTN entry operational state";
                            uses mpls-rib-ipv4-ftn-entry-state;
                            uses mpls-rib-ip-ftn-entry-state;
                        } // END of state-container definition.
                    } // End of ipv4-ftn-entry-list
                } // END of ftn-table-container definition.
                uses mpls-vrf-entry-state;
            } // END of rib-container definition.
        } // End of vrf-list
    } // END of vrf-grouping definition.
    grouping mpls-rib-ipv4-ftn-entry-state {
        description
            "mplsCMLSEPribCMLSEPipv4CMLSEPftnCMLSEPentryCMLSEPstate";
        leaf fec-prefix  {
            type  inet:ipv4-prefix;
            description "Forwarding Equivalence Class";
        } // END of fec-prefix definition.

        leaf owner  {
            type  ipi-mpls-types:mpls_rib_entry_owner_t;
            description "The protocol module which installed this entry";
        } // END of owner definition.

    } // END of mpls-rib-ipv4-ftn-entry-state definition.
    grouping mpls-rib-ip-ftn-entry-state {
        description
            "mplsCMLSEPribCMLSEPipCMLSEPftnCMLSEPentryCMLSEPstate";
        leaf lsp-type  {
            type  ipi-mpls-types:mpls_rib_lsp_type_t;
            description "Type of Label Switched Path";
        } // END of lsp-type definition.

        leaf ftn-index  {
            type  uint32;
            description "Unique system assigned index for the entry in FTN table";
        } // END of ftn-index definition.

        leaf is-primary  {
            type  boolean;
            description "Primary FTN entry";
        } // END of is-primary definition.

        leaf route-distance  {
            type  uint8;
            description "Route distance determined by the protocol module";
        } // END of route-distance definition.

        leaf redirect-action-type  {
            type  ipi-mpls-types:mpls_rib_action_type_t;
            description "redirection action to be performed on the packet";
        } // END of redirect-action-type definition.

        leaf qos-exp-bits  {
            type  uint8;
            description "QoS exp bit that is mapped to this entry";
        } // END of qos-exp-bits definition.

        leaf in-dscp-class-name  {
            type  string {
                length "1..max";
                pattern "[^?' =,>|]+";
            }
            description "Incoming DSCP value that is mapped to this entry";
        } // END of in-dscp-class-name definition.

        leaf tunnel-id  {
            type  uint32;
            description "RSVP tunnel id for which this entry is added";
        } // END of tunnel-id definition.

        leaf protected-lsp-id  {
            type  uint32;
            description "Identifier for the protected LSP, applicable only when LSP protection
                        is enabled for RSVP trunk";
        } // END of protected-lsp-id definition.

        leaf qos-resource-id  {
            type  uint32;
            description "Qos resource id";
        } // END of qos-resource-id definition.

    } // END of mpls-rib-ip-ftn-entry-state definition.
    grouping mpls-rib-ipv4-ftn-nhlfe-entry-state {
        description
            "mplsCMLSEPribCMLSEPipv4CMLSEPftnCMLSEPnhlfeCMLSEPentryCMLSEPstate";
        leaf out-interface  {
            type  leafref {
                path  "/ipi-interface:interfaces/ipi-interface:interface/ipi-interface:name";
            }
            description "Interface through which the packet should be forwarded";
        } // END of out-interface definition.

        leaf out-label  {
            type  uint32;
            description "Label value that is pushed to the outgoing MPLS header";
        } // END of out-label definition.

        leaf nexthop-address  {
            type  inet:ipv4-address;
            description "IP address of the next hop";
        } // END of nexthop-address definition.

    } // END of mpls-rib-ipv4-ftn-nhlfe-entry-state definition.
    grouping mpls-rib-ip-ftn-nhlfe-entry-state {
        description
            "mplsCMLSEPribCMLSEPipCMLSEPftnCMLSEPnhlfeCMLSEPentryCMLSEPstate";
        leaf admin-status  {
            type  ipi-mpls-types:mpls_rib_entry_admin_status_t;
            description "Admin status of this FTN NHLFE entry";
        } // END of admin-status definition.

        leaf oper-status  {
            type  ipi-mpls-types:mpls_rib_entry_oper_status_t;
            description "Oper status of this FTN NHLFE entry";
        } // END of oper-status definition.

        leaf nhlfe-owner  {
            type  ipi-mpls-types:mpls_rib_entry_owner_t;
            description "Protocol Module that installed this nhlfe entry";
        } // END of nhlfe-owner definition.

        leaf nhlfe-index  {
            type  uint32;
            description "System assigned index for this NHLFE entry";
        } // END of nhlfe-index definition.

        leaf is-stale  {
            type  boolean;
            description "A deleted NHLFE entry for which clean-up is pending";
        } // END of is-stale definition.

        leaf label-op-code  {
            type  ipi-mpls-types:mpls_rib_label_op_code_t;
            description "Action to be performed on the MPLS label stack";
        } // END of label-op-code definition.

    } // END of mpls-rib-ip-ftn-nhlfe-entry-state definition.
    grouping mpls-rib-ip-ilm-nhlfe-entry-state {
        description
            "mplsCMLSEPribCMLSEPipCMLSEPilmCMLSEPnhlfeCMLSEPentryCMLSEPstate";
        leaf out-interface  {
            type  leafref {
                path  "/ipi-interface:interfaces/ipi-interface:interface/ipi-interface:name";
            }
            description "Interface through which the packet should be forwarded";
        } // END of out-interface definition.

        leaf out-label  {
            type  uint32;
            description "Label value that is pushed to the outgoing MPLS header";
        } // END of out-label definition.

        leaf nexthop-address  {
            type  inet:ip-address;
            description "IP address of the next hop";
        } // END of nexthop-address definition.

        leaf nhlfe-owner  {
            type  ipi-mpls-types:mpls_rib_entry_owner_t;
            description "Protocol Module that installed this nhlfe entry";
        } // END of nhlfe-owner definition.

        leaf nhlfe-index  {
            type  uint32;
            description "System assigned index for this NHLFE entry";
        } // END of nhlfe-index definition.

        leaf label-op-code  {
            type  ipi-mpls-types:mpls_rib_label_op_code_t;
            description "Action to be performed on the MPLS label stack";
        } // END of label-op-code definition.

    } // END of mpls-rib-ip-ilm-nhlfe-entry-state definition.
    grouping mpls-vrf-entry-state {
        description
            "VRF entry operational state data";
        leaf vrf-name  {
            if-feature feature-list:HAVE_VRF;
            type  leafref {
                path  "/ipi-network-instance:network-instances/ipi-network-instance:network-instance/ipi-vrf:vrf/ipi-vrf:config/ipi-vrf:vrf-name";
            }
            description "VRF instance name";
        } // END of vrf-name definition.

    } // END of mpls-vrf-entry-state definition.
    grouping mpls-rib-ip-ilm-entry-state {
        description
            "ILM entry operational state";
        leaf in-interface  {
            type  leafref {
                path  "/ipi-interface:interfaces/ipi-interface:interface/ipi-interface:name";
            }
            description "Interface on which the MPLS packet is recieved";
        } // END of in-interface definition.

        leaf in-label  {
            type  uint32;
            description "MPLS label in the incoming packet header";
        } // END of in-label definition.

        leaf vrf-name  {
            type  leafref {
                path  "/ipi-network-instance:network-instances/ipi-network-instance:network-instance/ipi-vrf:vrf/ipi-vrf:config/ipi-vrf:vrf-name";
            }
            description "VRF instance name";
        } // END of vrf-name definition.

        leaf owner  {
            type  ipi-mpls-types:mpls_rib_entry_owner_t;
            description "The protocol module which installed this entry";
        } // END of owner definition.

        leaf ilm-index  {
            type  uint32;
            description "Unique system assigned index for this entry in ilm table";
        } // END of ilm-index definition.

        leaf is-stitched-to-ftn  {
            type  boolean;
            description "is this entry stitched to an FTN entry";
        } // END of is-stitched-to-ftn definition.

        leaf is-installed-in-fib  {
            type  boolean;
            description "is this entry succesfully installed in Forwarding Table";
        } // END of is-installed-in-fib definition.

        leaf is-selected  {
            type  boolean;
            description "is this entry updated to Forwarding Table";
        } // END of is-selected definition.

        leaf is-stale  {
            type  boolean;
            description "A deleted entry for which clean-up is pending";
        } // END of is-stale definition.

        leaf fec-prefix  {
            type  inet:ip-prefix;
            description "Forwarding Equivalence Class";
        } // END of fec-prefix definition.

        leaf label-op-code  {
            type  ipi-mpls-types:mpls_rib_label_op_code_t;
            description "Action to be performed on the MPLS label stack";
        } // END of label-op-code definition.

        leaf pseudowire-id  {
            type  uint32;
            description "pseudowire for which this ILM entry is added";
        } // END of pseudowire-id definition.

    } // END of mpls-rib-ip-ilm-entry-state definition.
    grouping mpls-static-ipv4-map-route-config {
        description
            "MPLS Static IPv4 Map Route Configurations";
        leaf route-prefix  {
            type  inet:ipv4-prefix;
            description "Use this attribute to specify the route prefix for which FEC mapping
                        needs to be added";
        } // END of route-prefix definition.

        leaf mapped-fec  {
            type  inet:ipv4-prefix;
            mandatory true;
            description "Use this attribute to specify the FEC prefix that is mapped to the
                        route";
        } // END of mapped-fec definition.

    } // END of mpls-static-ipv4-map-route-config definition.
    grouping mpls-tp-ipv4-map-route-config {
        description
            "MPLS TP Map Route Configuration";
        leaf route-prefix  {
            type  inet:ipv4-prefix;
            description "Use this attribute to specify the route prefix for which Tunnel
                        Mapping needs to be added";
        } // END of route-prefix definition.

        leaf mapped-tunnel-name  {
            type  string {
                length "1..max";
                pattern "[^?' =,>|]+";
            }
            mandatory true;
            description "Use this attribute to specify the Tunnel Name that is mapped to the
                        prefix";
        } // END of mapped-tunnel-name definition.

    } // END of mpls-tp-ipv4-map-route-config definition.

    grouping  rib-grouping {
    description
        "Top level container for MPLS rib , including configuration and state
                data";
    container rib {
        description
            "Top level container for MPLS rib , including configuration and state
                    data";
        container global-ftn-table {
            config false;
            description
                "Global FTN table";

            list ipv4-ftn-entry {
                key "fec-prefix owner lsp-type";
                config false;
                description
                    "Global IPv4 FTN entries";
                leaf fec-prefix  {
                    type  leafref {
                        path  "../state/fec-prefix";
                    }
                    description "Forwarding Equivalence Class";
                } // END of fec-prefix definition.

                leaf owner  {
                    type  leafref {
                        path  "../state/owner";
                    }
                    description "The protocol module which installed this entry";
                } // END of owner definition.

                leaf lsp-type  {
                    type  leafref {
                        path  "../state/lsp-type";
                    }
                    description "Type of Label Switched Path";
                } // END of lsp-type definition.


                list nhlfe-entry {
                    key "out-interface out-label";
                    config false;
                    description
                        "NHLFE entry";
                    leaf out-interface  {
                        type  leafref {
                            path  "../state/out-interface";
                        }
                        description "Interface through which the packet should be forwarded";
                    } // END of out-interface definition.

                    leaf out-label  {
                        type  leafref {
                            path  "../state/out-label";
                        }
                        description "Label value that is pushed to the outgoing MPLS header";
                    } // END of out-label definition.

                    container state {
                        config false;
                        description
                            "Container for FTN NHLFE entry operational state";
                        uses mpls-rib-ipv4-ftn-nhlfe-entry-state;
                        uses mpls-rib-ip-ftn-nhlfe-entry-state;
                    } // END of state-container definition.
                } // End of nhlfe-entry-list
                container state {
                    config false;
                    description
                        "Container for FTN entry operational state";
                    uses mpls-rib-ipv4-ftn-entry-state;
                    uses mpls-rib-ip-ftn-entry-state;
                } // END of state-container definition.
            } // End of ipv4-ftn-entry-list
        } // END of global-ftn-table-container definition.
        container ilm-table {
            config false;
            description
                "ILM table";

            list ip-ilm-entry {
                key "in-interface in-label";
                config false;
                description
                    "IP ILM entries";
                leaf in-interface  {
                    type  leafref {
                        path  "../state/in-interface";
                    }
                    description "Interface on which the MPLS packet is recieved";
                } // END of in-interface definition.

                leaf in-label  {
                    type  leafref {
                        path  "../state/in-label";
                    }
                    description "MPLS label in the incoming packet header";
                } // END of in-label definition.


                list nhlfe-entry {
                    key "out-interface out-label";
                    config false;
                    description
                        "NHLFE entries per ILM entry";
                    leaf out-interface  {
                        type  leafref {
                            path  "../state/out-interface";
                        }
                        description "Interface through which the packet should be forwarded";
                    } // END of out-interface definition.

                    leaf out-label  {
                        type  leafref {
                            path  "../state/out-label";
                        }
                        description "Label value that is pushed to the outgoing MPLS header";
                    } // END of out-label definition.

                    container state {
                        config false;
                        description
                            "Container for FTN NHLFE operational state";
                        uses mpls-rib-ip-ilm-nhlfe-entry-state;
                    } // END of state-container definition.
                } // End of nhlfe-entry-list
                container state {
                    config false;
                    description
                        "Container for ILM entry operational state";
                    uses mpls-rib-ip-ilm-entry-state;
                } // END of state-container definition.
            } // End of ip-ilm-entry-list
        } // END of ilm-table-container definition.
        container map-route {
            description
                "MPLS Map Route";

            list static-ipv4-map-route {
                key "route-prefix";
                description
                    "MPLS Static IPv4 Map Route Entries";
                leaf route-prefix  {
                    type  leafref {
                        path  "../config/route-prefix";
                    }
                    description "Use this attribute to specify the route prefix for which FEC mapping
                                needs to be added";
                } // END of route-prefix definition.

                container config {
                    description
                        "Config Container for MPLS Map Route";
                    uses mpls-static-ipv4-map-route-config;
                } // END of config-container definition.
                container state {
                    config false;
                    description
                        "State Container for MPLS Map Route";
                    uses mpls-static-ipv4-map-route-config;
                } // END of state-container definition.
            } // End of static-ipv4-map-route-list
        } // END of map-route-container definition.
    } // END of rib-container definition.
    } // END of rib-grouping definition.

    augment /ipi-mpls:mpls {
        description
            "Top level container for MPLS rib , including configuration and state
                    data";
        uses rib-grouping;
    }

    augment /ipi-mpls:mpls {
        description
            "mpls VRF";
        uses vrf-grouping;
    }


}
