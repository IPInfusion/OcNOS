/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-rib-vrf.yang
*
*/

module ipi-rib-vrf {

    yang-version 1.1;

    namespace   "http://www.ipinfusion.com/yang/ocnos/ipi-rib-vrf";

    prefix "ipi-rib-vrf";

    import ipi-rib-types {
        prefix ipi-rib-types;
    }

    import ipi-interface {
        prefix ipi-interface;
    }

    import ipi-rib-common {
        prefix ipi-rib-common;
    }

    import ipi-network-instance {
        prefix ipi-network-instance;
    }

    import ipi-vrf {
        prefix ipi-vrf;
    }

    import ietf-inet-types {
        prefix inet;
    }

    import feature-list {
        prefix feature-list;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for VRF RIB object";


    revision "2021-03-15" {
        description "Removed configuration of Interface name as nexthop for ipv6 mroute commands";
        reference " 0.4.0.";
    }

    revision "2021-01-27" {
        description "Mroute related changes, added description for RPCs";
        reference " 0.3.0.";
    }

    revision "2020-12-15" {
        description "Change to have data-types in lower case instead of camel case";
        reference " 0.2.0.";
    }

    revision "2020-09-07" {
        description "Datamodel restructuring";
        reference " 0.1.0.";
    }

    grouping rib-vrf-ipv4-gateway-config {
        description
            "Configuration attributes for ipv4 static route with gateway address";
        leaf destination-prefix  {
            type  inet:ipv4-prefix;
            description "IP destination prefix (e.g. 10.0.0.0/8)";
        } // END of destination-prefix definition.

        leaf gateway-address  {
            type  inet:ipv4-address;
            description "Use this attribute to configure IP gateway address for  IPv4 static
                        route.";
        } // END of gateway-address definition.

    } // END of rib-vrf-ipv4-gateway-config definition.
    grouping rib-vrf-ipv4-vrfglobal-config {
        description
            "Configuration attributes related to vrf ipv4 static route with gateway
                        address and interface name";
        leaf enable-global-table-lookup  {
            type  empty;
            description "Use this attribute to create an IPv4 vrf static route with gateway in
                        default vrf table.";
        } // END of enable-global-table-lookup definition.

    } // END of rib-vrf-ipv4-vrfglobal-config definition.
    grouping rib-vrf-ipv4-interface-config {
        description
            "Configuration attributes for static routes with interface";
        leaf destination-prefix  {
            type  inet:ipv4-prefix;
            description "IP destination prefix (e.g. 10.0.0.0/8)";
        } // END of destination-prefix definition.

        leaf interface-name  {
            type  string {
                length "1..max";
                pattern "[^?' =,>|]+";
            }
            description "Use this attribute to create an IPv4 static route where nexthop is
                        interface name.";
        } // END of interface-name definition.

        uses ipi-rib-common:rib-attr-config;
    } // END of rib-vrf-ipv4-interface-config definition.
    grouping rib-vrf-ipv6-gateway-config {
        description
            "Configuration attributes for ipv6 static routes";
        leaf destination-prefix  {
            type  inet:ipv6-prefix;
            description "IPv6 destination prefix (e.g. 3ffe:506::/32)";
        } // END of destination-prefix definition.

        leaf gateway-address  {
            type  inet:ipv6-address;
            description "Use this attribute to create an IPv6 static route for a subnet.";
        } // END of gateway-address definition.

        leaf-list interface-name  {
            type  string {
                length "1..max";
                pattern "[^?' =,>|]+";
            }
            description "Use this attribute to create an IPv6 static route where nexthop is
                        interface name.";
        } // END of interface-name definition.

    } // END of rib-vrf-ipv6-gateway-config definition.
    grouping rib-vrf-ipv6-interface-config {
        description
            "Configuration attributes for ipv6 static routes with interface";
        leaf destination-prefix  {
            type  inet:ipv6-prefix;
            description "IPv6 destination prefix (e.g. 3ffe:506::/32)";
        } // END of destination-prefix definition.

        leaf interface-name  {
            type  string {
                length "1..max";
                pattern "[^?' =,>|]+";
            }
            description "Use this attribute to create an IPv6 static route where nexthop is
                        interface name.";
        } // END of interface-name definition.

    } // END of rib-vrf-ipv6-interface-config definition.
    grouping rib-vrf-bfd-config {
        description
            "Configuration attributes related to bfd for vrf static routes";
        leaf bfd-state  {
            when " /ipi-network-instance:network-instances/ipi-network-instance:network-instance/ipi-vrf:vrf/ipi-rib-vrf:static-routes/ipi-rib-vrf:ipv4/ipi-rib-vrf:route/ipi-rib-vrf:gateway-interface-route/ipi-rib-vrf:interface-name ";
            type  ipi-rib-types:rib_static_bfd_enable_disable_t;
            description "Use this attribute to set fall-over detection.";
        } // END of bfd-state definition.

    } // END of rib-vrf-bfd-config definition.
    grouping rib-vrf-ipv6-bfd-config {
        description
            "Configuration attributes related to bfd for vrf static routes";
        leaf bfd-state  {
            type  ipi-rib-types:rib_static_bfd_enable_disable_t;
            description "Use this attribute to set fall-over detection.";
        } // END of bfd-state definition.

    } // END of rib-vrf-ipv6-bfd-config definition.
    grouping rib-global-vrf-bfd-config {
        description
            "Global BFD Configuration attributes";
        leaf ipv4-enable-bfd-all-interfaces  {
            type  empty;
            description "Use this attribute to enable static BFD on all interfaces.";
        } // END of ipv4-enable-bfd-all-interfaces definition.

        leaf ipv6-enable-bfd-all-interfaces  {
            type  empty;
            description "Use this attribute to enable ipv6 static BFD on all interfaces.";
        } // END of ipv6-enable-bfd-all-interfaces definition.

    } // END of rib-global-vrf-bfd-config definition.
    grouping rib-gw-ifname-config {
        description
            "Interface name for VRF route";
        leaf interface-name  {
            type  leafref {
                path  "/ipi-interface:interfaces/ipi-interface:interface/ipi-interface:name";
            }
            description "Use this attribute to create an IPv4 static route where nexthop is
                        interface name.";
        } // END of interface-name definition.

    } // END of rib-gw-ifname-config definition.
    grouping rib-vrf-ipv4-interface-global-config {
        description
            "Configuration attributes for ipv4 static route with interface in
                        global vrf";
        leaf destination-prefix  {
            type  inet:ipv4-prefix;
            description "IP destination prefix (e.g. 10.0.0.0/8)";
        } // END of destination-prefix definition.

        leaf enable-global-table-lookup  {
            type  empty;
            description "Use this attribute to create an IPv4 vrf static route with gateway in
                        default vrf table.";
        } // END of enable-global-table-lookup definition.

    } // END of rib-vrf-ipv4-interface-global-config definition.

    grouping  global-grouping {
    description
        "RIB global configurations";
    container global {
        description
            "RIB global configurations";
        container config {
            description
                "configuration attributes related to BFD for RIB VRF";
            uses rib-global-vrf-bfd-config;
        } // END of config-container definition.
        container state {
            config false;
            description
                "Operational data related to BFD for RIB VRF";
            uses rib-global-vrf-bfd-config;
        } // END of state-container definition.
    } // END of global-container definition.
    } // END of global-grouping definition.

    grouping  static-routes-grouping {
    description
        "VRF Static Route configurations";
    container static-routes {
        description
            "VRF Static Route configurations";
        container ipv4 {
            description
                "IPV4 Static Route configurations";

            list gateway-interface-route-global {
            when " /ipi-interface:interfaces/ipi-interface:interface/ipi-interface:config/ipi-interface:switchport-status != 'true' + /ipi-network-instance:network-instances/ipi-network-instance:network-instance/ipi-vrf:vrf/ipi-rib-vrf:static-routes/ipi-rib-vrf:ipv4/ipi-rib-vrf:gateway-interface-route-global/ipi-rib-vrf:interface-name ";
                key "destination-prefix interface-name";
                description
                    "IPV4 VRF static route with global gateway";
                leaf destination-prefix  {
                    type  leafref {
                        path  "../config/destination-prefix";
                    }
                    description "IP destination prefix (e.g. 10.0.0.0/8)";
                } // END of destination-prefix definition.

                leaf interface-name  {
                    type  leafref {
                        path  "/ipi-interface:interfaces/ipi-interface:interface/ipi-interface:name";
                    }
                    description "Use this attribute to create an IPv4 static route where nexthop is a
                                global interface.";
                } // END of interface-name definition.

                container config {
                    description
                        "configuration attributes for static route with global interface";
                    uses rib-vrf-ipv4-interface-global-config;
                } // END of config-container definition.
                container state {
                    config false;
                    description
                        "Operational data for static route with global interface";
                    uses rib-vrf-ipv4-interface-global-config;
                } // END of state-container definition.
            } // End of gateway-interface-route-global-list

            list route {
            when " /ipi-network-instance:network-instances/ipi-network-instance:network-instance/ipi-vrf:vrf/ipi-rib-vrf:static-routes/ipi-rib-vrf:ipv4/ipi-rib-vrf:route/ipi-rib-vrf:gateway-interface-route/ipi-rib-vrf:interface-name  or /ipi-network-instance:network-instances/ipi-network-instance:network-instance/ipi-vrf:vrf/ipi-rib-vrf:static-routes/ipi-rib-vrf:ipv4/ipi-rib-vrf:route/ipi-rib-vrf:interface-route-global/ipi-rib-vrf:interface-name ";
                key "destination-prefix gateway-address";
                description
                    "IPV4 static route config with gateway";
                leaf destination-prefix  {
                    type  leafref {
                        path  "../config/destination-prefix";
                    }
                    description "IP destination prefix (e.g. 10.0.0.0/8)";
                } // END of destination-prefix definition.

                leaf gateway-address  {
                    type  leafref {
                        path  "../config/gateway-address";
                    }
                    description "Gateway address to create an IPv4 static route.";
                } // END of gateway-address definition.


                list gateway-interface-route {
                    key "interface-name";
                    description
                        "IPV4 VRF static route with gateway and interface name";
                    leaf interface-name  {
                        type  leafref {
                            path  "../config/interface-name";
                        }
                        description "Use this attribute to create an IPv4 static route where nexthop is
                                    interface name.";
                    } // END of interface-name definition.

                    container config {
                        description
                            "configuration attributes for static route with interface name";
                        uses ipi-rib-common:rib-attr-config;
                        uses rib-gw-ifname-config;
                    } // END of config-container definition.
                    container state {
                        config false;
                        description
                            "Operational data for static route with interface name";
                        uses ipi-rib-common:rib-attr-config;
                        uses rib-gw-ifname-config;
                    } // END of state-container definition.
                } // End of gateway-interface-route-list

                list interface-route-global {
                when " /ipi-interface:interfaces/ipi-interface:interface/ipi-interface:config/ipi-interface:switchport-status != 'true' + /ipi-network-instance:network-instances/ipi-network-instance:network-instance/ipi-vrf:vrf/ipi-rib-vrf:static-routes/ipi-rib-vrf:ipv4/ipi-rib-vrf:route/ipi-rib-vrf:interface-route-global/ipi-rib-vrf:config/ipi-rib-vrf:enable-global-table-lookup ";
                    key "interface-name";
                    description
                        "IPV4 VRF static route with global gateway";
                    leaf interface-name  {
                        type  leafref {
                            path  "/ipi-interface:interfaces/ipi-interface:interface/ipi-interface:name";
                        }
                        description "Use this attribute to create an IPv4 static route where nexthop is a
                                    global interface.";
                    } // END of interface-name definition.

                    container config {
                        description
                            "configuration attributes for static route with global interface";
                        uses rib-vrf-ipv4-vrfglobal-config;
                    } // END of config-container definition.
                    container state {
                        config false;
                        description
                            "Operational data for static route with global interface";
                        uses rib-vrf-ipv4-vrfglobal-config;
                    } // END of state-container definition.
                } // End of interface-route-global-list
                container config {
                    description
                        "configuration attributes for IPV4 static route with gateway";
                    uses rib-vrf-bfd-config;
                    uses rib-vrf-ipv4-gateway-config;
                } // END of config-container definition.
                container state {
                    config false;
                    description
                        "Operational data for IPV4 static route with gateway";
                    uses rib-vrf-bfd-config;
                    uses rib-vrf-ipv4-gateway-config;
                } // END of state-container definition.
            } // End of route-list

            list interface-route {
                key "destination-prefix interface-name";
                description
                    "IPV4 static route with interface name";
                leaf destination-prefix  {
                    type  leafref {
                        path  "../config/destination-prefix";
                    }
                    description "IP destination prefix (e.g. 10.0.0.0/8)";
                } // END of destination-prefix definition.

                leaf interface-name  {
                    type  leafref {
                        path  "../config/interface-name";
                    }
                    description "Use this attribute to create an IPv4 static route where nexthop is
                                interface name.";
                } // END of interface-name definition.

                container config {
                    description
                        "configuration attributes for static route with interface name";
                    uses rib-vrf-ipv4-interface-config;
                } // END of config-container definition.
                container state {
                    config false;
                    description
                        "Operational data for static route with interface name";
                    uses rib-vrf-ipv4-interface-config;
                } // END of state-container definition.
            } // End of interface-route-list

            list multicast-route {
                key "source-prefix protocol-type";
                description
                    "Mroute vrf";
                leaf source-prefix  {
                    type  leafref {
                        path  "../config/source-prefix";
                    }
                    description "Source prefix";
                } // END of source-prefix definition.

                leaf protocol-type  {
                    type  leafref {
                        path  "../config/protocol-type";
                    }
                    description "mroute prototype";
                } // END of protocol-type definition.

                container config {
                    description
                        "configuration attributes for IPV4 static mroute";
                    uses ipi-rib-common:rib-ipv4-multicast-config;
                } // END of config-container definition.
                container state {
                    config false;
                    description
                        "Operational data for IPV4 static mroute";
                    uses ipi-rib-common:rib-ipv4-multicast-config;
                } // END of state-container definition.
            } // End of multicast-route-list
        } // END of ipv4-container definition.
        container ipv6 {
            if-feature feature-list:HAVE_IPV6;
            description
                "VRF IPV6 Static Route configurations";

            list route {
            when " /ipi-network-instance:network-instances/ipi-network-instance:network-instance/ipi-vrf:vrf/ipi-rib-vrf:static-routes/ipi-rib-vrf:ipv6/ipi-rib-vrf:route/ipi-rib-vrf:config/ipi-rib-vrf:interface-name ";
                key "destination-prefix gateway-address";
                description
                    "RIB IPv6 destination prefix";
                leaf destination-prefix  {
                    type  leafref {
                        path  "../config/destination-prefix";
                    }
                    description "IPv6 destination prefix (e.g. 3ffe:506::/32)";
                } // END of destination-prefix definition.

                leaf gateway-address  {
                    type  leafref {
                        path  "../config/gateway-address";
                    }
                    description "Use this attribute to create an IPv6 static route for a subnet.";
                } // END of gateway-address definition.

                container config {
                    description
                        "configuration attributes for IPV6 static route with gateway";
                    uses rib-vrf-ipv6-bfd-config;
                    uses rib-vrf-ipv6-gateway-config;
                } // END of config-container definition.
                container state {
                    config false;
                    description
                        "Operational data for IPV6 static route with gateway";
                    uses rib-vrf-ipv6-bfd-config;
                    uses rib-vrf-ipv6-gateway-config;
                } // END of state-container definition.
            } // End of route-list

            list interface-route {
                key "destination-prefix interface-name";
                description
                    "RIB IPv6 static route with interface name";
                leaf destination-prefix  {
                    type  leafref {
                        path  "../config/destination-prefix";
                    }
                    description "IPv6 destination prefix (e.g. 3ffe:506::/32)";
                } // END of destination-prefix definition.

                leaf interface-name  {
                    type  leafref {
                        path  "../config/interface-name";
                    }
                    description "Use this attribute to create an IPv6 static route where nexthop is
                                interface name.";
                } // END of interface-name definition.

                container config {
                    description
                        "configuration attributes for IPV6 static route with interface name";
                    uses rib-vrf-ipv6-interface-config;
                } // END of config-container definition.
                container state {
                    config false;
                    description
                        "Operational data for IPV6 static route with interface name";
                    uses rib-vrf-ipv6-interface-config;
                } // END of state-container definition.
            } // End of interface-route-list

            list multicast-route {
            when " /ipi-network-instance:network-instances/ipi-network-instance:network-instance/ipi-vrf:vrf/ipi-rib-vrf:static-routes/ipi-rib-vrf:ipv6/ipi-rib-vrf:multicast-route/ipi-rib-vrf:nexthop/ipi-rib-vrf:config/ipi-rib-vrf:gateway-mroute ";
                key "source-prefix protocol-type";
                description
                    "ipv6 mroute vrf";
                leaf source-prefix  {
                    type  leafref {
                        path  "../config/source-prefix";
                    }
                    description "Source prefix";
                } // END of source-prefix definition.

                leaf protocol-type  {
                    type  leafref {
                        path  "../config/protocol-type";
                    }
                    description "mroute prototype";
                } // END of protocol-type definition.

                container config {
                    description
                        "configuration attributes for IPV6 static mroute";
                    uses ipi-rib-common:rib-ipv6-multicast-config;
                } // END of config-container definition.
                container state {
                    config false;
                    description
                        "Operational data for IPV6 static mroute";
                    uses ipi-rib-common:rib-ipv6-multicast-config;
                } // END of state-container definition.
                container nexthop {
                    description
                        "ipv6 mroute nexthop information";
                    container config {
                        presence "yes";
                        description
                            "configuration attributes for IPV6 static mroute gateway";
                        uses ipi-rib-common:rib-ipv6-multicast-gateway-config;
                    } // END of config-container definition.
                    container state {
                        config false;
                        description
                            "Operational data for IPV6 static mroute";
                        uses ipi-rib-common:rib-ipv6-multicast-gateway-config;
                    } // END of state-container definition.
                } // END of nexthop-container definition.
            } // End of multicast-route-list
        } // END of ipv6-container definition.
    } // END of static-routes-container definition.
    } // END of static-routes-grouping definition.

    grouping  ribs-grouping {
    description
        "RIB run-time attributes";
    container ribs {
        config false;
        description
            "RIB run-time attributes";
        container ipv4 {
            config false;
            description
                "IPV4 routes";

            list ecmp-path-summary {
                key "path-count";
                config false;
                description
                    "RIB ecmp path information";
                leaf path-count  {
                    type  leafref {
                        path  "../state/path-count";
                    }
                    description "Number of paths";
                } // END of path-count definition.

                container state {
                    config false;
                    description
                        "IPV4 route ecmp path statistics";
                    container counters {
                        config false;
                        description
                            "IPV4 route ecmp path  statistics";
                        uses ipi-rib-common:rib-ecmp-route-count;
                    } // END of counters-container definition.
                    uses ipi-rib-common:rib-ecmp-path-count;
                } // END of state-container definition.
            } // End of ecmp-path-summary-list

            list protocol-rib-summary {
                key "protocol-type";
                config false;
                description
                    "Protocol RIB statistics";
                leaf protocol-type  {
                    type  leafref {
                        path  "../state/protocol-type";
                    }
                    description "route type";
                } // END of protocol-type definition.

                container state {
                    config false;
                    description
                        "IPV4 route statistics";
                    container counters {
                        config false;
                        description
                            "IPV4 route statistics";
                        uses ipi-rib-common:rib-protocol-route-count;
                    } // END of counters-container definition.
                    uses ipi-rib-common:rib-protocol-type;
                } // END of state-container definition.
            } // End of protocol-rib-summary-list
            container routes {
                config false;
                description
                    "IPV4 routes";

                list route {
                    key "destination-prefix protocol-type";
                    config false;
                    description
                        "RIB run-time attributes";
                    leaf destination-prefix  {
                        type  leafref {
                            path  "../state/destination-prefix";
                        }
                        description "IP destination prefix (e.g. 10.0.0.0/8)";
                    } // END of destination-prefix definition.

                    leaf protocol-type  {
                        type  leafref {
                            path  "../state/protocol-type";
                        }
                        description "route type";
                    } // END of protocol-type definition.


                    list next-hop {
                        key "gateway-address";
                        config false;
                        description
                            "next-hop run-time attributes";
                        leaf gateway-address  {
                            type  leafref {
                                path  "../state/gateway-address";
                            }
                            description "Nexthop ip address";
                        } // END of gateway-address definition.

                        container state {
                            config false;
                            description
                                "Operational data related to route next-hop";
                            uses ipi-rib-common:rib-route-nexthop-state;
                        } // END of state-container definition.
                    } // End of next-hop-list
                    container state {
                        config false;
                        description
                            "Operational data for IPV4 route";
                        uses ipi-rib-common:rib-ipv4-destination-prefix;
                        uses ipi-rib-common:rib-route-state;
                    } // END of state-container definition.
                } // End of route-list
                container state {
                    config false;
                    description
                        "IPV4 default-gateway";
                    uses ipi-rib-common:rib-route-default-gateway-state;
                } // END of state-container definition.
            } // END of routes-container definition.
            container state {
                config false;
                description
                    "IPV4 route statistics";
                container counters {
                    config false;
                    description
                        "IPV4 route statistics";
                    uses ipi-rib-common:rib-global-statistics-state;
                } // END of counters-container definition.
            } // END of state-container definition.
        } // END of ipv4-container definition.
        container ipv6 {
            if-feature feature-list:HAVE_IPV6;
            config false;
            description
                "IPV6 routes";

            list ecmp-path-summary {
                key "path-count";
                config false;
                description
                    "RIB ecmp path information";
                leaf path-count  {
                    type  leafref {
                        path  "../state/path-count";
                    }
                    description "Number of paths";
                } // END of path-count definition.

                container state {
                    config false;
                    description
                        "IPV6 route ecmp path statistics";
                    container counters {
                        config false;
                        description
                            "IPV6 route ecmp path  statistics";
                        uses ipi-rib-common:rib-ecmp-route-count;
                    } // END of counters-container definition.
                    uses ipi-rib-common:rib-ecmp-path-count;
                } // END of state-container definition.
            } // End of ecmp-path-summary-list

            list protocol-rib-summary {
                key "protocol-type";
                config false;
                description
                    "Protocol RIB statistics";
                leaf protocol-type  {
                    type  leafref {
                        path  "../state/protocol-type";
                    }
                    description "route type";
                } // END of protocol-type definition.

                container state {
                    config false;
                    description
                        "IPV6 route statistics";
                    container counters {
                        config false;
                        description
                            "IPV6 route statistics";
                        uses ipi-rib-common:rib-protocol-route-count;
                    } // END of counters-container definition.
                    uses ipi-rib-common:rib-protocol-type;
                } // END of state-container definition.
            } // End of protocol-rib-summary-list
            container routes {
                config false;
                description
                    "IPV6 routes";

                list route {
                    key "destination-prefix protocol-type";
                    config false;
                    description
                        "RIB run-time attributes";
                    leaf destination-prefix  {
                        type  leafref {
                            path  "../state/destination-prefix";
                        }
                        description "IP destination prefix (e.g. 10.0.0.0/8)";
                    } // END of destination-prefix definition.

                    leaf protocol-type  {
                        type  leafref {
                            path  "../state/protocol-type";
                        }
                        description "route type";
                    } // END of protocol-type definition.


                    list next-hop {
                        key "gateway-address";
                        config false;
                        description
                            "next-hop run-time attributes";
                        leaf gateway-address  {
                            type  leafref {
                                path  "../state/gateway-address";
                            }
                            description "Nexthop ip address";
                        } // END of gateway-address definition.

                        container state {
                            config false;
                            description
                                "Operational data related to route next-hop";
                            uses ipi-rib-common:rib-route-nexthop-state;
                        } // END of state-container definition.
                    } // End of next-hop-list
                    container state {
                        config false;
                        description
                            "Operational data for IPV6 route";
                        uses ipi-rib-common:rib-ipv6-destination-prefix;
                        uses ipi-rib-common:rib-route-state;
                    } // END of state-container definition.
                } // End of route-list
            } // END of routes-container definition.
            container state {
                config false;
                description
                    "IPV6 route statistics";
                container counters {
                    config false;
                    description
                        "IPV6 route statistics";
                    uses ipi-rib-common:rib-global-statistics-state;
                } // END of counters-container definition.
            } // END of state-container definition.
        } // END of ipv6-container definition.
    } // END of ribs-container definition.
    } // END of ribs-grouping definition.

    augment /ipi-network-instance:network-instances/ipi-network-instance:network-instance/ipi-vrf:vrf {
        description
            "RIB global configurations";
        uses global-grouping;
    }

    augment /ipi-network-instance:network-instances/ipi-network-instance:network-instance/ipi-vrf:vrf {
        description
            "VRF Static Route configurations";
        uses static-routes-grouping;
    }

    augment /ipi-network-instance:network-instances/ipi-network-instance:network-instance/ipi-vrf:vrf {
        description
            "RIB run-time attributes";
        uses ribs-grouping;
    }


    rpc clear-ip-vrf-route-all {
        description "Use clear-ip-vrf-route-all to clear all IPv4 VRF routes of any
                    particular VRF name";
        input  {
            leaf vrf-name  {
                type string;
                mandatory true;
                description "vrf name";
            }
        }
    }

    rpc clear-ip-vrf-route {
        description "Use clear-ip-vrf-route to clear any specific prefix IPv4 VRF route of
                    any particular VRF name";
        input  {
            leaf vrf-name  {
                type string;
                mandatory true;
                description "vrf name";
            }
            leaf prefix-address  {
                type inet:ipv4-prefix;
                mandatory true;
                description "Prefix to be cleared(e.g. 10.0.0.0/8)";
            }
        }
    }

    rpc clear-ipv6-vrf-route-all {
        description "Use clear-ipv6-vrf-route-all to clear all IPv6 VRF routes of any
                    particular VRF name";
        input  {
            leaf vrf-name  {
                type string;
                mandatory true;
                description "vrf name";
            }
        }
    }

    rpc clear-ipv6-vrf-route {
        description "Use clear-ipv6-vrf-route to clear any specific prefix IPv6 VRF route
                    of any particular VRF name";
        input  {
            leaf vrf-name  {
                type string;
                mandatory true;
                description "Virtual router id";
            }
            leaf prefix-ipv6-address  {
                type inet:ipv6-prefix;
                mandatory true;
                description "Prefix to be cleared(e.g. 3ffe:506::/32)";
            }
        }
    }

}
