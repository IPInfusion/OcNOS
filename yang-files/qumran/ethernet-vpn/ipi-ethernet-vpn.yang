/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-ethernet-vpn.yang
*
*/

module ipi-ethernet-vpn {

    yang-version 1.1;

    namespace   "http://www.ipinfusion.com/yang/ocnos/ipi-ethernet-vpn";

    prefix "ipi-ethernet-vpn";

    import cml-data-types {
        prefix cml-data-types;
        revision-date 2021-05-03;
    }

    import ipi-vrf {
        prefix ipi-vrf;
        revision-date 2021-01-27;
    }

    import ipi-network-instance {
        prefix ipi-network-instance;
        revision-date 2020-12-15;
    }

    import ipi-interface {
        prefix ipi-interface;
        revision-date 2021-06-14;
    }

    import ipi-if-aggregate {
        prefix ipi-if-aggregate;
        revision-date 2020-12-15;
    }

    import feature-list {
        prefix feature-list;
        revision-date 2021-05-03;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for EVPN protocol";


    revision "2021-05-08" {
        description "addition of esi/system-mac for MH interface";
        reference " 0.4.0.";
    }

    revision "2021-01-27" {
        description "anycast gateway mac changes for IRB forwarding interface";
        reference " 0.3.0.";
    }

    revision "2020-12-15" {
        description "Change to have data-types in lower case instead of camel case";
        reference " 0.2.0.";
    }

    revision "2020-06-02" {
        description "Restructured as per Openconfig style";
        reference " 0.1.0.";
    }

    grouping evpn-global-config {
        description
            "Grouping for global evpn configuration";
        leaf enable-vxlan-multihoming  {
            if-feature feature-list:HAVE_TUNNEL;
            if-feature feature-list:HAVE_NVO;
            type  empty;
            description "Use this attribute to enable multihoming module on vxlan. Without this
                        attribute  multihomig functionality can not be achieved";
        } // END of enable-vxlan-multihoming definition.

        leaf enable-evpn-mpls-multihoming  {
            if-feature feature-list:HAVE_MPLS;
            if-feature feature-list:HAVE_BGP_EVPN;
            if-feature feature-list:HAVE_NVO;
            type  empty;
            description "Use this attribute to enable multihoming module on evpn mpls. Without
                        this attribute  multihomig functionality can not be achieved";
        } // END of enable-evpn-mpls-multihoming definition.

        leaf enable-irb  {
            if-feature feature-list:HAVE_TUNNEL;
            if-feature feature-list:HAVE_NVO;
            type  empty;
            description "Use this attribute to enable integrated routing and bridging module.
                        Without this attribute IRB functionality can not be achieved";
        } // END of enable-irb definition.

    } // END of evpn-global-config definition.
    grouping evpn-multihoming-config {
        description
            "Grouping for evpn multihoming configuration";
        leaf esi-hold-time  {
            if-feature feature-list:HAVE_BGP_EVPN;
            type  uint32 {
                 range "10..300"  {
                    description "10..300:Hold time in seconds";
                 }
            }
            units "seconds";
            description "Use this attribute to set time before ESI can be made up on enabling
                        evpn";
        } // END of esi-hold-time definition.

    } // END of evpn-multihoming-config definition.
    grouping evpn-interface-config {
        description
            "Grouping for interface configuration";
        leaf name  {
            type  leafref {
                path  "/ipi-interface:interfaces/ipi-interface:interface/ipi-interface:name";
            }
            description "Use this attribute to map a physical interface to identify
                        the tenant traffic and to enter access interface mode";
        } // END of name definition.

    } // END of evpn-interface-config definition.
    grouping mh-interface-config {
        description
            "MH interface configuration for esi";
        leaf evpn-segment-id  {
            type  string {
                length "1..1965";
                pattern "[^?' =,>|]+";
            }
            description "This Object is used to configure the evpn multi-homed Ethernet Segment
                        Identifier value";
        } // END of evpn-segment-id definition.

        leaf system-mac  {
            type  cml-data-types:cml_mac_addr_t {
                length "1..1965";
            }
            description "This Object is used to configure evpn multi-homed system-mac";
        } // END of system-mac definition.

    } // END of mh-interface-config definition.
    grouping evpn-irb-anycast-config {
        description
            "Grouping for evpn irb configuration";
        leaf mac-address  {
            if-feature feature-list:HAVE_TUNNEL;
            if-feature feature-list:HAVE_NVO;
            type  cml-data-types:cml_mac_addr_t {
                length "1..1965";
            }
            description "Use this attribute to configure common anycast mac-address for all IRB
                        interfaces";
        } // END of mac-address definition.

    } // END of evpn-irb-anycast-config definition.
    grouping irb-interface-anycast-config {
        description
            "IRB interface forwarding for anycast gateway mac";
        leaf name  {
            type  leafref {
                path  "/ipi-interface:interfaces/ipi-interface:interface/ipi-interface:name";
            }
            description "Use this attribute to map a physical interface to identify the tenant
                        traffic and to enter NVO access interface mode";
        } // END of name definition.

        leaf gateway-mac  {
            if-feature feature-list:HAVE_TUNNEL;
            if-feature feature-list:HAVE_NVO;
            if-feature feature-list:HAVE_VXLAN;
            type  empty;
            description "Use this attribute to configure anycast mac-address for an IRB
                        interface";
        } // END of gateway-mac definition.

    } // END of irb-interface-anycast-config definition.
    grouping evpn-interface-top {
        description
            "Top-Level Grouping for evpn interface";
        container interfaces {
            description
                "Top level container for evpn interface";

            list interface {
                key "name";
                description
                    "EVPN interface related operations";
                leaf name  {
                    type  leafref {
                        path  "../config/name";
                    }
                    description "Reference to interface name";
                } // END of name definition.

                container config {
                    description
                        "Configuration data";
                    uses evpn-interface-config;
                    uses mh-interface-config;
                } // END of config-container definition.
                container state {
                    config false;
                    description
                        "Operational state data";
                    uses evpn-interface-config;
                    uses mh-interface-config;
                } // END of state-container definition.
            } // End of interface-list
        } // END of interfaces-container definition.
    } // END of evpn-interface-top definition.
    grouping irb-interface-anycast-top {
        description
            "Top-Level Grouping for IRB interface";

        list irb-interface {
        when " not(/ipi-interface:interfaces/ipi-interface:interface/ipi-if-aggregate:member-aggregation) ";
            key "name";
            description
                "IRB interface related configurations";
            leaf name  {
                type  leafref {
                    path  "../config/name";
                }
                description "Use this attribute to map a physical interface to identify the tenant
                            traffic and to enter NVO access interface mode";
            } // END of name definition.

            container config {
                description
                    "Configuration data";
                uses irb-interface-anycast-config;
            } // END of config-container definition.
            container state {
                config false;
                description
                    "Operational state data";
                uses irb-interface-anycast-config;
            } // END of state-container definition.
        } // End of irb-interface-list
    } // END of irb-interface-anycast-top definition.
    grouping evpn-vlan-service-mapping-top {
        description
            "Top-Level Grouping for vrf to vlan-service mapping";

        list vrf {
            key "vrf-name";
            description
                "List of vrfs which holds evpn vlan service type";
            leaf vrf-name  {
                type  leafref {
                    path  "/ipi-network-instance:network-instances/ipi-network-instance:network-instance/ipi-vrf:vrf/ipi-vrf:config/ipi-vrf:vrf-name";
                }
                description "Vrf Name under which evpn vlan service can be mapped.";
            } // END of vrf-name definition.

            container config {
                description
                    "Configuration data";
                uses evpn-vlan-service-config;
            } // END of config-container definition.
            container state {
                config false;
                description
                    "Operational state data";
                uses evpn-vlan-service-config;
            } // END of state-container definition.
        } // End of vrf-list
    } // END of evpn-vlan-service-mapping-top definition.
    grouping evpn-vlan-service-config {
        description
            "EVPN vlan service config related data";
        leaf service-type  {
            type  cml-data-types:cml_evpn_service_type_t;
            description "Use this attribute to configure Vlan-Based EVPN-Service Type";
        } // END of service-type definition.

    } // END of evpn-vlan-service-config definition.

    grouping  evpn-grouping {
    description
        "EVPN global level container";
    container evpn {
        description
            "EVPN global level container";
        container global {
            description
                "Configuration data for EVPN global capability configuration";
            container config {
                description
                    "Configuration data";
                uses evpn-global-config;
            } // END of config-container definition.
            container state {
                config false;
                description
                    "Operational state data";
                uses evpn-global-config;
            } // END of state-container definition.
        } // END of global-container definition.
        container multi-homing {
            description
                "Configuration data for multi-homing feature";
            container config {
                description
                    "Configuration data";
                uses evpn-multihoming-config;
            } // END of config-container definition.
            container state {
                config false;
                description
                    "Operational state data";
                uses evpn-multihoming-config;
            } // END of state-container definition.
        } // END of multi-homing-container definition.
        container irb-forwarding {
            when " /ipi-ethernet-vpn:evpn/ipi-ethernet-vpn:global/ipi-ethernet-vpn:config/ipi-ethernet-vpn:enable-irb = '1' ";
            description
                "Configuration data for integrated routing and bridging feature";
            container config {
                description
                    "Configuration data";
                uses evpn-irb-anycast-config;
            } // END of config-container definition.
            container state {
                config false;
                description
                    "Operational state data";
                uses evpn-irb-anycast-config;
            } // END of state-container definition.
            uses irb-interface-anycast-top;
        } // END of irb-forwarding-container definition.
        uses evpn-interface-top;
        uses evpn-vlan-service-mapping-top;
    } // END of evpn-container definition.
    } // END of evpn-grouping definition.

    uses evpn-grouping;

}
