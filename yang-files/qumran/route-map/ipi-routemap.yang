/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-routemap.yang
*
*/

module ipi-routemap {

    yang-version 1.1;

    namespace   "http://www.ipinfusion.com/yang/ocnos/ipi-routemap";

    prefix "ipi-routemap";

    import cml-data-types {
        prefix cml-data-types;
        revision-date 2021-05-03;
    }

    import ipi-routemap-types {
        prefix ipi-routemap-types;
        revision-date 2020-12-15;
    }

    import ipi-interface {
        prefix ipi-interface;
        revision-date 2021-06-14;
    }

    import ietf-inet-types {
        prefix inet;
        revision-date 2013-07-15;
    }

    import feature-list {
        prefix feature-list;
        revision-date 2021-05-03;
    }

    organization
        "IP Infusion Inc.";

    contact
        "Address: 3965 Freedom Circle, Suite 200, Santa Clara, CA 95054
         Phone: +1 408-400-1900
         E-mail: support@ipinfusion.com
         Web: http://www.ipinfusion.com/";

    description
        "Layer-3 pbr configurations";


    revision "2020-12-15" {
        description "Change to have data-types in lower case instead of camel case";
        reference " 0.2.0.";
    }

    revision "2020-08-14" {
        description "Initial Version";
        reference " 0.1.0.";
    }

    grouping rmap-entry {
        description
            "Route-map information";
        leaf routemap-name  {
            type  string {
                length "1..63";
                pattern "[a-zA-Z0-9][^?' =,>|]*";
            }
            description "Use this attribute to enter the route-map mode and to permit or deny
                        match/set operations.This attribute controls and modifies routing
                        information to allow redistribution of routes. It has a list of match
                        and set attributes associated with it. The match attributes specify
                        the conditions under which redistribution is allowed, and the set
                        attributes specify the particular redistribution actions to be
                        performed if the criteria enforced by match commands are met. Route
                        maps are used for detailed control over route distribution between
                        routing processes.Route maps also allow policy routing, and might
                        route packets to a different route than the obvious shortest path";
        } // END of routemap-name definition.

        leaf action  {
            type  ipi-routemap-types:rmap_action_type_t;
            mandatory true;
            description "Use this attribute to enter the route-map mode and to permit or deny
                        match/set operations.If deny is specified, and the match criteria are
                        met, the route is not redistributed, and any other route maps with the
                        same map tag are not examined.If permit is specified, and the match
                        criteria are met, the route is redistributed as specified by the set
                        actions. If the match criteria are not met, the next route map with
                        the same tag is tested.";
        } // END of action definition.

        leaf sequence-id  {
            type  uint32 {
                 range "1..65535"  {
                    description "1..65535:Sequence to insert to/delete from existing route-map entry";
                 }
            }
            description "Use this attribute to enter the route-map mode and to permit or deny
                        match/set operations.";
        } // END of sequence-id definition.

    } // END of rmap-entry definition.
    grouping continue-list {
        description
            "contiue entry config data";
        leaf continue-to-next-sequence  {
            when " not(/ipi-routemap:routemaps/ipi-routemap:routemap/ipi-routemap:continue-on-match/ipi-routemap:config/ipi-routemap:next-sequence-number) ";
            type  empty;
            description "The continue clause provides the capability to execute additional
                        entries in a route map after an entry is executed with a successful
                        match and set clauses Example the continue command allows multiple
                        entries to be evaluated within a single route-map.";
        } // END of continue-to-next-sequence definition.

        leaf next-sequence-number  {
            when " not(/ipi-routemap:routemaps/ipi-routemap:routemap/ipi-routemap:continue-on-match/ipi-routemap:config/ipi-routemap:continue-to-next-sequence) ";
            type  uint32 {
                 range "2..65535"  {
                    description "2..65535:Route-map entry to next sequence number";
                 }
            }
            description "Continue commands can be assigned optional sequence numbers that
                        indicate the order in which clauses are to be evaluated.";
        } // END of next-sequence-number definition.

    } // END of continue-list definition.
    grouping match-list {
        description
            "match entry config data";
        leaf interface-name  {
            type  leafref {
                path  "/ipi-interface:interfaces/ipi-interface:interface/ipi-interface:name";
            }
            description "Use this attribute to define the interface match criterion. This
                        command specifies the next-hop interface name of a route to be matched";
        } // END of interface-name definition.

        leaf metric  {
            type  uint32 {
                 range "1..4294967295"  {
                    description "1..4294967295:Metric value";
                 }
            }
            description "Use this attribute to match a metric of a route. The route specified
                        by the policies might not be the same as specified by the routing
                        protocols. Setting policies enable packets to take different routes
                        depending on their length or content. Packet forwarding based on
                        configured policies overrides packet forwarding specified in routing
                        tables.";
        } // END of metric definition.

        leaf vlan-id  {
            if-feature feature-list:HAVE_VLAN;
            if-feature feature-list:HAVE_PBR;
            type  cml-data-types:cml_range_t;
            description "use this attribute to set match entry traffic based on a VLAN";
        } // END of vlan-id definition.

        leaf mac-access-list-name  {
            if-feature feature-list:HAVE_PBR;
            type  string {
                length "1..63";
                pattern "[^?' =,>|]+";
            }
            description "use this attribute to set the  match entry for mac-access list";
        } // END of mac-access-list-name definition.

        leaf tag  {
            type  uint32 {
                 range "1..4294967295"  {
                    description "1..4294967295:Tag value";
                 }
            }
            description "Use this command to set a tag value. The parameter is the route tag
                        that is labeled by another routing protocol (BGP or other IGP when
                        redistributing), because AS-external-LSA has a route-tag field in its
                        LSAs. In addition, when using route-map, OcNOS can tag the LSAs with
                        the appropriate tag value. Sometimes the tag matches with using
                        route-map and sometimes, the value may be used by another application.";
        } // END of tag definition.

        leaf route-type  {
            type  ipi-routemap-types:rmap_route_type_t;
            description "Use this attribute to match an external route type. AS-external LSA is
                        either Type-1 or Type-2. External type-1 matches only Type 1 external
                        routes and external type-2 matches only Type 2 external routes.";
        } // END of route-type definition.

        leaf as-path-name  {
            type  string {
                length "1..1965";
                pattern "[^?' =,>|]+";
            }
            description "Use this command to match an autonomous system path access list. This
                        command specifies the autonomous system path to be matched. If there
                        is a match for the specified AS path, and permit is specified, the
                        route is redistributed or controlled, as specified by the set action.
                        If the match criteria are met, and deny is specified, the route is not
                        redistributed or controlled. If the match criteria are not met then
                        the route is neither accepted nor forwarded,irrespective of permit or
                        deny specifications.The route specified by the policies might not be
                        the same as specified by the routing protocols. Setting policies
                        enable packets to take different routes, depending on their length or
                        content. Packet forwarding based on configured policies overrides
                        packet forwarding specified in routing tables.";
        } // END of as-path-name definition.

        leaf route-origin  {
            type  ipi-routemap-types:rmap_origin_type_t;
            description "Use this attribute to match origin code.The origin attribute defines
                        the origin of the path information. The egp parameter is indicated as
                        an e in the routing table, and it indicates that the origin of the
                        information is learned via EGP (Exterior Gateway Protocol). The igp
                        parameter is indicated as an i in the routing table, and it indicates
                        the origin of the path information is interior to the originating AS.
                        The incomplete parameter is indicated as a ? in the routing table, and
                        indicates that the origin of the path information is unknown or
                        learned through other means. If a static route is redistributed into
                        BGP, the origin of the route is incomplete.This command specifies the
                        origin to be matched. If there is a match for the specified origin,
                        and permit is specified when you created the route-map, the route is
                        redistributed or controlled as specified by the set action. If the
                        match criteria are met, and deny is specified, the route is not
                        redistributed or controlled. If the match criteria are not met, the
                        route is neither accepted nor forwarded, irrespective of permit or
                        deny specifications. The route specified by the policies might not be
                        the same as specified by the routing protocols. Setting policies
                        enable packets to take different routes depending on their length or
                        content. Packet forwarding based on configured policies overrides
                        packet forwarding specified in routing tables";
        } // END of route-origin definition.

    } // END of match-list definition.
    grouping extended-community-info {
        description
            "Match extended community list";
        leaf extended-community-identifier  {
            type  ipi-routemap-types:rmap_community_string_t;
            description "Use this attribute to match BGP external community list.Communities
                        are used to group and filter routes. They are designed to provide the
                        ability to apply policies to large numbers of routes by using match
                        and set commands. Community lists are used to identify and filter
                        routes by their common attributes. This command allows the matching
                        based on community lists. The values set by this command overrides the
                        global values. The route that does not match at least one match clause
                        is ignored";
        } // END of extended-community-identifier definition.

        leaf match-type  {
            type  ipi-routemap-types:rmap_community_type_t;
            mandatory true;
            description "Do exact matching of communities";
        } // END of match-type definition.

    } // END of extended-community-info definition.
    grouping extended-community-list-entry {
        description
            "Match extended community list";
        container extended-communities {
            description
                "Match extended community list";

            list extended-community {
            when " /ipi-routemap:routemaps/ipi-routemap:routemap/ipi-routemap:match-condition/ipi-routemap:extended-communities/ipi-routemap:extended-community/ipi-routemap:config/ipi-routemap:match-type ";
                key "extended-community-identifier";
                max-elements 1;
                description
                    "Match extended community list";
                leaf extended-community-identifier  {
                    type  leafref {
                        path  "../config/extended-community-identifier";
                    }
                    description "Use this attribute to match BGP external community list.Communities
                                are used to group and filter routes. They are designed to provide the
                                ability to apply policies to large numbers of routes by using match
                                and set commands. Community lists are used to identify and filter
                                routes by their common attributes. This command allows the matching
                                based on community lists. The values set by this command overrides the
                                global values. The route that does not match at least one match clause
                                is ignored";
                } // END of extended-community-identifier definition.

                container config {
                    description
                        "Match extended community list";
                    uses extended-community-info;
                } // END of config-container definition.
                container state {
                    config false;
                    description
                        "Match extended Community Operational state data";
                    uses extended-community-info;
                } // END of state-container definition.
            } // End of extended-community-list
        } // END of extended-communities-container definition.
    } // END of extended-community-list-entry definition.
    grouping community-info {
        description
            "Match community list";
        leaf community-identifier  {
            type  ipi-routemap-types:rmap_community_string_t;
            description "Use this attribute to specify the community to be matched.Communities
                        are used to group and filter routes. They are designed to provide the
                        ability to apply policies to large numbers of routes by using match
                        and set commands.Community lists are used to identify and filter
                        routes by their common attributes. This command allows the matching
                        based on community lists.The values set by the match community command
                        overrides the global values. The route that does not match at least
                        one match clause is ignored.";
        } // END of community-identifier definition.

        leaf match-type  {
            type  ipi-routemap-types:rmap_community_type_t;
            mandatory true;
            description "Do exact matching of communities";
        } // END of match-type definition.

    } // END of community-info definition.
    grouping community-list-entry {
        description
            "Match community list";
        container communities {
            description
                "Match community info";

            list community {
            when " /ipi-routemap:routemaps/ipi-routemap:routemap/ipi-routemap:match-condition/ipi-routemap:communities/ipi-routemap:community/ipi-routemap:config/ipi-routemap:match-type ";
                key "community-identifier";
                max-elements 1;
                description
                    "Match community list";
                leaf community-identifier  {
                    type  leafref {
                        path  "../config/community-identifier";
                    }
                    description "Use this attribute to specify the community to be matched.Communities
                                are used to group and filter routes. They are designed to provide the
                                ability to apply policies to large numbers of routes by using match
                                and set commands.Community lists are used to identify and filter
                                routes by their common attributes. This command allows the matching
                                based on community lists.The values set by the match community command
                                overrides the global values. The route that does not match at least
                                one match clause is ignored.";
                } // END of community-identifier definition.

                container config {
                    description
                        "Match community list";
                    uses community-info;
                } // END of config-container definition.
                container state {
                    config false;
                    description
                        "Match Community Operational state data";
                    uses community-info;
                } // END of state-container definition.
            } // End of community-list
        } // END of communities-container definition.
    } // END of community-list-entry definition.
    grouping length-info {
        description
            "Match community length list";
        leaf packet-min-length  {
            type  uint16 {
                 range "0..65535"  {
                    description "0..65535:Minimum packet length";
                 }
            }
            description "use this attribute to set match community minimum length";
        } // END of packet-min-length definition.

        leaf packet-max-length  {
            type  uint16 {
                 range "0..65535"  {
                    description "0..65535:Maximum packet length";
                 }
            }
            description "use this attribute to set match community maximum length";
        } // END of packet-max-length definition.

    } // END of length-info definition.
    grouping spf-length-entry {
        description
            "Match community length list";
        container route-filter {
            if-feature feature-list:HAVE_PBR;
            description
                "Match community length list";

            list packet-length-constraints {
                if-feature feature-list:HAVE_PBR;
                key "packet-min-length packet-max-length";
                max-elements 1;
                description
                    "Match community length list";
                leaf packet-min-length  {
                    type  leafref {
                        path  "../config/packet-min-length";
                    }
                    description "use this attribute to set match community minimum length";
                } // END of packet-min-length definition.

                leaf packet-max-length  {
                    type  leafref {
                        path  "../config/packet-max-length";
                    }
                    description "use this attribute to set match community maximum length";
                } // END of packet-max-length definition.

                container config {
                    description
                        "Match community length list";
                    uses length-info;
                } // END of config-container definition.
                container state {
                    config false;
                    description
                        "Match Community length Operational state data";
                    uses length-info;
                } // END of state-container definition.
            } // End of packet-length-constraints-list
        } // END of route-filter-container definition.
    } // END of spf-length-entry definition.
    grouping match-ipv4-info {
        description
            "Match ipv4 entry";
        leaf ip-access-list-name  {
            type  string {
                length "1..1965";
                pattern "[^?' =,>|]+";
            }
            description "Use this attribute to specify the match address of route. If there is
                        a match for the specified IP address, and permit is specified, the
                        route is redistributed or controlled, as specified by the set action.
                        If the match criteria are met, and deny is specified then the route is
                        not redistributed or controlled. If the match criteria are not met,
                        the route is neither accepted nor forwarded, irrespective of permit or
                        deny specifications.The route specified by the policies might not be
                        the same as specified by the routing protocols. Setting policies
                        enable packets to take different routes, depending on their length or
                        content. Packet forwarding based on configured policies overrides
                        packet forwarding specified in routing tables.";
        } // END of ip-access-list-name definition.

        leaf ip-prefix-list-name  {
            type  string {
                length "1..1965";
                pattern "[^?' =,>|]+";
            }
            description "Use this attribute to match entries of a prefix-list. The route
                        specified by the policies might not be the same as specified by the
                        routing protocols. Setting policies enable packets to take different
                        routes depending on their length or content. Packet forwarding based
                        on configured policies overrides packet forwarding specified in
                        routing tables.";
        } // END of ip-prefix-list-name definition.

        leaf peer-access-list-name  {
            type  string {
                length "1..1965";
                pattern "[^?' =,>|]+";
            }
            description "Use this attribute to specify the match peer IPv4 address of a route.";
        } // END of peer-access-list-name definition.

        leaf next-hop-prefix-list-name  {
            type  string {
                length "1..1965";
                pattern "[^?' =,>|]+";
            }
            description "Use this attribute to specify the next-hop IP address match criterion
                        using the prefix-list. This command matches the next-hop IP address of
                        a route.";
        } // END of next-hop-prefix-list-name definition.

        leaf next-hop-access-list-name  {
            type  string {
                length "1..1965";
                pattern "[^?' =,>|]+";
            }
            description "Use this attribute to specify a next-hop address to be matched in a
                        route-map. The route specified by the policies might not be the same
                        as specified by the routing protocols. Setting policies enable packets
                        to take different routes depending on their length or content. Packet
                        forwarding based on configured policies overrides packet forwarding
                        specified in routing tables.";
        } // END of next-hop-access-list-name definition.

    } // END of match-ipv4-info definition.
    grouping match-ipv6-info {
        description
            "Match ipv6 entry";
        leaf ipv6-address-access-list-name  {
            type  string {
                length "1..1965";
                pattern "[^?' =,>|]+";
            }
            description "Use this attribute to specify the match address of route. The route
                        specified by the policies might not be the same as specified by the
                        routing protocols. Setting policies enable packets to take different
                        routes depending on their length or content. Packet forwarding based
                        on configured policies overrides packet forwarding specified in
                        routing tables";
        } // END of ipv6-address-access-list-name definition.

        leaf ipv6-prefix-list-name  {
            type  string {
                length "1..1965";
                pattern "[^?' =,>|]+";
            }
            description "Use this attribute to match entries of a prefix-list. The route
                        specified by the policies might not be the same as specified by the
                        routing protocols. Setting policies enable packets to take different
                        routes, depending on their length or content. Packet forwarding based
                        on configured policies overrides packet forwarding specified in
                        routing tables.";
        } // END of ipv6-prefix-list-name definition.

        leaf peer-access-list-name  {
            type  string {
                length "1..1965";
                pattern "[^?' =,>|]+";
            }
            description "Use this attribute to specify the match peer IPv6 address of a route.";
        } // END of peer-access-list-name definition.

        leaf next-hop-prefix-list-name  {
            type  string {
                length "1..1965";
                pattern "[^?' =,>|]+";
            }
            description "Use this attribute to match entries of a prefix-list. The route
                        specified by the policies might not be the same as specified by the
                        routing protocols. Setting policies enable packets to take different
                        routes depending on their length or content. Packet forwarding based
                        on configured policies overrides packet forwarding specified in
                        routing tables.";
        } // END of next-hop-prefix-list-name definition.

        leaf next-hop-match-string  {
            type  ipi-routemap-types:rmap_ipv6_nexthop_t;
            description "Use this attribute to specify the next-hop address to be matched. The
                        route specified by the policies might not be the same as specified by
                        the routing protocols. Setting policies enable packets to take
                        different routes depending on their length or content. Packet
                        forwarding based on configured policies overrides packet forwarding
                        specified in routing tables.";
        } // END of next-hop-match-string definition.

    } // END of match-ipv6-info definition.
    grouping ipv4-entry {
        description
            "Match ipv4 entry";
        container ipv4 {
            description
                "Match ipv4 entry";
            container config {
                description
                    "match entry config data";
                uses match-ipv4-info;
            } // END of config-container definition.
            container state {
                config false;
                description
                    "Match Operational state data";
                uses match-ipv4-info;
            } // END of state-container definition.
        } // END of ipv4-container definition.
    } // END of ipv4-entry definition.
    grouping ipv6-entry {
        description
            "Match ipv6 entry";
        container ipv6 {
            if-feature feature-list:HAVE_IPV6;
            description
                "Match ipv6 entry";
            container config {
                if-feature feature-list:HAVE_IPV6;
                description
                    "match entry config data";
                uses match-ipv6-info;
            } // END of config-container definition.
            container state {
                config false;
                description
                    "Match Operational state data";
                uses match-ipv6-info;
            } // END of state-container definition.
        } // END of ipv6-container definition.
    } // END of ipv6-entry definition.
    grouping match-entry-list {
        description
            "Match values from routing entry";
        container match-condition {
            description
                "Match values from routing entry";
            container config {
                description
                    "match entry config data";
                uses match-list;
            } // END of config-container definition.
            container state {
                config false;
                description
                    "Match Operational state data";
                uses match-list;
            } // END of state-container definition.
            uses spf-length-entry;
            uses community-list-entry;
            uses extended-community-list-entry;
            uses ipv4-entry;
            uses ipv6-entry;
        } // END of match-condition-container definition.
    } // END of match-entry-list definition.
    grouping continue-entry {
        description
            "Continue on a different entry";
        container continue-on-match {
            description
                "Information of Continue on a different entry";
            container config {
                description
                    "contiue entry config data";
                uses continue-list;
            } // END of config-container definition.
            container state {
                config false;
                description
                    "continue Operational state data";
                uses continue-list;
            } // END of state-container definition.
        } // END of continue-on-match-container definition.
    } // END of continue-entry definition.
    grouping aggregator-info {
        description
            "aggregator info";
        leaf as-number  {
            type  uint32 {
                 range "1..4294967295"  {
                    description "1..4294967295:AS number";
                 }
            }
            description "Use this attribute to set the AS number for the route map and router
                        ID. An Autonomous System (AS) is a collection of networks under a
                        common administration sharing a common routing strategy. It is
                        subdivided by areas, and is assigned a unique 16-bit number. Use the
                        set aggregator command to assign an AS number for the aggregator.To
                        use the set aggregator command, you must first have a match clause.
                        Match and set commands set the conditions for redistributing routes
                        from one routing protocol to another. The match command specifies the
                        match criteria under which redistribution is allowed for the current
                        route-map. The set command specifies the set redistribution actions to
                        be performed, if the match criteria are met.If the packets do not
                        match any of the defined criteria, they are routed through the normal
                        routing process.";
        } // END of as-number definition.

        leaf aggregator-ip-address  {
            type  inet:ipv4-address;
            description "IP address of aggregator.";
        } // END of aggregator-ip-address definition.

    } // END of aggregator-info definition.
    grouping set-aggregator-list {
        description
            "set entry config data";

        list bgp-aggregator-attribute {
            key "as-number aggregator-ip-address";
            max-elements 1;
            description
                "aggregator info";
            leaf as-number  {
                type  leafref {
                    path  "../config/as-number";
                }
                description "Use this attribute to set the AS number for the route map and router
                            ID. An Autonomous System (AS) is a collection of networks under a
                            common administration sharing a common routing strategy. It is
                            subdivided by areas, and is assigned a unique 16-bit number. Use the
                            set aggregator command to assign an AS number for the aggregator.To
                            use the set aggregator command, you must first have a match clause.
                            Match and set commands set the conditions for redistributing routes
                            from one routing protocol to another. The match command specifies the
                            match criteria under which redistribution is allowed for the current
                            route-map. The set command specifies the set redistribution actions to
                            be performed, if the match criteria are met.If the packets do not
                            match any of the defined criteria, they are routed through the normal
                            routing process.";
            } // END of as-number definition.

            leaf aggregator-ip-address  {
                type  leafref {
                    path  "../config/aggregator-ip-address";
                }
                description "IP address of aggregator.";
            } // END of aggregator-ip-address definition.

            container config {
                description
                    "aggregator list";
                uses aggregator-info;
            } // END of config-container definition.
            container state {
                config false;
                description
                    "aggregator Operational state data";
                uses aggregator-info;
            } // END of state-container definition.
        } // End of bgp-aggregator-attribute-list
    } // END of set-aggregator-list definition.
    grouping route-target-info {
        description
            "Route target info";
        leaf ext-community-rt  {
            type  cml-data-types:cml_line_t {
                length "1..1965";
            }
            description "use this attribute to set an Route target extended community";
        } // END of ext-community-rt definition.

        leaf additive-type  {
            type  ipi-routemap-types:rmap_additive_type_t;
            mandatory true;
            description "use this attribute to add to the exsisting community.";
        } // END of additive-type definition.

    } // END of route-target-info definition.
    grouping cost-info {
        description
            "extened community cost info";
        leaf comparison-type  {
            type  ipi-routemap-types:rmap_ext_cost_type_t;
            description "use this attribute to set Extended cost community.";
        } // END of comparison-type definition.

        leaf community-id  {
            type  uint8 {
                 range "0..255"  {
                    description "0..255:Community-ID";
                 }
            }
            description "use this attribute to set Extended community-id";
        } // END of community-id definition.

        leaf cost-value  {
            type  uint32 {
                 range "0..4294967295"  {
                    description "0..4294967295:Cost";
                 }
            }
            description "use this attribute to set Extended community cost value";
        } // END of cost-value definition.

    } // END of cost-info definition.
    grouping set-ext-cost-list {
        description
            "set extended community cost config data";

        list cost {
            key "comparison-type community-id cost-value";
            max-elements 1;
            description
                "extened community cost info";
            leaf comparison-type  {
                type  leafref {
                    path  "../config/comparison-type";
                }
                description "use this attribute to set Extended cost community.";
            } // END of comparison-type definition.

            leaf community-id  {
                type  leafref {
                    path  "../config/community-id";
                }
                description "use this attribute to set Extended community-id";
            } // END of community-id definition.

            leaf cost-value  {
                type  leafref {
                    path  "../config/cost-value";
                }
                description "use this attribute to set Extended community cost value";
            } // END of cost-value definition.

            container config {
                description
                    "cost list";
                uses cost-info;
            } // END of config-container definition.
            container state {
                config false;
                description
                    "cost Operational state data";
                uses cost-info;
            } // END of state-container definition.
        } // End of cost-list
    } // END of set-ext-cost-list definition.
    grouping set-ext-list {
        description
            "set entry route target config data";
        container extended-community {
            description
                "Use this container to set an extended community attribute.To use this
                        command you must first have a match clause. The match and set commands
                        define the conditions for redistributing routes from one routing
                        protocol to another: The match command defines the match criteria
                        under which redistribution is allowed for the current route-map. The
                        set command defines the set redistribution actions to be performed, if
                        the match criteria are met.If the packets do not match any of the
                        defined criteria, they are routed through the normal routing process.";
            uses set-ext-rt-list;
            uses set-ext-cost-list;
        } // END of extended-community-container definition.
    } // END of set-ext-list definition.
    grouping set-ext-rt-list {
        description
            "set entry route target config data";

        list route-target {
            key "ext-community-rt";
            max-elements 1;
            description
                "extened route target info";
            leaf ext-community-rt  {
                type  leafref {
                    path  "../config/ext-community-rt";
                }
                description "use this attribute to set an Route target extended community";
            } // END of ext-community-rt definition.

            container config {
                description
                    "route target list";
                uses route-target-info;
            } // END of config-container definition.
            container state {
                config false;
                description
                    "route target Operational state data";
                uses route-target-info;
            } // END of state-container definition.
        } // End of route-target-list
    } // END of set-ext-rt-list definition.
    grouping set-list {
        description
            "set entry config data";
        leaf forward-interface-type  {
            type  ipi-routemap-types:rmap_forward_interface_type_t;
            description "Use this attributes to discard routes based on policy/rules configured
                        for a route map.Route maps can be applied to BGP neighbors. When this
                        command is given for a route map and that route map is applied to a
                        BGP neighbor, the discard route entries are added by BGP for the
                        prefix permitted by the route map.";
        } // END of forward-interface-type definition.

        leaf metric-value  {
            type  string {
                length "1..11";
                pattern "[+-][0-9]+|[0-9]+";
            }
            description "Use this command to set a metric value for a route and influence
                        external neighbors about the preferred path into an Autonomous System
                        (AS). The preferred path is the one with a lower metric value. A
                        router compares metrics for paths from neighbors in the same ASs. To
                        compare metrics from neighbors coming from different ASs, use the bgp
                        always-compare-med command.To use this command, you must first have a
                        match clause. Match and set commands set the conditions for
                        redistributing routes from one routing protocol to another. The match
                        command specifies the match criteria under which redistribution is
                        allowed for the current route-map. The set command specifies the set
                        redistribution actions to be performed, if the match criteria are
                        met.If the packets do not match any of the defined criteria, they are
                        routed through the normal routing process.";
        } // END of metric-value definition.

        leaf route-tag  {
            type  uint32 {
                 range "1..4294967295"  {
                    description "1..4294967295:Tag value";
                 }
            }
            description "Use this attribute to set a tag value. The parameter is the route tag
                        that is labeled by another routing protocol (BGP or
                        other IGP when redistributing), because AS-external-LSA has a
                        route-tag field in its LSAs. In addition, when using route-map, OcNOS
                        can tag the LSAs with the appropriate tag value. Sometimes the tag
                        matches with using route-map, and sometimes, the value may be used by
                        another application.";
        } // END of route-tag definition.

        leaf weight  {
            type  uint32 {
                 range "0..4294967295"  {
                    description "0..4294967295:Weight value";
                 }
            }
            description "Use this attribute to set weights for the routing table.
                        The weight value is used to assist in best path selection. It is
                        assigned locally to a router. When there are several routes with a
                        common destination, the routes with a higher weight value are
                        preferred. To use this command, you must first have a match clause.
                        Match and set commands set the conditions for redistributing routes
                        from one routing protocol to another. The match command specifies the
                        match criteria under which redistribution is allowed for the current
                        route-map. The set command specifies the set redistribution actions to
                        be performed, if the match criteria are met.";
        } // END of weight definition.

        leaf local-preference  {
            type  uint32 {
                 range "0..4294967295"  {
                    description "0..4294967295:Preference value";
                 }
            }
            description "Use this attribute to set the BGP local preference path attribute";
        } // END of local-preference definition.

        leaf route-origin-type  {
            type  ipi-routemap-types:rmap_origin_type_t;
            description "Use this command to set the BGP origin code. The origin attribute
                        defines the origin of the path information. To use this command, you
                        must first have a match clause. Match and set commands set the
                        conditions for redistributing routes from one routing protocol to
                        another. The match command specifies the match criteria under which
                        redistribution is allowed for the current route-map. The set command
                        specifies the set redistribution actions to be performed, if the match
                        criteria are met.If the packets do not match any of the defined
                        criteria, they are routed through the normal routing process.";
        } // END of route-origin-type definition.

        leaf metric-type  {
            type  ipi-routemap-types:rmap_metric_type_t;
            description "Use this command to set the metric type for the destination routing
                        protocol. Select a type to be either Type-1 or Type2 in the
                        AS-external-LSA when the route-map matches the condition.";
        } // END of metric-type definition.

        leaf level-type  {
            type  ipi-routemap-types:rmap_level_type_t;
            description "Use this attribute to set the IS-IS level to export a route.";
        } // END of level-type definition.

        leaf enable-as-path-tag  {
            type  empty;
            description "Use this command to modify an autonomous system path for a route. By
                        specifying the length of the AS-Path, the
                        router influences the best path selection by a neighbor";
        } // END of enable-as-path-tag definition.

        leaf atomic-aggregate  {
            type  empty;
            description "Use this attribute to set an atomic aggregate attribute.To use this
                        command, you must first have a match clause. Match and set commands
                        set the conditions for redistributing routes from one routing protocol
                        to another. The match command specifies the match criteria under which
                        redistribution is allowed for the current route-map. The set command
                        specifies the set redistribution actions to
                        be performed, if the match criteria are met.If the packets do not
                        match any of the defined criteria, they are routed through the normal
                        routing process.";
        } // END of atomic-aggregate definition.

        leaf delete-community-value  {
            type  ipi-routemap-types:rmap_community_string_t;
            description "Use this attribute to delete the matched communities from the
                        community attribute of an inbound or outbound update when applying
                        route-map.";
        } // END of delete-community-value definition.

        leaf bgp-originator-id  {
            type  inet:ipv4-address;
            description "Use this command to set the originator ID attribute. To use this
                        command, you must first have a match clause. Match and set commands
                        set the conditions for redistributing routes from one routing protocol
                        to another. The match command specifies the match criteria under which
                        redistribution is allowed for the current route-map. The set command
                        specifies the set redistribution actions to be performed, if the match
                        criteria are met.If the packets do not match any of the defined
                        criteria, they are routed through the normal routing process";
        } // END of bgp-originator-id definition.

        leaf as-path-prepend  {
            type  cml-data-types:cml_line_t {
                length "1..1965";
            }
            description "Use this attributes to modify an autonomous system path for a route.
                        By specifying the length of the AS-Path, the router influences the
                        best path selection by a neighbor.Use this command to prepend an AS
                        path string to routes increasing the AS path length.To use this
                        command, you must first give the match and set commands configure the
                        conditions for redistributing routes from one routing protocol to
                        another: 1. The match command specifies the match criteria under which
                        redistribution is allowed for the current route-map. 2.The set command
                        specifies the set redistribution actions to be performed if the match
                        criteria are met.If the packets do not match any of the defined
                        criteria, they are routed through the normal routing process.";
        } // END of as-path-prepend definition.

        leaf ext-community-site-of-origin  {
            type  cml-data-types:cml_line_t {
                length "1..1965";
            }
            description "Use this attribute to set an extended community attribute as
                        Site-of-origin extended community.";
        } // END of ext-community-site-of-origin definition.

    } // END of set-list definition.
    grouping dampening-list {
        description
            "Set timer values for dampening";
        leaf enable-dampening  {
            type  empty;
            mandatory true;
            description "Use this attribute to enable route dampening and set various
                        parameters. Route dampening minimizes the instability caused by route
                        flapping. A penalty is added for every flap in a flapping route. As
                        soon as the total penalty reaches the suppress limit the advertisement
                        of the route is suppressed. This penalty is decayed according to the
                        configured half time value. Once the penalty is lower than the reuse
                        limit, the route advertisement is unsuppressed. The dampening
                        information is purged from the router once the penalty becomes less
                        than half of the reuse limit.Reachability half-life time for the
                        penalty in minutes. The time for the penalty to decrease to one-half
                        of its current value.";
        } // END of enable-dampening definition.

        leaf reachability-half-life-time  {
            type  uint8 {
                 range "1..45"  {
                    description "1..45:Reachability Half-life time for the penalty(minutes)";
                 }
            }
            default "15";
            description "Reachability half-life time for the penalty in minutes. The time for
                        the penalty to decrease to one-half of its current value.";
        } // END of reachability-half-life-time definition.

        leaf reuse-time-limit  {
            type  uint16 {
                 range "1..20000"  {
                    description "1..20000:Value to start reusing a route";
                 }
            }
            default "750";
            description "Value to start reusing a route. When the penalty for a suppressed
                        route decays below the reuse value, the routes become unsuppressed.";
        } // END of reuse-time-limit definition.

        leaf suppress-time-limit  {
            type  uint16 {
                 range "1..20000"  {
                    description "1..20000:Value to start suppressing a route";
                 }
            }
            default "2000";
            description "Value to start suppressing a route. When the penalty for a route
                        exceeds the suppress value, the route is suppressed";
        } // END of suppress-time-limit definition.

        leaf max-suppress-time-limit  {
            type  uint8 {
                 range "1..255"  {
                    description "1..255:Maximum duration to suppress a stable route(minutes)";
                 }
            }
            default "60";
            description "Maximum duration to suppress a stable route in minutes.";
        } // END of max-suppress-time-limit definition.

        leaf unreachability-half-life-time  {
            type  uint8 {
                 range "1..45"  {
                    description "1..45:Un-reachability Half-life time for the penalty(minutes)";
                 }
            }
            default "15";
            description "Un-reachability half-life time for the penalty in minutes.";
        } // END of unreachability-half-life-time definition.

    } // END of dampening-list definition.
    grouping set-community-attrs {
        description
            "Set BGP community info";
        leaf enable-internet  {
            when " not(/ipi-routemap:routemaps/ipi-routemap:routemap/ipi-routemap:set-action/ipi-routemap:communities/ipi-routemap:config/ipi-routemap:no-community-attribute) ";
            type  empty;
            description "Use this attribute to set the communities attribute and group
                        destinations in a certain community, as well as apply routing
                        decisions according to those communities.If the packets do not match
                        any of the defined criteria, they are routed through the normal
                        routing process.";
        } // END of enable-internet definition.

        leaf enable-local-as  {
            when " not(/ipi-routemap:routemaps/ipi-routemap:routemap/ipi-routemap:set-action/ipi-routemap:communities/ipi-routemap:config/ipi-routemap:no-community-attribute) ";
            type  empty;
            description "Specifies the local-as community (well-known community). Routes with
                        community are advertised to only peers that are part of the local
                        autonomous system or to only peers within a subautonomous system of a
                        confederation. These routes are not advertised to external peers or to
                        other subautonomous systems within a confederation.You can configure
                        one or more keywords.";
        } // END of enable-local-as definition.

        leaf enable-no-advertise  {
            when " not(/ipi-routemap:routemaps/ipi-routemap:routemap/ipi-routemap:set-action/ipi-routemap:communities/ipi-routemap:config/ipi-routemap:no-community-attribute) ";
            type  empty;
            description "Specifies the no-advertise community (well-known community). Routes
                        with this community are not advertised to any peer (internal or
                        external).";
        } // END of enable-no-advertise definition.

        leaf enable-no-export  {
            when " not(/ipi-routemap:routemaps/ipi-routemap:routemap/ipi-routemap:set-action/ipi-routemap:communities/ipi-routemap:config/ipi-routemap:no-community-attribute) ";
            type  empty;
            description "Specifies the no-export community (well-known community). Routes with
                        this community are advertised to only peers in the same autonomous
                        system or to only other subautonomous systems within a confederation.
                        These routes are not advertised to external peers.";
        } // END of enable-no-export definition.

        leaf no-community-attribute  {
            type  empty;
            description "Specifies the no community attribute.We cannot configure any other
                        keyword if you configure the none keyword.";
        } // END of no-community-attribute definition.

        leaf additive-set  {
            when " not(/ipi-routemap:routemaps/ipi-routemap:routemap/ipi-routemap:set-action/ipi-routemap:communities/ipi-routemap:config/ipi-routemap:no-community-attribute) ";
            type  empty;
            description "Adds to existing community.";
        } // END of additive-set definition.

        leaf community-number  {
            when " not(/ipi-routemap:routemaps/ipi-routemap:routemap/ipi-routemap:set-action/ipi-routemap:communities/ipi-routemap:config/ipi-routemap:no-community-attribute) ";
            type  cml-data-types:cml_line_t {
                length "1..1965";
            }
            description "Use this attributes to set the communities attribute. and group
                        destinations in a certain community, as well as apply routing
                        decisions according to those communities.";
        } // END of community-number definition.

        leaf community-with-as-number  {
            when " not(/ipi-routemap:routemaps/ipi-routemap:routemap/ipi-routemap:set-action/ipi-routemap:communities/ipi-routemap:config/ipi-routemap:no-community-attribute) ";
            type  cml-data-types:cml_line_t {
                length "1..1965";
            }
            description "Autonomous system (AS) number and network number entered in the 4-byte
                        new community format. This value is configured with two 2-byte numbers
                        separated by a colon. A number from 1 to 65535 can be entered as each
                        2-byte number. A single community can be entered or multiple
                        communities can be entered, each separated by a space.";
        } // END of community-with-as-number definition.

    } // END of set-community-attrs definition.
    grouping set-community-info {
        description
            "Set BGP community info";
        container communities {
            description
                "Set BGP community value";
            container config {
                description
                    "Set BGP community data";
                uses set-community-attrs;
            } // END of config-container definition.
            container state {
                config false;
                description
                    "Set Operational state data";
                uses set-community-attrs;
            } // END of state-container definition.
        } // END of communities-container definition.
    } // END of set-community-info definition.
    grouping set-dampening-info {
        description
            "Set timer values for dampening";
        container dampening {
            when " /ipi-routemap:routemaps/ipi-routemap:routemap/ipi-routemap:set-action/ipi-routemap:dampening/ipi-routemap:config/ipi-routemap:enable-dampening ";
            description
                "Enable route-flap dampening";
            container config {
                when " /ipi-routemap:routemaps/ipi-routemap:routemap/ipi-routemap:set-action/ipi-routemap:dampening/ipi-routemap:config/ipi-routemap:enable-dampening ";
                presence "Enabling dampening timers";
                description
                    "Set dampening entry config data";
                uses dampening-list;
            } // END of config-container definition.
            container state {
                config false;
                description
                    "Set Operational state data";
                uses dampening-list;
            } // END of state-container definition.
        } // END of dampening-container definition.
    } // END of set-dampening-info definition.
    grouping set-ipv4-info {
        description
            "Set ipv4 entry";
        leaf ip-nexthop-address  {
            when " not(/ipi-routemap:routemaps/ipi-routemap:routemap/ipi-routemap:set-action/ipi-routemap:config/ipi-routemap:forward-interface-type) + not(/ipi-routemap:routemaps/ipi-routemap:routemap/ipi-routemap:set-action/ipi-routemap:ipv4/ipi-routemap:config/ipi-routemap:default-nexthop-address) ";
            type  inet:ipv4-address;
            description "Use this attribute to set the specified next-hop value.";
        } // END of ip-nexthop-address definition.

        leaf use-peer-address  {
            type  empty;
            description "Use this attribute to set the next hop value as BGP peer-address";
        } // END of use-peer-address definition.

        leaf default-nexthop-address  {
            when " not(/ipi-routemap:routemaps/ipi-routemap:routemap/ipi-routemap:set-action/ipi-routemap:ipv4/ipi-routemap:config/ipi-routemap:ip-nexthop-address) + not(/ipi-routemap:routemaps/ipi-routemap:routemap/ipi-routemap:set-action/ipi-routemap:config/ipi-routemap:forward-interface-type) ";
            if-feature feature-list:HAVE_PBR;
            type  inet:ipv4-address;
            description "Use this attribute to set the default next hop value";
        } // END of default-nexthop-address definition.

        leaf vpnv4-nexthop-address  {
            if-feature feature-list:HAVE_VRF;
            type  inet:ipv4-address;
            description "Use this command to set a VPNv4 next-hop address. To use this command,
                        you must first have a match clause. Match and set commands set the
                        conditions for redistributing routes from one routing protocol to
                        another. The match command specifies the match criteria under which
                        redistribution is allowed for the current route-map. The set command
                        specifies the set redistribution actions to be performed, if the match
                        criteria are met. If the packets do not match any of the defined
                        criteria, they are routed through the normal routing process.";
        } // END of vpnv4-nexthop-address definition.

    } // END of set-ipv4-info definition.
    grouping set-ipv6-info {
        description
            "Set ipv4 entry";
        leaf ipv6-nexthop-address  {
            when " not(/ipi-routemap:routemaps/ipi-routemap:routemap/ipi-routemap:set-action/ipi-routemap:config/ipi-routemap:forward-interface-type) + not(/ipi-routemap:routemaps/ipi-routemap:routemap/ipi-routemap:set-action/ipi-routemap:ipv6/ipi-routemap:config/ipi-routemap:default-ipv6-nexthop-address) ";
            type  inet:ipv6-address;
            description "Use this attribute to set a next hop-address.";
        } // END of ipv6-nexthop-address definition.

        leaf default-ipv6-nexthop-address  {
            when " not(/ipi-routemap:routemaps/ipi-routemap:routemap/ipi-routemap:set-action/ipi-routemap:config/ipi-routemap:forward-interface-type) + not(/ipi-routemap:routemaps/ipi-routemap:routemap/ipi-routemap:set-action/ipi-routemap:ipv6/ipi-routemap:config/ipi-routemap:ipv6-nexthop-address) ";
            if-feature feature-list:HAVE_PBR;
            type  inet:ipv6-address;
            description "Use this attribute to set the default ipv6 next hop-address";
        } // END of default-ipv6-nexthop-address definition.

        leaf local-ipv6-nexthop-address  {
            type  inet:ipv6-address;
            description "Use this attribute to set Local IPv6 address as next hop-address";
        } // END of local-ipv6-nexthop-address definition.

    } // END of set-ipv6-info definition.
    grouping set-ipv6-entry {
        description
            "Set ipv6 entry";
        container ipv6 {
            description
                "Set ipv6 entry";
            container config {
                description
                    "Set ipv6 entry config data";
                uses set-ipv6-info;
            } // END of config-container definition.
            container state {
                config false;
                description
                    "Set ipv6 Operational state data";
                uses set-ipv6-info;
            } // END of state-container definition.
        } // END of ipv6-container definition.
    } // END of set-ipv6-entry definition.
    grouping set-ipv4-entry {
        description
            "Set ipv4 entry";
        container ipv4 {
            description
                "Set ipv4 entry";
            container config {
                description
                    "Set ipv4 entry config data";
                uses set-ipv4-info;
            } // END of config-container definition.
            container state {
                config false;
                description
                    "Set ipv4 Operational state data";
                uses set-ipv4-info;
            } // END of state-container definition.
        } // END of ipv4-container definition.
    } // END of set-ipv4-entry definition.
    grouping set-entry-list {
        description
            "Set values for routing entry";
        container set-action {
            description
                "Set values for routing entry";
            container config {
                description
                    "Set entry config data";
                uses set-list;
            } // END of config-container definition.
            container state {
                config false;
                description
                    "Set Operational state data";
                uses set-list;
            } // END of state-container definition.
            uses set-ipv4-entry;
            uses set-ipv6-entry;
            uses set-aggregator-list;
            uses set-ext-list;
            uses set-dampening-info;
            uses set-community-info;
        } // END of set-action-container definition.
    } // END of set-entry-list definition.
    grouping rmap-list-top {
        description
            "Route-map information";

        list routemap {
        when " /ipi-routemap:routemaps/ipi-routemap:routemap/ipi-routemap:config/ipi-routemap:action ";
            key "routemap-name sequence-id";
            description
                "PBR Config related operations";
            leaf routemap-name  {
                type  leafref {
                    path  "../config/routemap-name";
                }
                description "Use this attribute to enter the route-map mode and to permit or deny
                            match/set operations.This attribute controls and modifies routing
                            information to allow redistribution of routes. It has a list of match
                            and set attributes associated with it. The match attributes specify
                            the conditions under which redistribution is allowed, and the set
                            attributes specify the particular redistribution actions to be
                            performed if the criteria enforced by match commands are met. Route
                            maps are used for detailed control over route distribution between
                            routing processes.Route maps also allow policy routing, and might
                            route packets to a different route than the obvious shortest path";
            } // END of routemap-name definition.

            leaf sequence-id  {
                type  leafref {
                    path  "../config/sequence-id";
                }
                description "Sequence to insert into or delete from an existing route-map.";
            } // END of sequence-id definition.

            container config {
                when " /ipi-routemap:routemaps/ipi-routemap:routemap/ipi-routemap:config/ipi-routemap:action ";
                description
                    "PBR Config related operations";
                uses rmap-entry;
            } // END of config-container definition.
            container state {
                config false;
                description
                    "Operational state data";
                uses rmap-entry;
            } // END of state-container definition.
            uses continue-entry;
            uses match-entry-list;
            uses set-entry-list;
        } // End of routemap-list
    } // END of rmap-list-top definition.

    grouping  routemaps-grouping {
    description
        "Route-map information";
    container routemaps {
        description
            "Route-map information";
        uses rmap-list-top;
    } // END of routemaps-container definition.
    } // END of routemaps-grouping definition.

    uses routemaps-grouping;

}
