/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-switchportinterface.yang
*
*/

submodule zebos-switchportinterface {

    belongs-to  zebos { prefix zebos; }

    import cml_data_types {
        prefix cml_data_types;
    }

    import feature_list {
        prefix feature_list;
    }

    organization
        "IP Infusion Inc.";

    contact
        "Address: 3965 Freedom Circle, Suite 200, Santa Clara, CA 95054
         Phone: +1 408-400-1900
         E-mail: support@ipinfusion.com
         Web: http://www.ipinfusion.com/";

    description
        "switchport configuration";


    revision "2018-12-28" {
        description " Provider bridge static MAC support for Qumran platform.";
        reference "";
    }

    revision "2018-06-21" {
        description " Initial Version.";
        reference "";
    }



    grouping staticMac-grouping {
    description
        "staticMac";
        list staticMac {
            key "macAddr";
            description
                "staticMac";
            leaf ifName  {
                type  cml_data_types:CML_STRING_T {
                    length "0..255";
                }
                description "";
            } // END of ifName definition.


            leaf vlanIdMac  {
                type  cml_data_types:CML_UINT16_T {
                     range "2..4094";
                }
                description "";
            } // END of vlanIdMac definition.


            leaf svlanId  {
                if-feature feature_list:HAVE_PB_STATIC_FDB_CUSTOM_CONFIG;
                type  cml_data_types:CML_UINT16_T {
                     range "2..4094";
                }
                description "";
            } // END of svlanId definition.


            leaf macAddr  {
                type  cml_data_types:CML_MAC_ADDR_T {
                    length "0..255";
                }
                description "";
            } // END of macAddr definition.


            leaf discardForward  {
                type  cml_data_types:CML_DISCARDFORWARD_T;
                description "";
            } // END of discardForward definition.


        } // End of staticMac-list
    } // END of staticMac-grouping definition.

    grouping  switchportInterface-grouping {
    description
        "switchportInterface";
    container switchportInterface {
        description
            "switchportInterface";
        leaf useDeiFlag  {
            if-feature feature_list:HAVE_PROVIDER_BRIDGE;
            type  cml_data_types:CML_BOOL_T;
            default false;
            description "";
        } // END of useDeiFlag definition.


        leaf vlanStackEnable  {
            if-feature feature_list:HAVE_PROVIDER_BRIDGE;
            if-feature feature_list:HAVE_SWFWDR;
            type  cml_data_types:CML_VLANSTACK_T;
            description "vlan stack for port";
        } // END of vlanStackEnable definition.


        leaf etherType  {
            if-feature feature_list:HAVE_SWFWDR;
            type  cml_data_types:CML_STRING_T {
                length "0..255";
            }
            default "";
            description "";
        } // END of etherType definition.


        leaf ethType  {
            if-feature feature_list:NOT_HAVE_SWFWDR;
            type  cml_data_types:CML_STRING_T {
                length "0..255";
            }
            description "This Object is used to change Ethertype value ";
        } // END of ethType definition.


        leaf uniName  {
            if-feature feature_list:HAVE_PROVIDER_BRIDGE;
            if-feature feature_list:HAVE_SWFWDR;
            type  cml_data_types:CML_STRING_T {
                length "0..255";
            }
            description "ethernet uni name";
        } // END of uniName definition.


        leaf enniName  {
            if-feature feature_list:HAVE_PROVIDER_BRIDGE;
            if-feature feature_list:HAVE_SWFWDR;
            type  cml_data_types:CML_STRING_T {
                length "0..255";
            }
            description "ethernet enni name";
        } // END of enniName definition.


        leaf uniEnniType  {
            if-feature feature_list:HAVE_PROVIDER_BRIDGE;
            if-feature feature_list:HAVE_SWFWDR;
            type  cml_data_types:CML_UNI_ENNI_TYPE_T;
            description "ethernet type of UNI or ENNI";
        } // END of uniEnniType definition.


        leaf ethSvid  {
            if-feature feature_list:HAVE_VLAN;
            if-feature feature_list:HAVE_SWFWDR;
            type  cml_data_types:CML_INT32_T;
            description "";
        } // END of ethSvid definition.


        leaf evcId  {
            if-feature feature_list:HAVE_PROVIDER_BRIDGE;
            if-feature feature_list:HAVE_SWFWDR;
            type  cml_data_types:CML_STRING_T {
                length "0..255";
            }
            description "";
        } // END of evcId definition.


        leaf uniService  {
            if-feature feature_list:HAVE_PROVIDER_BRIDGE;
            if-feature feature_list:HAVE_SWFWDR;
            type  cml_data_types:CML_UNI_SERVICE_T;
            description "ethernet uni Service";
        } // END of uniService definition.


        leaf maxEvc  {
            if-feature feature_list:HAVE_PROVIDER_BRIDGE;
            if-feature feature_list:HAVE_SWFWDR;
            type  cml_data_types:CML_INT32_T {
                 range "1..4094";
            }
            description "ethernet uni maximum number of EVC ";
        } // END of maxEvc definition.


        leaf uniMode  {
            if-feature feature_list:HAVE_SWFWDR;
            type  cml_data_types:CML_UNI_ENABLE_DISABLE_T;
            description "";
        } // END of uniMode definition.


        leaf bridgeId  {
            if-feature feature_list:HAVE_SWFWDR;
            if-feature feature_list:HAVE_PROVIDER_BRIDGE;
            type  cml_data_types:CML_STRING_T {
                length "0..255";
            }
            description "";
        } // END of bridgeId definition.



        list nsmVlanPort {
            key "portMode";
            description
                "nsm vlan port";
            leaf portMode  {
                type  cml_data_types:CML_SWITCH_PORT_MODE_T;
                description "switchport mode";
            } // END of portMode definition.


            leaf vlanId  {
                type  cml_data_types:CML_UINT16_T {
                     range "2..4094";
                }
                description "vlan Id";
            } // END of vlanId definition.


            leaf nativeVlanId  {
                type  cml_data_types:CML_UINT16_T {
                     range "1..4094";
                }
                description "Native Vlan Id";
            } // END of nativeVlanId definition.


            leaf defaultsvlanId  {
                if-feature feature_list:HAVE_PROVIDER_BRIDGE;
                type  cml_data_types:CML_UINT16_T;
                description "default SVID";
            } // END of defaultsvlanId definition.


            leaf cvlanId  {
                if-feature feature_list:HAVE_PROVIDER_BRIDGE;
                type  cml_data_types:CML_UINT16_T;
                description "";
            } // END of cvlanId definition.


            leaf vlanPortIngressFilter  {
                type  cml_data_types:CML_ENABLE_DISABLE_T;
                default "enable";
                description "";
            } // END of vlanPortIngressFilter definition.


            leaf custTransVlanId  {
                if-feature feature_list:HAVE_PROVIDER_BRIDGE;
                type  cml_data_types:CML_UINT16_T;
                description "";
            } // END of custTransVlanId definition.


            leaf custVlanId  {
                if-feature feature_list:HAVE_PROVIDER_BRIDGE;
                type  cml_data_types:CML_UINT16_T;
                description "";
            } // END of custVlanId definition.


            leaf frameType  {
                type  cml_data_types:CML_VLAN_FRAME_TYPE_T;
                description "";
            } // END of frameType definition.



            list servicevlanTranslation {
                if-feature feature_list:HAVE_SWFWDR;
                key "tsvlan";
                description
                    "servicevlanTranslation";
                leaf tsvlan  {
                    type  cml_data_types:CML_UINT16_T;
                    description "translated SVlan Id";
                } // END of tsvlan definition.


                leaf svlan  {
                    if-feature feature_list:HAVE_SWFWDR;
                    type  cml_data_types:CML_UINT16_T;
                    description "original sVlan Id";
                } // END of svlan definition.


            } // End of servicevlanTranslation-list

            list cvlanTranslation {
                key "cvId";
                description
                    "cvlanTranslation";
                leaf cvId  {
                    type  cml_data_types:CML_UINT16_T {
                         range "1..4095";
                    }
                    description "default sVlan Id";
                } // END of cvId definition.



                list svlanTranslation {
                    key "svId";
                    description
                        "svlanTranslation";
                    leaf svId  {
                        type  cml_data_types:CML_UINT16_T {
                             range "1..4095";
                        }
                        description "default sVlan Id";
                    } // END of svId definition.


                    leaf TcVlanId  {
                        if-feature feature_list:NOT_HAVE_SWFWDR;
                        type  cml_data_types:CML_UINT16_T {
                             range "1..4095";
                        }
                        mandatory true;
                        description "default sVlan Id";
                    } // END of TcVlanId definition.


                    leaf TsVlanId  {
                        if-feature feature_list:NOT_HAVE_SWFWDR;
                        type  cml_data_types:CML_UINT16_T {
                             range "1..4095";
                        }
                        mandatory true;
                        description "default sVlan Id";
                    } // END of TsVlanId definition.


                    leaf svlanCos  {
                        if-feature feature_list:NOT_HAVE_DUNE;
                        type  cml_data_types:CML_INT8_T {
                             range "0..7";
                        }
                        description "";
                    } // END of svlanCos definition.


                    leaf svlanCfi  {
                        if-feature feature_list:NOT_HAVE_DUNE;
                        type  cml_data_types:CML_INT8_T {
                             range "0..1";
                        }
                        description "";
                    } // END of svlanCfi definition.


                    leaf cvlanCos  {
                        if-feature feature_list:NOT_HAVE_DUNE;
                        type  cml_data_types:CML_INT8_T {
                             range "0..7";
                        }
                        description "";
                    } // END of cvlanCos definition.


                    leaf cvlanCfi  {
                        if-feature feature_list:NOT_HAVE_DUNE;
                        type  cml_data_types:CML_INT8_T {
                             range "0..1";
                        }
                        description "";
                    } // END of cvlanCfi definition.


                } // End of svlanTranslation-list
            } // End of cvlanTranslation-list

            list allowedVlan {
                key "vlanRange";
                description
                    "allowedVlan";
                leaf vlanRange  {
                    type  cml_data_types:CML_RANGE_T {
                        length "1..255";
                    }
                    description "VLAN range";
                } // END of vlanRange definition.


                leaf egressTagged  {
                    type  cml_data_types:CML_EGERSS_TAGGED_TYPE_T;
                    description "Egress tagging per vlan";
                } // END of egressTagged definition.


                leaf swVlanOper  {
                    type  cml_data_types:CML_SWVLANOPER_T;
                    description "";
                } // END of swVlanOper definition.


            } // End of allowedVlan-list
        } // End of nsmVlanPort-list

        list l2protocol {
            if-feature feature_list:HAVE_PROVIDER_BRIDGE;
            key "l2protocolType";
            description
                "l2protocol";
            leaf l2protocolType  {
                type  cml_data_types:CML_L2_PROTOCOL_T;
                description "";
            } // END of l2protocolType definition.


            leaf process  {
                type  cml_data_types:CML_L2PROCESS_T;
                mandatory true;
                description "";
            } // END of process definition.


            leaf tunnelVlan  {
                if-feature feature_list:HAVE_SWFWDR;
                type  cml_data_types:CML_INT32_T;
                description "";
            } // END of tunnelVlan definition.


        } // End of l2protocol-list
        container portSecurity {
            if-feature feature_list:HAVE_HELIX4;
            description
                "portSecurity";
            leaf portSecurityMode  {
                type  cml_data_types:CML_PORT_SEC_MODE_T;
                description "port security type";
            } // END of portSecurityMode definition.


            leaf portSecurityMaxLimit  {
                type  cml_data_types:CML_UINT32_T {
                     range "1..1000";
                }
                default "1";
                description "port-security";
            } // END of portSecurityMaxLimit definition.



            list portSecurityMacAddrList {
                key "portSecurityMacAddr";
                description
                    "nsm port security Mac address list";
                leaf portSecurityMacAddr  {
                    type  cml_data_types:CML_STRING_T {
                        length "0..255";
                    }
                    description "";
                } // END of portSecurityMacAddr definition.



                list PortSecurityMacVlanList {
                    key "portSecurityVlanId";
                    description
                        "nsm port security Mac and vlan list";
                    leaf portSecurityVlanId  {
                        type  cml_data_types:CML_UINT16_T;
                        description "secured vlan Id";
                    } // END of portSecurityVlanId definition.



                    list PortSecurityMacSvlanList {
                        if-feature feature_list:HAVE_PROVIDER_BRIDGE;
                        key "portSecuritySvlanId";
                        description
                            "nsm port security Mac and svlan list";
                        leaf portSecuritySvlanId  {
                            type  cml_data_types:CML_UINT16_T;
                            description "secured vlan Id";
                        } // END of portSecuritySvlanId definition.


                    } // End of PortSecurityMacSvlanList-list
                } // End of PortSecurityMacVlanList-list
            } // End of portSecurityMacAddrList-list
        } // END of portSecurity-container definition.
        container cvanRegMode {
            description
                "cvanRegMode";
            leaf cvlanRegWord  {
                type  cml_data_types:CML_STRING_T {
                    length "0..255";
                }
                description "cvlan registration table";
            } // END of cvlanRegWord definition.


        } // END of cvanRegMode-container definition.
        container pVlanConfig {
            presence "yes";
            description
                "pVlanConfig";
            leaf pvlanMode  {
                type  cml_data_types:CML_PVLAN_MODE_T;
                mandatory true;
                description "Private VLAN port mode";
            } // END of pvlanMode definition.


            leaf pvlanConfigured  {
                type  cml_data_types:CML_BOOL_T;
                config false;
                description "";
            } // END of pvlanConfigured definition.



            list pvlanInstance {
                key "pvlanId";
                description
                    "mapped private-vlan instance with nsm pvlan struct";
                leaf pvlanId  {
                    type  cml_data_types:CML_UINT16_T {
                         range "2..4094";
                    }
                    description "Private VLAN id";
                } // END of pvlanId definition.


                leaf pvlanAssociate  {
                    type  cml_data_types:CML_UINT32_T;
                    description "Private VLAN Associate";
                } // END of pvlanAssociate definition.


                leaf pvlanMapVid  {
                    type  cml_data_types:CML_RANGE_T {
                        length "1..255";
                    }
                    description "private-vlan Mapping";
                } // END of pvlanMapVid definition.


            } // End of pvlanInstance-list
        } // END of pVlanConfig-container definition.
        container oepMapTable {
            if-feature feature_list:HAVE_PROVIDER_BRIDGE;
            if-feature feature_list:HAVE_SWFWDR;
            description
                "oepMapTable";
            leaf oepMapType  {
                type  cml_data_types:CML_OEP_MAP_TYPE_T;
                description "oep map type";
            } // END of oepMapType definition.


            leaf oepMapName  {
                type  cml_data_types:CML_STRING_T {
                    length "0..255";
                }
                description "oep mapping table name";
            } // END of oepMapName definition.


        } // END of oepMapTable-container definition.
    } // END of switchportInterface-container definition.
    } // END of switchportInterface-container definition.


}
