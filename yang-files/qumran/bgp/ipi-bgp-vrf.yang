/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-bgp-vrf.yang
*
*/

module ipi-bgp-vrf {

    yang-version 1.1;

    namespace   "http://www.ipinfusion.com/yang/ocnos/ipi-bgp-vrf";

    prefix "ipi-bgp-vrf";

    import cml-data-types {
        prefix cml-data-types;
    }

    import ipi-bgp-types {
        prefix ipi-bgp-types;
    }

    import ipi-network-instance {
        prefix ipi-network-instance;
    }

    import ipi-vrf {
        prefix ipi-vrf;
    }

    import ietf-inet-types {
        prefix inet;
    }

    import feature-list {
        prefix feature-list;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for BGP VRF";


    revision "2021-03-05" {
        description "Added BGP statistics attributes";
        reference " 0.3.0.";
    }

    revision "2020-12-15" {
        description "Change to have data-types in lower case instead of camel case";
        reference " 0.2.0.";
    }

    revision "2020-09-10" {
        description "Initial Version";
        reference " 0.1.0.";
    }

    grouping bgp-counters-socket-state {
        description
            "attributes realting to socket counters";
        leaf created  {
            type  uint32;
            default "0";
            config false;
            description "Sockets create";
        } // END of created definition.

        leaf accepted  {
            type  uint32;
            default "0";
            config false;
            description "Sockets accept";
        } // END of accepted definition.

        leaf closed  {
            type  uint32;
            default "0";
            config false;
            description "Sockets close";
        } // END of closed definition.

        leaf create-retries  {
            type  uint32;
            default "0";
            config false;
            description "Sockets create retries";
        } // END of create-retries definition.

        leaf create-failures  {
            type  uint32;
            default "0";
            config false;
            description "Sockets create failures";
        } // END of create-failures definition.

        leaf fd-close-session  {
            type  uint32;
            default "0";
            config false;
            description "Socket fd-close session";
        } // END of fd-close-session definition.

    } // END of bgp-counters-socket-state definition.
    grouping bgp-counters-input-output-state {
        description
            "attributes relating to input output counters";
        leaf active-open  {
            type  uint16;
            default "0";
            config false;
            description "Active Open attempts";
        } // END of active-open definition.

        leaf passive-open  {
            type  uint16;
            default "0";
            config false;
            description "Passive Open attempts";
        } // END of passive-open definition.

        leaf open-loops  {
            type  uint16;
            default "0";
            config false;
            description "BGP I/O Open loops";
        } // END of open-loops definition.

        leaf open-calls  {
            type  uint16;
            default "0";
            config false;
            description "BGP I/O Open calls";
        } // END of open-calls definition.

        leaf open-received-calls  {
            type  uint16;
            default "0";
            config false;
            description "BGP I/O Open recv calls";
        } // END of open-received-calls definition.

        leaf send-calls  {
            type  uint16;
            default "0";
            config false;
            description "BGP I/O Send calls";
        } // END of send-calls definition.

        leaf received-calls  {
            type  uint16;
            default "0";
            config false;
            description "BGP I/O Recv calls";
        } // END of received-calls definition.

        leaf write-calls  {
            type  uint16;
            default "0";
            config false;
            description "BGP I/O Write calls";
        } // END of write-calls definition.

        leaf write-loops  {
            type  uint16;
            default "0";
            config false;
            description "BGP I/O Write loops";
        } // END of write-loops definition.

        leaf write-loops-yield  {
            type  uint16;
            default "0";
            config false;
            description "BGP I/O Write loop yields";
        } // END of write-loops-yield definition.

        leaf read-calls  {
            type  uint16;
            default "0";
            config false;
            description "BGP I/O Read calls";
        } // END of read-calls definition.

        leaf read-loops  {
            type  uint16;
            default "0";
            config false;
            description "BGP I/O Read loops";
        } // END of read-loops definition.

        leaf read-loop-yield  {
            type  uint16;
            default "0";
            config false;
            description "BGP I/O Read loop yields";
        } // END of read-loop-yield definition.

        leaf process-nlri-yields  {
            type  uint16;
            default "0";
            config false;
            description "BGP I/O process nlri yields";
        } // END of process-nlri-yields definition.

        leaf process-withdraw-yields  {
            type  uint16;
            default "0";
            config false;
            description "BGP I/O process withdraw yields";
        } // END of process-withdraw-yields definition.

        leaf read-time-exceed  {
            type  uint16;
            default "0";
            config false;
            description "BGP Read time exceeded";
        } // END of read-time-exceed definition.

        leaf update-send-pending  {
            type  uint16;
            default "0";
            config false;
            description "BGP Update send pending";
        } // END of update-send-pending definition.

        leaf update-buffer-not-available  {
            type  uint16;
            default "0";
            config false;
            description "BGP Update buffer not available";
        } // END of update-buffer-not-available definition.

        leaf update-walk-suspend  {
            type  uint16;
            default "0";
            config false;
            description "BGP Update walk suspended";
        } // END of update-walk-suspend definition.

        leaf yield-in-update  {
            type  uint16;
            default "0";
            config false;
            description "BGP Yielded in updates";
        } // END of yield-in-update definition.

        leaf yield-in-pack  {
            type  uint16;
            default "0";
            config false;
            description "BGP Yielded in packing";
        } // END of yield-in-pack definition.

        leaf no-send-buffer-peer  {
            type  uint16;
            default "0";
            config false;
            description "BGP No sendbuf for peer";
        } // END of no-send-buffer-peer definition.

        leaf no-withdraw-buffer-peer  {
            type  uint16;
            default "0";
            config false;
            description "BGP No withdraw buf for peer";
        } // END of no-withdraw-buffer-peer definition.

        leaf yields-in-update-peer-loop  {
            type  uint16;
            default "0";
            config false;
            description "BGP Yields in update peer loop";
        } // END of yields-in-update-peer-loop definition.

        leaf no-updates-pending-or-no-buffers  {
            type  uint16;
            default "0";
            config false;
            description "No updates pending or no buffers";
        } // END of no-updates-pending-or-no-buffers definition.

        leaf no-data-to-write  {
            type  uint16;
            default "0";
            config false;
            description "No data to write";
        } // END of no-data-to-write definition.

        leaf message-queue-received-error  {
            type  uint16;
            default "0";
            config false;
            description "Msg queue recv errors";
        } // END of message-queue-received-error definition.

    } // END of bgp-counters-input-output-state definition.
    grouping bgp-counters-neighbor-sent-received-state {
        description
            "attributes relating to bgp counters";
        leaf messages-sent  {
            type  uint32;
            default "0";
            config false;
            description "Neighbor aggregated statistics sent messages";
        } // END of messages-sent definition.

        leaf messages-received  {
            type  uint32;
            default "0";
            config false;
            description "Neighbor aggregated statistics received messages";
        } // END of messages-received definition.

        leaf bytes-sent  {
            type  uint32;
            default "0";
            config false;
            description "Neighbor aggregated statistics sent bytes";
        } // END of bytes-sent definition.

        leaf bytes-received  {
            type  uint32;
            default "0";
            config false;
            description "Neighbor aggregated statistics received bytes";
        } // END of bytes-received definition.

        leaf opens-sent  {
            type  uint32;
            default "0";
            config false;
            description "Neighbor aggregated statistics sent opens";
        } // END of opens-sent definition.

        leaf opens-received  {
            type  uint32;
            default "0";
            config false;
            description "Neighbor aggregated statistics received opens";
        } // END of opens-received definition.

        leaf updates-sent  {
            type  uint32;
            default "0";
            config false;
            description "Neighbor aggregated statistics sent Updates";
        } // END of updates-sent definition.

        leaf updates-received  {
            type  uint32;
            default "0";
            config false;
            description "Neighbor aggregated statistics received Updates";
        } // END of updates-received definition.

        leaf keepalive-sent  {
            type  uint32;
            default "0";
            config false;
            description "Neighbor aggregated statistics sent keepalives";
        } // END of keepalive-sent definition.

        leaf keepalive-received  {
            type  uint32;
            default "0";
            config false;
            description "Neighbor aggregated statistics received keepalives";
        } // END of keepalive-received definition.

        leaf notification-sent  {
            type  uint32;
            default "0";
            config false;
            description "Neighbor aggregated statistics sent Notifications";
        } // END of notification-sent definition.

        leaf notification-received  {
            type  uint32;
            default "0";
            config false;
            description "Neighbor aggregated statistics received Notifications";
        } // END of notification-received definition.

        leaf route-refresh-sent  {
            type  uint32;
            default "0";
            config false;
            description "Neighbor aggregated statistics sent route-refresh";
        } // END of route-refresh-sent definition.

        leaf route-refresh-received  {
            type  uint32;
            default "0";
            config false;
            description "Neighbor aggregated statistics received route-refresh";
        } // END of route-refresh-received definition.

        leaf capabilities-sent  {
            type  uint32;
            default "0";
            config false;
            description "Neighbor aggregated statistics sent Capabilities";
        } // END of capabilities-sent definition.

        leaf capabilities-received  {
            type  uint32;
            default "0";
            config false;
            description "Neighbor aggregated statistics received Capabilities";
        } // END of capabilities-received definition.

    } // END of bgp-counters-neighbor-sent-received-state definition.
    grouping bgp-vrf-next-hop-tracking-state {
        description
            "attributes relating to bgp nexthop tracking state for VRF";
        leaf bgp-as  {
            type  uint32;
            config false;
            description "AS Number";
        } // END of bgp-as definition.

        leaf router-id  {
            type  inet:ipv4-address;
            config false;
            description "BGP Router-Id";
        } // END of router-id definition.

        leaf configured  {
            type  boolean;
            default false;
            config false;
            description "Configured NHT";
        } // END of configured definition.

        leaf delay-time  {
            type  uint32;
            units "seconds";
            default "5";
            config false;
            description "Nexthop Trigger Delay time interval between 1 and 100";
        } // END of delay-time definition.

        leaf received-message-count  {
            type  cml-data-types:cml_line_t;
            default "0";
            config false;
            description "Recvd Msg count from RIB/NSM";
        } // END of received-message-count definition.

        leaf ipv4-count  {
            type  int32;
            default "0";
            config false;
            description "Total number of IPV4 nexthops";
        } // END of ipv4-count definition.

        leaf ipv6-count  {
            type  int32;
            default "0";
            config false;
            description "Total number of IPV6 nexthops";
        } // END of ipv6-count definition.

        leaf delay-time-remaining  {
            type  int32;
            units "seconds";
            default "0";
            config false;
            description "NHT delay-timer remaining seconds";
        } // END of delay-time-remaining definition.

    } // END of bgp-vrf-next-hop-tracking-state definition.
    grouping bgp-vrf-config {
        description
            "Configuration data for bgp vrf";
        leaf import-map  {
            type  string {
                length "1..max";
                pattern "[^?' =,>|]+";
            }
            description "This attribute assigns a route map to the VRF. This map is applied for
                        routing information imported from another PE or VRF.
                        Use this attribute when an application requires finer control over the
                        routes imported into a VRF than provided by the import and export
                        extended communities. You can filter routes that are eligible for
                        import into a VRF through the use of a route map.The route map can
                        deny access to selected routes from a community that is on the import
                        list.";
        } // END of import-map definition.

        leaf export-map  {
            type  string {
                length "1..max";
                pattern "[^?' =,>|]+";
            }
            description "export map name";
        } // END of export-map definition.

        leaf rd-string  {
            type  string {
                length "1..32";
                pattern "[^?' =,>|]+";
            }
            description "Use this attribute to assign a route distinguisher (RD) for the VRF.
                        The route distinguisher value must be a unique value on the
                        router.This attribute creates routing and forwarding tables and
                        specifies the default RD for a VPN. The RD is added to the customers
                        IPv4 prefixes, changing them into globally unique VPN-IPv4 prefixes.";
        } // END of rd-string definition.

    } // END of bgp-vrf-config definition.
    grouping bgp-vrf-route-target-config {
        description
            "Configuration data for bgp vrf route target";
        leaf rt-rd-string  {
            type  string {
                length "1..32";
                pattern "[^?' =,>|]+";
            }
            description "Use this attribute to assign route target (RT) for the VRF.";
        } // END of rt-rd-string definition.

        leaf direction  {
            type  ipi-bgp-types:bgp_target_route_type_t;
            description "Use this attribute to add a list of import and export route-target
                        extended communities to the VRF.
                        This attribute creates lists of import and export route-target
                        extended communities for the VRF. It specifies a target VPN extended
                        community. All routes with the specific route-target extended
                        community are imported into all VRFs with the same extended community
                        as an import route-target.";
        } // END of direction definition.

    } // END of bgp-vrf-route-target-config definition.
    grouping bgp-vrf-route-target {
        description
            "Grouping for route target information";

        list route-target {
        when " /ipi-network-instance:network-instances/ipi-network-instance:network-instance/ipi-vrf:vrf/ipi-bgp-vrf:bgp-vrf/ipi-bgp-vrf:config/ipi-bgp-vrf:rd-string ";
            key "rt-rd-string direction";
            description
                "Route target information";
            leaf rt-rd-string  {
                type  leafref {
                    path  "../config/rt-rd-string";
                }
                description "Assigns Route distinguisher for the VRF";
            } // END of rt-rd-string definition.

            leaf direction  {
                type  leafref {
                    path  "../config/direction";
                }
                description "Use this attribute to add a list of import and export route-target
                            extended communities to the VRF.";
            } // END of direction definition.

            container config {
                description
                    "Configuration data for bgp vrf route target";
                uses bgp-vrf-route-target-config;
            } // END of config-container definition.
            container state {
                config false;
                description
                    "State parameters for bgp vrf route target";
                uses bgp-vrf-route-target-config;
            } // END of state-container definition.
        } // End of route-target-list
    } // END of bgp-vrf-route-target definition.
    grouping bgp-vrf-bgp-rd-as-state {
        description
            "Operational state data for Router Distinguisher AS";
        leaf brd-as  {
            type  int32;
            config false;
            description "Route-Distinguisher As";
        } // END of brd-as definition.

        leaf brd-as-number  {
            type  int32;
            config false;
            description "Route-Distinguisher As number";
        } // END of brd-as-number definition.

    } // END of bgp-vrf-bgp-rd-as-state definition.
    grouping bgp-vrf-bgp-rd-as4-state {
        description
            "Operational state data for Router Distinguisher 4-octet AS";
        leaf brd-as4  {
            type  int32;
            config false;
            description "Route-Distinguisher 4-octet As";
        } // END of brd-as4 definition.

        leaf brd-as-num4  {
            type  int32;
            config false;
            description "Route-Distinguisher 4-octet As number";
        } // END of brd-as-num4 definition.

    } // END of bgp-vrf-bgp-rd-as4-state definition.
    grouping bgp-vrf-bgp-rd-ip-state {
        description
            "Operational state data for Router Distinguisher IP-Type";
        leaf brd-ip  {
            type  int32;
            config false;
            description "Route-Distinguisher IP type";
        } // END of brd-ip definition.

        leaf brd-ip-number  {
            type  int32;
            config false;
            description "Route-Distinguisher IP number";
        } // END of brd-ip-number definition.

    } // END of bgp-vrf-bgp-rd-ip-state definition.
    grouping bgp-vrf-bgp-rd-state {
        description
            "Grouping for BGP router distinguisher";
        container bgp-rd {
            config false;
            description
                "BGP router distinguisher";
            container bgp-rd-as {
                config false;
                description
                    "BGP Router Distinguisher AS-Type";
                container state {
                    config false;
                    description
                        "Operational state data for Router Distinguisher AS";
                    uses bgp-vrf-bgp-rd-as-state;
                } // END of state-container definition.
            } // END of bgp-rd-as-container definition.
            container bgp-rd-as4 {
                config false;
                description
                    "BGP Router Distinguisher 4-octet-AS-Type";
                container state {
                    config false;
                    description
                        "Operational state data for Router Distinguisher 4-octet AS";
                    uses bgp-vrf-bgp-rd-as4-state;
                } // END of state-container definition.
            } // END of bgp-rd-as4-container definition.
            container bgp-rd-ip {
                config false;
                description
                    "BGP Router Distinguisher IP-Type";
                container state {
                    config false;
                    description
                        "Operational state data for Router Distinguisher IP-Type";
                    uses bgp-vrf-bgp-rd-ip-state;
                } // END of state-container definition.
            } // END of bgp-rd-ip-container definition.
        } // END of bgp-rd-container definition.
    } // END of bgp-vrf-bgp-rd-state definition.
    grouping bgp-vrf-evpn-service-config {
        description
            "Configuration data for EVPN VLAN Service Type";
        leaf service-type  {
            type  cml-data-types:cml_evpn_service_type_t;
            description "Vlan-Based EVPN-Service Type";
        } // END of service-type definition.

    } // END of bgp-vrf-evpn-service-config definition.

    grouping  bgp-vrf-grouping {
    description
        "BGP VRF Information";
    container bgp-vrf {
        description
            "BGP VRF Information";
        container config {
            description
                "Configuration parameters for BGP VRF";
            uses bgp-vrf-config;
        } // END of config-container definition.
        container state {
            config false;
            description
                "State parameters for BGP VRF";
            container counters {
                config false;
                description
                    "This describes bgp counters";
                container neighbor-rx-tx-stat {
                    config false;
                    description
                        "bgp neighbor sent received counters";
                    uses bgp-counters-neighbor-sent-received-state;
                } // END of neighbor-rx-tx-stat-container definition.
                container local-input-output {
                    config false;
                    description
                        "Container having the input output counters";
                    uses bgp-counters-input-output-state;
                } // END of local-input-output-container definition.
                container sockets {
                    config false;
                    description
                        "container conatining the socket counters";
                    uses bgp-counters-socket-state;
                } // END of sockets-container definition.
            } // END of counters-container definition.
            uses bgp-vrf-config;
        } // END of state-container definition.
        container next-hop-tracking {
            config false;
            description
                "container for bgp nexthop tracking";
            container state {
                config false;
                description
                    "state parameters relating to the BGP nexthop tracking for VRF";
                uses bgp-vrf-next-hop-tracking-state;
            } // END of state-container definition.
        } // END of next-hop-tracking-container definition.
        uses bgp-vrf-route-target;
        uses bgp-vrf-bgp-rd-state;
    } // END of bgp-vrf-container definition.
    } // END of bgp-vrf-grouping definition.

    grouping  evpn-service-type-grouping {
    description
        "EVPN VLAN Service Type";
    container evpn-service-type {
        if-feature feature-list:HAVE_MPLS;
        if-feature feature-list:HAVE_BGP_EVPN;
        description
            "EVPN VLAN Service Type";
        container config {
            description
                "Config paramters for EVPN VLAN Service Type";
            uses bgp-vrf-evpn-service-config;
        } // END of config-container definition.
        container state {
            config false;
            description
                "State parameters for EVPN VLAN Service Type";
            uses bgp-vrf-evpn-service-config;
        } // END of state-container definition.
    } // END of evpn-service-type-container definition.
    } // END of evpn-service-type-grouping definition.

    augment /ipi-network-instance:network-instances/ipi-network-instance:network-instance/ipi-vrf:vrf {
        description
            "BGP VRF Information";
        uses bgp-vrf-grouping;
    }

    augment /ipi-network-instance:network-instances/ipi-network-instance:network-instance/ipi-vrf:vrf {
        description
            "EVPN VLAN Service Type";
        uses evpn-service-type-grouping;
    }


}
