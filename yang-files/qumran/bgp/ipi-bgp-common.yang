/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-bgp-common.yang
*
*/

submodule ipi-bgp-common {

    yang-version 1.1;

    belongs-to  ipi-bgp { prefix ipi-bgp; }

    import feature-list {
        prefix feature-list;
    }

    import cml-data-types {
        prefix cml-data-types;
    }

    import ipi-bgp-types {
        prefix ipi-bgp-types;
    }

    import ietf-yang-types {
        prefix yang;
    }

    import ietf-inet-types {
        prefix inet;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for bgp network list";


    revision "2021-03-05" {
        description "Excluded yang generation for BGP Add path attributes";
        reference " 0.3.0.";
    }

    revision "2020-12-15" {
        description "Change to have data-types in lower case instead of camel case";
        reference " 0.2.0.";
    }

    revision "2020-09-10" {
        description "Initial Version";
        reference " 0.1.0.";
    }

    grouping bgp-af-maximum-paths-config {
        description
            "Configuration attributes related to multipath ECMP numbers";
        leaf ebgp-max-path  {
            type  int32 {
                 range "2..64"  {
                    description "Supported multipath number";
                 }
            }
            default "2";
            description "Use this attribute to set the number of equal-cost multi-path (ECMP)
                        routes for eBGP. You can install multiple BGP paths to the same
                        destination to balance the load on the forwarding path";
        } // END of ebgp-max-path definition.

        leaf ibgp-max-path  {
            type  int32 {
                 range "2..64"  {
                    description "Supported multipath number";
                 }
            }
            default "2";
            description "Use this attribute to set the number of equal-cost multi-path (ECMP)
                        routes for iBGP. You can install multiple BGP paths to the same
                        destination to balance the load on the forwarding path.";
        } // END of ibgp-max-path definition.

    } // END of bgp-af-maximum-paths-config definition.
    grouping address-family-redist-list-config {
        description
            "Configuration attributes related to redistribute for address-family";
        leaf protocol-type  {
            type  ipi-bgp-types:bgp_redistribute_type_t;
            description "Use this attribute to configure the protocol type of the routes that
                        are to be redistributed by BGP. Redistribution is used by routing
                        protocols to advertise routes that are learned by some other means,
                        such as by another routing protocol or by static routes.";
        } // END of protocol-type definition.

        leaf redist-route-map-name  {
            type  string {
                length "1..max";
                pattern "[^?' =,>|]+";
            }
            description "Use this attribute to configure route map to be used for redistributed
                        routes.";
        } // END of redist-route-map-name definition.

    } // END of address-family-redist-list-config definition.
    grouping bgp-network-list-state {
        description
            "Operational state data for bgp network list";
        leaf network-path-route-count  {
            type  int32;
            config false;
            description "Network path count";
        } // END of network-path-route-count definition.

        leaf no-advertise-route  {
            type  string {
                length "1..max";
                pattern "[^?' =,>|]+";
            }
            config false;
            description "Not advertised route";
        } // END of no-advertise-route definition.

        leaf no-export-route  {
            type  boolean;
            config false;
            description "Not advertised to EBGP peer";
        } // END of no-export-route definition.

        leaf local-as-route  {
            type  boolean;
            config false;
            description "Not advertised outside local AS";
        } // END of local-as-route definition.

        leaf suppress-route  {
            type  boolean;
            config false;
            description "Advertisements suppressed by an aggregate.";
        } // END of suppress-route definition.

        leaf network-best-path-route-count  {
            type  int32;
            config false;
            description "best";
        } // END of network-best-path-route-count definition.

        leaf ip-routing-table  {
            type  string {
                length "1..max";
                pattern "[^?' =,>|]+";
            }
            config false;
            description "IP Routing Table";
        } // END of ip-routing-table definition.

        leaf-list advertised-non-peer-group-address  {
            type  cml-data-types:cml_hostname_t;
            config false;
            description "Advertised non peer-group peers.";
        } // END of advertised-non-peer-group-address definition.

        leaf-list advertised-peer-group-name-route  {
            type  string {
                length "1..max";
                pattern "[^?' =,>|]+";
            }
            config false;
            description "Advertised peer-groups";
        } // END of advertised-peer-group-name-route definition.

        leaf advertised-any-peer  {
            type  boolean;
            config false;
            description "Advertised to any peer";
        } // END of advertised-any-peer definition.

        leaf route-distinguisher-string  {
            if-feature feature-list:HAVE_MPLS;
            type  string {
                length "1..max";
                pattern "[^?' =,>|]+";
            }
            config false;
            description "Route distinguisher";
        } // END of route-distinguisher-string definition.

    } // END of bgp-network-list-state definition.
    grouping bgp-next-hop-state {
        description
            "Operational state data for nexthop";
        leaf next-hop-address  {
            type  cml-data-types:cml_hostname_t;
            config false;
            description "NextHop Address";
        } // END of next-hop-address definition.

        leaf peer-network-weight  {
            type  int32;
            config false;
            description "BGP attribute weight";
        } // END of peer-network-weight definition.

        leaf flap-time-reuse-list  {
            type  string {
                length "1..max";
                pattern "[^?' =,>|]+";
            }
            config false;
            description "Dampinfo: reuse in";
        } // END of flap-time-reuse-list definition.

        leaf flap-record-duration  {
            type  string {
                length "1..max";
                pattern "[^?' =,>|]+";
            }
            config false;
            description "Flap record duration";
        } // END of flap-record-duration definition.

        leaf damp-time-to-reuse  {
            type  string {
                length "1..max";
                pattern "[^?' =,>|]+";
            }
            config false;
            description "Damp time to reuse";
        } // END of damp-time-to-reuse definition.

        leaf bgp-med-value  {
            type  int32;
            config false;
            description "BGP multi-exit discriminator attribute used in BGP route selection
                        process";
        } // END of bgp-med-value definition.

        leaf-list bgp-as-path-string  {
            type  cml-data-types:cml_line_t;
            config false;
            description "AS-path";
        } // END of bgp-as-path-string definition.

        leaf-list bgp-as-path-4-byte-string  {
            type  string {
                length "1..max";
                pattern "[^?' =,>|]+";
            }
            config false;
            description "AS-path for extended asn capability";
        } // END of bgp-as-path-4-byte-string definition.

        leaf bgp-as-path-4-byte-origin  {
            type  ipi-bgp-types:bgp_origin_t;
            config false;
            description "Origin: 0(IGP), 1(EGP), 2(Incomplete)";
        } // END of bgp-as-path-4-byte-origin definition.

        leaf ibgp-metric-route  {
            type  int32;
            config false;
            description "IGP metric value for route selection.";
        } // END of ibgp-metric-route definition.

        leaf aggregate-as-route  {
            type  int32;
            config false;
            description "Aggregated by as";
        } // END of aggregate-as-route definition.

        leaf aggregator-address-route  {
            type  cml-data-types:cml_hostname_t;
            config false;
            description "Aggregated by address";
        } // END of aggregator-address-route definition.

        leaf network-remote-address-route  {
            type  cml-data-types:cml_hostname_t;
            config false;
            description "Remote id";
        } // END of network-remote-address-route definition.

        leaf originator-id-route  {
            type  cml-data-types:cml_hostname_t;
            config false;
            description "Originator id";
        } // END of originator-id-route definition.

        leaf route-peer-address  {
            type  cml-data-types:cml_hostname_t;
            config false;
            description "Address of the peer";
        } // END of route-peer-address definition.

        leaf route-local-preference  {
            type  int32;
            config false;
            description "Local preference";
        } // END of route-local-preference definition.

        leaf route-prefix-label  {
            type  uint32;
            config false;
            description "label";
        } // END of route-prefix-label definition.

        leaf route-community-string  {
            type  string {
                length "1..max";
                pattern "[^?' =,>|]+";
            }
            config false;
            description "Community";
        } // END of route-community-string definition.

        leaf-list cluster-list-route  {
            type  cml-data-types:cml_hostname_t;
            config false;
            description "Cluster list";
        } // END of cluster-list-route definition.

        leaf route-penalty  {
            type  int32;
            config false;
            description "Dampinfo: penalty";
        } // END of route-penalty definition.

        leaf route-flap-count  {
            type  int32;
            config false;
            description "Dampinfo: no of times flapped";
        } // END of route-flap-count definition.

        leaf last-update-route  {
            type  yang:date-and-time {
                pattern "\\d{4}-\\d{2}-\\d{2}T\\d{2}:\\d{2}:\\d{2}(\\.\\d+)?(Z|[\\+\\-]\\d{2}:\\d{2})";
                }
                config false;
                description "Last Update";
            } // END of last-update-route definition.

            leaf reflector-client-route  {
                type  boolean;
                config false;
                description "Received from a RR-client";
            } // END of reflector-client-route definition.

            leaf route-dampening-active  {
                type  boolean;
                config false;
                description "suppressed due to dampening";
            } // END of route-dampening-active definition.

            leaf history-route  {
                type  boolean;
                config false;
                description "history entry";
            } // END of history-route definition.

            leaf nexthop-valid-route  {
                type  boolean;
                config false;
                description "Inactive redistribute routes";
            } // END of nexthop-valid-route definition.

            leaf med-flag-type-route  {
                type  boolean;
                config false;
                description "if REMOVE-MED flag is enabled";
            } // END of med-flag-type-route definition.

            leaf valid-route  {
                type  boolean;
                config false;
                description "Check if state is valid";
            } // END of valid-route definition.

            leaf stale-route  {
                type  boolean;
                config false;
                description "Check BGP info stale";
            } // END of stale-route definition.

            leaf route-type  {
                type  ipi-bgp-types:bgp_ri_type_t;
                config false;
                description "BGP route info type - internal, confed-external, external, sourced,
                            aggregated, local";
            } // END of route-type definition.

            leaf ecmp-multi-candidate-route  {
                type  boolean;
                config false;
                description "if ecmp multipath candidate";
            } // END of ecmp-multi-candidate-route definition.

            leaf multi-installed-route  {
                type  boolean;
                config false;
                description "if bgp info multi install- 1(installed)";
            } // END of multi-installed-route definition.

            leaf route-synchronized-flag-route  {
                type  boolean;
                config false;
                description "BGP info status - 0(not synchronized) 1(synchronized)";
            } // END of route-synchronized-flag-route definition.

            leaf atomic-aggregate-route  {
                type  boolean;
                config false;
                description "atomic-aggregate";
            } // END of atomic-aggregate-route definition.

            leaf selected-route  {
                type  boolean;
                config false;
                description "BGP info best selected route";
            } // END of selected-route definition.

            leaf ipv4-multicast-capability  {
                type  string {
                    length "1..max";
                    pattern "[^?' =,>|]+";
                }
                config false;
                description "IPV4 Multicast neighbour Capability";
            } // END of ipv4-multicast-capability definition.

            leaf vpnv4-unicast-capability  {
                type  string {
                    length "1..max";
                    pattern "[^?' =,>|]+";
                }
                config false;
                description "Vpnv4 Unicast neighbour Capability";
            } // END of vpnv4-unicast-capability definition.

            leaf rtfilter-unicast-capability  {
                type  string {
                    length "1..max";
                    pattern "[^?' =,>|]+";
                }
                config false;
                description "Rtfilter Unicast neighbour Capability";
            } // END of rtfilter-unicast-capability definition.

            leaf l2vpn-evpn-capability  {
                type  string {
                    length "1..max";
                    pattern "[^?' =,>|]+";
                }
                config false;
                description "L2vpn Evpn neighbour Capability";
            } // END of l2vpn-evpn-capability definition.

            leaf ipv6-unicast-capability  {
                type  string {
                    length "1..max";
                    pattern "[^?' =,>|]+";
                }
                config false;
                description "Ipv6 Unicast neighbour Capability";
            } // END of ipv6-unicast-capability definition.

            leaf ipv6-multicast-capability  {
                type  string {
                    length "1..max";
                    pattern "[^?' =,>|]+";
                }
                config false;
                description "Ipv6 Multicast neighbour Capability";
            } // END of ipv6-multicast-capability definition.

            leaf ipv6-label-unicast-capability  {
                type  string {
                    length "1..max";
                    pattern "[^?' =,>|]+";
                }
                config false;
                description "Ipv6 Label Unicast neighbour Capability";
            } // END of ipv6-label-unicast-capability definition.

            leaf in-label  {
                if-feature feature-list:HAVE_BGP_LU;
                type  uint32;
                config false;
                description "bgp LU In Label";
            } // END of in-label definition.

            leaf out-label  {
                if-feature feature-list:HAVE_BGP_LU;
                type  uint32;
                config false;
                description "bgp LU Out Label";
            } // END of out-label definition.

    } // END of bgp-next-hop-state definition.
    grouping bgp-next-hop-mpls-state {
        description
            "Operational state data for nexthop related to MPLS";
        leaf vrf-name  {
            if-feature feature-list:HAVE_MPLS;
            type  string {
                length "1..max";
                pattern "[^?' =,>|]+";
            }
            config false;
            description "VRF name";
        } // END of vrf-name definition.

        leaf route-distinguisher  {
            if-feature feature-list:HAVE_MPLS;
            type  string {
                length "1..max";
                pattern "[^?' =,>|]+";
            }
            config false;
            description "Route distinguisher";
        } // END of route-distinguisher definition.

    } // END of bgp-next-hop-mpls-state definition.
    grouping bgp-peer-adj-out-route-state {
        description
            "State parameter for Peer  Adj out route";
        leaf network-address  {
            type  ipi-bgp-types:bgp_ip_network_t;
            config false;
            description "Peer Adj-Out Network address";
        } // END of network-address definition.

    } // END of bgp-peer-adj-out-route-state definition.
    grouping bgp-peer-adj-in-route-state {
        description
            "State parameter for Peer  Adj in route";
        leaf network-address  {
            type  ipi-bgp-types:bgp_ip_network_t;
            config false;
            description "Peer Adj-In Nexthop address";
        } // END of network-address definition.

    } // END of bgp-peer-adj-in-route-state definition.
    grouping bgp-optional-as-list-config {
        description
            "Configuration parameters for BGP peer groups";
    } // END of bgp-optional-as-list-config definition.
    grouping bgp-address-family-peer-config {
        description
            "Configuration parameters for peer";
        leaf bgp-port  {
            when " /bgp/bgp-instance/peer/address-family/config/activate ";
            type  uint16 {
                 range "0..65535"  {
                    description "TCP port number";
                 }
            }
            default "179";
            description "The BGP port number of a neighbor";
        } // END of bgp-port definition.

        leaf activate  {
            when " /bgp/bgp-instance/peer/config/peer-as ";
            type  empty;
            description "Activate/Deactivate neighbor. This attribute enables or disables the
                        exchange of AF information with a neighboring router.";
        } // END of activate definition.

        leaf default-peer-route-map-name  {
            when " not(/bgp/bgp-instance/peer/address-family/config/peer-route-map-orig-name) ";
            type  empty;
            description "This attribute allows a BGP local router to send the default route
                        0.0.0.0 to a neighbor for use as a default route for specified
                        address-family.";
        } // END of default-peer-route-map-name definition.

        leaf peer-route-map-orig-name  {
            when " not(/bgp/bgp-instance/peer/address-family/config/default-peer-route-map-name) ";
            type  string {
                length "1..max";
                pattern "[^?' =,>|]+";
            }
            description "This attribute configures route map to be used for a BGP local router
                        to send the default route 0.0.0.0 to a neighbor for use as a default
                        route for specified address-family. This attribute can be used with
                        standard or extended access lists.";
        } // END of peer-route-map-orig-name definition.

        leaf soft-reconfig-inbound  {
            when " /bgp/bgp-instance/peer/address-family/config/activate ";
            type  empty;
            description "This attribute stores updates for inbound soft reconfiguration for
                        specified address-family. Soft-reconfiguration may be used in lieu of
                        BGP route refresh capability. Using this attribute enables local
                        storage of all the received routes and their attributes. This requires
                        additional memory. When a soft reset (inbound) is done on this
                        neighbor, the locally stored routes are re-processed according to the
                        inbound policy. The BGP neighbor connection is not affected.";
        } // END of soft-reconfig-inbound definition.

        leaf weight  {
            when " /bgp/bgp-instance/peer/address-family/config/activate ";
            type  uint16 {
                 range "0..65535"  {
                    description "Configure weight";
                 }
            }
            default "0";
            description "This attribute specifies a weight value, for specified address-family,
                        to all routes learned from a neighbor for specified address-family.
                        The route with the highest weight gets preference when the same prefix
                        is learned from more than one peer. Unlike the local-preference
                        attribute, the weight attribute is relevant only to the local router.
                        When the weight is set for a peer group, all members of the peer group
                        get the same weight. This attribute can also be used to assign a
                        different weight to an individual peer-group member. When an
                        individually-configured weight of a peer-group member is removed, its
                        weight is reset to its peer groups weight.";
        } // END of weight definition.

        leaf peer-route-reflector  {
            when " /bgp/bgp-instance/peer/address-family/config/activate ";
            type  empty;
            description "This attribute configures the router as a BGP route reflector and
                        configure the specified neighbor as its client for specified
                        address-family.
                        Route reflectors are a solution for the explosion of iBGP peering
                        within an autonomous system. By route reflection the number of iBGP
                        peers within an AS is reduced. Use this attribute to configure the
                        local router as the route reflector and specify neighbors as its
                        client. An AS can have more than one route reflector. One route
                        reflector treats the other route reflector as another iBGP speaker.";
        } // END of peer-route-reflector definition.

        leaf peer-remove-private-as  {
            when " /bgp/bgp-instance/peer/address-family/config/activate ";
            type  empty;
            description "This attribute removes the private Autonomous System (AS) number from
                        outbound updates. Private AS numbers are not advertised to the
                        Internet. This attribute is used with external BGP peers only. The
                        router removes the AS numbers only if the update includes private AS
                        numbers. If the update includes both private and public AS numbers,
                        the system treats it as an error.";
        } // END of peer-remove-private-as definition.

        leaf send-community  {
            when " /bgp/bgp-instance/peer/address-family/config/activate ";
            type  empty;
            description "This attribute specifies if a community attribute should be sent to a
                        BGP neighbor for specified address-family. The community attribute
                        groups destinations in a certain community and applies routing
                        decisions according to those communities. By default, both standard
                        and extended community attributes are sent to a neighbor";
        } // END of send-community definition.

        leaf send-community-type  {
            when " /bgp/bgp-instance/peer/address-family/config/activate ";
            type  ipi-bgp-types:bgp_send_commu_type_t;
            description "This attribute specifies the type of community attribute to be sent to
                        a BGP neighbor.";
        } // END of send-community-type definition.

        leaf neighbor-attribute-unchanged  {
            when " /bgp/bgp-instance/peer/address-family/config/activate ";
            type  ipi-bgp-types:bgp_attribute_unchanged_type_t;
            description "This attribute advertises unchanged BGP AS path, next hop and med to
                        the specified neighbor.";
        } // END of neighbor-attribute-unchanged definition.

        leaf orf-prefix-capability  {
            when " /bgp/bgp-instance/peer/address-family/config/activate ";
            type  ipi-bgp-types:bgp_orf_prefix_type_t;
            description "This attribute enables Outbound Router Filtering (ORF), and advertise
                        the ORF capability to its neighbors. The ORFs send and receive
                        capabilities to lessen the number of updates exchanged between
                        neighbors. By filtering updates, this option minimizes generating and
                        processing of updates. The two routers exchange updates to maintain
                        the ORF for each router.";
        } // END of orf-prefix-capability definition.

        leaf peer-allow-ebgp-vpn  {
            when " /bgp/bgp-instance/peer/address-family/config/activate ";
            if-feature feature-list:HAVE_VRF;
            type  empty;
            description "This attribute allows an eBGP neighbor to be a VPN peer. By default,
                        BGP VPN functionality is allowed only for iBGP peers. Using the
                        peer-allow-ebgp-vpn attribute allows the VPN connection to be
                        established to an eBGP peer.";
        } // END of peer-allow-ebgp-vpn definition.

        leaf allow-as-number  {
            when " /bgp/bgp-instance/peer/address-family/config/activate ";
            type  uint32 {
                 range "1..10"  {
                    description "Number of occurrences of AS number";
                 }
            }
            default "3";
            description "This attribute advertises prefixes (routes) even when the source of
                        the prefixes is from the same Autonomous System (AS) number for
                        specified address-family.
                        Use this attribute in a scenario where two routers at different
                        locations use the same Autonomous System number and are connected via
                        an ISP. Once prefixes arrive from one branch at the ISP, they are
                        tagged with the customers AS number. By default, when the ISP passes
                        the prefixes to the other router, the prefixes are dropped if the
                        other router uses the same AS number. Use this attribute to advertise
                        the prefixes at the other side. Control the number of times an AS
                        number is advertised by specifying a number.
                        In a hub and spoke configuration in a VPN, a PE (Provider Edge) router
                        advertises all prefixes containing duplicate AS numbers. Use this
                        attribute to configure two VRFs on each PE router to receive and
                        advertise prefixes. One of the VRFs receives prefixes with AS numbers
                        from all PE routers and then advertises them to neighboring PE
                        routers. The other VRF receives prefixes with AS numbers from the CE
                        (Customer Edge) router and advertises them to all PE routers in the
                        hub and spoke configuration.";
        } // END of allow-as-number definition.

        leaf capability-graceful-restart  {
            when " /bgp/bgp-instance/peer/address-family/config/activate ";
            type  empty;
            description "This attribute configures the router to advertise the Graceful Restart
                        Capability to the neighbors. This configuration indicates that the BGP
                        speaker has the ability to preserve its forwarding state for the
                        address family when BGP restarts. Use this attribute to advertise to
                        the neighbor routers the capability of graceful restart.";
        } // END of capability-graceful-restart definition.

        leaf unsuppress-route-map-name  {
            when " /bgp/bgp-instance/peer/address-family/config/activate ";
            type  string {
                length "1..max";
                pattern "[^?' =,>|]+";
            }
            description "unsuppress map name. This attribute is used to selectively leak
                        more-specific routes to a particular neighbor.";
        } // END of unsuppress-route-map-name definition.

    } // END of bgp-address-family-peer-config definition.
    grouping bgp-address-family-maximum-prefixes-config {
        description
            "Configuration parameters for peer maximum prefixes";
        leaf prefix-count  {
            when " /bgp/bgp-instance/peer/address-family/config/activate ";
            type  uint32 {
                 range "1..4294967295"  {
                    description "maximum no. of prefix limit";
                 }
            }
            description "This attribute specifies number of prefixes that a BGP router is
                        allowed to receive from a neighbor. When the maximum-prefix-warning
                        attribute is not set and extra prefixes are received, the router ends
                        the peering.";
        } // END of prefix-count definition.

        leaf stop-update  {
            when " /bgp/bgp-instance/peer/address-family/config/activate ";
            type  empty;
            description "Stop installing the routes when limit is exceeded.";
        } // END of stop-update definition.

        leaf maximum-prefix-warning  {
            when " /bgp/bgp-instance/peer/address-family/config/activate ";
            type  empty;
            description "This attribute when enabled only give warning message when limit is
                        exceeded. When it is not set and extra prefixes are received, the
                        router ends the peering.";
        } // END of maximum-prefix-warning definition.

        leaf threshold-percentage  {
            when " /bgp/bgp-instance/peer/address-family/config/activate ";
            type  uint8 {
                 range "1..100"  {
                    description "threshold-value, 1 to 100 percent";
                 }
            }
            default "75";
            description "Threshold-value in percen. This attribute controls the number of
                        prefixes that can be received from a neighbor. This attribute allows
                        the configuration of a specified number of prefixes that a BGP router
                        is allowed to receive from a neighbor. When the maximum-prefix-warning
                        attribute is not set and extra prefixes are received, the router ends
                        the peering.";
        } // END of threshold-percentage definition.

        leaf warning-only  {
            when " /bgp/bgp-instance/peer/address-family/config/activate ";
            type  empty;
            description "Throw warning if exceeds threshold-value";
        } // END of warning-only definition.

    } // END of bgp-address-family-maximum-prefixes-config definition.
    grouping bgp-distribute-list-filter-config {
        description
            "Grouping for BGP distribute list filter configuration";
        leaf access-list-identifier  {
            when " /bgp/bgp-instance/peer/address-family/config/activate ";
            type  string {
                length "1..max";
                pattern "[^?' =,>|]+";
            }
            description "Access List information";
        } // END of access-list-identifier definition.

        leaf filter-direction  {
            when " /bgp/bgp-instance/peer/address-family/config/activate ";
            type  ipi-bgp-types:bgp_distribute_list_direction_t;
            description "This attribute sets the direction of the filter (0=FILTER_IN
                        |1=FILTER_OUT). This attribute is used to filter route updates from a
                        particular BGP neighbor for specified address-family. Only one
                        distribute-list per BGP neighbor.";
        } // END of filter-direction definition.

    } // END of bgp-distribute-list-filter-config definition.
    grouping bgp-as-list-filter-config {
        description
            "Grouping for BGP AS list filter configuration";
        leaf as-access-list-identifier  {
            when " /bgp/bgp-instance/peer/address-family/config/activate ";
            type  string {
                length "1..max";
                pattern "[^?' =,>|]+";
            }
            description "Access-list number. This attribute sets a BGP filter. This attribute
                        specifies an access list filter on updates based on the BGP autonomous
                        system paths. Each filter is an access list based on regular
                        expressions";
        } // END of as-access-list-identifier definition.

        leaf as-list-direction  {
            when " /bgp/bgp-instance/peer/address-family/config/activate ";
            type  ipi-bgp-types:bgp_distribute_list_direction_t;
            description "Direction of the filter (0=FILTER_IN |1=FILTER_OUT)";
        } // END of as-list-direction definition.

    } // END of bgp-as-list-filter-config definition.
    grouping bgp-prefix-list-filter-config {
        description
            "Grouping for BGP prefix list filter configuration";
        leaf prefix-list-name  {
            when " /bgp/bgp-instance/peer/address-family/config/activate ";
            type  string {
                length "1..max";
                pattern "[^?' =,>|]+";
            }
            description "This attribute specify a prefix list for filtering BGP advertisements
                        for specified address-family. Filtering by prefix list matches the
                        prefixes of routes with those listed in the prefix list. If there is a
                        match, the route is used. An empty prefix list permits all prefixes.
                        If a given prefix does not match any entries of a prefix list, the
                        route is denied access. When multiple entries of a prefix list match a
                        prefix, the entry with the smallest sequence number is considered to
                        be a real match.
                        The router begins the search at the top of the prefix list, with the
                        sequence number 1. Once a match or deny occurs, the router does not
                        need to go through the rest of the prefix list. For efficiency the
                        most common matches or denies are listed at the top.";
        } // END of prefix-list-name definition.

        leaf prefix-filter-direction  {
            when " /bgp/bgp-instance/peer/address-family/config/activate ";
            type  ipi-bgp-types:bgp_distribute_list_direction_t;
            description "Direction of the filter (0=FILTER_IN |1=FILTER_OUT)";
        } // END of prefix-filter-direction definition.

    } // END of bgp-prefix-list-filter-config definition.
    grouping bgp-route-map-filter-config {
        description
            "Grouping for BGP route map filter configuration";
        leaf route-map-name  {
            when " /bgp/bgp-instance/peer/address-family/config/activate ";
            type  string {
                length "1..max";
                pattern "[^?' =,>|]+";
            }
            description "Use this attribute to apply a route map to incoming or outgoing
                        routes. This attribute filters updates and modifies attributes. A
                        route map is applied to inbound or outbound updates. Only the routes
                        that pass the route map are sent or accepted in updates.";
        } // END of route-map-name definition.

        leaf route-map-direction  {
            when " /bgp/bgp-instance/peer/address-family/config/activate ";
            type  ipi-bgp-types:bgp_distribute_list_direction_t;
            description "Use this attribute to configure the direction in which the route map
                        is to be applied. Direction of the filter (0=FILTER_IN |1=FILTER_OUT)";
        } // END of route-map-direction definition.

    } // END of bgp-route-map-filter-config definition.
    grouping bgp-password-config {
        description
            "Configuration parameters BGP address family VRF password";
        leaf password  {
            if-feature feature-list:HAVE_TCP_MD5SIG;
            type  cml-data-types:cml_md5_password_t;
            description "Enable authentication-key on this interface to be used in message
                        digest5 (MD5) authentication on a TCP connection between two BGP
                        peers. Configuring MD5 authentication between two BGP peers, means
                        that each segment sent on the TCP connection between the peers is
                        verified. MD5 authentication must be configured with the same password
                        on both BGP peers; otherwise, the connection between them will not be
                        established.";
        } // END of password definition.

        leaf auth-key-encrypt  {
            type  ipi-bgp-types:bgp_md5_t;
            description "Use this attribute to configure the authentication key to specify if
                        the password is to be encrypted or not.";
        } // END of auth-key-encrypt definition.

    } // END of bgp-password-config definition.
    grouping bgp-peer-timers-config {
        description
            "attributes having bgp timer configuration";
        leaf keep-alive  {
            type  uint16 {
                 range "0..65535"  {
                    description "Keepalive interval in seconds";
                 }
            }
            mandatory true;
            description "Use this attribute to globally set or reset the keepalive values for
                        all the neighbors";
        } // END of keep-alive definition.

        leaf hold-time  {
            type  uint16 {
                 range "0..65535"  {
                    description "Holdtime in seconds";
                 }
            }
            mandatory true;
            description "Use this attribute to globally set or reset the holdtime values for
                        all the neighbors.";
        } // END of hold-time definition.

    } // END of bgp-peer-timers-config definition.
    grouping bgp-address-family-table-map-config {
        description
            "Table map configuration for  BGP Address Family";
        leaf map-name  {
            if-feature feature-list:HAVE_BGP_TABLE_MAP;
            type  string {
                length "1..max";
                pattern "[^?' =,>|]+";
            }
            mandatory true;
            description "Use this attribute to enable or disable suppression/modification of
                        incoming BGP updates to IP RIB/FIB table installation.
                        In a dedicated route reflector, all the routes it receives may not be
                        required to be stored or only few selected routes need to be stored,
                        because it may not lie in the data path.
                        Table maps are particularly useful to attain this restriction.
                        When map-name attribute is set, the route map referenced in the
                        map-name attribute shall be used to set certain properties (such as
                        the traffic index) of the routes for installation into the RIB. The
                        route is always downloaded, regardless of whether it is permitted or
                        denied by the route map.";
        } // END of map-name definition.

        leaf table-map-filter  {
            when " /bgp/bgp-instance/address-family/table-map/config/map-name ";
            if-feature feature-list:HAVE_BGP_TABLE_MAP;
            type  boolean;
            description "When tableMapFilter attribute is given in the table map attribute, the
                        route map referenced is used to control whether a BGP route is to be
                        downloaded to the IP RIB (hence the filter). A BGP route is not
                        downloaded to the RIB if it is denied by the route map.";
        } // END of table-map-filter definition.

    } // END of bgp-address-family-table-map-config definition.
    grouping table-map-top {
        description
            "Grouping for attributes related to Table map";
        container table-map {
            description
                "Container for Attributes related to Table map";
            container config {
                presence "To configure table map";
                description
                    "Configuration attributes related to Table map";
                uses bgp-address-family-table-map-config;
            } // END of config-container definition.
            container state {
                config false;
                description
                    "Operational state data related to Distance for routes";
                uses bgp-address-family-table-map-config;
            } // END of state-container definition.
        } // END of table-map-container definition.
    } // END of table-map-top definition.
    grouping bgp-peer-run-time-attribute-prefix-state {
        description
            "Runtime parameters for BGP peer prefix";
        leaf entry-sequence  {
            type  int32;
            config false;
            description "Prefix sequence number";
        } // END of entry-sequence definition.

        leaf entry-type  {
            type  ipi-bgp-types:bgp_prefix_entry_type_t;
            config false;
            description "Prefix type 1(no_match), 2(deny), 3(permit)";
        } // END of entry-type definition.

        leaf entry-max-length  {
            type  int32;
            config false;
            description "Maximum prefix length to be matched";
        } // END of entry-max-length definition.

        leaf entry-min-length  {
            type  int32;
            config false;
            description "Minimum prefix length to be matched";
        } // END of entry-min-length definition.

        leaf prefix-length  {
            type  int32;
            config false;
            description "Prefix length";
        } // END of prefix-length definition.

    } // END of bgp-peer-run-time-attribute-prefix-state definition.
    grouping bgp-peer-run-time-attribute-index-state {
        description
            "Runtime parameters for BGP peer index";
        leaf peer-index  {
            type  int32;
            config false;
            description "Peer index";
        } // END of peer-index definition.

        leaf offset  {
            type  int32;
            config false;
            description "Peer offset";
        } // END of offset definition.

        leaf mask  {
            type  string {
                length "1..max";
                pattern "[^?' =,>|]+";
            }
            config false;
            description "Peer mask";
        } // END of mask definition.

    } // END of bgp-peer-run-time-attribute-index-state definition.
    grouping bgp-peer-run-time-counters-state {
        description
            "Runtime parameters for BGP peers";
        leaf keepalive-in-messages  {
            type  int32;
            config false;
            description "Keepalive input count";
        } // END of keepalive-in-messages definition.

        leaf keepalive-out-messages  {
            type  int32;
            config false;
            description "Keepalive output count";
        } // END of keepalive-out-messages definition.

        leaf open-messages-in  {
            type  int32;
            config false;
            description "Open message input count";
        } // END of open-messages-in definition.

        leaf open-messages-out  {
            type  int32;
            config false;
            description "Open message output count";
        } // END of open-messages-out definition.

        leaf as-path-count  {
            type  int32;
            config false;
            description "BGP AS-PATH entries";
        } // END of as-path-count definition.

        leaf as-path-extended-count  {
            type  int32;
            config false;
            description "BGP AS-PATH entries";
        } // END of as-path-extended-count definition.

        leaf update-message-in  {
            type  int32;
            default "0";
            config false;
            description "Update message input count";
        } // END of update-message-in definition.

        leaf update-message-out  {
            type  int32;
            default "0";
            config false;
            description "Update message ouput count";
        } // END of update-message-out definition.

        leaf received-packet-count  {
            type  int32;
            config false;
            description "Received messages";
        } // END of received-packet-count definition.

        leaf notification-in  {
            type  int32;
            config false;
            description "Notify input count";
        } // END of notification-in definition.

        leaf notification-out  {
            type  int32;
            config false;
            description "Notify output count";
        } // END of notification-out definition.

        leaf packet-in-queue  {
            type  int32;
            config false;
            description "messages queued to be processed from the neighbor";
        } // END of packet-in-queue definition.

        leaf packet-out-queue  {
            type  int32;
            config false;
            description "messages queued to be sent to the neighbor";
        } // END of packet-out-queue definition.

        leaf sent-packet-count  {
            type  int32;
            config false;
            description "Sent messages";
        } // END of sent-packet-count definition.

        leaf refresh-received-packet-count  {
            type  int32;
            config false;
            description "Route Refresh input count";
        } // END of refresh-received-packet-count definition.

        leaf refresh-sent-packet-count  {
            type  int32;
            config false;
            description "Route Refresh output count";
        } // END of refresh-sent-packet-count definition.

    } // END of bgp-peer-run-time-counters-state definition.
    grouping bgp-peer-run-time-orf-state {
        description
            "Runtime ORF parameters for BGP peers";
        leaf orf-prefix-string  {
            type  boolean;
            config false;
            description "Outbound Route Filter (ORF)";
        } // END of orf-prefix-string definition.

        leaf orf-prefix-send  {
            type  string {
                length "1..max";
                pattern "[^?' =,>|]+";
            }
            config false;
            description "Outbound Route Filter (ORF) sent";
        } // END of orf-prefix-send definition.

        leaf orf-prefix-count  {
            type  string {
                length "1..max";
                pattern "[^?' =,>|]+";
            }
            config false;
            description "Outbound Route Filter (ORF) received entries";
        } // END of orf-prefix-count definition.

        leaf orf-wait-refresh  {
            type  boolean;
            config false;
            description "First update is deferred until ORF or ROUTE-REFRESH is received";
        } // END of orf-wait-refresh definition.

    } // END of bgp-peer-run-time-orf-state definition.
    grouping bgp-peer-run-time-attribute-state {
        description
            "Runtime parameters for BGP peers";
        leaf max-paths-ibgp  {
            type  int16;
            config false;
            description "ECMP multipath ibgp maxpath";
        } // END of max-paths-ibgp definition.

        leaf as-local-count  {
            type  int32;
            default "1";
            config false;
            description "as-local count";
        } // END of as-local-count definition.

        leaf configured-max-paths-ebgp  {
            type  int16;
            config false;
            description "Configured ebgp ECMP multipath";
        } // END of configured-max-paths-ebgp definition.

        leaf max-paths-ebgp  {
            type  int16;
            config false;
            description "ECMP multipath ebgp maxpath";
        } // END of max-paths-ebgp definition.

        leaf configured-max-paths-ibgp  {
            type  int16;
            config false;
            description "Configured ibgp ECMP multipath";
        } // END of configured-max-paths-ibgp definition.

        leaf community-count  {
            type  int32;
            config false;
            description "bgp community count";
        } // END of community-count definition.

        leaf confederation-id-check  {
            type  boolean;
            config false;
            description "Check if AS is part of the confed";
        } // END of confederation-id-check definition.

        leaf peer-and-extended-asn-capability  {
            type  ipi-bgp-types:bgp_adv_rcv_type_t;
            config false;
            description "4-Octet ASN Capability: 1(advertise), 2(receive), 3(both advertise and
                        receive)";
        } // END of peer-and-extended-asn-capability definition.

        leaf address-family-capability  {
            type  ipi-bgp-types:bgp_adv_rcv_type_t;
            config false;
            description "Address family IPv4 Unicast: 1(advertise), 2(receive),3(both advertise
                        and receive)";
        } // END of address-family-capability definition.

        leaf ipv6-next-hop-global  {
            type  inet:ipv6-address;
            config false;
            description "Nexthop global";
        } // END of ipv6-next-hop-global definition.

        leaf ipv6-next-hop-local  {
            type  inet:ipv6-address;
            config false;
            description "Nexthop local";
        } // END of ipv6-next-hop-local definition.

        leaf remote-port  {
            type  int32;
            config false;
            description "Peer remote port";
        } // END of remote-port definition.

        leaf remote-address  {
            type  cml-data-types:cml_hostname_t;
            config false;
            description "Peer remote address";
        } // END of remote-address definition.

        leaf local-host  {
            type  cml-data-types:cml_hostname_t;
            config false;
            description "Peer Local host";
        } // END of local-host definition.

        leaf ipv4-next-hop  {
            type  inet:ipv4-address;
            config false;
            description "Nexthop";
        } // END of ipv4-next-hop definition.

        leaf local-port  {
            type  int32;
            config false;
            description "Peer local port";
        } // END of local-port definition.

        leaf prefix-list-count  {
            type  int32;
            config false;
            description "Prefix list count";
        } // END of prefix-list-count definition.

        leaf default-information-originate  {
            type  boolean;
            config false;
            description "Default information originate";
        } // END of default-information-originate definition.

        leaf inbound-path-policy  {
            type  boolean;
            config false;
            description "Inbound path policy configured";
        } // END of inbound-path-policy definition.

        leaf outbound-path-policy  {
            type  boolean;
            config false;
            description "Outbound path policy configured";
        } // END of outbound-path-policy definition.

        leaf default-originate-information-sent  {
            type  string {
                length "1..max";
                pattern "[^?' =,>|]+";
            }
            config false;
            description "default sent";
        } // END of default-originate-information-sent definition.

        leaf graceful-restart  {
            type  string {
                length "1..max";
                pattern "[^?' =,>|]+";
            }
            config false;
            description "Graceful restart-advertised/received";
        } // END of graceful-restart definition.

        leaf address-family-dependent-capability  {
            type  boolean;
            config false;
            description "AF-dependant capabilities";
        } // END of address-family-dependent-capability definition.

        leaf peer-address-family-table-version  {
            type  int32;
            config false;
            description "neighbor version";
        } // END of peer-address-family-table-version definition.

        leaf address-family-table-version  {
            type  int32;
            config false;
            description "BGP table version";
        } // END of address-family-table-version definition.

        leaf forward-status-preserve  {
            type  string {
                length "1..max";
                pattern "[^?' =,>|]+";
            }
            config false;
            description "Graceful restart:Forwarding states are being preserved";
        } // END of forward-status-preserve definition.

        leaf orf-type-prefix  {
            type  string {
                length "1..max";
                pattern "[^?' =,>|]+";
            }
            config false;
            description "Outbound Route Filter (ORF) type Prefix-list";
        } // END of orf-type-prefix definition.

        leaf orf-type-prefix-send-mode  {
            type  string {
                length "1..max";
                pattern "[^?' =,>|]+";
            }
            config false;
            description "ORF Send-mode advertised and received";
        } // END of orf-type-prefix-send-mode definition.

        leaf orf-type-prefix-receive-mode  {
            type  string {
                length "1..max";
                pattern "[^?' =,>|]+";
            }
            config false;
            description "ORF Receive-mode advertised and received";
        } // END of orf-type-prefix-receive-mode definition.

        leaf orf-type-prefix-old  {
            type  string {
                length "1..max";
                pattern "[^?' =,>|]+";
            }
            config false;
            description "Outbound Route Filter (ORF) type Prefix-list";
        } // END of orf-type-prefix-old definition.

        leaf orf-type-prefix-send-mode-old  {
            type  string {
                length "1..max";
                pattern "[^?' =,>|]+";
            }
            config false;
            description "peer afi orf cap Send-Mode";
        } // END of orf-type-prefix-send-mode-old definition.

        leaf orf-type-prefix-receive-mode-old  {
            type  string {
                length "1..max";
                pattern "[^?' =,>|]+";
            }
            config false;
            description "peer afi orf cap Receive-mode";
        } // END of orf-type-prefix-receive-mode-old definition.

        leaf prefix-count  {
            type  int32;
            config false;
            description "accepted prefixes";
        } // END of prefix-count definition.

        leaf send-prefix-count  {
            type  int32;
            config false;
            description "announced prefixes";
        } // END of send-prefix-count definition.

        leaf flag-shut-down  {
            type  ipi-bgp-types:bgp_peerflag_shutdown_t;
            config false;
            description "peer flag shutdown status: 1(Idle), 2(Connect), 3(Active),
                        4(Opensent), 5(Openconfirm), 6(Established), 7(Idle Admin), 8(Idle
                        PfxCt), 9(Idle G-shut)";
        } // END of flag-shut-down definition.

        leaf count  {
            type  int32;
            config false;
            description "peer count";
        } // END of count definition.

        leaf notify-info  {
            type  boolean;
            config false;
            description "BGP notify open error";
        } // END of notify-info definition.

        leaf error-notify-sent  {
            type  boolean;
            config false;
            description "Last reset due to notification type 0(sent), 1(received)";
        } // END of error-notify-sent definition.

        leaf notify-last-reset-time  {
            type  string {
                length "1..max";
                pattern "[^?' =,>|]+";
            }
            config false;
            description "Last reset in week:day:hour:min:sec format string";
        } // END of notify-last-reset-time definition.

        leaf notify-code-string  {
            type  cml-data-types:cml_line_t;
            config false;
            description "Notification Error Message code and subcode";
        } // END of notify-code-string definition.

        leaf connection-type  {
            type  ipi-bgp-types:bgp_connection_type_t;
            config false;
            description "Connection: shared network, non shared network";
        } // END of connection-type definition.

        leaf next-connection-timer  {
            type  int32;
            config false;
            description "Next connect timer due in seconds";
        } // END of next-connection-timer definition.

        leaf connection-established-count  {
            type  int32;
            config false;
            description "BGP state established count";
        } // END of connection-established-count definition.

        leaf connection-dropped-count  {
            type  int32;
            config false;
            description "BGP state drop count";
        } // END of connection-dropped-count definition.

        leaf graceful-restart-status  {
            type  string {
                length "1..max";
                pattern "[^?' =,>|]+";
            }
            config false;
            description "Graceful Restart Status";
        } // END of graceful-restart-status definition.

        leaf graceful-restart-time  {
            type  int32;
            config false;
            description "Remote restart-time in sec";
        } // END of graceful-restart-time definition.

        leaf bgp-established-up-time  {
            type  string {
                length "1..max";
                pattern "[^?' =,>|]+";
            }
            config false;
            description "Indicated up-time for the neighbor.If the uptime is less than a day
                        then the format is hour:min:sec.If the uptime is less than a week then
                        format is day:hour:min.If the uptime is more than a week then the
                        format is week:day:hour";
        } // END of bgp-established-up-time definition.

        leaf last-read-time  {
            type  string {
                length "1..max";
                pattern "[^?' =,>|]+";
            }
            config false;
            description "Indicated last update received time from the peer.If the time is less
                        than a day then the format is hour:min:sec.If the time is less than a
                        week then format is day:hour:min.If the time is more than a week then
                        the format is week:day:hour";
        } // END of last-read-time definition.

        leaf bgp-peer-state  {
            type  ipi-bgp-types:bgp_peer_status_t;
            config false;
            description "The bgp state of the session with following representation 1(Idle),
                        2(Connect), 3(Active), 4(Opensent), 5(Openconfirm), 6(Established)";
        } // END of bgp-peer-state definition.

        leaf link-type  {
            type  ipi-bgp-types:bgp_link_type_t;
            config false;
            description "Link type: internal, external";
        } // END of link-type definition.

        leaf ebgp-hop-away-count  {
            type  int32;
            config false;
            description "External BGP neighbor may be up to given hops away.";
        } // END of ebgp-hop-away-count definition.

        leaf router-id  {
            type  inet:ipv4-address;
            config false;
            description "peer router id";
        } // END of router-id definition.

        leaf advertisement-interval  {
            type  int32;
            config false;
            description "Minimum time between advertisement runs in seconds";
        } // END of advertisement-interval definition.

        leaf calculated-hold-time  {
            type  int32;
            config false;
            description "hold time in seconds";
        } // END of calculated-hold-time definition.

        leaf calculated-keepalive  {
            type  int32;
            config false;
            description "keepalive interval in seconds";
        } // END of calculated-keepalive definition.

        leaf dynamic-capability  {
            type  cml-data-types:cml_line_t;
            config false;
            description "Advertised capability";
        } // END of dynamic-capability definition.

        leaf route-refresh-capability  {
            type  ipi-bgp-types:bgp_route_refresh_cap_type_t;
            config false;
            description "Route Refresh";
        } // END of route-refresh-capability definition.

        leaf no-interface-binding  {
            type  boolean;
            config false;
            description "No Interfaces bound to BGP Instance";
        } // END of no-interface-binding definition.

        leaf capability-lable-unicast  {
            if-feature feature-list:HAVE_BGP_LU;
            type  ipi-bgp-types:bgp_capability_type_t;
            config false;
            description "Label Unicast neighbour Capability";
        } // END of capability-lable-unicast definition.

        leaf capability-ipv4-multicast  {
            type  ipi-bgp-types:bgp_capability_type_t;
            config false;
            description "IPV4 Multicast neighbour Capability";
        } // END of capability-ipv4-multicast definition.

        leaf capability-vpnv4-unicast  {
            type  ipi-bgp-types:bgp_capability_type_t;
            config false;
            description "Vpnv4 Unicast neighbour Capability";
        } // END of capability-vpnv4-unicast definition.

        leaf capability-vpnv6-unicast  {
            type  ipi-bgp-types:bgp_capability_type_t;
            config false;
            description "Vpnv6 Unicast neighbour Capability";
        } // END of capability-vpnv6-unicast definition.

        leaf capability-rtfilter-unicast  {
            type  ipi-bgp-types:bgp_capability_type_t;
            config false;
            description "Rtfilter Unicast neighbour Capability";
        } // END of capability-rtfilter-unicast definition.

        leaf capability-l2vpn-evpn  {
            type  ipi-bgp-types:bgp_capability_type_t;
            config false;
            description "L2vpn Evpn neighbour Capability";
        } // END of capability-l2vpn-evpn definition.

        leaf capability-ipv6-unicast  {
            type  ipi-bgp-types:bgp_capability_type_t;
            config false;
            description "Ipv6 Unicast neighbour Capability";
        } // END of capability-ipv6-unicast definition.

        leaf capability-ipv6-multicast  {
            type  ipi-bgp-types:bgp_capability_type_t;
            config false;
            description "Ipv6 Multicast neighbour Capability";
        } // END of capability-ipv6-multicast definition.

        leaf capability-ipv6-label-unicast  {
            type  ipi-bgp-types:bgp_capability_type_t;
            config false;
            description "Ipv6 Label Unicast neighbour Capability";
        } // END of capability-ipv6-label-unicast definition.

    } // END of bgp-peer-run-time-attribute-state definition.


}
