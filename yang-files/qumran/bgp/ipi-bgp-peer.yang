/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-bgp-peer.yang
*
*/

submodule ipi-bgp-peer {

    yang-version 1.1;

    belongs-to  ipi-bgp { prefix ipi-bgp; }

    import feature-list {
        prefix feature-list;
    }

    import cml-data-types {
        prefix cml-data-types;
    }

    import ipi-bgp-types {
        prefix ipi-bgp-types;
    }

    include ipi-bgp-common;
    include ipi-bgp-address-family;
    organization
        "IP Infusion Inc.";

    contact
        "Address: 3965 Freedom Circle, Suite 200, Santa Clara, CA 95054
         Phone: +1 408-400-1900
         E-mail: support@ipinfusion.com
         Web: http://www.ipinfusion.com/";

    description
        "";


    revision "2021-03-05" {
        description "Excluded yang generation for BGP Add path attributes";
        reference " 0.3.0.";
    }

    revision "2020-12-15" {
        description "Change to have data-types in lower case instead of camel case";
        reference " 0.2.0.";
    }

    revision "2020-09-10" {
        description "Initial Version";
        reference " 0.1.0.";
    }



    grouping peer-grouping {
    description
        "List of BGP neighbors configured on the local system, uniquely
                    identified by peer IPv[46] address";
        list peer {
            key "peer-address";
            description
                "List of BGP neighbors configured on the local system, uniquely
                            identified by peer IPv[46] address";
            leaf peer-address  {
                type  leafref {
                    path  "../config/peer-address";
                }
                description "Reference to the address of the BGP peer used as a key in the peer
                            list";
            } // END of peer-address definition.


            list bgp-password {
            when " /bgp/bgp-instance/peer/config/peer-as ";
                key "password auth-key-encrypt";
                max-elements 1;
                description
                    "list for BGP password";
                leaf password  {
                    type  leafref {
                        path  "../config/password";
                    }
                    description "Use this attribute to enable authentication-key";
                } // END of password definition.

                leaf auth-key-encrypt  {
                    type  leafref {
                        path  "../config/auth-key-encrypt";
                    }
                    description "Use this attribute to configure the authentication key to specify if
                                the password is to be encrypted or not.";
                } // END of auth-key-encrypt definition.

                container config {
                    description
                        "Configuration parameters relating to the BGP password";
                    uses bgp-password-config;
                } // END of config-container definition.
                container state {
                    config false;
                    description
                        "State parameters relating to the BGP password";
                    uses bgp-password-config;
                } // END of state-container definition.
            } // End of bgp-password-list

            list address-family {
            when " /bgp/bgp-instance/address-family/afi/bgp/bgp-instance/address-family/safi ";
                key "afi safi";
                description
                    "Container for address-family for BGP Peer";
                leaf afi  {
                    type  leafref {
                        path  "../config/afi";
                    }
                    description "BGP address family identifier";
                } // END of afi definition.

                leaf safi  {
                    type  leafref {
                        path  "../config/safi";
                    }
                    description "BGP sub address family identifier";
                } // END of safi definition.


                list maximum-prefixes {
                when " /bgp/bgp-instance/peer/address-family/config/activate ";
                    key "prefix-count";
                    max-elements 1;
                    description
                        "list for Prefix related configuration";
                    leaf prefix-count  {
                        type  leafref {
                            path  "../config/prefix-count";
                        }
                        description "Use this attribute to specify maximum number of prefixes that can be
                                    received from a neighbor";
                    } // END of prefix-count definition.

                    container config {
                        description
                            "Configuration parameters relating to the number of prefixes that can
                                    be received from a neighbor";
                        uses bgp-address-family-maximum-prefixes-config;
                    } // END of config-container definition.
                    container state {
                        config false;
                        description
                            "State parameters relating to the VRF address family";
                        uses bgp-address-family-maximum-prefixes-config;
                    } // END of state-container definition.
                } // End of maximum-prefixes-list

                list distribute-list-filter {
                when " /bgp/bgp-instance/peer/address-family/config/activate ";
                    key "filter-direction access-list-identifier";
                    description
                        "List of Distribute list Filter";
                    leaf filter-direction  {
                        type  leafref {
                            path  "../config/filter-direction";
                        }
                        description "Use this attribute to specify distribute list filter direction";
                    } // END of filter-direction definition.

                    leaf access-list-identifier  {
                        type  leafref {
                            path  "../config/access-list-identifier";
                        }
                        description "Access List information";
                    } // END of access-list-identifier definition.

                    container config {
                        description
                            "Configuration parameters relating to BGP Distribute list Filter";
                        uses bgp-distribute-list-filter-config;
                    } // END of config-container definition.
                    container state {
                        config false;
                        description
                            "State parameters relating to BGP Distribute list Filter";
                        uses bgp-distribute-list-filter-config;
                    } // END of state-container definition.
                } // End of distribute-list-filter-list

                list as-list-filter {
                when " /bgp/bgp-instance/peer/address-family/config/activate ";
                    key "as-list-direction as-access-list-identifier";
                    description
                        "List of AS list Filter";
                    leaf as-list-direction  {
                        type  leafref {
                            path  "../config/as-list-direction";
                        }
                        description "Use this attribute to specify access list filter direction";
                    } // END of as-list-direction definition.

                    leaf as-access-list-identifier  {
                        type  leafref {
                            path  "../config/as-access-list-identifier";
                        }
                        description "Access-list number. This attribute sets a BGP filter. This attribute
                                    specifies an access list filter on updates based on the BGP autonomous
                                    system paths. Each filter is an access list based on regular
                                    expressions";
                    } // END of as-access-list-identifier definition.

                    container config {
                        description
                            "Configuration parameters relating to BGP AS list Fileter";
                        uses bgp-as-list-filter-config;
                    } // END of config-container definition.
                    container state {
                        config false;
                        description
                            "State parameters relating to BGP AS list Fileter";
                        uses bgp-as-list-filter-config;
                    } // END of state-container definition.
                } // End of as-list-filter-list

                list prefix-list-filter {
                when " /bgp/bgp-instance/peer/address-family/config/activate ";
                    key "prefix-filter-direction prefix-list-name";
                    description
                        "List of Prefix list Filter";
                    leaf prefix-filter-direction  {
                        type  leafref {
                            path  "../config/prefix-filter-direction";
                        }
                        description "Use this attribute to specify prefix list filter direction";
                    } // END of prefix-filter-direction definition.

                    leaf prefix-list-name  {
                        type  leafref {
                            path  "../config/prefix-list-name";
                        }
                        description "This attribute specify a prefix list for filtering BGP advertisements
                                    for specified address-family. Filtering by prefix list matches the
                                    prefixes of routes with those listed in the prefix list. If there is a
                                    match, the route is used. An empty prefix list permits all prefixes.
                                    If a given prefix does not match any entries of a prefix list, the
                                    route is denied access. When multiple entries of a prefix list match a
                                    prefix, the entry with the smallest sequence number is considered to
                                    be a real match.
                                    The router begins the search at the top of the prefix list, with the
                                    sequence number 1. Once a match or deny occurs, the router does not
                                    need to go through the rest of the prefix list. For efficiency the
                                    most common matches or denies are listed at the top.";
                    } // END of prefix-list-name definition.

                    container config {
                        description
                            "Configuration parameters relating to BGP Prefix list Filter";
                        uses bgp-prefix-list-filter-config;
                    } // END of config-container definition.
                    container state {
                        config false;
                        description
                            "State parameters relating to BGP Prefix list Filter";
                        uses bgp-prefix-list-filter-config;
                    } // END of state-container definition.
                } // End of prefix-list-filter-list

                list route-map-filter {
                when " /bgp/bgp-instance/peer/address-family/config/activate ";
                    key "route-map-direction route-map-name";
                    description
                        "List of Route map Filter";
                    leaf route-map-direction  {
                        type  leafref {
                            path  "../config/route-map-direction";
                        }
                        description "Use this attribute to specify route-map direction";
                    } // END of route-map-direction definition.

                    leaf route-map-name  {
                        type  leafref {
                            path  "../config/route-map-name";
                        }
                        description "Use this attribute to apply a route map to incoming or outgoing
                                    routes. This attribute filters updates and modifies attributes. A
                                    route map is applied to inbound or outbound updates. Only the routes
                                    that pass the route map are sent or accepted in updates.";
                    } // END of route-map-name definition.

                    container config {
                        description
                            "Configuration parameters relating to BGP Route map Filter";
                        uses bgp-route-map-filter-config;
                    } // END of config-container definition.
                    container state {
                        config false;
                        description
                            "State parameters relating to BGP Route map Filter";
                        uses bgp-route-map-filter-config;
                    } // END of state-container definition.
                } // End of route-map-filter-list

                list peer-adj-out-route {
                    key "network-address";
                    config false;
                    description
                        "List of BGP Peer adj out route";
                    leaf network-address  {
                        type  leafref {
                            path  "../state/network-address";
                        }
                        description "Peer Adj-Out Network address";
                    } // END of network-address definition.


                    list next-hop {
                        key "next-hop-address";
                        config false;
                        description
                            "List of next-hop address and state parameters";
                        leaf next-hop-address  {
                            type  leafref {
                                path  "../state/next-hop-address";
                            }
                            description "Peer Adj-Out Nexthop address";
                        } // END of next-hop-address definition.

                        container state {
                            config false;
                            description
                                "State attributes for next-hop";
                            uses bgp-next-hop-state;
                        } // END of state-container definition.
                    } // End of next-hop-list
                    container state {
                        config false;
                        description
                            "State parameters relating to Adj out route";
                        uses bgp-peer-adj-out-route-state;
                    } // END of state-container definition.
                } // End of peer-adj-out-route-list

                list peer-adj-in-route {
                    key "network-address";
                    config false;
                    description
                        "List of BGP Peer adj  in route";
                    leaf network-address  {
                        type  leafref {
                            path  "../state/network-address";
                        }
                        description "Peer Adj-In Network address";
                    } // END of network-address definition.


                    list next-hop {
                        key "next-hop-address";
                        config false;
                        description
                            "List of next-hop address and state parameters";
                        leaf next-hop-address  {
                            type  leafref {
                                path  "../state/next-hop-address";
                            }
                            description "Peer Adj-In Nexthop address";
                        } // END of next-hop-address definition.

                        container state {
                            config false;
                            description
                                "State attributes for next-hop";
                            uses bgp-next-hop-state;
                        } // END of state-container definition.
                    } // End of next-hop-list
                    container state {
                        config false;
                        description
                            "State parameters relating to Adj In route";
                        uses bgp-peer-adj-in-route-state;
                    } // END of state-container definition.
                } // End of peer-adj-in-route-list
                container config {
                    description
                        "Configuration parameters relating to the address-family for BGP Peer";
                    uses bgp-peer-address-family-common-config;
                    uses bgp-address-family-peer-config;
                } // END of config-container definition.
                container state {
                    config false;
                    description
                        "State parameters relating to the address-family for BGP Peer";
                    container counters {
                        config false;
                        description
                            "Container for the peer runtime counters";
                        uses bgp-peer-run-time-counters-state;
                    } // END of counters-container definition.
                    uses bgp-peer-address-family-common-config;
                    uses bgp-address-family-peer-config;
                    uses bgp-peer-run-time-attribute-state;
                } // END of state-container definition.
                container outbound-route-filter {
                    config false;
                    description
                        "Container for the peer runtime outbound route filter";
                    container state {
                        config false;
                        description
                            "State parameters relating to outbound route filter";
                        uses bgp-peer-run-time-orf-state;
                    } // END of state-container definition.
                } // END of outbound-route-filter-container definition.
                container peer-prefix {
                    config false;
                    description
                        "Container for peer prefix attributes";
                    container state {
                        config false;
                        description
                            "State parameters relating to prefix attributes";
                        uses bgp-peer-run-time-attribute-prefix-state;
                    } // END of state-container definition.
                } // END of peer-prefix-container definition.
                container peer-index {
                    config false;
                    description
                        "Container for peer index attributes";
                    container state {
                        config false;
                        description
                            "State parameters relating to peer index attributes";
                        uses bgp-peer-run-time-attribute-index-state;
                    } // END of state-container definition.
                } // END of peer-index-container definition.
            } // End of address-family-list
            container config {
                description
                    "Configuration parameters relating to the BGP Peer";
                uses bgp-peer-common-config;
            } // END of config-container definition.
            container state {
                config false;
                description
                    "State parameters relating to the BGP";
                uses bgp-peer-common-config;
                uses bgp-peer-common-state;
            } // END of state-container definition.
            container timers {
                when " /bgp/bgp-instance/peer/config/peer-as ";
                description
                    "container for bgp timers";
                container config {
                    presence "To configure timers";
                    description
                        "configuration parameters relating to timers";
                    uses bgp-peer-timers-config;
                } // END of config-container definition.
                container state {
                    config false;
                    description
                        "state parameters relating to timers";
                    uses bgp-peer-timers-config;
                } // END of state-container definition.
            } // END of timers-container definition.
        } // End of peer-list
    } // END of peer-grouping definition.
    grouping bgp-peer-common-config {
        description
            "Configuration parameters common for BGP peers";
        leaf peer-address  {
            type  cml-data-types:cml_hostname_t;
            description "Address of the BGP peer, either in IPv4 or IPv6. The specified
                        neighbor exchanges routing information only if the neighbor is also
                        activated using the activate attribute.";
        } // END of peer-address definition.

        leaf peer-as  {
            type  uint32 {
                 range "1..4294967295"  {
                    description "AS number";
                 }
            }
            description "Autonomous system number of a neighbor.  If the specified ASN matches
                        the ASN number specified in the router bgp global configuration, the
                        neighbor is identified as internal. If the ASN does no match, it is
                        identified as external to the local AS.";
        } // END of peer-as definition.

        leaf graceful-shut  {
            type  empty;
            description "Use this attribute to start a graceful shutdown for the BGP session of
                        the specified BGP neighbor. The BGP session for this neighbor is shut
                        down after the graceful shutdown timer expires.
                        If there is no alternate path available for traffic to flow prior the
                        actual shutdown of the BGP session, this path is made available for 60
                        seconds or for configured time after which the path is no longer
                        available and traffic is dropped.";
        } // END of graceful-shut definition.

        leaf enable-peer-bfd  {
            when " /bgp/bgp-instance/peer/config/peer-as ";
            type  empty;
            description "Enable bidirectional forwarding detection (BFD) for the BGP peer";
        } // END of enable-peer-bfd definition.

        leaf enable-peer-bfd-multihop  {
            when " /bgp/bgp-instance/peer/config/enable-peer-bfd ";
            type  empty;
            description "Enable bidirectional forwarding detection (BFD) for the BGP peer with
                        multihop";
        } // END of enable-peer-bfd-multihop definition.

        leaf graceful-shutdown-timer  {
            when " /bgp/bgp-instance/peer/config/peer-as ";
            type  uint32 {
                 range "10..65535"  {
                    description "BGP peer g-shut time in secs";
                 }
            }
            description "Configure the value of the graceful shutdown timer. After the timer
                        expires, the BGP session initiated for graceful shutdown is shut down.";
        } // END of graceful-shutdown-timer definition.

        leaf peer-restart-time  {
            when " /bgp/bgp-instance/peer/config/peer-as ";
            if-feature feature-list:HAVE_RESTART;
            type  uint32 {
                 range "1..3600"  {
                    description "BGP peer g-shut time in secs";
                 }
            }
            description "Sets a different restart-time other than the global restart-time. This
                        attribute takes precedence over the restart-time value specified using
                        the grstSet attribute. The restart-time value is the maximum time that
                        a graceful-restart neighbor waits to come back up after a restart. The
                        default value is 120 seconds.";
        } // END of peer-restart-time definition.

        leaf peer-local-as  {
            when " /bgp/bgp-instance/peer/config/peer-as ";
            type  uint32 {
                 range "1..4294967295"  {
                    description "AS number";
                 }
            }
            description "Specifies an AS (autonomous system) number to use with BGP neighbor.";
        } // END of peer-local-as definition.

        leaf connect-retry-interval  {
            when " /bgp/bgp-instance/peer/config/peer-as ";
            type  int32 {
                 range "1..65535"  {
                    description "Connect timer";
                 }
            }
            default "120";
            description "Time interval in seconds between attempts to establish a session with
                        the peer.";
        } // END of connect-retry-interval definition.

        leaf peer-description  {
            when " /bgp/bgp-instance/peer/config/peer-as ";
            type  cml-data-types:cml_line_t;
            description "Associates a description with a neighbor. This helps in identifying a
                        neighbor quickly. It is useful for an ISP that has multiple neighbor
                        relationships.";
        } // END of peer-description definition.

        leaf enable-ebgp-multihop  {
            when " not(/bgp/bgp-instance/peer/config/ebgp-maximum-hop-count) + /bgp/bgp-instance/peer/config/peer-as ";
            type  empty;
            description "Accept and attempt BGP connections to external peers on indirectly
                        connected networks. Multihop is not established if the only route to
                        the multihop peer is a default route. This avoids loop formation.";
        } // END of enable-ebgp-multihop definition.

        leaf ebgp-maximum-hop-count  {
            when " not(/bgp/bgp-instance/peer/config/enable-ebgp-multihop) + /bgp/bgp-instance/peer/config/peer-as ";
            type  uint8 {
                 range "1..255"  {
                    description "maximum hop count";
                 }
            }
            default "255";
            description "Configures maximum hop count for the BGP neighbor ebgp-multihop
                        configuration.";
        } // END of ebgp-maximum-hop-count definition.

        leaf peer-connect-interval  {
            when " /bgp/bgp-instance/peer/config/peer-as ";
            type  uint32 {
                 range "1..65535"  {
                    description "Connect timer";
                 }
            }
            default "1";
            description "This attribute sets the timers for a specific BGP neighbor. Keepalive
                        messages are sent by a router to inform another router that the BGP
                        connection between the two is still active. The keepalive interval is
                        the period of time between each keepalive message sent by the router.
                        The holdtime interval is the time the router waits to receive a
                        keepalive message and if it does not receive a message for this period
                        it declares the neighbor dead.";
        } // END of peer-connect-interval definition.

        leaf peer-as-origin-interval  {
            when " /bgp/bgp-instance/peer/config/peer-as ";
            type  uint32 {
                 range "1..65535"  {
                    description "time in seconds";
                 }
            }
            default "1";
            description "Configures the minimum interval between the sending of AS-origination
                        routing updates.";
        } // END of peer-as-origin-interval definition.

        leaf min-route-advertisement-interval  {
            when " /bgp/bgp-instance/peer/config/peer-as ";
            type  uint32 {
                 range "0..65535"  {
                    description "time in seconds";
                 }
            }
            default "0";
            description "Sets a minimum route advertisement interval between the sending of BGP
                        routing updates. To reduce the flapping of routes to internet, a
                        minimum advertisement interval is set, so that the BGP routing updates
                        are sent only per interval seconds.";
        } // END of min-route-advertisement-interval definition.

        leaf enable-dynamic-capability  {
            when " /bgp/bgp-instance/peer/config/peer-as ";
            type  empty;
            description "Use this attribute to enable the dynamic capability for a specific
                        peer. This attribute allows a BGP speaker to advertise or withdraw an
                        address family capability to a peer in a non-disruptive manner.";
        } // END of enable-dynamic-capability definition.

        leaf collide-established  {
            when " /bgp/bgp-instance/peer/config/peer-as ";
            type  empty;
            description "Include a neighbor already in an established state for conflict
                        resolution when a TCP connection collision is detected.";
        } // END of collide-established definition.

        leaf source-identifier  {
            when " /bgp/bgp-instance/peer/config/peer-as ";
            type  string {
                length "1..max";
                pattern "[^?' =,>|]+";
            }
            default "NULL";
            description "Allows internal BGP sessions to use any operational interface for TCP
                        connections. This attribute can be used in conjunction with any
                        specified interface on the router. The loopback interface is the
                        interface that is most commonly used with this attribute. The use of
                        loopback interface eliminates a dependency and BGP does not have to
                        rely on the availability of a particular interface for making TCP
                        connections.";
        } // END of source-identifier definition.

        leaf enforce-multi-hop  {
            when " /bgp/bgp-instance/peer/config/peer-as ";
            type  empty;
            description "Turns on the enforcement of eBGP neighbors perform multihop.";
        } // END of enforce-multi-hop definition.

        leaf neighbor-override-capability  {
            when " /bgp/bgp-instance/peer/config/peer-as ";
            type  empty;
            description "Override a capability negotiation result and use locally configured
                        values.";
        } // END of neighbor-override-capability definition.

        leaf neighbor-strict-capability-match  {
            when " /bgp/bgp-instance/peer/config/peer-as ";
            type  empty;
            description "Close the BGP connection if capability value does not match the remote
                        peer.";
        } // END of neighbor-strict-capability-match definition.

        leaf disallow-infinite-hold-time  {
            when " /bgp/bgp-instance/peer/config/peer-as ";
            type  empty;
            description "Disallow configuration of infinite hold-time. A hold-time of 0 seconds
                        from the peer (during exchange of open messages) or the user (during
                        configuration) will be rejected.";
        } // END of disallow-infinite-hold-time definition.

        leaf disable-capability-negotiation  {
            when " /bgp/bgp-instance/peer/config/peer-as ";
            type  empty;
            description "Disable the capability negotiation. It allows compatibility with older
                        BGP versions that have no capability parameters used in open messages
                        between peers.";
        } // END of disable-capability-negotiation definition.

        leaf neighbor-passive  {
            when " /bgp/bgp-instance/peer/config/peer-as ";
            type  empty;
            description "Sets a BGP neighbor as passive.";
        } // END of neighbor-passive definition.

        leaf peer-shutdown  {
            when " /bgp/bgp-instance/peer/config/peer-as ";
            type  empty;
            description "Disables a neighbor administratively. It will terminate any active
                        session for a specified neighbor and clear all related routing
                        information. In case a peer group is specified for shutdown, a large
                        number of peering sessions could be terminated.";
        } // END of peer-shutdown definition.

        leaf peer-port  {
            when " /bgp/bgp-instance/peer/config/peer-as ";
            type  uint16 {
                 range "0..65535"  {
                    description "TCP port number";
                 }
            }
            default "179";
            description "Sets the BGP port number of a neighbor.";
        } // END of peer-port definition.

        leaf bgp-version  {
            when " /bgp/bgp-instance/peer/config/peer-as ";
            type  uint8;
            default "4";
            description "Configure router to accept only a particular BGP version. By default,
                        the system uses BGP version 4 and on request dynamically negotiates
                        down to version 2. Disables the routers version-negotiation capability
                        and forces the router to use only a specified version with the
                        neighbor.";
        } // END of bgp-version definition.

        leaf interface-name  {
            when " /bgp/bgp-instance/peer/config/peer-as ";
            type  string {
                length "1..max";
                pattern "[^?' =,>|]+";
            }
            description "Configure the interface name of a BGP neighbor.";
        } // END of interface-name definition.

    } // END of bgp-peer-common-config definition.
    grouping bgp-peer-common-state {
        description
            "Runtime parameters common for BGP peers";
    } // END of bgp-peer-common-state definition.
    grouping bgp-peer-address-family-common-config {
        description
            "Configuration parameters common for BGP address family";
        leaf afi  {
            type  ipi-bgp-types:bgp_afi_type_t;
            description "BGP address family identifier";
        } // END of afi definition.

        leaf safi  {
            type  ipi-bgp-types:bgp_safi_type_t;
            description "BGP sub address family identifier";
        } // END of safi definition.

        leaf route-server-client  {
            when " /bgp/bgp-instance/peer/address-family/config/activate ";
            type  empty;
            description "This attribute configures a neighbor as the route server client for
                        specified address-family.";
        } // END of route-server-client definition.

        leaf next-hop-self  {
            when " /bgp/bgp-instance/peer/address-family/config/activate ";
            type  empty;
            description "This attribute configure the router as the next hop for a BGP-speaking
                        neighbor or peer group. This attribute allows a BGP router to change
                        the nexthop information that is sent to the iBGP peer. The nexthop
                        information is set to the IP address of the interface used to
                        communicate with the neighbor.";
        } // END of next-hop-self definition.

    } // END of bgp-peer-address-family-common-config definition.
    grouping bgp-peer-group-config {
        description
            "Configuration parameters for BGP peer groups";
    } // END of bgp-peer-group-config definition.


}
