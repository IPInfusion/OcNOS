/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-bgp-address-family.yang
*
*/

submodule ipi-bgp-address-family {

    yang-version 1.1;

    belongs-to  ipi-bgp { prefix ipi-bgp; }

    import feature-list {
        prefix feature-list;
    }

    import cml-data-types {
        prefix cml-data-types;
    }

    import ipi-bgp-types {
        prefix ipi-bgp-types;
    }

    import ietf-inet-types {
        prefix inet;
    }

    include ipi-bgp-common;
    organization
        "IP Infusion Inc.";

    contact
        "Address: 3965 Freedom Circle, Suite 200, Santa Clara, CA 95054
         Phone: +1 408-400-1900
         E-mail: support@ipinfusion.com
         Web: http://www.ipinfusion.com/";

    description
        "Datamodel for bgp network list";


    revision "2021-03-05" {
        description "Excluded yang generation for BGP Add path attributes, Added support for address-family ipv6 labeled-unicast deletion.";
        reference " 0.3.0.";
    }

    revision "2020-12-15" {
        description "Change to have data-types in lower case instead of camel case";
        reference " 0.2.0.";
    }

    revision "2020-09-10" {
        description "Initial Version";
        reference " 0.1.0.";
    }



    grouping address-family-grouping {
    description
        "bgp address-family";
        list address-family {
            key "afi safi";
            description
                "bgp address-family";
            leaf afi  {
                type  leafref {
                    path  "../config/afi";
                }
                description "BGP address family identifier";
            } // END of afi definition.

            leaf safi  {
                type  leafref {
                    path  "../config/safi";
                }
                description "BGP sub address family identifier";
            } // END of safi definition.


            list network-list {
                key "local-network-prefix";
                description
                    "List of networks advertised by BGP";
                leaf local-network-prefix  {
                    type  leafref {
                        path  "../config/local-network-prefix";
                    }
                    description "Use this attribute to specify the networks to be advertised by the BGP
                                routing process. A unicast network address without a mask is accepted
                                if it falls into the natural boundary of its class. A class-boundary
                                mask is derived if the address matches its natural class-boundary.";
                } // END of local-network-prefix definition.

                container config {
                    description
                        "configuration parameters for address-family network list";
                    uses bgp-address-family-network-list-config;
                } // END of config-container definition.
                container state {
                    config false;
                    description
                        "state parameters for address-family network list";
                    uses bgp-network-list-state;
                    uses bgp-address-family-network-list-config;
                } // END of state-container definition.
            } // End of network-list-list
            container config {
                description
                    "Configuration data for bgp address family";
                uses address-family-common-config;
                uses address-family-config;
            } // END of config-container definition.
            container state {
                config false;
                description
                    "Operational state data for bgp address family";
                uses address-family-common-config;
                uses address-family-config;
            } // END of state-container definition.
            uses aggregate-address-top;
            uses administrative-disatance-top;
            uses maximum-paths-top;
            uses table-map-top;
            uses route-flap-dampening-config-param;
            uses address-family-redist-list-top;
            uses bgp-redistribute-ospf-top;
        } // End of address-family-list
    } // END of address-family-grouping definition.
    grouping address-family-config {
        description
            "Configuration data for bgp address family";
        leaf afi  {
            type  ipi-bgp-types:bgp_afi_type_t;
            description "BGP address family identifier";
        } // END of afi definition.

        leaf safi  {
            type  ipi-bgp-types:bgp_safi_type_t;
            description "BGP sub address family identifier";
        } // END of safi definition.

        leaf mvpn-abr-enable  {
            if-feature feature-list:HAVE_BGP_MVPN;
            type  empty;
            description "Use this attribute to enable RFC7524 ABR for MVPN";
        } // END of mvpn-abr-enable definition.

        leaf no-client-route-reflection  {
            type  empty;
            description "Use this attribute to configure routers as route reflectors. Route
                        reflectors are used when all Interior Border Gateway Protocol (iBGP)
                        speakers are not fully meshed. If the clients are fully meshed the
                        route reflector is not required.";
        } // END of no-client-route-reflection definition.

    } // END of address-family-config definition.
    grouping bgp-aggregate-address-config {
        description
            "Configuration data for Aggregate Address List";
        leaf aggregate-address  {
            type  inet:ip-prefix;
            description "Aggregates are used to minimize the size of routing tables.
                        Aggregation combines the characteristics of several different routes
                        and advertises a single route.The aggregateAddr attribute creates an
                        aggregate entry in the BGP routing table if any more-specific BGP
                        routes are available in the specified range.";
        } // END of aggregate-address definition.

        leaf aggregate-type  {
            type  ipi-bgp-types:bgp_aggregate_type_t;
            description "The aggregate-type attribute creates an aggregate entry advertising
                        the path for this route, consisting of all elements contained in all
                        paths being summarized. Use this parameter to reduce the size of path
                        information by listing the AS number only once, even if it was
                        included in multiple paths that were aggregated.";
        } // END of aggregate-type definition.

    } // END of bgp-aggregate-address-config definition.
    grouping aggregate-address-top {
        description
            "Grouping for Aggregate Address List";

        list aggregate-address-list {
            key "aggregate-address";
            description
                "Aggregate address list";
            leaf aggregate-address  {
                type  leafref {
                    path  "../config/aggregate-address";
                }
                description "Aggregates are used to minimize the size of routing tables.
                            Aggregation combines the characteristics of several different routes
                            and advertises a single route.The aggregate-address attribute creates
                            an aggregate entry in the BGP routing table if any more-specific BGP
                            routes are available in the specified range.";
            } // END of aggregate-address definition.

            container config {
                description
                    "Configuration data for Aggregate Address List";
                uses bgp-aggregate-address-config;
            } // END of config-container definition.
            container state {
                config false;
                description
                    "Operational state data for bgp aggregate address list";
                uses bgp-aggregate-address-config;
            } // END of state-container definition.
        } // End of aggregate-address-list-list
    } // END of aggregate-address-top definition.
    grouping address-family-common-config {
        description
            "Common configuration data for BGP Address Family";
        leaf enable-auto-summary  {
            type  empty;
            description "Use this attribute to enable sending summarized routes by a BGP
                        speaker to its peers. Auto-summary is used by a BGP router to
                        advertise summarized routes to its peers. Auto-summary can be enabled
                        if certain routes have already been advertised: in this case,
                        configuring auto-summary advertises the summarized routes first, then
                        corresponding non-summarized routes are withdrawn. If certain routes
                        have already been advertised, and auto-summary is disabled,
                        non-summarized routes are first advertised, then the corresponding
                        summarized routes are withdrawn from all the connected peers.";
        } // END of enable-auto-summary definition.

        leaf enable-network-igp-sync  {
            type  empty;
            description "Use this attribute to enable IGP synchronization for BGP static
                        network routes";
        } // END of enable-network-igp-sync definition.

        leaf enable-igp-sync  {
            type  empty;
            description "Use this attribute to enable IGP synchronization of Internal BGP
                        (iBGP) learned routes with the Internal Gateway Protocol (IGP) system.
                        Synchronization is used when a BGP router should not advertise routes
                        learned from iBGP neighbors, unless those routes are also present in
                        an IGP (for example, OSPF). Synchronization may be enabled when all
                        the routers in an autonomous system do not speak BGP, and the
                        autonomous system is a transit for other autonomous systems.";
        } // END of enable-igp-sync definition.

    } // END of address-family-common-config definition.
    grouping bgp-af-distance-config {
        description
            "Configuration attributes related to Distance for routes";
        leaf ebgp  {
            type  uint8 {
                 range "1..255"  {
                    description "Distance for routes external to the AS";
                 }
            }
            description "Use this attribute to define an administrative distance for external
                        routes. External paths are routes learned from a neighbor outside of
                        the AS. A distance is a rating of trustworthiness of a router. The
                        higher the distance the lower the trust rating.
                        If the administrative distance is changed, it could create
                        inconsistency in the routing table and obstruct routing.";
        } // END of ebgp definition.

        leaf ibgp  {
            type  uint8 {
                 range "1..255"  {
                    description "Distance for routes internal to the AS";
                 }
            }
            description "Use this attribute to define an administrative distance for internal
                        routes. Internal routes are routes learned from another router within
                        the same AS. A distance is a rating of trustworthiness of a router.
                        The higher the distance the lower the trust rating.
                        If the administrative distance is changed, it could create
                        inconsistency in the routing table and obstruct routing.";
        } // END of ibgp definition.

        leaf local  {
            type  uint8 {
                 range "1..255"  {
                    description "Distance for local routes";
                 }
            }
            description "Use this attribute to define an administrative distance for local
                        routes. Local routes are routes that is redistributed from another
                        process.A distance is a rating of trustworthiness of a router. The
                        higher the distance the lower the trust rating.
                        If the administrative distance is changed, it could create
                        inconsistency in the routing table and obstruct routing.";
        } // END of local definition.

    } // END of bgp-af-distance-config definition.
    grouping administrative-disatance-top {
        description
            "Grouping for attributes related to Distance for routes";

        list distance {
            key "ebgp ibgp local";
            description
                "Container for Attributes related to Distance for routes";
            leaf ebgp  {
                type  leafref {
                    path  "../config/ebgp";
                }
                description "Use this attribute to define an administrative distance for external
                            routes. External paths are routes learned from a neighbor outside of
                            the AS. A distance is a rating of trustworthiness of a router. The
                            higher the distance the lower the trust rating.
                            If the administrative distance is changed, it could create
                            inconsistency in the routing table and obstruct routing.";
            } // END of ebgp definition.

            leaf ibgp  {
                type  leafref {
                    path  "../config/ibgp";
                }
                description "Use this attribute to define an administrative distance for internal
                            routes. Internal routes are routes learned from another router within
                            the same AS. A distance is a rating of trustworthiness of a router.
                            The higher the distance the lower the trust rating.
                            If the administrative distance is changed, it could create
                            inconsistency in the routing table and obstruct routing.";
            } // END of ibgp definition.

            leaf local  {
                type  leafref {
                    path  "../config/local";
                }
                description "Use this attribute to define an administrative distance for local
                            routes. Local routes are routes that is redistributed from another
                            process.A distance is a rating of trustworthiness of a router. The
                            higher the distance the lower the trust rating.
                            If the administrative distance is changed, it could create
                            inconsistency in the routing table and obstruct routing.";
            } // END of local definition.

            container config {
                description
                    "Configuration attributes related to Distance for routes";
                uses bgp-af-distance-config;
            } // END of config-container definition.
            container state {
                config false;
                description
                    "Operational state data related to Distance for routes";
                uses bgp-af-distance-config;
            } // END of state-container definition.
        } // End of distance-list
    } // END of administrative-disatance-top definition.
    grouping maximum-paths-top {
        description
            "Grouping for attributes related to multipath ECMP numbers";
        container maximum-paths {
            description
                "Container for attributes related to multipath ECMP numbers";
            container config {
                description
                    "Configuration attributes related to multipath ECMP numbers";
                uses bgp-af-maximum-paths-config;
            } // END of config-container definition.
            container state {
                config false;
                description
                    "Operational state data related to multipath ECMP numbers";
                uses bgp-af-maximum-paths-config;
            } // END of state-container definition.
        } // END of maximum-paths-container definition.
    } // END of maximum-paths-top definition.
    grouping address-family-redist-list-top {
        description
            "Grouping for redistribute for address-family";

        list route-redistribute-list {
            key "protocol-type";
            description
                "redistribute for address-family";
            leaf protocol-type  {
                type  leafref {
                    path  "../config/protocol-type";
                }
                description "Use this attribute to inject routes from one routing process into
                            another. Redistribution is used by routing protocols to advertise
                            routes that are learned by some other means, such as by another
                            routing protocol or by static routes. Since all internal routes are
                            dumped into BGP, careful filtering is applied to make sure that only
                            routes to be advertised reach the internet, not everything. This
                            attribute allows redistribution by injecting prefixes from one routing
                            protocol into another routing protocol.";
            } // END of protocol-type definition.

            container config {
                description
                    "Configuration data for redistribute for address-family";
                uses address-family-redist-list-config;
            } // END of config-container definition.
            container state {
                config false;
                description
                    "Operational state data for redistribute for address-family";
                uses address-family-redist-list-config;
            } // END of state-container definition.
        } // End of route-redistribute-list-list
    } // END of address-family-redist-list-top definition.
    grouping bgp-redistribute-ospf-config {
        description
            "Configuration attributes related to redistribute with ospf proc Id for
                        address family";
        leaf ospf-instance-number  {
            type  cml-data-types:cml_ospf_area_id_t;
            description "Use this attribute to inject routes from OSPF with specified OSPF
                        instance number to BGP.";
        } // END of ospf-instance-number definition.

        leaf redistribute-ospf-route-map  {
            type  string {
                length "1..max";
                pattern "[^?' =,>|]+";
            }
            description "Use this attribute to specify route map to redistribute routes from
                        OSPF into BGP.";
        } // END of redistribute-ospf-route-map definition.

    } // END of bgp-redistribute-ospf-config definition.
    grouping bgp-redistribute-ospf-top {
        description
            "Grouping for redistribute with ospf proc Id for address family";

        list bgp-redistribute-ospf {
            key "ospf-instance-number";
            description
                "redistribute with ospf proc Id for address family";
            leaf ospf-instance-number  {
                type  leafref {
                    path  "../config/ospf-instance-number";
                }
                description "Use this attribute to inject routes from one routing process into
                            another. Redistribution is used by routing protocols to advertise
                            routes that are learned by some other means, such as by another
                            routing protocol or by static routes. Since all internal routes are
                            dumped into BGP, careful filtering is applied to make sure that only
                            routes to be advertised reach the internet, not everything. This
                            attribute allows redistribution by injecting prefixes from one routing
                            protocol into another routing protocol.";
            } // END of ospf-instance-number definition.

            container config {
                description
                    "Configuration data for redistribute with ospf proc Id for address
                            family";
                uses bgp-redistribute-ospf-config;
            } // END of config-container definition.
            container state {
                config false;
                description
                    "Operational state data related to redistribute with ospf proc Id for
                            address family";
                uses bgp-redistribute-ospf-config;
            } // END of state-container definition.
        } // End of bgp-redistribute-ospf-list
    } // END of bgp-redistribute-ospf-top definition.
    grouping route-flap-dampening-param-config {
        description
            "BGP Route Flap Dampening User Configurable Parameters";
        leaf enable-dampening  {
            type  ipi-bgp-types:bgp_dampening_t;
            description "This attribute enable BGP route dampening and set various parameters
                        to default values.";
        } // END of enable-dampening definition.

        leaf reach-half-life  {
            when " not(/bgp/bgp-instance/address-family/route-flap-dampening/config/dampening-rmap-name) ";
            type  uint32 {
                 range "1..45"  {
                    description "Reachability Half-life time for the penalty(minutes)";
                 }
            }
            default "15";
            description "Use this attribute to configure reachability half-life time for the
                        penalty in minutes for the bgp route dampening. The time for the
                        penalty to decrease to one-half of its current value.";
        } // END of reach-half-life definition.

        leaf reuse-penalty  {
            when " /bgp/bgp-instance/address-family/route-flap-dampening/config/reach-half-life ";
            type  uint32 {
                 range "1..20000"  {
                    description "Value to start reusing a route";
                 }
            }
            description "reuse Penalty <1-20000>";
        } // END of reuse-penalty definition.

        leaf suppress-penalty  {
            when " /bgp/bgp-instance/address-family/route-flap-dampening/config/reach-half-life ";
            type  uint32 {
                 range "1..20000"  {
                    description "Value to start suppressing a route";
                 }
            }
            description "Use this attribute to specify suppress-penalty value";
        } // END of suppress-penalty definition.

        leaf max-suppress-time  {
            when " /bgp/bgp-instance/address-family/route-flap-dampening/config/reach-half-life ";
            type  uint32 {
                 range "1..255"  {
                    description "Maximum duration to suppress a stable route(minutes)";
                 }
            }
            description "Use this attribute to configure the value to start suppressing a route
                        for BGP route dampening. When the penalty for a route exceeds the
                        suppress value, the route is suppressed";
        } // END of max-suppress-time definition.

        leaf unreach-half-life  {
            when " /bgp/bgp-instance/address-family/route-flap-dampening/config/reach-half-life ";
            type  uint32 {
                 range "1..45"  {
                    description "Un-reachability Half-life time for the penalty(minutes)";
                 }
            }
            description "Use this attribute to configure un-reachability half-life time for the
                        penalty in minutes for bgp route dampening. The dampening information
                        is purged from the router once the penalty becomes less than half of
                        the reuse limit.";
        } // END of unreach-half-life definition.

        leaf dampening-rmap-name  {
            when " not(/bgp/bgp-instance/address-family/route-flap-dampening/config/reach-half-life) ";
            type  string {
                length "1..max";
                pattern "[^?' =,>|]+";
            }
            description "Use this attribute to configure route map to specify criteria for
                        dampening.";
        } // END of dampening-rmap-name definition.

    } // END of route-flap-dampening-param-config definition.
    grouping bgp-address-family-network-list-config {
        description
            "grouping for BGP address-family network-list config";
        leaf local-network-prefix  {
            type  ipi-bgp-types:bgp_ip_network_t;
            description "Use this attribute to specify the networks to be advertised by the BGP
                        routing process. A unicast network address without a mask is accepted
                        if it falls into the natural boundary of its class. A class-boundary
                        mask is derived if the address matches its natural class-boundary.";
        } // END of local-network-prefix definition.

        leaf network-rmap-name  {
            type  string {
                length "1..max";
                pattern "[^?' =,>|]+";
            }
            default "NULL";
            description "Use this attribute to configure route map for the network specified in
                        local-network-prefix";
        } // END of network-rmap-name definition.

        leaf backdoor  {
            type  empty;
            description "network address with backdoor for address family";
        } // END of backdoor definition.

    } // END of bgp-address-family-network-list-config definition.
    grouping route-flap-dampening-config-param {
        description
            "Grouping for BGP Route Flap Dampening User Configurable Parameters";

        list route-flap-dampening {
            key "enable-dampening";
            max-elements 1;
            description
                "Container for BGP Route Flap Dampening User Configurable Parameters";
            leaf enable-dampening  {
                type  leafref {
                    path  "../config/enable-dampening";
                }
                description "This attribute enable BGP route dampening and set various parameters
                            to default values.";
            } // END of enable-dampening definition.

            container config {
                description
                    "BGP Route Flap Dampening User Configurable Parameters";
                uses route-flap-dampening-param-config;
            } // END of config-container definition.
            container state {
                config false;
                description
                    "Operational state data related to BGP Route Flap Dampening";
                uses route-flap-dampening-param-config;
            } // END of state-container definition.
        } // End of route-flap-dampening-list
    } // END of route-flap-dampening-config-param definition.


}
