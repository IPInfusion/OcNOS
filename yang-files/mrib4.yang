/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : mrib4.yang
*
*/

submodule mrib4 {

    belongs-to  ZebOS { prefix ZebOS; }
    include interface;


    import cml_data_types {
        prefix cml_data_types;
    }


    revision "2017-02-07" {
        description "Fix for Jira13151.";
    }

    revision "2017-02-02" {
        description "changes for Documentation.";
    }

    revision "2017-01-27" {
        description "changes for Debug command.";
    }

    revision "2016-10-06" {
        description "Updated snmp oid.";
    }



    grouping mrib4Vrf-grouping {
        list mrib4Vrf {
             
            description
                "mrib4Vrf";

            config true;
            key "vrfName";

            
            leaf vrId  {
                type  cml_data_types:CML_UINT32_T;  
                default "0";
            } // END of vrId definition.

            leaf vrfName  {
                type  cml_data_types:CML_STRING_T {
                    length "0..255";
                }
            } // END of vrfName definition.

            leaf setMulticastFlag  {
                type  cml_data_types:CML_BOOL_T;  
                default false;
                description "ip multicast-routing";
            } // END of setMulticastFlag definition.

            leaf configs_flag  {
                type  cml_data_types:CML_UINT32_T;  
                config false;
            } // END of configs_flag definition.

            leaf rtLimit  {
                type  cml_data_types:CML_UINT32_T {
                     range "1..2147483647";
                }
            } // END of rtLimit definition.

            leaf rtThresh  {
                type  cml_data_types:CML_UINT32_T {
                     range "1..2147483647";
                }
                description "ip multicast route-limit";
            } // END of rtThresh definition.

            leaf debugFlag  {
                type  cml_data_types:CML_MRIB4_DEBUG_T;  
            } // END of debugFlag definition.

            leaf termdebugFlag  {
                type  cml_data_types:CML_MRIB4_DEBUG_T;  
            } // END of termdebugFlag definition.

            leaf interface_storage_type  {
                type  cml_data_types:CML_UINT32_T;  
                config false;
            } // END of interface_storage_type definition.

            leaf mrt_entry_count  {
                type  cml_data_types:CML_UINT32_T;  
                config false;
            } // END of mrt_entry_count definition.

            leaf mrt_entry_sm_count  {
                type  cml_data_types:CML_UINT32_T;  
                config false;
            } // END of mrt_entry_sm_count definition.

            leaf mrt_entry_dm_count  {
                type  cml_data_types:CML_UINT32_T;  
                config false;
            } // END of mrt_entry_dm_count definition.

            leaf stat_poll_exptime  {
                type  cml_data_types:CML_STRING_T {
                    length "0..255";
                }
                config false;
            } // END of stat_poll_exptime definition.

            leaf num_nocache_recv  {
                type  cml_data_types:CML_UINT32_T;  
                config false;
            } // END of num_nocache_recv definition.

            leaf num_nocache_sent  {
                type  cml_data_types:CML_UINT32_T;  
                config false;
            } // END of num_nocache_sent definition.

            leaf num_wrongvif_recv  {
                type  cml_data_types:CML_UINT32_T;  
                config false;
            } // END of num_wrongvif_recv definition.

            leaf num_wrongvif_sent  {
                type  cml_data_types:CML_UINT32_T;  
                config false;
            } // END of num_wrongvif_sent definition.

            leaf num_wholepkt_recv  {
                type  cml_data_types:CML_UINT32_T;  
                config false;
            } // END of num_wholepkt_recv definition.

            leaf num_wholepkt_sent  {
                type  cml_data_types:CML_UINT32_T;  
                config false;
            } // END of num_wholepkt_sent definition.

            leaf num_imm_stat_sent  {
                type  cml_data_types:CML_UINT32_T;  
                config false;
            } // END of num_imm_stat_sent definition.

            leaf num_timed_stat_sent  {
                type  cml_data_types:CML_UINT32_T;  
                config false;
            } // END of num_timed_stat_sent definition.

            leaf num_reg_pkt_sent  {
                type  cml_data_types:CML_UINT32_T;  
                config false;
            } // END of num_reg_pkt_sent definition.

            leaf reg_ack_recv  {
                type  cml_data_types:CML_UINT32_T;  
                config false;
            } // END of reg_ack_recv definition.

            leaf reg_nack_recv  {
                type  cml_data_types:CML_UINT32_T;  
                config false;
            } // END of reg_nack_recv definition.

            leaf rate_nocache_recv  {
                type  cml_data_types:CML_STRING_T {
                    length "0..255";
                }
                config false;
            } // END of rate_nocache_recv definition.

            leaf rate_reg_pkt_sent  {
                type  cml_data_types:CML_STRING_T {
                    length "0..255";
                }
                config false;
            } // END of rate_reg_pkt_sent definition.


            list mrib_mrt {
                 
                description
                    "mribCMLSEPmrt";

                config false;
                key "mrib_any_src_group";

                
                leaf mrib_any_src_group  {
                    type  cml_data_types:CML_STRING_T {
                        length "0..255";
                    }
                } // END of mrib_any_src_group definition.

                leaf iif_index  {
                    type  cml_data_types:CML_UINT16_T;  
                } // END of iif_index definition.

                leaf rpf_addr  {
                    type  cml_data_types:CML_STRING_T {
                        length "0..255";
                    }
                } // END of rpf_addr definition.

                leaf safi  {
                    type  cml_data_types:CML_STRING_T {
                        length "0..255";
                    }
                } // END of safi definition.

                leaf route_type  {
                    type  cml_data_types:CML_UINT8_T;  
                } // END of route_type definition.

                leaf stats_exptime  {
                    type  cml_data_types:CML_STRING_T {
                        length "0..255";
                    }
                } // END of stats_exptime definition.

                leaf pkts_fwd  {
                    type  cml_data_types:CML_UINT32_T;  
                } // END of pkts_fwd definition.

                leaf bytes_fwd  {
                    type  cml_data_types:CML_UINT32_T;  
                } // END of bytes_fwd definition.

                leaf wrong_if  {
                    type  cml_data_types:CML_UINT32_T;  
                } // END of wrong_if definition.


                list olist_vifs {
                     
                    description
                        "olistCMLSEPvifs";

                    config false;
                    key "if_name";

                    
                    leaf if_name  {
                        type  cml_data_types:CML_STRING_T {
                            length "0..255";
                        }
                    } // END of if_name definition.

                    leaf ttl  {
                        type  cml_data_types:CML_UINT8_T;  
                    } // END of ttl definition.

                } // End of olist_vifs-list
            } // End of mrib_mrt-list
        } // End of mrib4Vrf-list
    } // END of mrib4Vrf-grouping definition.


    grouping mrib4Interface-grouping {
        list mrib4Interface {
             
            description
                "mrib4Interface";

            config true;
            key "ifName";

            
            leaf ifName  {
                type  cml_data_types:CML_STRING_T {
                    length "0..255";
                }
            } // END of ifName definition.

            leaf ttlThresh  {
                type  cml_data_types:CML_UINT8_T {
                     range "1..255";
                }
                description "ip multicast ttl-threshold";
            } // END of ttlThresh definition.

            leaf LocalAddress  {
                type  cml_data_types:CML_STRING_T {
                    length "0..255";
                }
                config false;
            } // END of LocalAddress definition.

            leaf RemoteAddress  {
                type  cml_data_types:CML_STRING_T {
                    length "0..255";
                }
                config false;
            } // END of RemoteAddress definition.

            leaf uptime  {
                type  cml_data_types:CML_STRING_T {
                    length "0..255";
                }
                config false;
            } // END of uptime definition.

        } // End of mrib4Interface-list
    } // END of mrib4Interface-grouping definition.


}
