/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-ethernet-vpn.yang
*
*/

module ipi-ethernet-vpn {

    yang-version 1.1;

    namespace   "http://www.ipinfusion.com/yang/ocnos/ipi-ethernet-vpn";

    prefix "ipi-ethernet-vpn";

    import cml-data-types {
        prefix cml-data-types;
        revision-date 2022-09-30;
    }

    import ietf-inet-types {
        prefix inet;
        revision-date 2013-07-15;
    }

    import ipi-vrf {
        prefix ipi-vrf;
        revision-date 2022-07-13;
    }

    import ipi-network-instance {
        prefix ipi-network-instance;
        revision-date 2022-06-01;
    }

    import ipi-interface {
        prefix ipi-interface;
        revision-date 2022-08-24;
    }

    import ipi-evpn-mpls {
        prefix ipi-evpn-mpls;
        revision-date 2022-09-22;
    }

    import ipi-if-extended {
        prefix ipi-if-extended;
        revision-date 2022-10-12;
    }

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for EVPN protocol";


    revision "2022-07-07" {
        description "Updated the subinterface encapsulation dependencies correctly";
        reference " 0.6.1.";
    }

    revision "2022-06-27" {
        description "Updated when expressions in yang file";
        reference " 0.6.0.";
    }

    revision "2022-06-01" {
        description "Updated the yang file with feature";
        reference " 0.5.0.";
    }

    revision "2022-04-28" {
        description "Addition of EVPN-MPLS IRB CLI";
        reference " 0.4.0.";
    }

    revision "2022-03-08" {
        description "Addition of VXLAN dependencies for EVPN access-interfaces";
        reference " 0.3.2.";
    }

    revision "2022-01-14" {
        description "Addition of when tag for EVPN access-interfaces";
        reference " 0.3.1.";
    }

    revision "2021-10-13" {
        description "Unification of evpn access interface CLI common to vxlan and evpn-mpls";
        reference " 0.3.0.";
    }

    revision "2021-09-29" {
        description "Addition of when tag for evpn mpls related CLI";
        reference " 0.2.1.";
    }

    revision "2021-05-08" {
        description "addition of esi/system-mac for MH interface";
        reference " 0.2.0.";
    }

    revision "2021-01-27" {
        description "anycast gateway mac changes for IRB forwarding interface";
        reference " 0.1.2.";
    }

    revision "2020-12-15" {
        description "Change to have data-types in lower case instead of camel case";
        reference " 0.1.1.";
    }

    revision "2020-06-02" {
        description "Restructured as per Openconfig style";
        reference " 0.1.0.";
    }

    grouping evpn-global-config {
        description
            "Grouping for global evpn configuration";
        leaf enable-vxlan-multihoming  {
            if-feature feature-list:HAVE_TUNNEL;
            if-feature feature-list:HAVE_NVO;
            type  empty;
            description "Use this attribute to enable multihoming module on vxlan. Without this
                        attribute  multihomig functionality can not be achieved";
        } // END of enable-vxlan-multihoming definition.

        leaf enable-evpn-mpls-multihoming  {
            when " /ipi-evpn-mpls:evpn-mpls/ipi-evpn-mpls:global/ipi-evpn-mpls:config/ipi-evpn-mpls:enable-evpn-mpls ";
            if-feature feature-list:HAVE_MPLS;
            if-feature feature-list:HAVE_BGP_EVPN;
            if-feature feature-list:HAVE_NVO;
            type  empty;
            description "Use this attribute to enable multihoming module on evpn mpls. Without
                        this attribute  multihomig functionality can not be achieved";
        } // END of enable-evpn-mpls-multihoming definition.

        leaf enable-irb  {
            if-feature feature-list:HAVE_TUNNEL;
            if-feature feature-list:HAVE_NVO;
            type  empty;
            description "Use this attribute to enable integrated routing and bridging module.
                        Without this attribute IRB functionality can not be achieved";
        } // END of enable-irb definition.

        leaf enable-mpls-irb  {
            when " /ipi-evpn-mpls:evpn-mpls/ipi-evpn-mpls:global/ipi-evpn-mpls:config/ipi-evpn-mpls:enable-evpn-mpls ";
            if-feature feature-list:HAVE_TUNNEL;
            if-feature feature-list:HAVE_MPLS;
            if-feature feature-list:HAVE_BGP_EVPN;
            if-feature feature-list:HAVE_NVO;
            type  empty;
            description "Use this attribute to enable integrated routing and bridging module.
                        Without this attribute IRB functionality can not be achieved";
        } // END of enable-mpls-irb definition.

    } // END of evpn-global-config definition.
    grouping evpn-multihoming-config {
        description
            "Grouping for evpn multihoming configuration";
        leaf esi-hold-time  {
            if-feature feature-list:HAVE_BGP_EVPN;
            type  uint32 {
                 range "10..300"  {
                    description "10..300: Supported range 10 - 300";
                 }
            }
            units "seconds";
            description "Use this attribute to set time before ESI can be made up on enabling
                        evpn";
        } // END of esi-hold-time definition.

    } // END of evpn-multihoming-config definition.
    grouping evpn-interface-config {
        description
            "Grouping for interface configuration";
        leaf name  {
            type  leafref {
                path  "/ipi-interface:interfaces/ipi-interface:interface/ipi-interface:name";
            }
            description "Use this attribute to map a physical interface to identify
                        the tenant traffic and to enter access interface mode";
        } // END of name definition.

    } // END of evpn-interface-config definition.
    grouping mh-interface-config {
        description
            "MH interface configuration for esi";
        leaf evpn-segment-id  {
            type  string {
                length "1..1965";
                pattern "[^?' =,>|]+";
            }
            description "This Object is used to configure the evpn multi-homed Ethernet Segment
                        Identifier value";
        } // END of evpn-segment-id definition.

        leaf system-mac  {
            type  cml-data-types:cml_mac_addr_t {
                length "1..1965";
            }
            description "This Object is used to configure evpn multi-homed system-mac";
        } // END of system-mac definition.

    } // END of mh-interface-config definition.
    grouping evpn-irb-anycast-config {
        description
            "Grouping for evpn irb configuration";
        leaf mac-address  {
            if-feature feature-list:HAVE_TUNNEL;
            if-feature feature-list:HAVE_NVO;
            if-feature feature-list:HAVE_BGP_EVPN;
            type  cml-data-types:cml_mac_addr_t {
                length "1..1965";
            }
            description "Use this attribute to configure common anycast mac-address for all IRB
                        interfaces";
        } // END of mac-address definition.

    } // END of evpn-irb-anycast-config definition.
    grouping irb-interface-anycast-config {
        description
            "IRB interface forwarding for anycast gateway mac";
        leaf name  {
            type  leafref {
                path  "/ipi-interface:interfaces/ipi-interface:interface/ipi-interface:name";
            }
            description "Use this attribute to map a physical interface to identify the tenant
                        traffic and to enter NVO access interface mode";
        } // END of name definition.

        leaf gateway-mac  {
            when " /ipi-ethernet-vpn:evpn/ipi-ethernet-vpn:irb-forwarding/ipi-ethernet-vpn:config/ipi-ethernet-vpn:mac-address ";
            if-feature feature-list:HAVE_TUNNEL;
            if-feature feature-list:HAVE_NVO;
            if-feature feature-list:HAVE_VXLAN;
            if-feature feature-list:HAVE_BGP_EVPN;
            type  empty;
            description "Use this attribute to configure anycast mac-address for an IRB
                        interface";
        } // END of gateway-mac definition.

    } // END of irb-interface-anycast-config definition.
    grouping evpn-access-interface-config {
        description
            "Grouping for EVPN access interface configuration";
        leaf access-if  {
            type  cml-data-types:evpn_acc_if_t;
            description "evpn access port";
        } // END of access-if definition.

        leaf evpn-identifier  {
            if-feature feature-list:HAVE_BGP_EVPN;
            if-feature feature-list:HAVE_NVO;
            if-feature feature-list:HAVE_MPLS_OR_HAVE_VXLAN_OR_HAVE_SRV6;
            type  uint32 {
                 range "1..16777215"  {
                    description "1..16777215: Supported range 1 - 16777215";
                 }
            }
            description "Map already created tenant id";
        } // END of evpn-identifier definition.

        leaf dynamic-learning-disable  {
            type  empty;
            description "Use this attribute to disable dynamic learning of MACs
                        and MAC/IP at the access port";
        } // END of dynamic-learning-disable definition.

        leaf arp-nd-flood-suppress  {
            type  empty;
            description "Use this attribute to restrict the flood of ARP/ND packets
                        towards remote VTEPs or other access ports";
        } // END of arp-nd-flood-suppress definition.

        leaf arp-cache-disable  {
            type  empty;
            description "Use this attribute to disable the ARP cache for MAC/IP";
        } // END of arp-cache-disable definition.

        leaf nd-cache-disable  {
            type  empty;
            description "Use this attribute to disable ND-cache on access interface";
        } // END of nd-cache-disable definition.

        leaf mac-hold-time  {
            type  int16 {
                 range "-1..300"  {
                    description "-1..300: Supported range -1 - 300";
                 }
            }
            units "seconds";
            default "0";
            description "Use this attribute to set the time a host MAC entry will persist after
                        unconfig";
        } // END of mac-hold-time definition.

        leaf-list mac-address  {
            type  cml-data-types:cml_mac_addr_t {
                length "1..1965";
            }
            description "Use this attribute to configure static MAC only Host under Access
                        Circuit";
        } // END of mac-address definition.

    } // END of evpn-access-interface-config definition.
    grouping evpn-mpls-access-mac-ipv4-config {
        description
            "Grouping for access interface configuration";
        leaf mac-address  {
            type  cml-data-types:cml_mac_addr_t {
                length "1..1965";
            }
            description "MAC Address of host connected to evpn-mpls access port";
        } // END of mac-address definition.

        leaf ipv4-address  {
            type  inet:ipv4-address;
            description "USe this attribute to associate a static IPv4 address on an access
                        interface.";
        } // END of ipv4-address definition.

    } // END of evpn-mpls-access-mac-ipv4-config definition.
    grouping evpn-mpls-access-mac-ipv6-config {
        description
            "Grouping for access host configuration";
        leaf mac-address  {
            type  cml-data-types:cml_mac_addr_t {
                length "1..1965";
            }
            description "MAC Address of host connected to evpn-mpls access port";
        } // END of mac-address definition.

        leaf ipv6-address  {
            type  inet:ipv6-address;
            description "USe this attribute to associate a static IPv6 address on an access
                        interface.";
        } // END of ipv6-address definition.

    } // END of evpn-mpls-access-mac-ipv6-config definition.
    grouping evpn-interface-top {
        description
            "Top-Level Grouping for evpn interface";
        container interfaces {
            description
                "Top level container for evpn interface";

            list interface {
                key "name";
                description
                    "EVPN interface related operations";
                leaf name  {
                    type  leafref {
                        path  "../config/name";
                    }
                    description "Reference to interface name";
                } // END of name definition.

                container config {
                    description
                        "Configuration data";
                    uses evpn-interface-config;
                    uses mh-interface-config;
                } // END of config-container definition.
                container state {
                    config false;
                    description
                        "Operational state data";
                    uses evpn-interface-config;
                    uses mh-interface-config;
                } // END of state-container definition.
                uses evpn-access-interface-top;
            } // End of interface-list
        } // END of interfaces-container definition.
    } // END of evpn-interface-top definition.
    grouping irb-interface-anycast-top {
        description
            "Top-Level Grouping for IRB interface";

        list irb-interface {
            key "name";
            description
                "IRB interface related configurations";
            leaf name  {
                type  leafref {
                    path  "../config/name";
                }
                description "Use this attribute to map a physical interface to identify the tenant
                            traffic and to enter NVO access interface mode";
            } // END of name definition.

            container config {
                description
                    "Configuration data";
                uses irb-interface-anycast-config;
            } // END of config-container definition.
            container state {
                config false;
                description
                    "Operational state data";
                uses irb-interface-anycast-config;
            } // END of state-container definition.
        } // End of irb-interface-list
    } // END of irb-interface-anycast-top definition.
    grouping evpn-vlan-service-mapping-top {
        description
            "Top-Level Grouping for vrf to vlan-service mapping";

        list vrf {
            key "vrf-name";
            description
                "List of vrfs which holds evpn vlan service type";
            leaf vrf-name  {
                type  leafref {
                    path  "/ipi-network-instance:network-instances/ipi-network-instance:network-instance/ipi-vrf:vrf/ipi-vrf:config/ipi-vrf:vrf-name";
                }
                description "Vrf Name under which evpn vlan service can be mapped.";
            } // END of vrf-name definition.

            container config {
                description
                    "Configuration data";
                uses evpn-vlan-service-config;
            } // END of config-container definition.
            container state {
                config false;
                description
                    "Operational state data";
                uses evpn-vlan-service-config;
            } // END of state-container definition.
        } // End of vrf-list
    } // END of evpn-vlan-service-mapping-top definition.
    grouping evpn-vlan-service-config {
        description
            "EVPN vlan service config related data";
        leaf service-type  {
            type  cml-data-types:cml_evpn_service_type_t;
            description "Use this attribute to configure Vlan-Based EVPN-Service Type";
        } // END of service-type definition.

    } // END of evpn-vlan-service-config definition.
    grouping evpn-access-interface-top {
        description
            "Top level grouping for interface config";
        container access-interfaces {
            description
                "Top level container for interface level configuration";

            list access-interface {
            when " /ipi-interface:interfaces/ipi-interface:interface/ipi-if-extended:extended/ipi-if-extended:subinterface-encapsulation/ipi-if-extended:single-tag-vlan-matches/ipi-if-extended:single-tag-vlan-match  or /ipi-interface:interfaces/ipi-interface:interface/ipi-if-extended:extended/ipi-if-extended:subinterface-encapsulation/ipi-if-extended:double-tag-vlan-matches/ipi-if-extended:double-tag-vlan-match  or /ipi-interface:interfaces/ipi-interface:interface/ipi-if-extended:extended/ipi-if-extended:subinterface-encapsulation/ipi-if-extended:config/ipi-if-extended:encap-default  or /ipi-interface:interfaces/ipi-interface:interface/ipi-if-extended:extended/ipi-if-extended:subinterface-encapsulation/ipi-if-extended:config/ipi-if-extended:encap-untagged ";
            // when " ipi-interface:interfaces/interface/config/enable-switchport == '1' ";
                if-feature feature-list:HAVE_SUBINTERFACE;
                if-feature feature-list:HAVE_NVO;
                key "access-if";
                description
                    "Configuration and state information";
                leaf access-if  {
                    type  leafref {
                        path  "../config/access-if";
                    }
                    description "evpn-mpls access port";
                } // END of access-if definition.

                container config {
                    description
                        "Configuration data";
                    uses evpn-access-interface-config;
                } // END of config-container definition.
                container state {
                    config false;
                    description
                        "Operational state data";
                    uses evpn-access-interface-config;
                } // END of state-container definition.
                uses evpn-mpls-access-interface-mac-ipv4-list-top;
                uses evpn-mpls-access-interface-mac-ipv6-list-top;
            } // End of access-interface-list
        } // END of access-interfaces-container definition.
    } // END of evpn-access-interface-top definition.
    grouping evpn-mpls-access-interface-mac-ipv4-list-top {
        description
            "Grouping for mac-ipv4 configuration for access port";
        container ipv4-host-mac-mappings {
            description
                "Top level container for mac-ipv4 configuration for access port";

            list ipv4-host-mac-mapping {
                if-feature feature-list:HAVE_SUBINTERFACE;
                if-feature feature-list:HAVE_NVO;
                key "mac-address ipv4-address";
                description
                    "access side host related configurations";
                leaf mac-address  {
                    type  leafref {
                        path  "../config/mac-address";
                    }
                    description "Use this attribute to configure static MAC address of the host";
                } // END of mac-address definition.

                leaf ipv4-address  {
                    type  leafref {
                        path  "../config/ipv4-address";
                    }
                    description "USe this attribute to associate a static IPv4 address on an access
                                interface.";
                } // END of ipv4-address definition.

                container config {
                    description
                        "Configuration data";
                    uses evpn-mpls-access-mac-ipv4-config;
                } // END of config-container definition.
                container state {
                    config false;
                    description
                        "Operational state data";
                    uses evpn-mpls-access-mac-ipv4-config;
                } // END of state-container definition.
            } // End of ipv4-host-mac-mapping-list
        } // END of ipv4-host-mac-mappings-container definition.
    } // END of evpn-mpls-access-interface-mac-ipv4-list-top definition.
    grouping evpn-mpls-access-interface-mac-ipv6-list-top {
        description
            "Grouping for mac-ipv6 configuration for access port";
        container ipv6-host-mac-mappings {
            description
                "Top level container for mac-ipv6 configuration for access port";

            list ipv6-host-mac-mapping {
                if-feature feature-list:HAVE_SUBINTERFACE;
                if-feature feature-list:HAVE_NVO;
                if-feature feature-list:HAVE_IPV6;
                key "mac-address ipv6-address";
                description
                    "access side host related configurations";
                leaf mac-address  {
                    type  leafref {
                        path  "../config/mac-address";
                    }
                    description "Use this attribute to configure static MAC address of the host";
                } // END of mac-address definition.

                leaf ipv6-address  {
                    type  leafref {
                        path  "../config/ipv6-address";
                    }
                    description "USe this attribute to associate a static IPv6 address on an access
                                interface.";
                } // END of ipv6-address definition.

                container config {
                    description
                        "Configuration data";
                    uses evpn-mpls-access-mac-ipv6-config;
                } // END of config-container definition.
                container state {
                    config false;
                    description
                        "Operational state data";
                    uses evpn-mpls-access-mac-ipv6-config;
                } // END of state-container definition.
            } // End of ipv6-host-mac-mapping-list
        } // END of ipv6-host-mac-mappings-container definition.
    } // END of evpn-mpls-access-interface-mac-ipv6-list-top definition.

    grouping  evpn-grouping {
    description
        "EVPN global level container";
    container evpn {
        if-feature feature-list:HAVE_BGP_EVPN;
        description
            "EVPN global level container";
        container multi-homing {
            description
                "Configuration data for multi-homing feature";
            container config {
                description
                    "Configuration data";
                uses evpn-multihoming-config;
            } // END of config-container definition.
            container state {
                config false;
                description
                    "Operational state data";
                uses evpn-multihoming-config;
            } // END of state-container definition.
        } // END of multi-homing-container definition.
        container global {
            description
                "Configuration data for EVPN global capability configuration";
            container config {
                description
                    "Configuration data";
                uses evpn-global-config;
            } // END of config-container definition.
            container state {
                config false;
                description
                    "Operational state data";
                uses evpn-global-config;
            } // END of state-container definition.
        } // END of global-container definition.
        container irb-forwarding {
            description
                "Configuration data for integrated routing and bridging feature";
            container config {
                description
                    "Configuration data";
                uses evpn-irb-anycast-config;
            } // END of config-container definition.
            container state {
                config false;
                description
                    "Operational state data";
                uses evpn-irb-anycast-config;
            } // END of state-container definition.
            uses irb-interface-anycast-top;
        } // END of irb-forwarding-container definition.
        uses evpn-interface-top;
        uses evpn-vlan-service-mapping-top;
    } // END of evpn-container definition.
    } // END of evpn-grouping definition.

    uses evpn-grouping;

}
