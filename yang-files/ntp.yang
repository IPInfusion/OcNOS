/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ntp.yang
*
*/

submodule ntp {

    belongs-to  ZebOS { prefix ZebOS; }
    include vrf;


    import cml_data_types {
        prefix cml_data_types;
    }

    import feature_list {
        prefix feature_list;
    }

    description
        "ntp configurations";


    revision "2016-12-27" {
        description "Added snmp oid and documentation tag.";
    }

    revision "2016-10-28" {
        description "Initial version of NTP datamodel.";
    }


    grouping  ntp-grouping {
    container ntp {
                config true;

        description
            "ntp";

        leaf vrfName  {
            type  cml_data_types:CML_STRING_T {
                length "0..255";
            }
            default "default";
        } // END of vrfName definition.

        leaf featurentp  {
            if-feature feature_list:HAVE_HOSTP_NTP;
            type  cml_data_types:CML_BOOL_T;  
            description "feature ntp";
        } // END of featurentp definition.

        leaf enableNTP  {
            if-feature feature_list:HAVE_HOSTP_NTP;
            type  cml_data_types:CML_BOOL_T;  
            description "enable ntp";
        } // END of enableNTP definition.

        leaf loggingNTP  {
            if-feature feature_list:HAVE_HOSTP_NTP;
            type  cml_data_types:CML_BOOL_T;  
            default false;
            description "ntp logging";
        } // END of loggingNTP definition.

        leaf authenticateNTP  {
            if-feature feature_list:HAVE_HOSTP_NTP;
            type  cml_data_types:CML_BOOL_T;  
            default false;
            description "ntp authenticate";
        } // END of authenticateNTP definition.

        leaf debugntp  {
            type  cml_data_types:CML_BOOL_T;  
            default false;
            description "debug ntp";
        } // END of debugntp definition.


        list ntpKey {
             
            description
                "ntpKey";

            config true;
            key "keyAuthenticate";

            
            leaf vrfName  {
                type  cml_data_types:CML_STRING_T {
                    length "0..255";
                }
                default "default";
            } // END of vrfName definition.

            leaf keyAuthenticate  {
                type  cml_data_types:CML_INT32_T {
                     range "1..65534";
                }
                description "ntp authentication-key";
            } // END of keyAuthenticate definition.

            leaf authenticateScheme  {
                mandatory true;
                type  cml_data_types:CML_STRING_T {
                    length "0..255";
                }
            } // END of authenticateScheme definition.

        } // End of ntpKey-list

        list trustedKey {
             
            description
                "trustedKey";

            config true;
            key "trustedkeyNTP";

            
            leaf vrfName  {
                type  cml_data_types:CML_STRING_T {
                    length "0..255";
                }
                default "default";
            } // END of vrfName definition.

            leaf trustedkeyNTP  {
                type  cml_data_types:CML_INT32_T {
                     range "1..65534";
                }
                description "ntp trusted-key";
            } // END of trustedkeyNTP definition.

        } // End of trustedKey-list

        list PeerOptions {
             
            description
                "PeerOptions";

            config true;
            key "Address";

            
            leaf vrfName  {
                type  cml_data_types:CML_STRING_T {
                    length "0..255";
                }
                default "default";
            } // END of vrfName definition.

            leaf mode  {
                mandatory true;
                type  cml_data_types:CML_NTP_MODE_T;  
            } // END of mode definition.

            leaf Address  {
                type  cml_data_types:CML_HOSTNAME_T;  
                description "IP address";
            } // END of Address definition.

            leaf prefer  {
                type  cml_data_types:CML_BOOL_T;  
                description " NTP preference";
            } // END of prefer definition.

            leaf key  {
                type  cml_data_types:CML_UINT32_T {
                     range "1..65534";
                }
                description "key";
            } // END of key definition.

            leaf minpoll  {
                type  cml_data_types:CML_UINT16_T {
                     range "4..16";
                }
                default "4";
                description "Min poll interval for NTP messages";
            } // END of minpoll definition.

            leaf maxpoll  {
                type  cml_data_types:CML_UINT16_T {
                     range "4..16";
                }
                default "6";
                description "Max poll interval for NTP messages";
            } // END of maxpoll definition.

        } // End of PeerOptions-list
    } // END of ntp-container definition.
    } // END of ntp-container definition.


}
