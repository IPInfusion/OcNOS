/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : vr.yang
*
*/

submodule vr {

    belongs-to  ZebOS { prefix ZebOS; }

    import cml_data_types {
        prefix cml_data_types;
    }

    include vrf;
    include interface;
    include vlan;
    include switchportinterface;
    include bridge;
    include mstp;
    include rib;
    include ospf;
    include ospfv3;
    include bgp;
    include oambfd;
    include vrrp;
    include isis;
    include keychain;
    include pim;
    include pim4;
    include vxlan;
    include featuredhcp;
    include radius;
    include dhcpc;
    include mrib4;
    include igmp;
    include igmpsnooping;
    include routemap;
    include hqos;
    include cmm;
    include auth;
    include rip;
    include acl;
    include aclinterface;
    include imi;
    organization
        "IP Infusion Inc.";

    contact
        "Address: 3965 Freedom Circle, Suite 200, Santa Clara, CA 95054
        Phone: +1 408-400-1900
        E-mail: support@ipinfusion.com
        Web: http://www.ipinfusion.com/";

    description
        "Virtual router";


    revision "2016-10-29" {
        description "Added configurable attributes and operations.";
    }

    revision "2015-10-08" {
        description "Revised on 2015-10-08.";
    }



    grouping vr-grouping {
        list vr {
            key "vrId";
            description
                "Virtual router object";
            leaf vrId  {
                type  cml_data_types:CML_UINT32_T {
                     range "0..255";
                }
            } // END of vrId definition.

            leaf name  {
                type  cml_data_types:CML_STRING_T {
                    length "0..255";
                }
            } // END of name definition.


            list vrInstances {
                key "vrName";
                description
                    "object for virtual router configurations";
                leaf vrName  {
                    type  cml_data_types:CML_STRING_T {
                        length "1..12";
                    }
                } // END of vrName definition.

                leaf description  {
                    type  cml_data_types:CML_LINE_T;
                } // END of description definition.

                leaf protocol  {
                    type  cml_data_types:CML_VR_PROTOCOL_T;
                } // END of protocol definition.

            } // End of vrInstances-list
            uses vrf-grouping;
            uses interface-grouping;
            uses ifIndexList-grouping;
            uses nsmMaster-grouping;
            uses loadBalance-grouping;
            uses debugConfigMode-grouping;
            uses debugPktConfigMode-grouping;
            uses debugExecMode-grouping;
            uses pvlan-grouping;
            uses vlanAccessMap-grouping;
            uses switchportInterface-grouping;
            uses macAddressTable-grouping;
            uses vlanStacking-grouping;
            uses l2protocol-grouping;
            uses bridge-grouping;
            uses spanningTree-grouping;
            uses mstpSpanningTree-grouping;
            uses mstpbridge-grouping;
            uses spanningPort-grouping;
            uses bridgePort-grouping;
            uses backboneBridge-grouping;
            uses backboneBridgeInstance-grouping;
            uses customerSpanningtree-grouping;
            uses ribInterface-grouping;
            uses rib-grouping;
            uses ospf-grouping;
            uses teLinkOspf-grouping;
            uses ospf6_master-grouping;
            uses bgp-grouping;
            uses vrfTable-grouping;
            uses bgpDebug-grouping;
            uses bfdInterface-grouping;
            uses bfd-grouping;
            uses Vrrp4Instance-grouping;
            uses Vrrp6Instance-grouping;
            uses vrrp-grouping;
            uses isismaster-grouping;
            uses keychain-grouping;
            uses pimDebug-grouping;
            uses pimTermDebug-grouping;
            uses pim4Vrf-grouping;
            uses pim4Interface-grouping;
            uses pim4Debug-grouping;
            uses nvo-grouping;
            uses featuredhcp-grouping;
            uses Hostpdradius-grouping;
            uses radius-grouping;
            uses DHCPClientInterface-grouping;
            uses mrib4Vrf-grouping;
            uses mrib4Interface-grouping;
            uses mrib4Igmp-grouping;
            uses mrib4IgmpInterface-grouping;
            uses igmpSnoopInterface-grouping;
            uses pbrConfig-grouping;
            uses qos-grouping;
            uses ddmFalseAlarm-grouping;
            uses cmmInterface-grouping;
            uses authPort-grouping;
            uses authmac-grouping;
            uses ripConfiguration-grouping;
            uses accessMasterIPv4-grouping;
            uses accessMasterIPv6-grouping;
            uses aclInterface-grouping;
            uses hostname-grouping;
            uses webUser-grouping;
        } // End of vr-list
    } // END of vr-grouping definition.


}
