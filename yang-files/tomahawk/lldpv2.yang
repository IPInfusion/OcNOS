/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : lldpv2.yang
*
*/

submodule lldpv2 {

    belongs-to  ZebOS { prefix ZebOS; }

    import cml_data_types {
        prefix cml_data_types;
    }

    import feature_list {
        prefix feature_list;
    }

    include interface;
    include vr;
    organization
        "IP Infusion Inc.";

    contact
        "Address: 3965 Freedom Circle, Suite 200, Santa Clara, CA 95054
        Phone: +1 408-400-1900
        E-mail: support@ipinfusion.com
        Web: http://www.ipinfusion.com/";

    description
        "Link Layer Discovery Protocol";


    revision "2017-03-09" {
        description "when tag added fro limit command.";
    }

    revision "2016-12-26" {
        description "Initial version of LLDP datamodel.";
    }



    grouping lldpMaster-grouping {
        list lldpMaster {
            if-feature feature_list:HAVE_LLDPV2;
            key "vrId";
            description
                "lldpMaster";
            leaf vrId  {
                type  cml_data_types:CML_INT32_T;
            } // END of vrId definition.

            leaf lldpRun  {
                type  cml_data_types:CML_BOOL_T;
            } // END of lldpRun definition.

            leaf ifCnt  {
                type  cml_data_types:CML_UINT16_T;
                config false;
            } // END of ifCnt definition.

            leaf syscapEnabled  {
                type  cml_data_types:CML_UINT16_T;
                config false;
            } // END of syscapEnabled definition.

            leaf sysNameConf  {
                type  cml_data_types:CML_BOOL_T;
                config false;
            } // END of sysNameConf definition.

            leaf sysDescrConf  {
                type  cml_data_types:CML_BOOL_T;
                config false;
            } // END of sysDescrConf definition.

            leaf lldpStatsTablesInserts  {
                type  cml_data_types:CML_UINT32_T;
                config false;
            } // END of lldpStatsTablesInserts definition.

            leaf lldpStatsTablesDeletes  {
                type  cml_data_types:CML_UINT32_T;
                config false;
            } // END of lldpStatsTablesDeletes definition.

            leaf lldpStatsTablesDrops  {
                type  cml_data_types:CML_UINT32_T;
                config false;
            } // END of lldpStatsTablesDrops definition.

            leaf lldpStateRemTablesAgeouts  {
                type  cml_data_types:CML_UINT32_T;
                config false;
            } // END of lldpStateRemTablesAgeouts definition.

            leaf lldpNtfInterval  {
                type  cml_data_types:CML_UINT32_T;
                config false;
            } // END of lldpNtfInterval definition.

            leaf lldpStatStablesAgeouts  {
                type  cml_data_types:CML_UINT32_T;
                config false;
            } // END of lldpStatStablesAgeouts definition.

            leaf confFlag  {
                type  cml_data_types:CML_UINT8_T;
                config false;
            } // END of confFlag definition.

            leaf hostConfName  {
                type  cml_data_types:CML_STRING_T {
                    length "0..255";
                }
                config false;
            } // END of hostConfName definition.


            list lldpv2Interface {
                key "ifName";
                description
                    "LLDPV2 interface related operations";
                leaf ifName  {
                    type  cml_data_types:CML_STRING_T {
                        length "0..255";
                    }
                } // END of ifName definition.

                leaf lldpPortDescription  {
                    if-feature feature_list:HAVE_LLDPV2;
                    type  cml_data_types:CML_LINE_T;
                    default "NULL";
                } // END of lldpPortDescription definition.

                leaf lldpAgtCircuitId  {
                    type  cml_data_types:CML_STRING_T {
                        length "0..255";
                    }
                    default "NULL";
                } // END of lldpAgtCircuitId definition.

                leaf lldpmedDevType  {
                    type  cml_data_types:CML_LLDP_MEDDEV_T;
                    description "lldp med-devtype";
                } // END of lldpmedDevType definition.

                leaf localName  {
                    type  cml_data_types:CML_STRING_T {
                        length "0..255";
                    }
                    description "lldp locally-assigned";
                } // END of localName definition.

                leaf entityPhyAliasPort  {
                    type  cml_data_types:CML_STRING_T {
                        length "0..255";
                    }
                    config false;
                } // END of entityPhyAliasPort definition.

                leaf entityPhyAliasChassis  {
                    type  cml_data_types:CML_STRING_T {
                        length "0..255";
                    }
                    config false;
                } // END of entityPhyAliasChassis definition.

                leaf lldpAgentLocallyEnabled  {
                    type  cml_data_types:CML_BOOL_T;
                    config false;
                } // END of lldpAgentLocallyEnabled definition.

                leaf lldpAgentDisabled  {
                    type  cml_data_types:CML_BOOL_T;
                    config false;
                } // END of lldpAgentDisabled definition.


                list lldpAgent {
                    key "lldpAgent";
                    description
                        "LLDP configuration related operations";
                    leaf lldpAgent  {
                        type  cml_data_types:CML_LLDP_AGENT_T;
                    } // END of lldpAgent definition.

                    leaf lldpEnable  {
                        type  cml_data_types:CML_LLDP_ENABLE_T;
                        default "rxonly";
                        description "lldp enable";
                    } // END of lldpEnable definition.

                    leaf destMacAddr  {
                        type  cml_data_types:CML_STRING_T {
                            length "0..255";
                        }
                        config false;
                    } // END of destMacAddr definition.

                    leaf newNeighbour  {
                        type  cml_data_types:CML_UINT32_T;
                        config false;
                    } // END of newNeighbour definition.

                    container lldpTxSmConfig {
                        description
                            "lldpTxSmConfig";
                        leaf reinitDelay  {
                            type  cml_data_types:CML_STRING_T {
                                length "0..255";
                            }
                            description "lldp reinitDelay timer";
                        } // END of reinitDelay definition.

                        leaf MsgTxInterval  {
                            type  cml_data_types:CML_UINT32_T {
                                 range "5..3600";
                            }
                            default "30";
                            description "lldp timer msg-tx-interval";
                        } // END of MsgTxInterval definition.

                        leaf MsgTxValue  {
                            type  cml_data_types:CML_STRING_T {
                                length "0..255";
                            }
                            description "lldp msg-tx-hold";
                        } // END of MsgTxValue definition.

                        leaf MsgFastTx  {
                            type  cml_data_types:CML_UINT32_T {
                                 range "1..3600";
                            }
                            default "1";
                            description "lldp msg-fast-tx timer";
                        } // END of MsgFastTx definition.

                        leaf txMaxCredit  {
                            type  cml_data_types:CML_UINT32_T {
                                 range "1..10";
                            }
                            default "5";
                        } // END of txMaxCredit definition.

                        leaf txFastInit  {
                            type  cml_data_types:CML_UINT32_T {
                                 range "1..8";
                            }
                            default "4";
                        } // END of txFastInit definition.

                    } // END of lldpTxSmConfig-container definition.
                    container lldpTxSm {
                        config false;
                        description
                            "lldpTxSm";
                        leaf txCredit  {
                            type  cml_data_types:CML_UINT32_T;
                        } // END of txCredit definition.

                        leaf txFast  {
                            type  cml_data_types:CML_UINT32_T;
                        } // END of txFast definition.

                        leaf state  {
                            type  cml_data_types:CML_UINT8_T;
                        } // END of state definition.

                        leaf txNow  {
                            type  cml_data_types:CML_BOOL_T;
                        } // END of txNow definition.

                        leaf txTick  {
                            type  cml_data_types:CML_BOOL_T;
                        } // END of txTick definition.

                        leaf localChange  {
                            type  cml_data_types:CML_BOOL_T;
                        } // END of localChange definition.

                        leaf txTtl  {
                            type  cml_data_types:CML_INT16_T;
                        } // END of txTtl definition.

                        leaf lengthErrorsTotal  {
                            type  cml_data_types:CML_UINT32_T;
                        } // END of lengthErrorsTotal definition.

                        leaf framesOutTotal  {
                            type  cml_data_types:CML_UINT32_T;
                        } // END of framesOutTotal definition.

                    } // END of lldpTxSm-container definition.
                    container lldpRxSmConfig {
                        description
                            "lldpRxSmConfig";
                        leaf neighborLimit  {
                            type  cml_data_types:CML_UINT32_T {
                                 range "1..65535";
                            }
                        } // END of neighborLimit definition.

                        leaf neighborTimer  {
                            type  cml_data_types:CML_UINT32_T {
                                 range "1..65535";
                            }
                            description "lldp too-many-neighbors received-info";
                        } // END of neighborTimer definition.

                        leaf portMac  {
                            type  cml_data_types:CML_STRING_T {
                                length "0..255";
                            }
                        } // END of portMac definition.

                        leaf portTimer  {
                            type  cml_data_types:CML_UINT32_T {
                                 range "1..65535";
                            }
                            description "lldp too-many-neighbors existing-info";
                        } // END of portTimer definition.

                    } // END of lldpRxSmConfig-container definition.
                    container lldpRxSm {
                        config false;
                        description
                            "lldpRxSm";
                        leaf badFrame  {
                            type  cml_data_types:CML_BOOL_T;
                        } // END of badFrame definition.

                        leaf rxChanges  {
                            type  cml_data_types:CML_BOOL_T;
                        } // END of rxChanges definition.

                        leaf remoteChanges  {
                            type  cml_data_types:CML_BOOL_T;
                        } // END of remoteChanges definition.

                        leaf tooManyNeighbours  {
                            type  cml_data_types:CML_BOOL_T;
                        } // END of tooManyNeighbours definition.

                        leaf rxInfoAge  {
                            type  cml_data_types:CML_BOOL_T;
                        } // END of rxInfoAge definition.

                        leaf ageoutsTotal  {
                            type  cml_data_types:CML_UINT32_T;
                        } // END of ageoutsTotal definition.

                        leaf framesDiscardedTotal  {
                            type  cml_data_types:CML_UINT32_T;
                        } // END of framesDiscardedTotal definition.

                        leaf framesInErrorsTotal  {
                            type  cml_data_types:CML_UINT32_T;
                        } // END of framesInErrorsTotal definition.

                        leaf framesInTotal  {
                            type  cml_data_types:CML_UINT32_T;
                        } // END of framesInTotal definition.

                        leaf tlvsDiscardedTotal  {
                            type  cml_data_types:CML_UINT32_T;
                        } // END of tlvsDiscardedTotal definition.

                        leaf tlvsUnrecognizedTotal  {
                            type  cml_data_types:CML_UINT32_T;
                        } // END of tlvsUnrecognizedTotal definition.

                        leaf tooManyNeighborsFlag  {
                            type  cml_data_types:CML_UINT8_T;
                        } // END of tooManyNeighborsFlag definition.

                        leaf tooManyNeighborsCount  {
                            type  cml_data_types:CML_UINT32_T;
                        } // END of tooManyNeighborsCount definition.

                        leaf tooManyNeighborsDiscardType  {
                            type  cml_data_types:CML_UINT8_T;
                        } // END of tooManyNeighborsDiscardType definition.

                        leaf tooManyNeighborsDiscardMac  {
                            type  cml_data_types:CML_STRING_T {
                                length "0..255";
                            }
                        } // END of tooManyNeighborsDiscardMac definition.


                        list rlldpList {
                            key "remoteIfname";
                            config false;
                            description
                                "rlldpList";
                            leaf remoteIfname  {
                                type  cml_data_types:CML_STRING_T {
                                    length "0..255";
                                }
                            } // END of remoteIfname definition.

                            leaf remoteSysName  {
                                type  cml_data_types:CML_STRING_T {
                                    length "0..255";
                                }
                            } // END of remoteSysName definition.

                            leaf remotePortIdSubtype  {
                                type  cml_data_types:CML_UINT8_T;
                            } // END of remotePortIdSubtype definition.

                            leaf remoteChassicComp  {
                                type  cml_data_types:CML_UINT8_T;
                            } // END of remoteChassicComp definition.

                            leaf remotePortComp  {
                                type  cml_data_types:CML_UINT8_T;
                            } // END of remotePortComp definition.

                            leaf remoteIfalias  {
                                type  cml_data_types:CML_STRING_T {
                                    length "0..255";
                                }
                            } // END of remoteIfalias definition.

                            leaf remoteMacAddr  {
                                type  cml_data_types:CML_STRING_T {
                                    length "0..255";
                                }
                            } // END of remoteMacAddr definition.

                            leaf remoteIfagentcircuitid  {
                                type  cml_data_types:CML_STRING_T {
                                    length "0..255";
                                }
                            } // END of remoteIfagentcircuitid definition.

                            leaf remoteLocal  {
                                type  cml_data_types:CML_STRING_T {
                                    length "0..255";
                                }
                            } // END of remoteLocal definition.

                            leaf remoteEntityPhyAlias  {
                                type  cml_data_types:CML_STRING_T {
                                    length "0..255";
                                }
                            } // END of remoteEntityPhyAlias definition.

                            leaf remoteChassisIdType  {
                                type  cml_data_types:CML_UINT8_T;
                            } // END of remoteChassisIdType definition.

                            leaf remotePortIdType  {
                                type  cml_data_types:CML_UINT8_T;
                            } // END of remotePortIdType definition.

                            leaf rxTtl  {
                                type  cml_data_types:CML_UINT16_T;
                            } // END of rxTtl definition.

                            leaf remoteIfNumbering  {
                                type  cml_data_types:CML_UINT8_T;
                            } // END of remoteIfNumbering definition.

                            leaf remoteIfNumber  {
                                type  cml_data_types:CML_UINT32_T;
                            } // END of remoteIfNumber definition.

                            leaf remotePortVlanId  {
                                type  cml_data_types:CML_UINT16_T;
                            } // END of remotePortVlanId definition.

                            leaf remotePpvidFlag  {
                                type  cml_data_types:CML_UINT8_T;
                            } // END of remotePpvidFlag definition.

                            leaf remotePpVlanId  {
                                type  cml_data_types:CML_UINT16_T;
                            } // END of remotePpVlanId definition.

                            leaf remoteProtocol  {
                                type  cml_data_types:CML_UINT16_T;
                            } // END of remoteProtocol definition.

                            leaf remoteVidUsageDigest  {
                                type  cml_data_types:CML_UINT32_T;
                            } // END of remoteVidUsageDigest definition.

                            leaf remoteMgmtVlan  {
                                type  cml_data_types:CML_UINT16_T;
                            } // END of remoteMgmtVlan definition.

                            leaf remoteAutonegoSupport  {
                                type  cml_data_types:CML_UINT8_T;
                            } // END of remoteAutonegoSupport definition.

                            leaf remoteAutonegoCap  {
                                type  cml_data_types:CML_UINT16_T;
                            } // END of remoteAutonegoCap definition.

                            leaf remoteOperMauType  {
                                type  cml_data_types:CML_UINT16_T;
                            } // END of remoteOperMauType definition.

                            leaf remoteLinkAggrStatus  {
                                type  cml_data_types:CML_UINT8_T;
                            } // END of remoteLinkAggrStatus definition.

                            leaf remoteLinkAggrId  {
                                type  cml_data_types:CML_UINT32_T;
                            } // END of remoteLinkAggrId definition.

                            leaf remoteMaxFrameSize  {
                                type  cml_data_types:CML_UINT16_T;
                            } // END of remoteMaxFrameSize definition.

                            leaf remoteSysDescr  {
                                type  cml_data_types:CML_STRING_T {
                                    length "0..255";
                                }
                            } // END of remoteSysDescr definition.

                            leaf remoteSysCap  {
                                type  cml_data_types:CML_UINT16_T;
                            } // END of remoteSysCap definition.

                            leaf remoteSysCapEnabled  {
                                type  cml_data_types:CML_UINT16_T;
                            } // END of remoteSysCapEnabled definition.

                            leaf remoteMgmtAddr  {
                                type  cml_data_types:CML_STRING_T {
                                    length "0..255";
                                }
                            } // END of remoteMgmtAddr definition.

                            leaf remoteMgmtAddrSubType  {
                                type  cml_data_types:CML_UINT8_T;
                            } // END of remoteMgmtAddrSubType definition.

                            leaf remoteOid  {
                                type  cml_data_types:CML_STRING_T {
                                    length "0..255";
                                }
                            } // END of remoteOid definition.

                            leaf timeMarkIndex  {
                                type  cml_data_types:CML_UINT8_T;
                            } // END of timeMarkIndex definition.

                            leaf remoteIndex  {
                                type  cml_data_types:CML_UINT32_T;
                            } // END of remoteIndex definition.

                            leaf remoteUnknownTlvType  {
                                type  cml_data_types:CML_UINT32_T;
                            } // END of remoteUnknownTlvType definition.

                            leaf remoteUnknownTlvInfo  {
                                type  cml_data_types:CML_STRING_T {
                                    length "0..255";
                                }
                            } // END of remoteUnknownTlvInfo definition.

                            leaf remoteUnknownTlvInfoLen  {
                                type  cml_data_types:CML_UINT16_T;
                            } // END of remoteUnknownTlvInfoLen definition.

                            leaf remoteMdiPowerSupport  {
                                type  cml_data_types:CML_UINT8_T;
                            } // END of remoteMdiPowerSupport definition.

                            leaf remotePsePowerPair  {
                                type  cml_data_types:CML_UINT8_T;
                            } // END of remotePsePowerPair definition.

                            leaf remotePowerClass  {
                                type  cml_data_types:CML_UINT8_T;
                            } // END of remotePowerClass definition.

                            leaf remoteTypeSourcePriority  {
                                type  cml_data_types:CML_UINT8_T;
                            } // END of remoteTypeSourcePriority definition.

                            leaf remotePdRequestedPower  {
                                type  cml_data_types:CML_UINT16_T;
                            } // END of remotePdRequestedPower definition.

                            leaf remotePseAllocatedPower  {
                                type  cml_data_types:CML_UINT16_T;
                            } // END of remotePseAllocatedPower definition.

                            leaf peerEts  {
                                type  cml_data_types:CML_BOOL_T;
                            } // END of peerEts definition.

                            leaf etsError  {
                                type  cml_data_types:CML_BOOL_T;
                            } // END of etsError definition.

                            leaf etsTcgNum  {
                                type  cml_data_types:CML_UINT8_T;
                            } // END of etsTcgNum definition.

                            leaf peerApp  {
                                type  cml_data_types:CML_BOOL_T;
                            } // END of peerApp definition.

                            leaf appError  {
                                type  cml_data_types:CML_BOOL_T;
                            } // END of appError definition.

                            leaf cdcpStatus  {
                                type  cml_data_types:CML_BOOL_T;
                            } // END of cdcpStatus definition.

                            leaf peerEvb  {
                                type  cml_data_types:CML_BOOL_T;
                            } // END of peerEvb definition.

                            leaf peerCdcp  {
                                type  cml_data_types:CML_BOOL_T;
                            } // END of peerCdcp definition.

                            leaf remoteQcnTlv  {
                                type  cml_data_types:CML_BOOL_T;
                            } // END of remoteQcnTlv definition.

                            leaf remoteQcnCnpv  {
                                type  cml_data_types:CML_UINT8_T;
                            } // END of remoteQcnCnpv definition.

                            leaf remoteQcnReady  {
                                type  cml_data_types:CML_UINT8_T;
                            } // END of remoteQcnReady definition.


                            list remoteVlanList {
                                key "vlanId";
                                config false;
                                description
                                    "remoteVlanList";
                                leaf vlanId  {
                                    type  cml_data_types:CML_UINT16_T;
                                } // END of vlanId definition.

                                leaf vlanName  {
                                    type  cml_data_types:CML_STRING_T {
                                        length "0..255";
                                    }
                                } // END of vlanName definition.

                            } // End of remoteVlanList-list

                            list remoteMgmtInfo {
                                key "remoteMgmtAddr";
                                config false;
                                description
                                    "remoteMgmtInfo";
                                leaf remoteMgmtAddr  {
                                    type  cml_data_types:CML_STRING_T {
                                        length "0..255";
                                    }
                                } // END of remoteMgmtAddr definition.

                                leaf remoteMgmtAddrSubType  {
                                    type  cml_data_types:CML_UINT8_T;
                                } // END of remoteMgmtAddrSubType definition.

                                leaf remoteIfNumbering  {
                                    type  cml_data_types:CML_UINT8_T;
                                } // END of remoteIfNumbering definition.

                                leaf remoteIfNumber  {
                                    type  cml_data_types:CML_UINT32_T;
                                } // END of remoteIfNumber definition.

                                leaf remoteOid  {
                                    type  cml_data_types:CML_STRING_T {
                                        length "0..255";
                                    }
                                } // END of remoteOid definition.

                            } // End of remoteMgmtInfo-list
                        } // End of rlldpList-list
                    } // END of lldpRxSm-container definition.
                    container lldpTlvConfigCmd {
                        description
                            "lldpTlvConfigCmd";
                        leaf portAddr  {
                            type  cml_data_types:CML_LLDP_MGMT_ADDR_T;
                            default "mac-address";
                            description "lldp management-address-tlv";
                        } // END of portAddr definition.

                        leaf chassisId  {
                            type  cml_data_types:CML_LLDP_CHASSIS_T;
                            default "mac-address";
                            description "lldp chassis-id-tlv";
                        } // END of chassisId definition.

                        leaf portId  {
                            type  cml_data_types:CML_LLDP_PORT_T;
                            default "mac-address";
                            description "lldp port-id-tlv";
                        } // END of portId definition.

                        leaf tlvFlag  {
                            type  cml_data_types:CML_LLDP_TVL_FLAG_T;
                            description "lldp tlv-select";
                        } // END of tlvFlag definition.

                        leaf TlvSelect  {
                            type  cml_data_types:CML_LLDP_IEEE_8023_T;
                        } // END of TlvSelect definition.

                        leaf TlvSelectIeee  {
                            type  cml_data_types:CML_LLDP_IEEE_8021_T;
                        } // END of TlvSelectIeee definition.

                        leaf TlvSelectBasic  {
                            type  cml_data_types:CML_LLDP_BASIC_T;
                            description "lldp tlv-select basic-mgmt";
                        } // END of TlvSelectBasic definition.

                        leaf tlvMed  {
                            type  cml_data_types:CML_LLDP_MED_T;
                            description "lldp tlv-select med";
                        } // END of tlvMed definition.

                    } // END of lldpTlvConfigCmd-container definition.
                    container lldpTlvConfig {
                        config false;
                        description
                            "lldpTlvConfig";
                        leaf protocol  {
                            type  cml_data_types:CML_UINT16_T;
                        } // END of protocol definition.

                        leaf tooManyNeighborsCount  {
                            type  cml_data_types:CML_UINT32_T;
                        } // END of tooManyNeighborsCount definition.

                        leaf tooManyNeighborsLimit  {
                            type  cml_data_types:CML_UINT32_T;
                        } // END of tooManyNeighborsLimit definition.

                        leaf tooManyNeighborsDiscardType  {
                            type  cml_data_types:CML_UINT8_T;
                        } // END of tooManyNeighborsDiscardType definition.

                        leaf tooManyNeighborsDiscardMac  {
                            type  cml_data_types:CML_STRING_T {
                                length "0..255";
                            }
                        } // END of tooManyNeighborsDiscardMac definition.

                        leaf tooManyNeighborsInterval  {
                            type  cml_data_types:CML_UINT32_T;
                        } // END of tooManyNeighborsInterval definition.

                    } // END of lldpTlvConfig-container definition.
                } // End of lldpAgent-list
            } // End of lldpv2Interface-list
            container lldpMgmtIF {
                description
                    "lldpMgmtIF";
                leaf locallyAssigned  {
                    type  cml_data_types:CML_STRING_T {
                        length "0..255";
                    }
                    default "NULL";
                    description "lldp chassis locally-assigned";
                } // END of locallyAssigned definition.

            } // END of lldpMgmtIF-container definition.
        } // End of lldpMaster-list
    } // END of lldpMaster-grouping definition.


}
