/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : sflow.yang
*
*/

submodule sflow {

    belongs-to  ZebOS { prefix ZebOS; }

    import cml_data_types {
        prefix cml_data_types;
    }

    import feature_list {
        prefix feature_list;
    }

    organization
        "IP Infusion Inc.";

    contact
        "Address: 3965 Freedom Circle, Suite 200, Santa Clara, CA 95054
        Phone: +1 408-400-1900
        E-mail: support@ipinfusion.com
        Web: http://www.ipinfusion.com/";

    description
        "sflow configurations";


    revision "2017-05-04" {
        description "When any attr is removed from payload, unconfigures from backend to update DB..";
    }

    revision "2017-04-26" {
        description "removed ingress and egress Instance attribute.";
    }

    revision "2017-04-21" {
        description "ACL rate-limit sFlow.";
    }

    revision "2017-04-19" {
        description "sflow get api.";
    }

    revision "2017-04-14" {
        description "Added when tag for sflow Interface configurations.";
    }

    revision "2016-12-27" {
        description "Added snmp oid and documentation tag.";
    }

    revision "2016-10-28" {
        description "Initial version of SFLOW datamodel.";
    }


    grouping  sflow-grouping {
    container sflow {
        presence "yes";
        description
            "sflow";
        leaf sflowInstance  {
            type  cml_data_types:CML_BOOL_T;
            mandatory true;
            description "feature sflow";
        } // END of sflowInstance definition.

        leaf sflowVersion  {
            type  cml_data_types:CML_UINT8_T;
            config false;
            description "sflow version";
        } // END of sflowVersion definition.

        leaf sflowAgentIp  {
            type  cml_data_types:CML_IPV4_ADDR_T;
            config false;
            description "sflow version";
        } // END of sflowAgentIp definition.

        leaf collectorIP  {
            if-feature feature_list:HAVE_SFLOW;
            type  cml_data_types:CML_IPV4_ADDR_T;
        } // END of collectorIP definition.

        leaf port  {
            if-feature feature_list:HAVE_SFLOW;
            type  cml_data_types:CML_INT32_T {
                 range "1024..65535";
            }
            description "sFlow Collector Port Number";
        } // END of port definition.

        leaf receiverTimeout  {
            if-feature feature_list:HAVE_SFLOW;
            type  cml_data_types:CML_UINT32_T {
                 range "0..2147483647";
            }
            description "receiver timeout value in sec";
        } // END of receiverTimeout definition.

        leaf maxDatagramSize  {
            if-feature feature_list:HAVE_SFLOW;
            type  cml_data_types:CML_UINT16_T {
                 range "200..9000";
            }
            description "sflow collector";
        } // END of maxDatagramSize definition.

        leaf rate  {
            if-feature feature_list:HAVE_SFLOW;
            if-feature feature_list:HAVE_BROADCOM;
            type  cml_data_types:CML_INT32_T {
                 range "2000..100000";
            }
            description "Rate in packets per second";
        } // END of rate definition.

    } // END of sflow-container definition.
    } // END of sflow-container definition.

    grouping  sflowInterfaceConfigs-grouping {
    container sflowInterfaceConfigs {
        description
            "sampling and polling-interval configs of an interface";
        leaf pollingInterval  {
            type  cml_data_types:CML_UINT8_T {
                 range "5..60";
            }
            description "sflow poll-interval";
        } // END of pollingInterval definition.

        leaf pollingCount  {
            type  cml_data_types:CML_UINT32_T;
            config false;
            description "Retrieved from SFLOWPoller";
        } // END of pollingCount definition.

        leaf IngressSamplingStatus  {
            type  cml_data_types:CML_STRING_T {
                length "0..255";
            }
            config false;
            description "Ingress status";
        } // END of IngressSamplingStatus definition.

        leaf IngressSampledPktCount  {
            type  cml_data_types:CML_UINT32_T;
            config false;
            description "Retrieved from SFLOWSampler";
        } // END of IngressSampledPktCount definition.

        leaf EgressSampledPktCount  {
            type  cml_data_types:CML_UINT32_T;
            config false;
            description "Retrieved from SFLOWSampler";
        } // END of EgressSampledPktCount definition.

        leaf EgressSamplingStatus  {
            type  cml_data_types:CML_STRING_T {
                length "0..255";
            }
            config false;
            description "Egress status";
        } // END of EgressSamplingStatus definition.

        leaf limit  {
            if-feature feature_list:HAVE_SFLOW;
            if-feature feature_list:HAVE_UT;
            if-feature feature_list:HAVE_MARVELL;
            type  cml_data_types:CML_UINT32_T;
            config false;
            description "hw configured sampling rate";
        } // END of limit definition.

        leaf sampledPktCnt  {
            if-feature feature_list:HAVE_SFLOW;
            if-feature feature_list:HAVE_UT;
            if-feature feature_list:HAVE_MARVELL;
            type  cml_data_types:CML_UINT32_T;
            config false;
            description "packet sampled count in the hw";
        } // END of sampledPktCnt definition.

        leaf countdownCnt  {
            if-feature feature_list:HAVE_SFLOW;
            if-feature feature_list:HAVE_UT;
            if-feature feature_list:HAVE_MARVELL;
            type  cml_data_types:CML_UINT32_T;
            config false;
            description "packet count down information";
        } // END of countdownCnt definition.

        container samplingIngress {
            description
                "samplingIngress";
            leaf samplingRateIngress  {
                type  cml_data_types:CML_UINT32_T {
                     range "1024..1073741823";
                }
            } // END of samplingRateIngress definition.

            leaf maxHeaderSizeIngress  {
                type  cml_data_types:CML_UINT16_T {
                     range "16..256";
                }
                description "sflow ingress sampling-rate";
            } // END of maxHeaderSizeIngress definition.

        } // END of samplingIngress-container definition.
        container samplingEgress {
            description
                "samplingEgress";
            leaf samplingRateEgress  {
                type  cml_data_types:CML_UINT32_T {
                     range "1024..1073741823";
                }
            } // END of samplingRateEgress definition.

            leaf maxHeaderSizeEgress  {
                type  cml_data_types:CML_UINT16_T {
                     range "16..256";
                }
                description "sflow egress sampling-rate";
            } // END of maxHeaderSizeEgress definition.

        } // END of samplingEgress-container definition.
        container samplingEnable {
            description
                "samplingEnable";
            leaf samplingEnable  {
                type  cml_data_types:CML_BOOL_T;
                description "sflow sampling enable";
            } // END of samplingEnable definition.

        } // END of samplingEnable-container definition.
    } // END of sflowInterfaceConfigs-container definition.
    } // END of sflowInterfaceConfigs-container definition.

    grouping  debugsflow-grouping {
    container debugsflow {
        description
            "debugsflow";
        leaf debugsflow  {
            if-feature feature_list:HAVE_SFLOW;
            type  cml_data_types:CML_SFLOW_DEBUG_TYPE_T;
        } // END of debugsflow definition.

        leaf debugtermsflow  {
            if-feature feature_list:HAVE_SFLOW;
            type  cml_data_types:CML_SFLOW_DEBUG_TYPE_T;
        } // END of debugtermsflow definition.

    } // END of debugsflow-container definition.
    } // END of debugsflow-container definition.

    grouping  ACLsFlow-grouping {
    container ACLsFlow {
        description
            "ACLsFlow";
        leaf cacheSize  {
            if-feature feature_list:HAVE_SFLOW;
            if-feature feature_list:HAVE_ACL;
            type  cml_data_types:CML_INT32_T {
                 range "1000..10000";
            }
        } // END of cacheSize definition.

        leaf accessRate  {
            if-feature feature_list:HAVE_SFLOW;
            if-feature feature_list:HAVE_ACL;
            if-feature feature_list:HAVE_BROADCOM;
            type  cml_data_types:CML_INT16_T {
                 range "0..1000";
            }
        } // END of accessRate definition.

    } // END of ACLsFlow-container definition.
    } // END of ACLsFlow-container definition.


}
