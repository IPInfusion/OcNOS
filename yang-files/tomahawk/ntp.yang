/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ntp.yang
*
*/

submodule ntp {

    belongs-to  ZebOS { prefix ZebOS; }

    import cml_data_types {
        prefix cml_data_types;
    }

    import feature_list {
        prefix feature_list;
    }

    include vrf;
    organization
        "IP Infusion Inc.";

    contact
        "Address: 3965 Freedom Circle, Suite 200, Santa Clara, CA 95054
        Phone: +1 408-400-1900
        E-mail: support@ipinfusion.com
        Web: http://www.ipinfusion.com/";

    description
        "ntp configurations";


    revision "2017-05-15" {
        description "Added autopopulate custom tag.";
    }

    revision "2016-12-27" {
        description "Added snmp oid and documentation tag.";
    }

    revision "2016-10-28" {
        description "Initial version of NTP datamodel.";
    }



    grouping ntp-grouping {
        list ntp {
            key "vrfName";
            description
                "ntp";
            leaf vrfName  {
                type  cml_data_types:CML_STRING_T {
                    length "0..255";
                }
            } // END of vrfName definition.

            leaf featurentp  {
                if-feature feature_list:HAVE_HOSTP_NTP;
                type  cml_data_types:CML_BOOL_T;
                description "feature ntp";
            } // END of featurentp definition.

            leaf enableNTP  {
                if-feature feature_list:HAVE_HOSTP_NTP;
                type  cml_data_types:CML_BOOL_T;
                description "enable ntp";
            } // END of enableNTP definition.

            leaf loggingNTP  {
                if-feature feature_list:HAVE_HOSTP_NTP;
                type  cml_data_types:CML_BOOL_T;
                default false;
                description "ntp logging";
            } // END of loggingNTP definition.

            leaf authenticateNTP  {
                if-feature feature_list:HAVE_HOSTP_NTP;
                type  cml_data_types:CML_BOOL_T;
                default false;
                description "ntp authenticate";
            } // END of authenticateNTP definition.


            list ntpKey {
                key "keyAuthenticate";
                description
                    "ntpKey";
                leaf keyAuthenticate  {
                    type  cml_data_types:CML_INT32_T {
                         range "1..65535";
                    }
                    description "ntp authentication-key";
                } // END of keyAuthenticate definition.

                leaf authenticateScheme  {
                    type  cml_data_types:CML_STRING_T {
                        length "1..8";
                    }
                    mandatory true;
                } // END of authenticateScheme definition.

                leaf keyEncrytion  {
                    type  cml_data_types:CML_HOSTP_KEY_TYPE_T;
                } // END of keyEncrytion definition.

            } // End of ntpKey-list

            list trustedKey {
                key "trustedkeyNTP";
                description
                    "trustedKey";
                leaf trustedkeyNTP  {
                    type  cml_data_types:CML_INT32_T {
                         range "1..65535";
                    }
                    description "ntp trusted-key";
                } // END of trustedkeyNTP definition.

            } // End of trustedKey-list

            list PeerOptions {
                key "Address";
                description
                    "PeerOptions";
                leaf mode  {
                    type  cml_data_types:CML_NTP_MODE_T;
                    mandatory true;
                    description "ntp peer and server";
                } // END of mode definition.

                leaf Address  {
                    type  cml_data_types:CML_STRING_T {
                        length "1..64";
                    }
                    description "IP address";
                } // END of Address definition.

                leaf prefer  {
                    type  cml_data_types:CML_BOOL_T;
                    default false;
                    description " NTP preference";
                } // END of prefer definition.

                leaf key  {
                    type  cml_data_types:CML_UINT32_T {
                         range "1..65535";
                    }
                    default "65535";
                    description "key";
                } // END of key definition.

                leaf minpoll  {
                    type  cml_data_types:CML_UINT16_T {
                         range "4..16";
                    }
                    default "4";
                    description "Min poll interval for NTP messages";
                } // END of minpoll definition.

                leaf maxpoll  {
                    type  cml_data_types:CML_UINT16_T {
                         range "4..16";
                    }
                    default "6";
                    description "Max poll interval for NTP messages";
                } // END of maxpoll definition.

            } // End of PeerOptions-list
        } // End of ntp-list
    } // END of ntp-grouping definition.

    grouping  sourceNTP-grouping {
    container sourceNTP {
        description
            "sourceNTP";
        leaf sourceInterface  {
            if-feature feature_list:HAVE_HOSTP_NTP;
            type  cml_data_types:CML_STRING_T {
                length "0..255";
            }
            description "Source interface";
        } // END of sourceInterface definition.

    } // END of sourceNTP-container definition.
    } // END of sourceNTP-container definition.

    grouping  debugNTP-grouping {
    container debugNTP {
        description
            "debugNTP";
        leaf debugntp  {
            type  cml_data_types:CML_BOOL_T;
            description "debug ntp";
        } // END of debugntp definition.

        leaf debugntpConf  {
            type  cml_data_types:CML_BOOL_T;
            description "debug ntp";
        } // END of debugntpConf definition.

    } // END of debugNTP-container definition.
    } // END of debugNTP-container definition.


}
