/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-bridge.yang
*
*/

submodule zebos-bridge {

    belongs-to  zebos { prefix zebos; }

    import cml_data_types {
        prefix cml_data_types;
    }

    import feature_list {
        prefix feature_list;
    }

    include zebos-interface;
    include zebos-vlan;
    include zebos-switchportinterface;
    include zebos-mstp;
    include zebos-lldpv2;
    organization
        "IP Infusion Inc.";

    contact
        "Address: 3965 Freedom Circle, Suite 200, Santa Clara, CA 95054
        Phone: +1 408-400-1900
        E-mail: support@ipinfusion.com
        Web: http://www.ipinfusion.com/";

    description
        "Layer-2 bridge configurations";


    revision "2018-06-21" {
        description " Initial Version.";
        reference "";
    }



    grouping bridge-grouping {
    description
        "bridge";
        list bridge {
            key "bridgeId";
            description
                "bridge";
            leaf bridgeId  {
                type  cml_data_types:CML_STRING_T;
                description "";
            } // END of bridgeId definition.

            leaf bridgeType  {
                type  cml_data_types:CML_BRIDGE_PROTOCOL_T;
                mandatory true;
                description "";
            } // END of bridgeType definition.

            leaf brType  {
                type  cml_data_types:CML_BRIDGE_TYPE_T;
                description "";
            } // END of brType definition.

            leaf providerType  {
                if-feature feature_list:HAVE_PROVIDER_BRIDGE;
                type  cml_data_types:CML_PROVIDER_EDGE_T;
                description "";
            } // END of providerType definition.

            leaf bridgeMac  {
                if-feature feature_list:HAVE_I_BEB;
                if-feature feature_list:HAVE_B_BEB;
                if-feature feature_list:HAVE_UDLD;
                type  cml_data_types:CML_MAC_ADDR_T;
                description "";
            } // END of bridgeMac definition.

            leaf learning  {
                type  cml_data_types:CML_BOOL_T;
                description "";
            } // END of learning definition.

            leaf topologyType  {
                type  cml_data_types:CML_BRIDGE_TOPOLOGY_T;
                mandatory true;
                description "";
            } // END of topologyType definition.

            leaf macType  {
                type  cml_data_types:CML_MACTYPE_T;
                description "";
            } // END of macType definition.


            list interface {
                key "ifName";
                description
                    " Group of bridge attribute having interface property";
                leaf ifName  {
                    type  cml_data_types:CML_STRING_T;
                    description "";
                } // END of ifName definition.

                leaf spanningTreeStatus  {
                    type  cml_data_types:CML_SPANNINGTREE_ENABLE_DISABLE_T;
                    mandatory true;
                    description "";
                } // END of spanningTreeStatus definition.

            } // End of interface-list

            list staticFdb {
                key "ifName";
                description
                    "static forwarding table entry for the bridge";
                leaf ifName  {
                    type  cml_data_types:CML_STRING_T;
                    description "";
                } // END of ifName definition.

                leaf-list macAddr  {
                    type  cml_data_types:CML_MAC_ADDR_T;
                    description "";
                } // END of macAddr definition.

                leaf discardForward  {
                    type  cml_data_types:CML_DISCARDFORWARD_T;
                    description "";
                } // END of discardForward definition.

                leaf macAddressTableLearning  {
                    type  cml_data_types:CML_ENABLE_DISABLE_T;
                    default "enable";
                    description "";
                } // END of macAddressTableLearning definition.

                leaf macLimit  {
                    if-feature feature_list:HAVE_CUSTOM_CLI_STYLE;
                    type  cml_data_types:CML_INT32_T;
                    description "";
                } // END of macLimit definition.

                leaf macLimitRange  {
                    if-feature feature_list:HAVE_CUSTOM_CLI_STYLE;
                    type  cml_data_types:CML_INT32_T {
                         range "5..32768";
                    }
                    description "";
                } // END of macLimitRange definition.

            } // End of staticFdb-list

            list oepMapTab {
                if-feature feature_list:HAVE_VLAN;
                key "oepTableName";
                description
                    "oepMapTab";
                leaf oepTableName  {
                    type  cml_data_types:CML_STRING_T;
                    description "";
                } // END of oepTableName definition.

                leaf oepType  {
                    type  cml_data_types:CML_UINT32_T;
                    config false;
                    description "";
                } // END of oepType definition.


                list oepvlan {
                    key "oepId";
                    description
                        "oepvlan";
                    leaf oepvlanTypeId  {
                        type  cml_data_types:CML_OEP_VLAN_TYPE_T;
                        description "";
                    } // END of oepvlanTypeId definition.

                    leaf-list oepvlanId  {
                        type  cml_data_types:CML_UINT16_T;
                        description "";
                    } // END of oepvlanId definition.

                    leaf oepId  {
                        type  cml_data_types:CML_STRING_T;
                        description "";
                    } // END of oepId definition.

                } // End of oepvlan-list
            } // End of oepMapTab-list

            list cvlanRegTab {
                if-feature feature_list:HAVE_VLAN;
                key "tablename";
                description
                    "cvlanRegTab";
                leaf tablename  {
                    type  cml_data_types:CML_STRING_T;
                    description "";
                } // END of tablename definition.


                list svlanReg {
                    if-feature feature_list:HAVE_PROVIDER_BRIDGE;
                    key "svlanRegId";
                    description
                        "svlanReg";
                    leaf svlanRegId  {
                        type  cml_data_types:CML_UINT16_T {
                             range "1..4094";
                        }
                        description "";
                    } // END of svlanRegId definition.


                    list cvlanReg {
                        key "cvlanRegId";
                        description
                            "cvlanReg";
                        leaf cvlanRegId  {
                            type  cml_data_types:CML_RANGE_T;
                            description "";
                        } // END of cvlanRegId definition.

                        leaf cvlanPepConfig  {
                            type  cml_data_types:CML_CVLAN_CONFIG_T;
                            description "";
                        } // END of cvlanPepConfig definition.

                        leaf Tcvid  {
                            type  cml_data_types:CML_UINT16_T {
                                 range "1..4094";
                            }
                            description "";
                        } // END of Tcvid definition.

                        leaf svlanCos  {
                            type  cml_data_types:CML_INT8_T {
                                 range "0..7";
                            }
                            description "";
                        } // END of svlanCos definition.

                        leaf svlanCfi  {
                            type  cml_data_types:CML_INT8_T {
                                 range "0..1";
                            }
                            description "";
                        } // END of svlanCfi definition.

                        leaf cvlanCos  {
                            type  cml_data_types:CML_INT8_T {
                                 range "0..7";
                            }
                            description "";
                        } // END of cvlanCos definition.

                        leaf cvlanCfi  {
                            type  cml_data_types:CML_INT8_T {
                                 range "0..1";
                            }
                            description "";
                        } // END of cvlanCfi definition.

                    } // End of cvlanReg-list
                } // End of svlanReg-list
            } // End of cvlanRegTab-list
            uses bridgeRuntimeAttrs;
            uses vlan-grouping;
            uses nsmEvcInfo-grouping;
            uses nsmOvcInfo-grouping;
            uses ovcVlanType-grouping;
            uses vlanDtag-grouping;
            uses staticMac-grouping;
            uses backboneBridgeInstance-grouping;
            uses mstpbridge-grouping;
            uses backboneBridge-grouping;
            uses evbbridge-grouping;
        } // End of bridge-list
    } // END of bridge-grouping definition.


    grouping spanningTree-grouping {
    description
        "spanningTree";
        list spanningTree {
            if-feature feature_list:HAVE_DEFAULT_BRIDGE;
            key "bridgeId";
            description
                "spanningTree";
            leaf bridgeId  {
                type  cml_data_types:CML_STRING_T;
                description "";
            } // END of bridgeId definition.

            leaf spanningTreeMode  {
                type  cml_data_types:CML_BRIDGE_SPANMODE_T;
                description "";
            } // END of spanningTreeMode definition.

            leaf learning  {
                type  cml_data_types:CML_BOOL_T;
                description "";
            } // END of learning definition.

            leaf edgeFlag  {
                type  cml_data_types:CML_BOOL_T;
                default false;
                description "";
            } // END of edgeFlag definition.


            list staticFdb {
                key "ifName";
                description
                    "static forwarding table entry for the bridge";
                leaf ifName  {
                    type  cml_data_types:CML_STRING_T;
                    description "";
                } // END of ifName definition.

                leaf-list macAddr  {
                    type  cml_data_types:CML_MAC_ADDR_T;
                    description "";
                } // END of macAddr definition.

                leaf discardForward  {
                    type  cml_data_types:CML_DISCARDFORWARD_T;
                    description "";
                } // END of discardForward definition.

                leaf vlanId  {
                    if-feature feature_list:HAVE_PROVIDER_BRIDGE;
                    type  cml_data_types:CML_UINT32_T {
                         range "2..4094";
                    }
                    description "";
                } // END of vlanId definition.

                leaf sVlanId  {
                    if-feature feature_list:HAVE_PROVIDER_BRIDGE;
                    type  cml_data_types:CML_UINT32_T {
                         range "2..4094";
                    }
                    description "";
                } // END of sVlanId definition.

                leaf macAddressTableLearning  {
                    type  cml_data_types:CML_ENABLE_DISABLE_T;
                    default "enable";
                    description "";
                } // END of macAddressTableLearning definition.

                leaf macLimit  {
                    if-feature feature_list:HAVE_CUSTOM_CLI_STYLE;
                    type  cml_data_types:CML_INT32_T;
                    description "";
                } // END of macLimit definition.

                leaf macLimitRange  {
                    if-feature feature_list:HAVE_CUSTOM_CLI_STYLE;
                    type  cml_data_types:CML_INT32_T {
                         range "5..32768";
                    }
                    description "";
                } // END of macLimitRange definition.

            } // End of staticFdb-list

            list spanningTreeinterface {
                key "ifName";
                description
                    " Group of bridge attribute having interface property";
                leaf ifName  {
                    type  cml_data_types:CML_STRING_T;
                    description "";
                } // END of ifName definition.

                leaf spanningState  {
                    type  cml_data_types:CML_SPANNINGTREE_ENABLE_DISABLE_T;
                    default "enable";
                    description "";
                } // END of spanningState definition.

            } // End of spanningTreeinterface-list
            uses bridgeRuntimeAttrs;
            uses mstpSpanningTree-grouping;
        } // End of spanningTree-list
    } // END of spanningTree-grouping definition.
    grouping bridgeRuntimeAttrs {
        description
            "bridgeRuntimeAttrs";
        leaf ageingTime  {
            type  cml_data_types:CML_UINT32_T;
            config false;
            description "";
        } // END of ageingTime definition.

        leaf spanningTreeEnable  {
            type  cml_data_types:CML_UINT32_T;
            config false;
            description "";
        } // END of spanningTreeEnable definition.

        leaf backboneEdge  {
            if-feature feature_list:HAVE_I_BEB;
            if-feature feature_list:HAVE_B_BEB;
            if-feature feature_list:HAVE_UDLD;
            type  cml_data_types:CML_UINT32_T;
            config false;
            description "";
        } // END of backboneEdge definition.

        leaf vlanNumDeletes  {
            if-feature feature_list:HAVE_PROVIDER_BRIDGE;
            type  cml_data_types:CML_UINT32_T;
            config false;
            description "";
        } // END of vlanNumDeletes definition.

        leaf trafficClassEnabled  {
            if-feature feature_list:HAVE_PROVIDER_BRIDGE;
            type  cml_data_types:CML_UINT32_T;
            config false;
            description "";
        } // END of trafficClassEnabled definition.

        leaf numCosq  {
            if-feature feature_list:HAVE_QOS;
            type  cml_data_types:CML_UINT32_T;
            config false;
            description "";
        } // END of numCosq definition.

        leaf maxMstInstances  {
            type  cml_data_types:CML_UINT16_T;
            config false;
            description "";
        } // END of maxMstInstances definition.

        leaf uniTypeMode  {
            type  cml_data_types:CML_UINT16_T;
            config false;
            description "";
        } // END of uniTypeMode definition.

    } // END of bridgeRuntimeAttrs definition.


}
