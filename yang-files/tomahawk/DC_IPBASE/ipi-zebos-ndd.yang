/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-zebos-ndd.yang
*
*/

submodule ipi-zebos-ndd {

    belongs-to  ipi-zebos { prefix ipi-zebos; }

    import cml-data-types {
        prefix cml-data-types;
    }

    import feature-list {
        prefix feature-list;
    }

    organization
        "IP Infusion Inc.";

    contact
        "Address: 3965 Freedom Circle, Suite 200, Santa Clara, CA 95054
        Phone: +1 408-400-1900
        E-mail: support@ipinfusion.com
        Web: http://www.ipinfusion.com/";

    description
        "network device driver";


    revision "2018-06-21" {
        description " Initial Version.";
        reference "";
    }



    grouping ndstaticarpentry-grouping {
    description
        "ndstaticarpentry";
        list ndstaticarpentry {
            if-feature feature-list:HAVE_L3;
            key "ipAddr";
            description
                "ndstaticarpentry";
            leaf ipAddr  {
                type  cml-data-types:CML_IPV4_ADDR_T;
                description "";
            } // END of ipAddr definition.

            leaf vrfName  {
                type  cml-data-types:CML_STRING_T;
                description "";
            } // END of vrfName definition.

            leaf macAddr  {
                type  cml-data-types:CML_MAC_ADDR_T;
                mandatory true;
                description "";
            } // END of macAddr definition.

            leaf proxyArp  {
                type  cml-data-types:CML_BOOL_T;
                mandatory true;
                description "";
            } // END of proxyArp definition.

        } // End of ndstaticarpentry-list
    } // END of ndstaticarpentry-grouping definition.

    grouping  nd_interface-grouping {
    description
        "ndCMLSEPinterface";
    container nd_interface {
        if-feature feature-list:HAVE_L3;
        description
            "ndCMLSEPinterface";
        leaf ipProxyArp  {
            type  cml-data-types:CML_BOOL_T;
            description "";
        } // END of ipProxyArp definition.

        leaf iplocalProxyArp  {
            type  cml-data-types:CML_BOOL_T;
            description "";
        } // END of iplocalProxyArp definition.

        leaf ipRedirects  {
            type  cml-data-types:CML_BOOL_T;
            description "";
        } // END of ipRedirects definition.

        leaf timeout  {
            type  cml-data-types:CML_UINT32_T {
                 range "60..28800";
            }
            default "1500";
            description "";
        } // END of timeout definition.

        leaf arpReachableTime  {
            type  cml-data-types:CML_UINT32_T {
                 range "10..3600";
            }
            default "60";
            description "";
        } // END of arpReachableTime definition.

        leaf ndAgeingTimeout  {
            type  cml-data-types:CML_UINT32_T {
                 range "60..28800";
            }
            default "1500";
            description "";
        } // END of ndAgeingTimeout definition.

        leaf ndReachableTime  {
            type  cml-data-types:CML_UINT32_T {
                 range "10..3600";
            }
            default "60";
            description "";
        } // END of ndReachableTime definition.

        leaf staticArpCount  {
            type  cml-data-types:CML_INT32_T;
            config false;
            description "";
        } // END of staticArpCount definition.


        list staticarpentrylist {
            if-feature feature-list:HAVE_L3;
            key "ipAddress";
            config false;
            description
                "staticarpentrylist";
            leaf ipAddress  {
                type  cml-data-types:CML_STRING_T;
                description "";
            } // END of ipAddress definition.

            leaf macAddress  {
                type  cml-data-types:CML_STRING_T;
                description "";
            } // END of macAddress definition.

            leaf ipisintfdown  {
                type  cml-data-types:CML_IFSTATE_T;
                description "";
            } // END of ipisintfdown definition.

            leaf ipsvioutifindex  {
                type  cml-data-types:CML_UINT32_T;
                description "";
            } // END of ipsvioutifindex definition.

            leaf state  {
                type  cml-data-types:CML_PERMASTATE_T;
                description "";
            } // END of state definition.

        } // End of staticarpentrylist-list
    } // END of nd_interface-container definition.
    } // END of nd_interface-container definition.

    grouping  ndipv6staticnbrentry-grouping {
    description
        "ndipv6staticnbrentry";
    container ndipv6staticnbrentry {
        if-feature feature-list:HAVE_L3;
        description
            "ndipv6staticnbrentry";
        leaf ipv6Addr  {
            type  cml-data-types:CML_IPV6_ADDR_T;
            description "";
        } // END of ipv6Addr definition.

        leaf macAddr  {
            type  cml-data-types:CML_MAC_ADDR_T;
            description "";
        } // END of macAddr definition.

        leaf isintfdown  {
            type  cml-data-types:CML_UINT8_T;
            config false;
            description "";
        } // END of isintfdown definition.

        leaf state  {
            type  cml-data-types:CML_STRING_T;
            config false;
            description "";
        } // END of state definition.

    } // END of ndipv6staticnbrentry-container definition.
    } // END of ndipv6staticnbrentry-container definition.

    grouping  debugndd-grouping {
    description
        "debugndd";
    container debugndd {
        if-feature feature-list:HAVE_L3;
        description
            "debugndd";
        leaf debugIpFlag  {
            type  cml-data-types:CML_DEBUG_EVENT_T;
            description "";
        } // END of debugIpFlag definition.

        leaf debugIpv6  {
            type  cml-data-types:CML_DEBUG_EVENT_T;
            description "";
        } // END of debugIpv6 definition.

    } // END of debugndd-container definition.
    } // END of debugndd-container definition.


}
