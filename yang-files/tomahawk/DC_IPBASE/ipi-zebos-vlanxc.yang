/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-zebos-vlanxc.yang
*
*/

submodule ipi-zebos-vlanxc {

    belongs-to  ipi-zebos { prefix ipi-zebos; }

    import cml-data-types {
        prefix cml-data-types;
    }

    import feature-list {
        prefix feature-list;
    }

    organization
        "IP Infusion Inc.";

    contact
        "Address: 3965 Freedom Circle, Suite 200, Santa Clara, CA 95054
        Phone: +1 408-400-1900
        E-mail: support@ipinfusion.com
        Web: http://www.ipinfusion.com/";

    description
        "VLAN XC Managed Object";


    revision "2019-04-08" {
        description " Initial Version.";
        reference "";
    }



    grouping crossconnect-grouping {
    description
        "list cross-connect's";
        list crossconnect {
            if-feature feature-list:HAVE_VLAN_XC;
            key "xc-name";
            description
                "list cross-connect's";
            leaf xc-name  {
                type  cml-data-types:CML_STRING_T {
                    length "1..255";
                }
                description "";
            } // END of xc-name definition.

            leaf disable  {
                type  cml-data-types:CML_BOOL_T;
                description "";
            } // END of disable definition.


            list vlanep1 {
                key "vlanep1";
                description
                    "vlan cross-connect";
                leaf vlanep1  {
                    type  cml-data-types:CML_STRING_T;
                    description "";
                } // END of vlanep1 definition.


                list vlanep2 {
                    key "vlanep2";
                    description
                        "vlan cross-connect ep2";
                    leaf vlanep2  {
                        type  cml-data-types:CML_STRING_T;
                        description "";
                    } // END of vlanep2 definition.

                    uses vlan-xc-entries-config;
                } // End of vlanep2-list
            } // End of vlanep1-list
            container state {
                config false;
                description
                    "Cross-connect State variables for Ethernet interfaces";
                uses crossconnect-state;
            } // END of state-container definition.
            container config {
                description
                    "Cross-connect Configuration data for ethernet interfaces";
                uses crossconnect-config;
            } // END of config-container definition.
        } // End of crossconnect-list
    } // END of crossconnect-grouping definition.
    grouping vlan-xc-statistics-state {
        description
            "Grouping for VLAN XC entry state";
        leaf ep1-rx-pkts  {
            type  cml-data-types:CML_COUNTER64_T;
            description "The number of packets received on EP1 ";
        } // END of ep1-rx-pkts definition.

        leaf ep1-rx-bytes  {
            type  cml-data-types:CML_COUNTER64_T;
            description " The number of bytes received on EP1 ";
        } // END of ep1-rx-bytes definition.

        leaf ep1-tx-pkts  {
            type  cml-data-types:CML_COUNTER64_T;
            description "The number of packets transmitted from EP1 ";
        } // END of ep1-tx-pkts definition.

        leaf ep1-tx-bytes  {
            type  cml-data-types:CML_COUNTER64_T;
            description " The number of bytes transmitted from EP1 ";
        } // END of ep1-tx-bytes definition.

        leaf ep2-rx-pkts  {
            type  cml-data-types:CML_COUNTER64_T;
            description " The number of packets received on EP2";
        } // END of ep2-rx-pkts definition.

        leaf ep2-rx-bytes  {
            type  cml-data-types:CML_COUNTER64_T;
            description " The number of bytes received on EP2 ";
        } // END of ep2-rx-bytes definition.

        leaf ep2-tx-pkts  {
            type  cml-data-types:CML_COUNTER64_T;
            description " The number of packets transmitted from EP2";
        } // END of ep2-tx-pkts definition.

        leaf ep2-tx-bytes  {
            type  cml-data-types:CML_COUNTER64_T;
            description " The number of bytes transmitted from EP2 ";
        } // END of ep2-tx-bytes definition.

    } // END of vlan-xc-statistics-state definition.
    grouping vlan-xc-entries-config {
        description
            "Grouping for VLAN XC entry config";

        list vlanXcEntries {
            key "outerVlanRange";
            description
                "vlan xc entry list";
            leaf outerVlanRange  {
                type  cml-data-types:CML_STRING_T;
                description "";
            } // END of outerVlanRange definition.

            leaf innerVlanRange  {
                type  cml-data-types:CML_STRING_T;
                description "";
            } // END of innerVlanRange definition.

            container state {
                config false;
                description
                    "Operational state data for XC entry";
                uses vlan-xc-statistics-state;
            } // END of state-container definition.
        } // End of vlanXcEntries-list
    } // END of vlan-xc-entries-config definition.
    grouping crossconnect-config {
        description
            "Grouping for Cross-connect Configuration data for ethernet interfaces";
        leaf portEp1  {
            type  cml-data-types:CML_STRING_T;
            description "";
        } // END of portEp1 definition.

        leaf portEp2  {
            type  cml-data-types:CML_STRING_T;
            description "";
        } // END of portEp2 definition.

        container state {
            config false;
            description
                "Operational state data for XC entry";
            uses vlan-xc-statistics-state;
        } // END of state-container definition.
    } // END of crossconnect-config definition.
    grouping crossconnect-state {
        description
            "Grouping for Cross-connect state variables for ethernet interfaces";
        leaf admin-status  {
            type  cml-data-types:CML_NSM_MPLS_ADMIN_STATUS_T;
            config false;
            description "";
        } // END of admin-status definition.

        leaf oper-status  {
            type  cml-data-types:CML_NSM_MPLS_ADMIN_STATUS_T;
            config false;
            description "";
        } // END of oper-status definition.

    } // END of crossconnect-state definition.


}
