/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-featuredhcp.yang
*
*/

submodule zebos-featuredhcp {

    belongs-to  zebos { prefix zebos; }

    import cml_data_types {
        prefix cml_data_types;
    }

    organization
        "IP Infusion Inc.";

    contact
        "Address: 3965 Freedom Circle, Suite 200, Santa Clara, CA 95054
        Phone: +1 408-400-1900
        E-mail: support@ipinfusion.com
        Web: http://www.ipinfusion.com/";

    description
        "feature_dhcp_configuration";


    revision "2017-05-15" {
        description "Added autopopulate custom tag.";
    }

    revision "2016-12-27" {
        description "Added support for multi module installation.";
    }

    revision "2016-10-28" {
        description "Initial version of featuredhcp datamodel.";
    }


    grouping  featuredhcp-grouping {
    container featuredhcp {
        description
            "featuredhcp";
        leaf dhcp  {
            type  cml_data_types:CML_BOOL_T;
            description "";
        } // END of dhcp definition.

    } // END of featuredhcp-container definition.
    } // END of featuredhcp-container definition.


}
