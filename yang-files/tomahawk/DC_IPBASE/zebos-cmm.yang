/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-cmm.yang
*
*/

submodule zebos-cmm {

    belongs-to  zebos { prefix zebos; }

    import cml_data_types {
        prefix cml_data_types;
    }

    organization
        "IP Infusion Inc.";

    contact
        "Address: 3965 Freedom Circle, Suite 200, Santa Clara, CA 95054
        Phone: +1 408-400-1900
        E-mail: support@ipinfusion.com
        Web: http://www.ipinfusion.com/";

    description
        "Chassis Monitoring Module";


    revision "2018-06-21" {
        description " Initial Version.";
        reference "";
    }



    grouping cmmStackUnitTable-grouping {
    description
        "list of stack units configured in the chassis";
        list cmmStackUnitTable {
            key "cmmStackUnitIndex";
            config false;
            description
                "list of stack units configured in the chassis";
            leaf cmmStackUnitIndex  {
                type  cml_data_types:CML_INT32_T;
                description "The unique index for this entry.Refer to the object cmmStackUnitIndexNext.";
            } // END of cmmStackUnitIndex definition.

            leaf cmmStackUnitModelName  {
                type  cml_data_types:CML_STRING_T;
                description "The plugged-in model ID for this unit. Blank indicates unavailable.";
            } // END of cmmStackUnitModelName definition.

            leaf cmmStackUnitSerialNumber  {
                type  cml_data_types:CML_STRING_T;
                description "The unit's serial number. Blank indicates unavailable.";
            } // END of cmmStackUnitSerialNumber definition.

            leaf cmmStackUnitUpTime  {
                type  cml_data_types:CML_TIMETICKS_T;
                description "The system up time of the unit.";
            } // END of cmmStackUnitUpTime definition.

            leaf cmmStackUnitMfgDate  {
                type  cml_data_types:CML_DATE_TIME_T;
                description "The date the unit is manufactured. Blank indicates unavailable.";
            } // END of cmmStackUnitMfgDate definition.

            leaf cmmStackUnitMacAddress  {
                type  cml_data_types:CML_MAC_ADDRESS_T;
                description "A 6-octet MAC Address assigned to this unit.";
            } // END of cmmStackUnitMacAddress definition.

            leaf cmmStackUnitPartNum  {
                type  cml_data_types:CML_STRING_T;
                description "The unit part number. Blank indicates unavailable";
            } // END of cmmStackUnitPartNum definition.

            leaf cmmStackLabelRevision  {
                type  cml_data_types:CML_STRING_T;
                description "The unit's label Revesion. Blank indicates unavailable";
            } // END of cmmStackLabelRevision definition.

            leaf cmmStackUnitCountryCode  {
                type  cml_data_types:CML_STRING_T;
                description "The unit manufacturer's country code";
            } // END of cmmStackUnitCountryCode definition.

            leaf cmmStackUnitNumFanTrays  {
                type  cml_data_types:CML_INT32_T;
                description "The number of fan trays on the unit.. '-100001' indicates unavailable.";
            } // END of cmmStackUnitNumFanTrays definition.

            leaf cmmStackUnitNumPowerSupplies  {
                type  cml_data_types:CML_INT32_T;
                description "The number of power supplies available to the unit.. '-100001' indicates unavailable.";
            } // END of cmmStackUnitNumPowerSupplies definition.

            leaf cmmStackUnitNumPluggableModules  {
                type  cml_data_types:CML_INT32_T;
                description "The number of pluggable modules in the stack. '-100001' indicates unavailable.";
            } // END of cmmStackUnitNumPluggableModules definition.

            leaf cmmStackUnitNumFastEtherPorts  {
                type  cml_data_types:CML_INT32_T;
                description "The number of 100M Ethernet/802.3 interfaces in this unit. '-100001' indicates unavailable.";
            } // END of cmmStackUnitNumFastEtherPorts definition.

            leaf cmmStackUnitNumGigEtherPorts  {
                type  cml_data_types:CML_INT32_T;
                description "The number of 1G Ethernet/802.3 interfaces in this unit. '-100001' indicates unavailable.";
            } // END of cmmStackUnitNumGigEtherPorts definition.

            leaf cmmStackUnitNum10GigEtherPorts  {
                type  cml_data_types:CML_INT32_T;
                description "The number of 10G Ethernet/802.3 interfaces in this unit. '-100001' indicates unavailable.";
            } // END of cmmStackUnitNum10GigEtherPorts definition.

            leaf cmmStackUnitNum25GigEtherPorts  {
                type  cml_data_types:CML_INT32_T;
                description "The number of 25G Ethernet/802.3 interfaces in this unit. '-100001' indicates unavailable.";
            } // END of cmmStackUnitNum25GigEtherPorts definition.

            leaf cmmStackUnitNum40GigEtherPorts  {
                type  cml_data_types:CML_INT32_T;
                description "The number of 40G Ethernet/802.3 interfaces in this unit. '-100001' indicates unavailable.";
            } // END of cmmStackUnitNum40GigEtherPorts definition.

            leaf cmmStackUnitNum50GigEtherPorts  {
                type  cml_data_types:CML_INT32_T;
                description "The number of 50G Ethernet/802.3 interfaces in this unit. '-100001' indicates unavailable.";
            } // END of cmmStackUnitNum50GigEtherPorts definition.

            leaf cmmStackUnitNum100GigEtherPorts  {
                type  cml_data_types:CML_INT32_T;
                description "The number of 100G Ethernet/802.3 interfaces in this unit. '-100001' indicates unavailable.";
            } // END of cmmStackUnitNum100GigEtherPorts definition.

            leaf cmmStackUnitServiceTag  {
                type  cml_data_types:CML_STRING_T;
                description "The unit's service tag. Blank indicates unavailable.";
            } // END of cmmStackUnitServiceTag definition.

            leaf cmmStackPlatformName  {
                type  cml_data_types:CML_STRING_T;
                description "The unit's Platform Name. Blank indicates unavailable.";
            } // END of cmmStackPlatformName definition.

            leaf cmmStackOnieVersion  {
                type  cml_data_types:CML_STRING_T;
                description "The unit's ONIE Version. Blank indicates unavailable.";
            } // END of cmmStackOnieVersion definition.

            leaf cmmStackMfg  {
                type  cml_data_types:CML_STRING_T;
                description "The unit's Manufacturer Name. Blank indicates unavailable.";
            } // END of cmmStackMfg definition.

            leaf cmmStackVendorName  {
                type  cml_data_types:CML_STRING_T;
                description "The unit's Vendor Name. Blank indicates unavailable.";
            } // END of cmmStackVendorName definition.

            leaf cmmStackDiagVersion  {
                type  cml_data_types:CML_STRING_T;
                description "The unit's Diagnostic Version. Blank indicates unavailable.";
            } // END of cmmStackDiagVersion definition.

            leaf cmmStackCrc32  {
                type  cml_data_types:CML_STRING_T;
                description "The unit's Cyclic Redundancy Check 32 Bit value.";
            } // END of cmmStackCrc32 definition.

            leaf cmmStackUnitSwitchChipRev  {
                type  cml_data_types:CML_STRING_T;
                description "The Unit's Switch Chip Revision. Blank indicates unavailable";
            } // END of cmmStackUnitSwitchChipRev definition.

            leaf cmmStackFanBoardId  {
                type  cml_data_types:CML_STRING_T;
                description "The Unit's Fan Board Id. Blank indicates unavailable.";
            } // END of cmmStackFanBoardId definition.

            leaf cmmStackSupportedLabelRevision  {
                type  cml_data_types:CML_STRING_T;
                description "The unit's supported label Revesion. Blank indicates unavailable";
            } // END of cmmStackSupportedLabelRevision definition.

            leaf cmmStackUnitSupportedSwitchChipRev  {
                type  cml_data_types:CML_STRING_T;
                description "The Unit's Switch Supported Chip Revision. Blank indicates unavailable";
            } // END of cmmStackUnitSupportedSwitchChipRev definition.


            list cmmTransEEPROMTable {
                key "cmmTransIndex";
                config false;
                description
                    "list of transceiver entries EEPROM information in the chassis";
                leaf cmmTransIndex  {
                    type  cml_data_types:CML_UINT32_T;
                    description "A unique index for each slot within the unit.";
                } // END of cmmTransIndex definition.

                leaf cmmTransType  {
                    type  cml_data_types:CML_CMM_TRANS_TYPE_T;
                    description "Type of the transceiver SFP/QSFP.";
                } // END of cmmTransType definition.

                leaf cmmTransNoOfChannels  {
                    type  cml_data_types:CML_INT32_T;
                    description "Number of channels available for this transceiver. '-100001' indicates unavailable.";
                } // END of cmmTransNoOfChannels definition.

                leaf cmmTransidentifier  {
                    type  cml_data_types:CML_CMM_TRANS_IDENTIFIER_T;
                    description "The Type of transceiver present eg:SFP/SFP+/SFP28/QSFP/QSFP+/QSFP28.";
                } // END of cmmTransidentifier definition.

                leaf cmmTransSFPextendedidentifier  {
                    type  cml_data_types:CML_CMM_TRANS_SFP_EXTENDED_IDENTIFIER_T;
                    description "Extended identifier of SFP transceiver for additional information.";
                } // END of cmmTransSFPextendedidentifier definition.

                leaf cmmTransQSFPextendedidentifier  {
                    type  cml_data_types:CML_CMM_QSFP_EXTENDED_IDENTIFIER_T;
                    description "Extended identifier of QSFP transceiver for additional information. null indicates unavailable.";
                } // END of cmmTransQSFPextendedidentifier definition.

                leaf cmmTransconnectortype  {
                    type  cml_data_types:CML_CMM_TRANS_CONNECTOR_TYPE_T;
                    description "Connector type for the transceiver.";
                } // END of cmmTransconnectortype definition.

                leaf cmmTransEthCompliance  {
                    type  cml_data_types:CML_CMM_TRANS_ETH_COMPLIANCE_T;
                    description "Values of Ethernet Compliance codes.";
                } // END of cmmTransEthCompliance definition.

                leaf cmmTransExtEthCompliance  {
                    type  cml_data_types:CML_CMM_TRANS_EXT_ETH_COMPLIANCE_T;
                    description "Bitmap of Extended Ethernet Compliance codes. null indicates unavailable.";
                } // END of cmmTransExtEthCompliance definition.

                leaf cmmTransSonetCompliance  {
                    type  cml_data_types:CML_CMM_TRANS_SONET_COMPLIANCE_T;
                    description "Sonet Compliance codes of transceiver. null indicates unavailable.";
                } // END of cmmTransSonetCompliance definition.

                leaf cmmTransFiberChnlLinkLen  {
                    type  cml_data_types:CML_CMM_TRANS_FIBER_CHANNEL_LINKLEN_T;
                    description "Fibre Channel Link Length. null indicates unavailable.";
                } // END of cmmTransFiberChnlLinkLen definition.

                leaf cmmTransFiberChnlTransTech  {
                    type  cml_data_types:CML_CMM_TRANS_FIBER_CHANNEL_TRANSMITTECH_T;
                    description "Fibre Channel Transmitter Technology. null indicates unavailable.";
                } // END of cmmTransFiberChnlTransTech definition.

                leaf cmmTransFiberChnlTransMedia  {
                    type  cml_data_types:CML_CMM_TRANS_FIBER_CHANNEL_TRANSMITMEDIA_T;
                    description "Fibre Channel Transmission Media. null indicates unavailable.";
                } // END of cmmTransFiberChnlTransMedia definition.

                leaf cmmTransSFPFiberChnlSpeed  {
                    type  cml_data_types:CML_CMM_TRANS_FIBER_CHANNEL_SPEED_T;
                    description "SFP Fibre Channel Speed. null indicates unavailable.";
                } // END of cmmTransSFPFiberChnlSpeed definition.

                leaf cmmTransQSFPFiberChnlSpeed  {
                    type  cml_data_types:CML_CMM_TRANS_FIBER_CHANNEL_SPEED_T;
                    description "QSFP Fibre Channel Speed. null indicates unavailable.";
                } // END of cmmTransQSFPFiberChnlSpeed definition.

                leaf cmmTransSFPInfiniBandCompliance  {
                    type  cml_data_types:CML_CMM_TRANS_SFP_INIFINBAND_COMPLIANCE_T;
                    description "SFP Infiniband Compliance";
                } // END of cmmTransSFPInfiniBandCompliance definition.

                leaf cmmTransSFPEsconCompliance  {
                    type  cml_data_types:CML_CMM_TRANS_SFP_ESCON_COMPLIANCE_T;
                    description "SFP Enterprise Systems Connection compliance.";
                } // END of cmmTransSFPEsconCompliance definition.

                leaf cmmTransSfpPlusCableTech  {
                    type  cml_data_types:CML_CMM_TRANS_SFP_PLUS_CABLE_TECH_T;
                    description "SFP+ Cable Technology";
                } // END of cmmTransSfpPlusCableTech definition.

                leaf cmmTransEncoding  {
                    type  cml_data_types:CML_CMM_TRANS_ENCODING_T;
                    description "Code for high speed serial encoding algorithm";
                } // END of cmmTransEncoding definition.

                leaf cmmTransLengthKmtrs  {
                    type  cml_data_types:CML_INT32_T;
                    units "Km";
                    description "Link length supported for single mode fiber, units of km. '-100001' indicates unavailable.";
                } // END of cmmTransLengthKmtrs definition.

                leaf cmmTransLengthMtrs  {
                    type  cml_data_types:CML_INT32_T;
                    units "100m";
                    description "Link length supported for single mode fiber, units of 100 m. '-100001' indicates unavailable.";
                } // END of cmmTransLengthMtrs definition.

                leaf cmmTransLengthOM1  {
                    type  cml_data_types:CML_INT32_T;
                    units "10m";
                    description "Link length supported for 62.5 um OM1 fiber, units of 10 m. '-100001' indicates unavailable.";
                } // END of cmmTransLengthOM1 definition.

                leaf cmmTransLengthOM2  {
                    type  cml_data_types:CML_INT32_T;
                    units "10m";
                    description "Link length supported for 50 um OM2 fiber, units of 10 m. '-100001' indicates unavailable";
                } // END of cmmTransLengthOM2 definition.

                leaf cmmTransLengthOM3  {
                    type  cml_data_types:CML_INT32_T;
                    units "10m";
                    description "Link length supported for 50 um OM3 fiber, units of 10 m. '-100001' indicates unavailable";
                } // END of cmmTransLengthOM3 definition.

                leaf cmmTransLengthOM4  {
                    type  cml_data_types:CML_INT32_T;
                    units "10m";
                    description "Link length supported for 50 um OM4 fiber, units of 10 m. '-100001' indicates unavailable";
                } // END of cmmTransLengthOM4 definition.

                leaf cmmTransVendorName  {
                    type  cml_data_types:CML_STRING_T;
                    description "Transceiver vendor name. Blank indicates unavailable.";
                } // END of cmmTransVendorName definition.

                leaf cmmTransVendorOUI  {
                    type  cml_data_types:CML_LINE_T;
                    description "SFP vendor IEEE company ID. Blank indicates unavailable.";
                } // END of cmmTransVendorOUI definition.

                leaf cmmTransVendorPartNumber  {
                    type  cml_data_types:CML_LINE_T;
                    description "Part number provided by Tranceiver vendor. Blank indicates unavailable.";
                } // END of cmmTransVendorPartNumber definition.

                leaf cmmTransVendorRevision  {
                    type  cml_data_types:CML_STRING_T;
                    description "Revision level for part number provided by vendor. Blank indicates unavailable.";
                } // END of cmmTransVendorRevision definition.

                leaf cmmTransCheckCode  {
                    type  cml_data_types:CML_STRING_T;
                    description "Check code for Base ID Fields. Blank indicates unavailable.";
                } // END of cmmTransCheckCode definition.

                leaf cmmTransCheckCodeExtended  {
                    type  cml_data_types:CML_STRING_T;
                    description "Check code for the Extended ID Fields. Blank indicates unavailable.";
                } // END of cmmTransCheckCodeExtended definition.

                leaf cmmTransNominalBitRate  {
                    type  cml_data_types:CML_INT32_T;
                    units "100MBd";
                    description "Nominal signalling rate, units of 100MBd. '-100001' indicates unavailable.";
                } // END of cmmTransNominalBitRate definition.

                leaf cmmTransBitRateMax  {
                    type  cml_data_types:CML_INT32_T;
                    description "Upper bit rate margin, units of 1% above the Nominal Bit Rate. '-100001' indicates unavailable. '-100002' indicates not-applicable.";
                } // END of cmmTransBitRateMax definition.

                leaf cmmTransBitRateMin  {
                    type  cml_data_types:CML_INT32_T;
                    description "Lower bit rate margin, units of 1% below the Nominal Bit Rate. '-100001' indicates unavailable. '-100002' indicates not-applicable.";
                } // END of cmmTransBitRateMin definition.

                leaf cmmTransVendorSerialNumber  {
                    type  cml_data_types:CML_STRING_T;
                    description "Serial number provided by vendor. Blank indicates unavailable.";
                } // END of cmmTransVendorSerialNumber definition.

                leaf cmmTransDateCode  {
                    type  cml_data_types:CML_STRING_T;
                    description "Vendor's manufacturing date code. Blank indicates unavailable.";
                } // END of cmmTransDateCode definition.

                leaf cmmTransDDMSupport  {
                    type  cml_data_types:CML_CMM_TRANS_DDM_SUPPORT_T;
                    description "Indicates which type of diagnostic monitoring is implemented";
                } // END of cmmTransDDMSupport definition.

                leaf cmmTransMaxCaseTemp  {
                    type  cml_data_types:CML_FLOAT_T;
                    units "C";
                    description "Maximum case temperature in Celsius. '-1000.01' indicates unavailable. '-1000.02' indicates not-applicable.";
                } // END of cmmTransMaxCaseTemp definition.

                leaf cmmTransSFPOptionsImp  {
                    type  cml_data_types:CML_CMM_TRANS_SFP_OPTIONS_IMPLEMENTED_T;
                    description "Transceiver Options Implemented for SFP Transceiver. null indicates unavailable.";
                } // END of cmmTransSFPOptionsImp definition.

                leaf cmmTransQSFPOptionsImp  {
                    type  cml_data_types:CML_CMM_TRANS_QSFP_OPTIONS_IMPLEMENTED_T;
                    description "Transceiver Options Implemented for QSFP Transceiver null indicates unavailable..";
                } // END of cmmTransQSFPOptionsImp definition.

                leaf cmmTransPresence  {
                    type  cml_data_types:CML_CMM_TRANS_PRESENCE_T;
                    description "Indicates Transceiver presence status.";
                } // END of cmmTransPresence definition.


                list cmmTransDDMTable {
                    key "cmmTransChannelIndex";
                    config false;
                    description
                        "Information about Digital Optical Monitoring for each interface per channel.";
                    leaf cmmTransChannelIndex  {
                        type  cml_data_types:CML_UINT8_T;
                        description "A unique value, greater than zero, for each channel in the transceiver within the unit.For SFP transceivers, only channel '1' is applicable.";
                    } // END of cmmTransChannelIndex definition.

                    leaf cmmTransTemperature  {
                        type  cml_data_types:CML_FLOAT_T;
                        units "C";
                        description "Internally measured temperature of the transceiver.This is common across channels for a transceiver. '-1000.01' indicates unavailable";
                    } // END of cmmTransTemperature definition.

                    leaf cmmTransTempCriticalThresholdMin  {
                        type  cml_data_types:CML_FLOAT_T;
                        units "C";
                        description "Min Alarm Threshold temperature of the transceiver.This is common across channels for a transceiver. '-1000.01' indicates unavailable.";
                    } // END of cmmTransTempCriticalThresholdMin definition.

                    leaf cmmTransTempCriticalThresholdMax  {
                        type  cml_data_types:CML_FLOAT_T;
                        units "C";
                        description "Max Alarm Threshold temperature of the transceiver.This is common across channels for a transceiver. '-1000.01' indicates unavailable.";
                    } // END of cmmTransTempCriticalThresholdMax definition.

                    leaf cmmTransTempAlertThresholdMin  {
                        type  cml_data_types:CML_FLOAT_T;
                        units "C";
                        description "Min Alert Threshold temperature of the transceiver.This is common across channels for a transceiver. '-1000.01' indicates unavailable.";
                    } // END of cmmTransTempAlertThresholdMin definition.

                    leaf cmmTransTempAlertThresholdMax  {
                        type  cml_data_types:CML_FLOAT_T;
                        units "C";
                        description "Max Alert Threshold temperature of the transceiver.This is common across channels for a transceiver. '-1000.01' indicates unavailable.";
                    } // END of cmmTransTempAlertThresholdMax definition.

                    leaf cmmTransVoltage  {
                        type  cml_data_types:CML_FLOAT_PRECISION_3_T;
                        units "V";
                        description "Internally measured supply voltage of the transceiver.This is common across channels for a transceiver. '-100.001' indicates unavailable.";
                    } // END of cmmTransVoltage definition.

                    leaf cmmTransVoltCriticalThresholdMin  {
                        type  cml_data_types:CML_FLOAT_PRECISION_3_T;
                        units "V";
                        description "Min Alarm Threshold voltage of the transceiver.This is common across channels for a transceiver. '-100.001' indicates unavailable.";
                    } // END of cmmTransVoltCriticalThresholdMin definition.

                    leaf cmmTransVoltCriticalThresholdMax  {
                        type  cml_data_types:CML_FLOAT_PRECISION_3_T;
                        units "V";
                        description "Max Alarm Threshold voltage of the transceiver.This is common across channels for a transceiver. '-100.001' indicates unavailable.";
                    } // END of cmmTransVoltCriticalThresholdMax definition.

                    leaf cmmTransVoltAlertThresholdMin  {
                        type  cml_data_types:CML_FLOAT_PRECISION_3_T;
                        units "V";
                        description "Min Alert Threshold voltage of the transceiver.This is common across channels for a transceiver. '-100.001' indicates unavailable.";
                    } // END of cmmTransVoltAlertThresholdMin definition.

                    leaf cmmTransVoltAlertThresholdMax  {
                        type  cml_data_types:CML_FLOAT_PRECISION_3_T;
                        units "V";
                        description "Max Alert Threshold voltage of the transceiver.This is common across channels for a transceiver. '-100.001' indicates unavailable.";
                    } // END of cmmTransVoltAlertThresholdMax definition.

                    leaf cmmTransLaserBiasCurrent  {
                        type  cml_data_types:CML_FLOAT_PRECISION_3_T;
                        units "mA";
                        description "Internally measured TX Bias Current in Channel of transceiver. '-100.001' indicates unavailable.";
                    } // END of cmmTransLaserBiasCurrent definition.

                    leaf cmmTransLaserBiasCurrCriticalThresholdMin  {
                        type  cml_data_types:CML_FLOAT_PRECISION_3_T;
                        units "mA";
                        description "Min Alarm Threshold of Laser Bias Current per channel. '-100.001' indicates unavailable.";
                    } // END of cmmTransLaserBiasCurrCriticalThresholdMin definition.

                    leaf cmmTransLaserBiasCurrCriticalThresholdMax  {
                        type  cml_data_types:CML_FLOAT_PRECISION_3_T;
                        units "mA";
                        description "Max Alarm Threshold of Laser Bias Current per channel. '-100.001' indicates unavailable.";
                    } // END of cmmTransLaserBiasCurrCriticalThresholdMax definition.

                    leaf cmmTransLaserBiasCurrAlertThresholdMin  {
                        type  cml_data_types:CML_FLOAT_PRECISION_3_T;
                        units "mA";
                        description "Min Alert Threshold of Laser Bias Current per channel. '-100.001' indicates unavailable.";
                    } // END of cmmTransLaserBiasCurrAlertThresholdMin definition.

                    leaf cmmTransLaserBiasCurrAlertThresholdMax  {
                        type  cml_data_types:CML_FLOAT_PRECISION_3_T;
                        units "mA";
                        description "Max Alert Threshold of Laser Bias Current per channel. '-100.001' indicates unavailable.";
                    } // END of cmmTransLaserBiasCurrAlertThresholdMax definition.

                    leaf cmmTransTxPower  {
                        type  cml_data_types:CML_FLOAT_PRECISION_3_T;
                        units "dBm";
                        description "Measured TX output power in Channel of transceiver.'-100' value represents no power. '-100.001' indicates unavailable.";
                    } // END of cmmTransTxPower definition.

                    leaf cmmTransTxPowerCriticalThresholdMin  {
                        type  cml_data_types:CML_FLOAT_PRECISION_3_T;
                        units "dBm";
                        description "Min Alarm Threshold of TxOutput Power per channel.'-100' value represents no power. '-100.001' indicates unavailable.";
                    } // END of cmmTransTxPowerCriticalThresholdMin definition.

                    leaf cmmTransTxPowerCriticalThresholdMax  {
                        type  cml_data_types:CML_FLOAT_PRECISION_3_T;
                        units "dBm";
                        description "Max Alarm Threshold of TxOutput Power per channel.'-100' value represents no power. '-100.001' indicates unavailable.";
                    } // END of cmmTransTxPowerCriticalThresholdMax definition.

                    leaf cmmTransTxPowerAlertThresholdMin  {
                        type  cml_data_types:CML_FLOAT_PRECISION_3_T;
                        units "dBm";
                        description "Min Alert Threshold of TxOutput Power per channel.'-100' value represents no power. '-100.001' indicates unavailable.";
                    } // END of cmmTransTxPowerAlertThresholdMin definition.

                    leaf cmmTransTxPowerAlertThresholdMax  {
                        type  cml_data_types:CML_FLOAT_PRECISION_3_T;
                        units "dBm";
                        description "Max Alert Threshold of TxOutput Power per channel.'-100' value represents no power. '-100.001' indicates unavailable.";
                    } // END of cmmTransTxPowerAlertThresholdMax definition.

                    leaf cmmTransRxPower  {
                        type  cml_data_types:CML_FLOAT_PRECISION_3_T;
                        units "dBm";
                        description "Measured RX input power in Channel of transceiver.'-100' value represents no power. '-100.001' indicates unavailable.";
                    } // END of cmmTransRxPower definition.

                    leaf cmmTransRxPowerCriticalThresholdMin  {
                        type  cml_data_types:CML_FLOAT_PRECISION_3_T;
                        units "dBm";
                        description "Min Alarm Threshold value of Rx Input Power per channel.'-100' value represents no power. '-100.001' indicates unavailable.";
                    } // END of cmmTransRxPowerCriticalThresholdMin definition.

                    leaf cmmTransRxPowerCriticalThresholdMax  {
                        type  cml_data_types:CML_FLOAT_PRECISION_3_T;
                        units "dBm";
                        description "Max Alarm Threshold value of Rx Input Power per channel.'-100' value represents no power. '-100.001' indicates unavailable.";
                    } // END of cmmTransRxPowerCriticalThresholdMax definition.

                    leaf cmmTransRxPowerAlertThresholdMin  {
                        type  cml_data_types:CML_FLOAT_PRECISION_3_T;
                        units "dBm";
                        description "Min Alert Threshold value of Rx Input Power per channel.'-100' value represents no power. '-100.001' indicates unavailable.";
                    } // END of cmmTransRxPowerAlertThresholdMin definition.

                    leaf cmmTransRxPowerAlertThresholdMax  {
                        type  cml_data_types:CML_FLOAT_PRECISION_3_T;
                        units "dBm";
                        description "Max Alert Threshold value of Rx Input Power per channel.'-100' value represents no power. '-100.001' indicates unavailable.";
                    } // END of cmmTransRxPowerAlertThresholdMax definition.

                    leaf cmmTransTxPowerSupported  {
                        type  cml_data_types:CML_CMM_TRANS_TX_RX_POWER_SUPPORTED_T;
                        description "Value represents Transceiver TxPower supported or not.";
                    } // END of cmmTransTxPowerSupported definition.

                    leaf cmmTransRxPowerSupported  {
                        type  cml_data_types:CML_CMM_TRANS_TX_RX_POWER_SUPPORTED_T;
                        description "Value represents Transceiver RxPower supported or not.";
                    } // END of cmmTransRxPowerSupported definition.

                    leaf cmmTransDDMStatus  {
                        type  cml_data_types:CML_CMM_TRANS_DDM_STATUS_T;
                        description "Value represents Transceiver ddm status";
                    } // END of cmmTransDDMStatus definition.

                    leaf cmmTransTxState  {
                        type  cml_data_types:CML_CMM_TRANS_TX_RX_STATE_T;
                        description "Transceiver TX State";
                    } // END of cmmTransTxState definition.

                    leaf cmmTransRxLosState  {
                        type  cml_data_types:CML_CMM_TRANS_TX_RX_STATE_T;
                        description "Transceiver Rx Los State";
                    } // END of cmmTransRxLosState definition.

                    leaf cmmTransTxLosState  {
                        type  cml_data_types:CML_CMM_TRANS_TX_RX_STATE_T;
                        description "Transceiver TX Los State (applicable only for QSFP).";
                    } // END of cmmTransTxLosState definition.

                    leaf cmmTransResetState  {
                        type  cml_data_types:CML_CMM_TRANS_RESET_STATE_T;
                        description "Transceiver Reset State (applicable only for QSFP).";
                    } // END of cmmTransResetState definition.

                    leaf cmmTransPowerMode  {
                        type  cml_data_types:CML_CMM_TRANS_POWER_MODE_T;
                        description "Transceiver Power mode (applicable only for QSFP).";
                    } // END of cmmTransPowerMode definition.

                    leaf cmmTransPreFecBerVal  {
                        type  cml_data_types:CML_STRING_T;
                        units "ber/ms";
                        description "Forward error correction bit error rate value, -100002' indicates not-applicable";
                    } // END of cmmTransPreFecBerVal definition.

                    leaf cmmTransPreFecBerAlertMax  {
                        type  cml_data_types:CML_STRING_T;
                        units "ber/ms";
                        description "Max alert value for pre-forward error correction ber, -100002' indicates not-applicable";
                    } // END of cmmTransPreFecBerAlertMax definition.

                    leaf cmmTransPreFecBerAlertMin  {
                        type  cml_data_types:CML_STRING_T;
                        units "ber/ms";
                        description "Min alert value for pre-forward error correction ber, -100002' indicates not-applicable";
                    } // END of cmmTransPreFecBerAlertMin definition.

                    leaf cmmTransPreFecBerCriticMax  {
                        type  cml_data_types:CML_STRING_T;
                        units "ber/ms";
                        description "Max critical value for pre-forward error correction ber, -100002' indicates not-applicable";
                    } // END of cmmTransPreFecBerCriticMax definition.

                    leaf cmmTransPreFecBerCriticMin  {
                        type  cml_data_types:CML_STRING_T;
                        units "ber/ms";
                        description "Min critical value for pre-forward error correction ber, -100002' indicates not-applicable";
                    } // END of cmmTransPreFecBerCriticMin definition.

                    leaf cmmTransUncorrectedBerVal  {
                        type  cml_data_types:CML_STRING_T;
                        units "ber/ms";
                        description "Frame error rate value, -100002' indicates not-applicable";
                    } // END of cmmTransUncorrectedBerVal definition.

                    leaf cmmTransUncorrectedBerValAlertMax  {
                        type  cml_data_types:CML_STRING_T;
                        units "ber/ms";
                        description "Max alert value for Uncorrected BER, -100002' indicates not-applicable";
                    } // END of cmmTransUncorrectedBerValAlertMax definition.

                    leaf cmmTransUncorrectedBerValAlertMin  {
                        type  cml_data_types:CML_STRING_T;
                        units "ber/ms";
                        description "Min alert value for Uncorrected BER, -100002' indicates not-applicable";
                    } // END of cmmTransUncorrectedBerValAlertMin definition.

                    leaf cmmTransUncorrectedBerValCriticMax  {
                        type  cml_data_types:CML_STRING_T;
                        units "ber/ms";
                        description "Max critical value for Uncorrected BER, -100002' indicates not-applicable";
                    } // END of cmmTransUncorrectedBerValCriticMax definition.

                    leaf cmmTransUncorrectedBerValCriticMin  {
                        type  cml_data_types:CML_STRING_T;
                        units "ber/ms";
                        description "Min critical value for Uncorrected BER, -100002' indicates not-applicable";
                    } // END of cmmTransUncorrectedBerValCriticMin definition.

                    leaf cmmTransSnrVal  {
                        type  cml_data_types:CML_FLOAT_PRECISION_3_T;
                        units "dBm";
                        description "Signal to noise ratio on ingress lane, -100002' indicates not-applicable";
                    } // END of cmmTransSnrVal definition.

                    leaf cmmTransSnrAlertMax  {
                        type  cml_data_types:CML_FLOAT_PRECISION_3_T;
                        units "dBm";
                        description "Max alert value for signal-to-noise ratio on ingress lane, -100002' indicates not-applicable";
                    } // END of cmmTransSnrAlertMax definition.

                    leaf cmmTransSnrAlertMin  {
                        type  cml_data_types:CML_FLOAT_PRECISION_3_T;
                        units "dBm";
                        description "Min alert value for signal-to-noise ratio on ingress lane, -100002' indicates not-applicable";
                    } // END of cmmTransSnrAlertMin definition.

                    leaf cmmTransSnrCriticMax  {
                        type  cml_data_types:CML_FLOAT_PRECISION_3_T;
                        units "dBm";
                        description "Max critical value for signal-to-noise ratio on ingress lane, -100002' indicates not-applicable";
                    } // END of cmmTransSnrCriticMax definition.

                    leaf cmmTransSnrCriticMin  {
                        type  cml_data_types:CML_FLOAT_PRECISION_3_T;
                        units "dBm";
                        description "Min critical value for signal-to-noise ratio on ingress lane, -100002' indicates not-applicable";
                    } // END of cmmTransSnrCriticMin definition.

                    leaf cmmTransResIsiVal  {
                        type  cml_data_types:CML_FLOAT_PRECISION_3_T;
                        units "ps/nm";
                        description "Residual-isi value, -100002' indicates not-applicable";
                    } // END of cmmTransResIsiVal definition.

                    leaf cmmTransResIsiAlertMax  {
                        type  cml_data_types:CML_FLOAT_PRECISION_3_T;
                        units "ps/nm";
                        description "Max alert value for residual-isi, -100002' indicates not-applicable";
                    } // END of cmmTransResIsiAlertMax definition.

                    leaf cmmTransResIsiAlertMin  {
                        type  cml_data_types:CML_FLOAT_PRECISION_3_T;
                        units "ps/nm";
                        description "Min alert value for residual-isi, -100002' indicates not-applicable";
                    } // END of cmmTransResIsiAlertMin definition.

                    leaf cmmTransResIsiCriticMax  {
                        type  cml_data_types:CML_FLOAT_PRECISION_3_T;
                        units "ps/nm";
                        description "Max critical value for residual-isi, -100002' indicates not-applicable";
                    } // END of cmmTransResIsiCriticMax definition.

                    leaf cmmTransResIsiCriticMin  {
                        type  cml_data_types:CML_FLOAT_PRECISION_3_T;
                        units "ps/nm";
                        description "Min critical value for residual-isi, -100002' indicates not-applicable";
                    } // END of cmmTransResIsiCriticMin definition.

                    leaf cmmTransLvlTransVal  {
                        type  cml_data_types:CML_FLOAT_PRECISION_3_T;
                        description "Level transition value, -100002' indicates not-applicable";
                    } // END of cmmTransLvlTransVal definition.

                    leaf cmmTransLvlTransAlertMax  {
                        type  cml_data_types:CML_FLOAT_PRECISION_3_T;
                        description "Max alert value for level transition, -100002' indicates not-applicable";
                    } // END of cmmTransLvlTransAlertMax definition.

                    leaf cmmTransLvlTransAlertMin  {
                        type  cml_data_types:CML_FLOAT_PRECISION_3_T;
                        description "Min alert value for level transition, -100002' indicates not-applicable";
                    } // END of cmmTransLvlTransAlertMin definition.

                    leaf cmmTransLvlTransCriticMax  {
                        type  cml_data_types:CML_FLOAT_PRECISION_3_T;
                        description "Max critical value for level transition, -100002' indicates not-applicable";
                    } // END of cmmTransLvlTransCriticMax definition.

                    leaf cmmTransLvlTransCriticMin  {
                        type  cml_data_types:CML_FLOAT_PRECISION_3_T;
                        description "Min critical value for level transition, -100002' indicates not-applicable";
                    } // END of cmmTransLvlTransCriticMin definition.

                    leaf cmmTransTecCurrErrVal  {
                        type  cml_data_types:CML_FLOAT_PRECISION_3_T;
                        units "mA";
                        description "Thermo-elecrical cooler current value, -100002' indicates not-applicable";
                    } // END of cmmTransTecCurrErrVal definition.

                    leaf cmmTransTecCurrErrAlertMax  {
                        type  cml_data_types:CML_FLOAT_PRECISION_3_T;
                        units "mA";
                        description "Max alert value for thermo-elecrical cooler current, -100002' indicates not-applicable";
                    } // END of cmmTransTecCurrErrAlertMax definition.

                    leaf cmmTransTecCurrErrAlertMin  {
                        type  cml_data_types:CML_FLOAT_PRECISION_3_T;
                        units "mA";
                        description "Min alert value for thermo-elecrical cooler current, -100002' indicates not-applicable";
                    } // END of cmmTransTecCurrErrAlertMin definition.

                    leaf cmmTransTecCurrErrCriticMax  {
                        type  cml_data_types:CML_FLOAT_PRECISION_3_T;
                        units "mA";
                        description "Max critical value for thermo-elecrical cooler current, -100002' indicates not-applicable";
                    } // END of cmmTransTecCurrErrCriticMax definition.

                    leaf cmmTransTecCurrErrCriticMin  {
                        type  cml_data_types:CML_FLOAT_PRECISION_3_T;
                        units "mA";
                        description "Min critical value for thermo-elecrical cooler current, -100002' indicates not-applicable";
                    } // END of cmmTransTecCurrErrCriticMin definition.

                    leaf cmmTransLaserTempVal  {
                        type  cml_data_types:CML_FLOAT_PRECISION_3_T;
                        units "C";
                        description "Laser Temparature value, -100002' indicates not-applicable";
                    } // END of cmmTransLaserTempVal definition.

                    leaf cmmTransLaserTempAlertMax  {
                        type  cml_data_types:CML_FLOAT_PRECISION_3_T;
                        units "C";
                        description "Max alert value for Laser Temperature, -100002' indicates not-applicable";
                    } // END of cmmTransLaserTempAlertMax definition.

                    leaf cmmTransLaserTempAlertMin  {
                        type  cml_data_types:CML_FLOAT_PRECISION_3_T;
                        units "C";
                        description "Min alert value for Laser Temperature, -100002' indicates not-applicable";
                    } // END of cmmTransLaserTempAlertMin definition.

                    leaf cmmTransLaserTempCriticMax  {
                        type  cml_data_types:CML_FLOAT_PRECISION_3_T;
                        units "C";
                        description "Max critical value for Laser Temperature, -100002' indicates not-applicable";
                    } // END of cmmTransLaserTempCriticMax definition.

                    leaf cmmTransLaserTempCriticMin  {
                        type  cml_data_types:CML_FLOAT_PRECISION_3_T;
                        units "C";
                        description "Min critical value for Laser Temperature, -100002' indicates not-applicable";
                    } // END of cmmTransLaserTempCriticMin definition.

                } // End of cmmTransDDMTable-list
            } // End of cmmTransEEPROMTable-list

            list cmmSysPowerSupplyTable {
                key "cmmSysPSUIndex";
                config false;
                description
                    "list of power supply resident in the chassis";
                leaf cmmSysPSUIndex  {
                    type  cml_data_types:CML_INT32_T;
                    description "The unique index of the power supply.";
                } // END of cmmSysPSUIndex definition.

                container cmmSysPSUTable {
                    config false;
                    description
                        "list of power supply information resident in the chassis";
                    leaf cmmSysPowerSupplyOperStatus  {
                        type  cml_data_types:CML_CMM_POWER_SUPPLY_OPERSTATUS_T;
                        description "The status of the power supply.";
                    } // END of cmmSysPowerSupplyOperStatus definition.

                    leaf cmmSysPowerSupplyType  {
                        type  cml_data_types:CML_CMM_POWER_SUPPLY_TYPE_T;
                        description "The type of the power supply.";
                    } // END of cmmSysPowerSupplyType definition.

                    leaf cmmSysHotSwapStat  {
                        type  cml_data_types:CML_CMM_POWER_RAIL_T;
                        description "Power status for HOT SWAP";
                    } // END of cmmSysHotSwapStat definition.

                    leaf cmmSysPSConsumption  {
                        type  cml_data_types:CML_FLOAT_T;
                        units "W";
                        description "Output Power of Power supply. '-1000.01' indicates unavailable.";
                    } // END of cmmSysPSConsumption definition.

                    leaf cmmSysInputPower  {
                        type  cml_data_types:CML_FLOAT_T;
                        units "W";
                        description "Input Power of Power supply. '-1000.01' indicates unavailable.";
                    } // END of cmmSysInputPower definition.

                    leaf cmmSysInputVoltage  {
                        type  cml_data_types:CML_FLOAT_T;
                        units "V";
                        description "Input Voltage of Power supply. '-1000.01' indicates unavailable.";
                    } // END of cmmSysInputVoltage definition.

                    leaf cmmSysOutputVoltage  {
                        type  cml_data_types:CML_FLOAT_T;
                        units "V";
                        description "Output Voltage of Power supply. '-1000.01' indicates unavailable.";
                    } // END of cmmSysOutputVoltage definition.

                    leaf cmmSysInputCurrent  {
                        type  cml_data_types:CML_FLOAT_T;
                        units "A";
                        description "Input Current of Power supply. '-1000.01' indicates unavailable.";
                    } // END of cmmSysInputCurrent definition.

                    leaf cmmSysOutputCurrent  {
                        type  cml_data_types:CML_FLOAT_T;
                        units "A";
                        description "Output Current of Power supply. '-1000.01' indicates unavailable.";
                    } // END of cmmSysOutputCurrent definition.

                    leaf cmmSysPSTemperature1  {
                        type  cml_data_types:CML_FLOAT_T;
                        units "C";
                        description "Temperature of Power supply sensor1. '-1000.01' indicates unavailable.";
                    } // END of cmmSysPSTemperature1 definition.

                    leaf cmmSysPSTemperature2  {
                        type  cml_data_types:CML_FLOAT_T;
                        units "C";
                        description "Temperature of Power supply sensor2. '-1000.01' indicates unavailable.";
                    } // END of cmmSysPSTemperature2 definition.

                    leaf cmmSysPSFan1Rpm  {
                        type  cml_data_types:CML_INT32_T;
                        description "Fan1 rpm of Power supply. '-100001' indicates unavailable.";
                    } // END of cmmSysPSFan1Rpm definition.

                    leaf cmmSysPSFan2Rpm  {
                        type  cml_data_types:CML_INT32_T;
                        description "Fan2 rpm of Power supply. '-100001' indicates unavailable. '-100002' indicates notapplicable";
                    } // END of cmmSysPSFan2Rpm definition.

                    leaf cmmSysPS12VPg  {
                        type  cml_data_types:CML_CMM_POWER_RAIL_T;
                        description "Status of Output Power";
                    } // END of cmmSysPS12VPg definition.

                    leaf cmmSysPSAcAlert  {
                        type  cml_data_types:CML_CMM_POWER_RAIL_T;
                        description "Status of Input Power";
                    } // END of cmmSysPSAcAlert definition.

                    leaf cmmSysPSParamsSupport  {
                        type  cml_data_types:CML_CMM_PSU_PMBUS_PARAM_SUPPORT_T;
                        description "Bitmap of supported paramaters of PSU Unit. 0 - not supported (values only for information). 1 - supported (values can be used for monitoring). null indicates unsupported.";
                    } // END of cmmSysPSParamsSupport definition.

                } // END of cmmSysPSUTable-container definition.
                container cmmPsuFruTable {
                    config false;
                    description
                        "list of power supply fru information resident in the chassis";
                    leaf cmmPsuPpid  {
                        type  cml_data_types:CML_STRING_T;
                        description "The unique ppid of the power supply. Blank indicates unavailable.";
                    } // END of cmmPsuPpid definition.

                    leaf cmmPsuCountryofOrigin  {
                        type  cml_data_types:CML_STRING_T;
                        description "PSU Country of Origin. Blank indicates unavailable.";
                    } // END of cmmPsuCountryofOrigin definition.

                    leaf cmmPsuPpidPartNum  {
                        type  cml_data_types:CML_STRING_T;
                        description "PSU PPID Part Number. Blank indicates unavailable.";
                    } // END of cmmPsuPpidPartNum definition.

                    leaf cmmPsuPpidPartNumRev  {
                        type  cml_data_types:CML_STRING_T;
                        description "PSU PPID Part Number Rev. Blank indicates unavailable.";
                    } // END of cmmPsuPpidPartNumRev definition.

                    leaf cmmPsuManufactureId  {
                        type  cml_data_types:CML_LINE_T;
                        description "PSU Manufacturer ID. Blank indicates unavailable.";
                    } // END of cmmPsuManufactureId definition.

                    leaf cmmPsuDateCode  {
                        type  cml_data_types:CML_STRING_T;
                        description "PSU Date Code. Blank indicates unavailable.";
                    } // END of cmmPsuDateCode definition.

                    leaf cmmPsuSerialNumber  {
                        type  cml_data_types:CML_STRING_T;
                        description "PSU Date Code. Blank indicates unavailable.";
                    } // END of cmmPsuSerialNumber definition.

                    leaf cmmPsuPartNum  {
                        type  cml_data_types:CML_STRING_T;
                        description "PSU Part Number. Blank indicates unavailable.";
                    } // END of cmmPsuPartNum definition.

                    leaf cmmPsuPartNumRev  {
                        type  cml_data_types:CML_STRING_T;
                        description "PSU Part Num Rev. Blank indicates unavailable.";
                    } // END of cmmPsuPartNumRev definition.

                    leaf cmmPsuNumOfFanPerTray  {
                        type  cml_data_types:CML_INT32_T;
                        description "Number of Fans in the tray in PSU. '-100001' indicates unavailable.";
                    } // END of cmmPsuNumOfFanPerTray definition.

                    leaf cmmPsuType  {
                        type  cml_data_types:CML_UINT8_T;
                        description "The Type of PSU.";
                    } // END of cmmPsuType definition.

                    leaf cmmPsuServiceTag  {
                        type  cml_data_types:CML_STRING_T;
                        description "PSU Service Tag. Blank indicates unavailable.";
                    } // END of cmmPsuServiceTag definition.

                    leaf cmmPsuIanaNum  {
                        type  cml_data_types:CML_STRING_T;
                        description "PSU IANA Num. Blank indicates unavailable.";
                    } // END of cmmPsuIanaNum definition.

                    leaf cmmPsuFanMaxRpm  {
                        type  cml_data_types:CML_INT32_T;
                        description "PSU Fan Max RPM. '-100001' indicates unavailable.";
                    } // END of cmmPsuFanMaxRpm definition.

                    leaf cmmPsuAirFlowDir  {
                        type  cml_data_types:CML_STRING_T;
                        description "PSU Air Flow Direction.";
                    } // END of cmmPsuAirFlowDir definition.

                    leaf cmmPsuMaxOutputWatt  {
                        type  cml_data_types:CML_INT32_T;
                        description "PSU Max Output Watts.";
                    } // END of cmmPsuMaxOutputWatt definition.

                } // END of cmmPsuFruTable-container definition.
            } // End of cmmSysPowerSupplyTable-list

            list cmmFanTrayTable {
                key "cmmFanTrayNumber";
                config false;
                description
                    "list of fan tray details resident in the chassis";
                leaf cmmFanTrayNumber  {
                    type  cml_data_types:CML_INT8_T;
                    description "Value represents the fan tray Number.";
                } // END of cmmFanTrayNumber definition.


                list cmmFanTable {
                    key "cmmFanIndex";
                    config false;
                    description
                        "list of fan details resident in the chassis";
                    leaf cmmFanIndex  {
                        type  cml_data_types:CML_INT8_T;
                        description "Index of the fan per fantray.";
                    } // END of cmmFanIndex definition.

                    leaf cmmFanRpm  {
                        type  cml_data_types:CML_INT32_T;
                        description "Value represents the fan rpm. '-100001' indicates unavailable.";
                    } // END of cmmFanRpm definition.

                    leaf cmmFanRpmMin  {
                        type  cml_data_types:CML_INT32_T;
                        description "Value represents the minimum supported RPM of fan. '-100001' indicates unavailable.";
                    } // END of cmmFanRpmMin definition.

                    leaf cmmFanRpmMax  {
                        type  cml_data_types:CML_INT32_T;
                        description "Value represents the maximum supported RPM of fan. '-100001' indicates unavailable.";
                    } // END of cmmFanRpmMax definition.

                    leaf cmmFanStatus  {
                        type  cml_data_types:CML_CMM_FAN_STATUS_T;
                        description "The status of the fan.";
                    } // END of cmmFanStatus definition.

                    leaf cmmFanLocation  {
                        type  cml_data_types:CML_CMM_FAN_LOCATION_T;
                        description "The location of fan in tray.";
                    } // END of cmmFanLocation definition.

                } // End of cmmFanTable-list
                container cmmFanTrayStatusTable {
                    config false;
                    description
                        "list of fan tray details resident in the chassis";
                    leaf cmmFanTrayStatus  {
                        type  cml_data_types:CML_CMM_FAN_TRAY_STATUS_T;
                        description "Value represents the fan tray status.";
                    } // END of cmmFanTrayStatus definition.

                    leaf cmmFanTrayLedColor  {
                        type  cml_data_types:CML_CMM_LED_COLOR_CODE_T;
                        description "Value represents the Color of the fan led.";
                    } // END of cmmFanTrayLedColor definition.

                } // END of cmmFanTrayStatusTable-container definition.
                container cmmFanFruTable {
                    config false;
                    description
                        "list of fan tray details resident in the chassis";
                    leaf cmmFanPpid  {
                        type  cml_data_types:CML_STRING_T;
                        description "The unique ppid of the fan tray. Blank indicates unavailable.";
                    } // END of cmmFanPpid definition.

                    leaf cmmFanCountryofOrigin  {
                        type  cml_data_types:CML_STRING_T;
                        description "FanTray Country of Origin. Blank indicates unavailable.";
                    } // END of cmmFanCountryofOrigin definition.

                    leaf cmmFanPpidPartNum  {
                        type  cml_data_types:CML_STRING_T;
                        description "FanTray PPID Part Num. Blank indicates unavailable.";
                    } // END of cmmFanPpidPartNum definition.

                    leaf cmmFanPpidPartNumRev  {
                        type  cml_data_types:CML_STRING_T;
                        description "FanTray PPID Part Num Rev. Blank indicates unavailable.";
                    } // END of cmmFanPpidPartNumRev definition.

                    leaf cmmFanManufactureId  {
                        type  cml_data_types:CML_STRING_T;
                        description "Fan Manufacturer Id. Blank indicates unavailable.";
                    } // END of cmmFanManufactureId definition.

                    leaf cmmFanDateCode  {
                        type  cml_data_types:CML_STRING_T;
                        description "Fan Date Code. Blank indicates unavailable.";
                    } // END of cmmFanDateCode definition.

                    leaf cmmFanSerialNumber  {
                        type  cml_data_types:CML_STRING_T;
                        description "Fan Serial Number. Blank indicates unavailable.";
                    } // END of cmmFanSerialNumber definition.

                    leaf cmmFanPartNum  {
                        type  cml_data_types:CML_STRING_T;
                        description "Fan Part Number. Blank indicates unavailable.";
                    } // END of cmmFanPartNum definition.

                    leaf cmmFanPartNumRev  {
                        type  cml_data_types:CML_STRING_T;
                        description "Fan Part Number Rev. Blank indicates unavailable.";
                    } // END of cmmFanPartNumRev definition.

                    leaf cmmFanNumOfFanPerTray  {
                        type  cml_data_types:CML_INT32_T;
                        description "Number of fans in the tray. '-100001' indicates unavailable.";
                    } // END of cmmFanNumOfFanPerTray definition.

                    leaf cmmFanType  {
                        type  cml_data_types:CML_CMM_FAN_TYPE_T;
                        description "Fan Type.";
                    } // END of cmmFanType definition.

                    leaf cmmFanServiceTag  {
                        type  cml_data_types:CML_STRING_T;
                        description "Fan Service Tag. Blank indicates unavailable.";
                    } // END of cmmFanServiceTag definition.

                    leaf cmmFanIanaNum  {
                        type  cml_data_types:CML_STRING_T;
                        description "Fan IANA Num. Blank indicates unavailable.";
                    } // END of cmmFanIanaNum definition.

                    leaf cmmFanMaxRpm  {
                        type  cml_data_types:CML_INT32_T;
                        description "Max RPM of fan. '-100001' indicates unavailable";
                    } // END of cmmFanMaxRpm definition.

                } // END of cmmFanFruTable-container definition.
            } // End of cmmFanTrayTable-list

            list cmmSysTemperatureTable {
                key "cmmSysTemperatureSensorIndex";
                config false;
                description
                    "list of Temperature Entities on board";
                leaf cmmSysTemperatureSensorIndex  {
                    type  cml_data_types:CML_INT8_T;
                    description "Value represents Temperature Sensor Index";
                } // END of cmmSysTemperatureSensorIndex definition.

                leaf cmmSysTemperatureSensorName  {
                    type  cml_data_types:CML_LINE_T;
                    description "Temperature Sensor Name. Blank indicates unavailable.";
                } // END of cmmSysTemperatureSensorName definition.

                leaf cmmSysTemperatureValue  {
                    type  cml_data_types:CML_FLOAT_T;
                    units "C";
                    description "Value represents Temperature Sensor value. '-1000.01' indicates unavailable.";
                } // END of cmmSysTemperatureValue definition.

                leaf cmmSysTempEmergencyThresholdMin  {
                    type  cml_data_types:CML_FLOAT_T;
                    units "C";
                    description "Value represents Temperature Sensor Min Emergency threshold. '-1000.01' indicates unavailable.";
                } // END of cmmSysTempEmergencyThresholdMin definition.

                leaf cmmSysTempEmergencyThresholdMax  {
                    type  cml_data_types:CML_FLOAT_T;
                    units "C";
                    description "Value represents Temperature Sensor Max Emergency threshold. '-1000.01' indicates unavailable.";
                } // END of cmmSysTempEmergencyThresholdMax definition.

                leaf cmmSysTempAlertThresholdMin  {
                    type  cml_data_types:CML_FLOAT_T;
                    units "C";
                    description "Value represents Temperature Sensor Min Alert threshold. '-1000.01' indicates unavailable.";
                } // END of cmmSysTempAlertThresholdMin definition.

                leaf cmmSysTempAlertThresholdMax  {
                    type  cml_data_types:CML_FLOAT_T;
                    units "C";
                    description "Value represents Temperature Sensor Max Alert threshold. '-1000.01' indicates unavailable.";
                } // END of cmmSysTempAlertThresholdMax definition.

                leaf cmmSysTempCriticalThresholdMin  {
                    type  cml_data_types:CML_FLOAT_T;
                    units "C";
                    description "Value represents Temperature Sensor Min Critical threshold. '-1000.01' indicates unavailable.";
                } // END of cmmSysTempCriticalThresholdMin definition.

                leaf cmmSysTempCriticalThresholdMax  {
                    type  cml_data_types:CML_FLOAT_T;
                    units "C";
                    description "Value represents Temperature Sensor Min Critical threshold. '-1000.01' indicates unavailable.";
                } // END of cmmSysTempCriticalThresholdMax definition.

            } // End of cmmSysTemperatureTable-list

            list cmmSwitchTemperatureTable {
                key "cmmSwitchTemperatureSensorIndex";
                config false;
                description
                    "list of Temperature Entities inside board chip";
                leaf cmmSwitchTemperatureSensorIndex  {
                    type  cml_data_types:CML_UINT8_T;
                    description "Value represents Temperature Monitor Index inside chip. '-100001' indicates unavailable.";
                } // END of cmmSwitchTemperatureSensorIndex definition.

                leaf cmmSwitchTemperatureValue  {
                    type  cml_data_types:CML_FLOAT_T;
                    units "C";
                    description "Value represents Temperature monitor value. '-1000.01' indicates unavailable.";
                } // END of cmmSwitchTemperatureValue definition.

                leaf cmmSwitchTempPeakValue  {
                    type  cml_data_types:CML_FLOAT_T;
                    units "C";
                    description "Value represents Temperature monitor peak value since last reading. '-1000.01' indicates unavailable.";
                } // END of cmmSwitchTempPeakValue definition.

            } // End of cmmSwitchTemperatureTable-list

            list cmmCpuCoreUtilTable {
                key "cmmCpuCoreIndex";
                config false;
                description
                    "Details of CPU utilization per core";
                leaf cmmCpuCoreIndex  {
                    type  cml_data_types:CML_UINT8_T;
                    description "Cpu Core number.";
                } // END of cmmCpuCoreIndex definition.

                leaf cmmCpuCoreUtilization  {
                    type  cml_data_types:CML_FLOAT_T;
                    units "%";
                    description "Cpu Utilization per core.";
                } // END of cmmCpuCoreUtilization definition.

                leaf cmmCpuCoreModelName  {
                    type  cml_data_types:CML_LINE_T;
                    description "Displays CPU processor Model Name. Blank indicates unavailable";
                } // END of cmmCpuCoreModelName definition.

            } // End of cmmCpuCoreUtilTable-list

            list cmmSysCpldTable {
                key "cmmSysCpldIndex";
                config false;
                description
                    "list of CPLD Entities on board";
                leaf cmmSysCpldIndex  {
                    type  cml_data_types:CML_INT8_T;
                    description "Value represents CPLD Index";
                } // END of cmmSysCpldIndex definition.

                leaf cmmSysCpldName  {
                    type  cml_data_types:CML_LINE_T;
                    description "CPLD Name. Blank indicates unavailable.";
                } // END of cmmSysCpldName definition.

                leaf cmmSysCpldSupportedVer  {
                    type  cml_data_types:CML_STRING_T;
                    description "CPLD supported version on board. Blank indicates unavailable";
                } // END of cmmSysCpldSupportedVer definition.

                leaf cmmSysCpldCurrentVer  {
                    type  cml_data_types:CML_STRING_T;
                    description "CPLD current version on board. Blank indicates unavailable";
                } // END of cmmSysCpldCurrentVer definition.

            } // End of cmmSysCpldTable-list
            container cmmSysRamTable {
                config false;
                description
                    " An entry containing RAM related information of the Unit.";
                leaf cmmSysRamTotalMem  {
                    type  cml_data_types:CML_INT32_T;
                    units "MBytes";
                    description "CPU RAM's total free memory available for utilisation in MBytes. '-100001' indicates unavailable.";
                } // END of cmmSysRamTotalMem definition.

                leaf cmmSysRamUsedMem  {
                    type  cml_data_types:CML_INT32_T;
                    units "%";
                    description "CPU RAM's Used memory available for utilisation in MBytes. '-100001' indicates unavailable.";
                } // END of cmmSysRamUsedMem definition.

                leaf cmmSysRamFreeMem  {
                    type  cml_data_types:CML_INT32_T;
                    units "%";
                    description "CPU RAM's Free memory available for utilisation in MBytes. '-100001' indicates unavailable.";
                } // END of cmmSysRamFreeMem definition.

                leaf cmmSysRamSharedMem  {
                    type  cml_data_types:CML_INT32_T;
                    description "CPU RAM's Shared memory available for utilisation in MBytes. '-100001' indicates unavailable.";
                } // END of cmmSysRamSharedMem definition.

                leaf cmmSysRamBuffers  {
                    type  cml_data_types:CML_INT32_T;
                    description "CPU RAM's Bufffer available for utilisation in MBytes. '-100001' indicates unavailable.";
                } // END of cmmSysRamBuffers definition.

                leaf cmmSysRamTotalSwap  {
                    type  cml_data_types:CML_INT32_T;
                    description "CPU RAM's Total Swap memory available for utilisation in MBytes. '-100001' indicates unavailable.";
                } // END of cmmSysRamTotalSwap definition.

                leaf cmmSysRamFreeSwap  {
                    type  cml_data_types:CML_INT32_T;
                    description "CPU RAM's Free Swap memory available for utilisation in MBytes. '-100001' indicates unavailable.";
                } // END of cmmSysRamFreeSwap definition.

                leaf cmmSysRamCurrentProcesses  {
                    type  cml_data_types:CML_INT32_T;
                    description "Number of processes currently running in RAM. '-100001' indicates unavailable.";
                } // END of cmmSysRamCurrentProcesses definition.

                leaf cmmSysRamTotalHighMemory  {
                    type  cml_data_types:CML_INT32_T;
                    description "CPU RAM's Total High memory in MBytes. '-100001' indicates unavailable.";
                } // END of cmmSysRamTotalHighMemory definition.

                leaf cmmSysRamAvailableHighMemory  {
                    type  cml_data_types:CML_INT32_T;
                    description "CPU RAM's Available High memory in MBytes. '-100001' indicates unavailable.";
                } // END of cmmSysRamAvailableHighMemory definition.

                leaf cmmSysRamUnitSize  {
                    type  cml_data_types:CML_INT32_T;
                    description "CPU RAM's Memory unit size in Bytes. '-100001' indicates unavailable.";
                } // END of cmmSysRamUnitSize definition.

                leaf cmmSysRamCriticalThreshold  {
                    type  cml_data_types:CML_INT32_T;
                    units "%";
                    description "RAM usage threshold % for Critical level. '-100001' indicates unavailable.";
                } // END of cmmSysRamCriticalThreshold definition.

                leaf cmmSysRamAlertThreshold  {
                    type  cml_data_types:CML_INT32_T;
                    units "%";
                    description "RAM usage threshold % for Alert level. '-100001' indicates unavailable.";
                } // END of cmmSysRamAlertThreshold definition.

            } // END of cmmSysRamTable-container definition.
            container cmmStackCpuTable {
                config false;
                description
                    "list of Stack Unit Util Entries";
                leaf cmmStackUnitNumCpuProcessor  {
                    type  cml_data_types:CML_INT32_T;
                    description "The number of Online Processors Available. '-100001' indicates unavailable.";
                } // END of cmmStackUnitNumCpuProcessor definition.

                leaf cmmStackUnitCpuLoad1Min  {
                    type  cml_data_types:CML_FLOAT_T;
                    units "%";
                    description "CPU Load in percentage for last 1 minute. '-1000.01' indicates unavailable.";
                } // END of cmmStackUnitCpuLoad1Min definition.

                leaf cmmStackUnitCpuLoad5Min  {
                    type  cml_data_types:CML_FLOAT_T;
                    units "%";
                    description "CPU Load in percentage for last 5 minutes. '-1000.01' indicates unavailable.";
                } // END of cmmStackUnitCpuLoad5Min definition.

                leaf cmmStackUnitCpuLoad15Min  {
                    type  cml_data_types:CML_FLOAT_T;
                    units "%";
                    description "CPU Load in percentage for last 15 minutes. '-1000.01' indicates unavailable.";
                } // END of cmmStackUnitCpuLoad15Min definition.

                leaf cmmStackCpuLoad1minAlertThreshold  {
                    type  cml_data_types:CML_FLOAT_T;
                    units "%";
                    description "The CPU Alert Threshold percentage value for 1 min load. '-1000.01' indicates unavailable.";
                } // END of cmmStackCpuLoad1minAlertThreshold definition.

                leaf cmmStackCpuLoad1minCriticalThreshold  {
                    type  cml_data_types:CML_FLOAT_T;
                    units "%";
                    description "The CPU Critical Threshold percentage value for 1 min load. '-1000.01' indicates unavailable.";
                } // END of cmmStackCpuLoad1minCriticalThreshold definition.

                leaf cmmStackCpuLoad5minCriticalThreshold  {
                    type  cml_data_types:CML_FLOAT_T;
                    units "%";
                    description "The CPU Critical Threshold percentage value for 5 min load. '-1000.01' indicates unavailable.";
                } // END of cmmStackCpuLoad5minCriticalThreshold definition.

                leaf cmmStackCpuLoad15minCriticalThreshold  {
                    type  cml_data_types:CML_FLOAT_T;
                    units "%";
                    description "The CPU Critical Threshold percentage value for 15 min load. '-1000.01' indicates unavailable.";
                } // END of cmmStackCpuLoad15minCriticalThreshold definition.

                leaf cmmStackUnitCpuUtilization  {
                    type  cml_data_types:CML_FLOAT_T;
                    units "%";
                    description "Total cpu usage in percentage. '-1000.01' indicates unavailable.";
                } // END of cmmStackUnitCpuUtilization definition.

                leaf cmmStackUnitCpuUtilAlertThreshold  {
                    type  cml_data_types:CML_FLOAT_T;
                    units "%";
                    description "The CPU utilization Alert Threshold %. '-1000.01' indicates unavailable.";
                } // END of cmmStackUnitCpuUtilAlertThreshold definition.

                leaf cmmStackUnitCpuUtilCriticalThreshold  {
                    type  cml_data_types:CML_FLOAT_T;
                    units "%";
                    description "The CPU utilization Critical Threshold %. '-1000.01' indicates unavailable.";
                } // END of cmmStackUnitCpuUtilCriticalThreshold definition.

            } // END of cmmStackCpuTable-container definition.
            container cmmSysPowerRailTable {
                config false;
                description
                    "list of power rail information in the chassis";
                leaf cmmSysPOWERVDDR  {
                    type  cml_data_types:CML_CMM_POWER_RAIL_T;
                    description "Power statistics for VCC 3.3v on Main board";
                } // END of cmmSysPOWERVDDR definition.

                leaf cmmSysPOWERCORE  {
                    type  cml_data_types:CML_CMM_POWER_RAIL_T;
                    description "Power statistics for Mac 1v on Main board";
                } // END of cmmSysPOWERCORE definition.

                leaf cmmSysV1P1POWERRAIL  {
                    type  cml_data_types:CML_CMM_POWER_RAIL_T;
                    description "Power statistics for Mac AVS 1v on Main board";
                } // END of cmmSysV1P1POWERRAIL definition.

                leaf cmmSysMAINBOARDPOWERRAIL  {
                    type  cml_data_types:CML_CMM_POWER_RAIL_T;
                    description "Power status  for Main Board";
                } // END of cmmSysMAINBOARDPOWERRAIL definition.

                leaf cmmSysVCC5V  {
                    type  cml_data_types:CML_CMM_POWER_RAIL_T;
                    description "Power status of VCC 5V";
                } // END of cmmSysVCC5V definition.

                leaf cmmSysVCC33V  {
                    type  cml_data_types:CML_CMM_POWER_RAIL_T;
                    description "Power status of VCC 33V";
                } // END of cmmSysVCC33V definition.

                leaf cmmSysVCCMAC1V  {
                    type  cml_data_types:CML_CMM_POWER_RAIL_T;
                    description "Power status of VCCMAC1V";
                } // END of cmmSysVCCMAC1V definition.

                leaf cmmSysVCCMACAVS1V  {
                    type  cml_data_types:CML_CMM_POWER_RAIL_T;
                    description "Power status of VCCMACAVS1V";
                } // END of cmmSysVCCMACAVS1V definition.

                leaf cmmSysVCCV1P05  {
                    type  cml_data_types:CML_CMM_POWER_RAIL_T;
                    description "Power Status of VCCV1P05";
                } // END of cmmSysVCCV1P05 definition.

                leaf cmmSysVCCV1P5  {
                    type  cml_data_types:CML_CMM_POWER_RAIL_T;
                    description "Power Status of VCCV1P5";
                } // END of cmmSysVCCV1P5 definition.

                leaf cmmSysVCCV1P8  {
                    type  cml_data_types:CML_CMM_POWER_RAIL_T;
                    description "Power Status of VCCV1P8";
                } // END of cmmSysVCCV1P8 definition.

                leaf cmmSysV1P05POWERRAIL  {
                    type  cml_data_types:CML_CMM_POWER_RAIL_T;
                    description "Power status of V1P05POWERRAIL";
                } // END of cmmSysV1P05POWERRAIL definition.

                leaf cmmSysV1P5POWERRAIL  {
                    type  cml_data_types:CML_CMM_POWER_RAIL_T;
                    description "Power status of V1P5POWERRAIL";
                } // END of cmmSysV1P5POWERRAIL definition.

                leaf cmmSysVCCPOWERRAIL  {
                    type  cml_data_types:CML_CMM_POWER_RAIL_T;
                    description "Power status of VCCPOWERRAIL";
                } // END of cmmSysVCCPOWERRAIL definition.

                leaf cmmSysSBV1P5POWERRAIL  {
                    type  cml_data_types:CML_CMM_POWER_RAIL_T;
                    description "Power status of SBV1P5POWERRAIL";
                } // END of cmmSysSBV1P5POWERRAIL definition.

                leaf cmmSysV1P0POWERRAIL  {
                    type  cml_data_types:CML_CMM_POWER_RAIL_T;
                    description "Power rail 1.0V Status";
                } // END of cmmSysV1P0POWERRAIL definition.

                leaf cmmSysV3P3POWERRAIL  {
                    type  cml_data_types:CML_CMM_POWER_RAIL_T;
                    description "Power rail 3.3V Status";
                } // END of cmmSysV3P3POWERRAIL definition.

                leaf cmmSysV1P8POWERRAIL  {
                    type  cml_data_types:CML_CMM_POWER_RAIL_T;
                    description "Power rail 1.8V Status";
                } // END of cmmSysV1P8POWERRAIL definition.

                leaf cmmSysV1P35POWERRAIL  {
                    type  cml_data_types:CML_CMM_POWER_RAIL_T;
                    description "Power Rail 1.35 Status";
                } // END of cmmSysV1P35POWERRAIL definition.

                leaf cmmSysVCCAVS1V  {
                    type  cml_data_types:CML_CMM_POWER_RAIL_T;
                    description "Power status of VCCAVS1V";
                } // END of cmmSysVCCAVS1V definition.

                leaf cmmSysDDRVTT  {
                    type  cml_data_types:CML_CMM_POWER_RAIL_T;
                    description "Power statistics for VCC 5v on Main board.";
                } // END of cmmSysDDRVTT definition.

            } // END of cmmSysPowerRailTable-container definition.
            container cmmSysComponentStatusTable {
                config false;
                description
                    "Details of each component status in the Unit.";
                leaf cmmSysPsu1Status  {
                    type  cml_data_types:CML_CMM_SYS_AND_COMPONENT_STATUS_T;
                    description "Status of PSU1.";
                } // END of cmmSysPsu1Status definition.

                leaf cmmSysPsu1LedColor  {
                    type  cml_data_types:CML_CMM_LED_COLOR_CODE_T;
                    description "Color of the power led of PSU1.";
                } // END of cmmSysPsu1LedColor definition.

                leaf cmmSysPsu2Status  {
                    type  cml_data_types:CML_CMM_SYS_AND_COMPONENT_STATUS_T;
                    description "Status of PSU2.";
                } // END of cmmSysPsu2Status definition.

                leaf cmmSysPsu2LedColor  {
                    type  cml_data_types:CML_CMM_LED_COLOR_CODE_T;
                    description "Color of the power led of PSU2.";
                } // END of cmmSysPsu2LedColor definition.

                leaf cmmSysLocatorLedStatus  {
                    type  cml_data_types:CML_CMM_MASTER_LOCATOR_STATUS_T;
                    description "Status of Locator led.";
                } // END of cmmSysLocatorLedStatus definition.

                leaf cmmSysLocatorLedColor  {
                    type  cml_data_types:CML_CMM_LED_COLOR_CODE_T;
                    description "Color of Locator led";
                } // END of cmmSysLocatorLedColor definition.

                leaf cmmSysMasterLedStatus  {
                    type  cml_data_types:CML_CMM_MASTER_LOCATOR_STATUS_T;
                    description "Status of Master led";
                } // END of cmmSysMasterLedStatus definition.

                leaf cmmSysMasterLedColor  {
                    type  cml_data_types:CML_CMM_LED_COLOR_CODE_T;
                    description "Color of Master led";
                } // END of cmmSysMasterLedColor definition.

                leaf cmmSysFanStatus  {
                    type  cml_data_types:CML_CMM_SYS_AND_COMPONENT_STATUS_T;
                    description "Overall Status of Fans in the Unit.";
                } // END of cmmSysFanStatus definition.

                leaf cmmSysFrontFanLedColor  {
                    type  cml_data_types:CML_CMM_LED_COLOR_CODE_T;
                    description "Color of the Front Fan led.";
                } // END of cmmSysFrontFanLedColor definition.

                leaf cmmSysRamStatus  {
                    type  cml_data_types:CML_CMM_SYS_AND_COMPONENT_STATUS_T;
                    description "Status of RAM in the unit";
                } // END of cmmSysRamStatus definition.

                leaf cmmSysCpuStatus  {
                    type  cml_data_types:CML_CMM_SYS_AND_COMPONENT_STATUS_T;
                    description "Status of CPU in the unit";
                } // END of cmmSysCpuStatus definition.

                leaf cmmSysDiskStatus  {
                    type  cml_data_types:CML_CMM_SYS_AND_COMPONENT_STATUS_T;
                    description "Status of HARD DISK in the unit";
                } // END of cmmSysDiskStatus definition.

                leaf cmmSysTemperatureStatus  {
                    type  cml_data_types:CML_CMM_SYS_AND_COMPONENT_STATUS_T;
                    description "Status of Temperature sensors in the unit.";
                } // END of cmmSysTemperatureStatus definition.

            } // END of cmmSysComponentStatusTable-container definition.
            container cmmSysSwModuleTable {
                config false;
                description
                    "list of software version information in a processor";
                leaf cmmSysSwRuntimeImgVersion  {
                    type  cml_data_types:CML_STRING_T;
                    description "This variable indicates the software module version that is currently running on the processor.The software release version is in the format as follow: <major version>.<minor version>.<minor version>......'1.2' indicate major version of 1 and minor release of 2.";
                } // END of cmmSysSwRuntimeImgVersion definition.

                leaf cmmSysSwRuntimeImgDate  {
                    type  cml_data_types:CML_DATE_TIME_T;
                    description "The release date of this software module.";
                } // END of cmmSysSwRuntimeImgDate definition.

            } // END of cmmSysSwModuleTable-container definition.
            container cmmSysHardDiskTable {
                config false;
                description
                    "Details of Hard disk information of the Unit.";
                leaf cmmSysHarddiskSerialno  {
                    type  cml_data_types:CML_STRING_T;
                    description "Hard disk's serial number. Blank indicates unavailable.";
                } // END of cmmSysHarddiskSerialno definition.

                leaf cmmSysHarddiskModelno  {
                    type  cml_data_types:CML_STRING_T;
                    description "Hard disk's model number. Blank indicates unavailable.";
                } // END of cmmSysHarddiskModelno definition.

                leaf cmmSysHarddiskFirmwarerev  {
                    type  cml_data_types:CML_LINE_T;
                    description "Hard disk's firmware revision. Blank indicates unavailable.";
                } // END of cmmSysHarddiskFirmwarerev definition.

                leaf cmmSysHarddiskCylinders  {
                    type  cml_data_types:CML_INT32_T;
                    description "Hard disk's Cylinder unit. '-100001' indicates unavailable.";
                } // END of cmmSysHarddiskCylinders definition.

                leaf cmmSysHarddiskHeads  {
                    type  cml_data_types:CML_INT32_T;
                    description "Hard disk's Head unit. '-100001' indicates unavailable.";
                } // END of cmmSysHarddiskHeads definition.

                leaf cmmSysHarddiskSectors  {
                    type  cml_data_types:CML_INT32_T;
                    description "Hard disk's Sector unit. '-100001' indicates unavailable.";
                } // END of cmmSysHarddiskSectors definition.

                leaf cmmSysHarddiskUnformattedBytesorTrack  {
                    type  cml_data_types:CML_INT32_T;
                    description "Hard disk's unformated bytes or track. '-100001' indicates unavailable.";
                } // END of cmmSysHarddiskUnformattedBytesorTrack definition.

                leaf cmmSysHarddiskUnformattedBytesorSector  {
                    type  cml_data_types:CML_INT32_T;
                    description "Hard disk's unformated bytes or sector. '-100001' indicates unavailable.";
                } // END of cmmSysHarddiskUnformattedBytesorSector definition.

                leaf cmmSysHarddiskRevisionNum  {
                    type  cml_data_types:CML_STRING_T;
                    description "Hard disk's Revision number. Blank indicates unavailable";
                } // END of cmmSysHarddiskRevisionNum definition.

                leaf cmmSysHarddiskTotalsize  {
                    type  cml_data_types:CML_INT32_T;
                    units "MBytes";
                    description "Total memory of the Hard disk. '-100001' indicates unavailable.";
                } // END of cmmSysHarddiskTotalsize definition.

                leaf cmmSysHarddiskUsedMem  {
                    type  cml_data_types:CML_INT32_T;
                    units "%";
                    description "Used memory of the Hard disk. '-100001' indicates unavailable.";
                } // END of cmmSysHarddiskUsedMem definition.

                leaf cmmSysHarddiskFreeMem  {
                    type  cml_data_types:CML_INT32_T;
                    units "%";
                    description "Free memory of the Hard disk. '-100001' indicates unavailable.";
                } // END of cmmSysHarddiskFreeMem definition.

                leaf cmmSysHarddiskCriticalThreshold  {
                    type  cml_data_types:CML_INT32_T;
                    units "%";
                    description "Harddisk usage threshold %  for Critical Level. '-100001' indicates unavailable.";
                } // END of cmmSysHarddiskCriticalThreshold definition.

                leaf cmmSysHarddiskAlertThreshold  {
                    type  cml_data_types:CML_INT32_T;
                    units "%";
                    description "Harddisk usage threshold %  for Alert Level. '-100001' indicates unavailable.";
                } // END of cmmSysHarddiskAlertThreshold definition.

            } // END of cmmSysHardDiskTable-container definition.
            container cmmSystemStatusTable {
                config false;
                description
                    "Details of overall system status of the Unit";
                leaf cmmSystemMinorFaultStatus  {
                    type  cml_data_types:CML_CMM_SYS_FAULT_STATUS_T;
                    description "overall Alert status caused by individual components in the unit.";
                } // END of cmmSystemMinorFaultStatus definition.

                leaf cmmSystemMajorFaultStatus  {
                    type  cml_data_types:CML_CMM_SYS_FAULT_STATUS_T;
                    description "overall Critical status caused by individual components in the unit.";
                } // END of cmmSystemMajorFaultStatus definition.

                leaf cmmSysStatus  {
                    type  cml_data_types:CML_CMM_SYS_AND_COMPONENT_STATUS_T;
                    description "Overall Status/Health of System.";
                } // END of cmmSysStatus definition.

                leaf cmmSysLedColor  {
                    type  cml_data_types:CML_CMM_LED_COLOR_CODE_T;
                    description "Color of the system led.";
                } // END of cmmSysLedColor definition.

            } // END of cmmSystemStatusTable-container definition.
        } // End of cmmStackUnitTable-list
    } // END of cmmStackUnitTable-grouping definition.

    grouping  cmmGlobals-grouping {
    description
        "cmm global structure";
    container cmmGlobals {
        description
            "cmm global structure";
        leaf locatorLed  {
            type  cml_data_types:CML_BOOL_T;
            description "To set the locator-led on or off.";
        } // END of locatorLed definition.

        leaf ddmDebugFlag  {
            type  cml_data_types:CML_BOOL_T;
            description "";
        } // END of ddmDebugFlag definition.

        leaf cmmDebugFlag  {
            type  cml_data_types:CML_BOOL_T;
            description "";
        } // END of cmmDebugFlag definition.

        leaf cmmWarningRepeat  {
            type  cml_data_types:CML_BOOL_T;
            description "To enable cmm warning level logs to repeat.";
        } // END of cmmWarningRepeat definition.

    } // END of cmmGlobals-container definition.
    } // END of cmmGlobals-container definition.

    grouping  cmmDdm-grouping {
    description
        "ddm monitor";
    container cmmDdm {
        description
            "ddm monitor";
        leaf monitorTimerInterval  {
            type  cml_data_types:CML_UINT16_T {
                 range "60..3600";
            }
            description "To set DDM Monitor interval time.";
        } // END of monitorTimerInterval definition.

        leaf statusServiceUnsuppTrans  {
            type  cml_data_types:CML_BOOL_T;
            description "To enable DDM Monitor for unsupported transceivers at user risk.";
        } // END of statusServiceUnsuppTrans definition.

    } // END of cmmDdm-container definition.
    } // END of cmmDdm-container definition.

    grouping  cmmInterface-grouping {
    description
        "CMM Interface properties";
    container cmmInterface {
        description
            "CMM Interface properties";
        leaf monitorPort  {
            type  cml_data_types:CML_BOOL_T;
            description "To enable DDM monitor for current transceiver.";
        } // END of monitorPort definition.

        leaf transceiverCode  {
            type  cml_data_types:CML_CMM_TRANSCEIVER_T;
            description "To set transceiver code for current transceiver.";
        } // END of transceiverCode definition.

    } // END of cmmInterface-container definition.
    } // END of cmmInterface-container definition.

    grouping  cmmCpuLoadThresh-grouping {
    description
        "CPU load average 1, 5, and 15 minute thresholds";
    container cmmCpuLoadThresh {
        description
            "CPU load average 1, 5, and 15 minute thresholds";
        leaf cmmCpuLoad1MinWarnVal  {
            type  cml_data_types:CML_UINT8_T {
                 range "41..100";
            }
            description "";
        } // END of cmmCpuLoad1MinWarnVal definition.

        leaf cmmCpuLoad1MinAlarmVal  {
            type  cml_data_types:CML_UINT8_T {
                 range "51..100";
            }
            description "";
        } // END of cmmCpuLoad1MinAlarmVal definition.

        leaf cmmCpuLoad5MinAlarmVal  {
            type  cml_data_types:CML_UINT8_T {
                 range "51..100";
            }
            description "";
        } // END of cmmCpuLoad5MinAlarmVal definition.

        leaf cmmCpuLoad15MinAlarmVal  {
            type  cml_data_types:CML_UINT8_T {
                 range "51..100";
            }
            description "";
        } // END of cmmCpuLoad15MinAlarmVal definition.

    } // END of cmmCpuLoadThresh-container definition.
    } // END of cmmCpuLoadThresh-container definition.

    grouping  cmmCpuCoreThresh-grouping {
    description
        "CPU core usage thresholds";
    container cmmCpuCoreThresh {
        description
            "CPU core usage thresholds";
        leaf cmmCpuCoreWarnVal  {
            type  cml_data_types:CML_UINT8_T {
                 range "51..100";
            }
            description "";
        } // END of cmmCpuCoreWarnVal definition.

        leaf cmmCpuCoreAlarmVal  {
            type  cml_data_types:CML_UINT8_T {
                 range "91..100";
            }
            description "";
        } // END of cmmCpuCoreAlarmVal definition.

    } // END of cmmCpuCoreThresh-container definition.
    } // END of cmmCpuCoreThresh-container definition.

    grouping  cmmAlarmVariable-grouping {
    description
        "cmmAlarmVariable";
    container cmmAlarmVariable {
        config false;
        description
            "cmmAlarmVariable";
        leaf cmmAlarmVarInteger  {
            type  cml_data_types:CML_INT32_T;
            description "An generic integer value in the notification object";
        } // END of cmmAlarmVarInteger definition.

        leaf cmmAlarmVarString  {
            type  cml_data_types:CML_LINE_T;
            description "An generic string value in the notification object";
        } // END of cmmAlarmVarString definition.

    } // END of cmmAlarmVariable-container definition.
    } // END of cmmAlarmVariable-container definition.


}
