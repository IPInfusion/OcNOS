/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-acl.yang
*
*/

submodule zebos-acl {

    belongs-to  zebos { prefix zebos; }

    import cml_data_types {
        prefix cml_data_types;
    }

    import feature_list {
        prefix feature_list;
    }

    organization
        "IP Infusion Inc.";

    contact
        "Address: 3965 Freedom Circle, Suite 200, Santa Clara, CA 95054
        Phone: +1 408-400-1900
        E-mail: support@ipinfusion.com
        Web: http://www.ipinfusion.com/";

    description
        "Access List Related Configurations";


    revision "2017-05-23" {
        description " Initial Version.";
        reference "";
    }

    grouping accessListAttr {
        description
            "accessListAttr";
        leaf remark  {
            type  cml_data_types:CML_STRING_T {
                length "0..255";
            }
            description "";
        } // END of remark definition.

        leaf startSeqNum  {
            type  cml_data_types:CML_UINT32_T;
            description "";
        } // END of startSeqNum definition.

        leaf increment  {
            type  cml_data_types:CML_UINT64_T;
            description "";
        } // END of increment definition.

        leaf filterTypeDF  {
            type  cml_data_types:CML_ACL_FILTER_ACTION_T;
            default "deny-all";
            description "";
        } // END of filterTypeDF definition.

        leaf logDF  {
            if-feature feature_list:HAVE_SFLOW;
            type  cml_data_types:CML_BOOL_T;
            description "";
        } // END of logDF definition.

        leaf sampleDF  {
            if-feature feature_list:HAVE_SFLOW;
            type  cml_data_types:CML_BOOL_T;
            description "";
        } // END of sampleDF definition.


        list filterList {
            key "accessNumFL";
            description
                "filterList";
            leaf accessNumFL  {
                type  cml_data_types:CML_UINT32_T {
                     range "1..268435453";
                }
                description "";
            } // END of accessNumFL definition.

            leaf filterTypeFL  {
                type  cml_data_types:CML_ACL_FILTER_ACTION_T;
                description "";
            } // END of filterTypeFL definition.

            leaf logFL  {
                if-feature feature_list:HAVE_SFLOW;
                type  cml_data_types:CML_BOOL_T;
                description "";
            } // END of logFL definition.

            leaf sampleFL  {
                if-feature feature_list:HAVE_SFLOW;
                type  cml_data_types:CML_BOOL_T;
                description "";
            } // END of sampleFL definition.

            leaf redirectPortFL  {
                type  cml_data_types:CML_STRING_T {
                    length "0..255";
                }
                description "";
            } // END of redirectPortFL definition.

            leaf packetFormatFM  {
                type  cml_data_types:CML_ACL_ETHER_TYPE_T {
                    length "0..255";
                }
                description "";
            } // END of packetFormatFM definition.

            leaf cosFM  {
                type  cml_data_types:CML_INT32_T {
                     range "0..7";
                }
                description "";
            } // END of cosFM definition.

            leaf vlanFM  {
                type  cml_data_types:CML_INT32_T {
                     range "1..4094";
                }
                description "";
            } // END of vlanFM definition.

            leaf arpFM  {
                type  cml_data_types:CML_ACL_ARP_TYPE_T;
                description "";
            } // END of arpFM definition.

            leaf sMacFM  {
                type  cml_data_types:CML_STRING_T {
                    length "0..255";

                    pattern "[0-9a-fA-F]{1,4}\.[0-9a-fA-F]{1,4}\.[0-9a-fA-F]{1,4}|[0-9a-fA-F]{2}\-[0-9a-fA-F]{2}\-[0-9a-fA-F]{2}\-[0-9a-fA-F]{2}\-[0-9a-fA-F]{2}\-[0-9a-fA-F]{2}|[0-9a-fA-F]{2}:[0-9a-fA-F]{2}:[0-9a-fA-F]{2}:[0-9a-fA-F]{2}:[0-9a-fA-F]{2}:[0-9a-fA-F]{2}|any";
                }
                description "";
            } // END of sMacFM definition.

            leaf sMacMaskFM  {
                type  cml_data_types:CML_STRING_T {
                    length "0..255";

                    pattern "[0-9a-fA-F]{1,4}\.[0-9a-fA-F]{1,4}\.[0-9a-fA-F]{1,4}|[0-9a-fA-F]{2}\-[0-9a-fA-F]{2}\-[0-9a-fA-F]{2}\-[0-9a-fA-F]{2}\-[0-9a-fA-F]{2}\-[0-9a-fA-F]{2}|[0-9a-fA-F]{2}:[0-9a-fA-F]{2}:[0-9a-fA-F]{2}:[0-9a-fA-F]{2}:[0-9a-fA-F]{2}:[0-9a-fA-F]{2}";
                }
                description "";
            } // END of sMacMaskFM definition.

            leaf dMacFM  {
                type  cml_data_types:CML_STRING_T {
                    length "0..255";

                    pattern "[0-9a-fA-F]{1,4}\.[0-9a-fA-F]{1,4}\.[0-9a-fA-F]{1,4}|[0-9a-fA-F]{2}\-[0-9a-fA-F]{2}\-[0-9a-fA-F]{2}\-[0-9a-fA-F]{2}\-[0-9a-fA-F]{2}\-[0-9a-fA-F]{2}|[0-9a-fA-F]{2}:[0-9a-fA-F]{2}:[0-9a-fA-F]{2}:[0-9a-fA-F]{2}:[0-9a-fA-F]{2}:[0-9a-fA-F]{2}|any";
                }
                description "";
            } // END of dMacFM definition.

            leaf dMacMaskFM  {
                type  cml_data_types:CML_STRING_T {
                    length "0..255";

                    pattern "[0-9a-fA-F]{1,4}\.[0-9a-fA-F]{1,4}\.[0-9a-fA-F]{1,4}|[0-9a-fA-F]{2}\-[0-9a-fA-F]{2}\-[0-9a-fA-F]{2}\-[0-9a-fA-F]{2}\-[0-9a-fA-F]{2}\-[0-9a-fA-F]{2}|[0-9a-fA-F]{2}:[0-9a-fA-F]{2}:[0-9a-fA-F]{2}:[0-9a-fA-F]{2}:[0-9a-fA-F]{2}:[0-9a-fA-F]{2}";
                }
                description "";
            } // END of dMacMaskFM definition.

            leaf sIpFC  {
                type  cml_data_types:CML_ACL_ANY_IPV4_ADDR_T {
                    length "0..255";
                }
                description "";
            } // END of sIpFC definition.

            leaf dIpFC  {
                type  cml_data_types:CML_ACL_ANY_IPV4_ADDR_T {
                    length "0..255";
                }
                description "";
            } // END of dIpFC definition.

            leaf protocolFC  {
                type  cml_data_types:CML_ACL_IP_PROTO_T;
                description "";
            } // END of protocolFC definition.

            leaf srcPortMinFC  {
                type  cml_data_types:CML_UINT16_T {
                     range "0..65535";
                }
                description "";
            } // END of srcPortMinFC definition.

            leaf srcPortMaxFC  {
                type  cml_data_types:CML_UINT16_T {
                     range "0..65535";
                }
                description "";
            } // END of srcPortMaxFC definition.

            leaf srcPortUdpFC  {
                type  cml_data_types:CML_ACL_UDP_KEYWORD_T;
                description "";
            } // END of srcPortUdpFC definition.

            leaf srcPortTcpFC  {
                type  cml_data_types:CML_ACL_TCP_KEYWORD_T;
                description "";
            } // END of srcPortTcpFC definition.

            leaf srcPortOperFC  {
                type  cml_data_types:CML_ACL_PORT_OPERATIONS_T;
                description "";
            } // END of srcPortOperFC definition.

            leaf destPortMinFC  {
                type  cml_data_types:CML_UINT16_T {
                     range "0..65535";
                }
                description "";
            } // END of destPortMinFC definition.

            leaf destPortMaxFC  {
                type  cml_data_types:CML_UINT16_T {
                     range "0..65535";
                }
                description "";
            } // END of destPortMaxFC definition.

            leaf destPortUdpFC  {
                type  cml_data_types:CML_ACL_UDP_KEYWORD_T;
                description "";
            } // END of destPortUdpFC definition.

            leaf destPortTcpFC  {
                type  cml_data_types:CML_ACL_TCP_KEYWORD_T;
                description "";
            } // END of destPortTcpFC definition.

            leaf destPortOperFC  {
                type  cml_data_types:CML_ACL_PORT_OPERATIONS_T;
                description "";
            } // END of destPortOperFC definition.

            leaf dscpFC  {
                type  cml_data_types:CML_ACL_DSCP_T;
                description "";
            } // END of dscpFC definition.

            leaf precedenceFC  {
                type  cml_data_types:CML_ACL_PRECEDENCE_T;
                description "";
            } // END of precedenceFC definition.

            leaf fragmentsFC  {
                type  cml_data_types:CML_INT32_T;
                description "";
            } // END of fragmentsFC definition.

            leaf vlanFC  {
                type  cml_data_types:CML_INT32_T {
                     range "1..4094";
                }
                description "";
            } // END of vlanFC definition.

            leaf tcpFlagFC  {
                type  cml_data_types:CML_ACL_TCP_FLAGS_T;
                description "";
            } // END of tcpFlagFC definition.

            leaf icmpMsgFC  {
                type  cml_data_types:CML_ACL_ICMP_OPTIONS_T;
                description "";
            } // END of icmpMsgFC definition.

            leaf icmpTypeFC  {
                type  cml_data_types:CML_UINT8_T {
                     range "0..255";
                }
                description "";
            } // END of icmpTypeFC definition.

            leaf icmpCodeFC  {
                type  cml_data_types:CML_UINT8_T {
                     range "0..255";
                }
                description "";
            } // END of icmpCodeFC definition.

            leaf protocolFZE  {
                type  cml_data_types:CML_ACL_IPV6_PROTO_T;
                description "";
            } // END of protocolFZE definition.

            leaf srcAddrFZE  {
                if-feature feature_list:HAVE_IPV6;
                type  cml_data_types:CML_ACL_ANY_IPV6_ADDR_T {
                    length "0..255";
                }
                description "";
            } // END of srcAddrFZE definition.

            leaf srcPortOperFZE  {
                type  cml_data_types:CML_ACL_PORT_OPERATIONS_T;
                description "";
            } // END of srcPortOperFZE definition.

            leaf srcPortMaxFZE  {
                type  cml_data_types:CML_UINT16_T {
                     range "0..65535";
                }
                description "";
            } // END of srcPortMaxFZE definition.

            leaf srcPortMinFZE  {
                type  cml_data_types:CML_UINT16_T {
                     range "0..65535";
                }
                description "";
            } // END of srcPortMinFZE definition.

            leaf srcPortUdpFZE  {
                type  cml_data_types:CML_ACL_UDP_KEYWORD_T;
                description "";
            } // END of srcPortUdpFZE definition.

            leaf srcPortTcpFZE  {
                type  cml_data_types:CML_ACL_TCP_KEYWORD_T;
                description "";
            } // END of srcPortTcpFZE definition.

            leaf destAddrFZE  {
                if-feature feature_list:HAVE_IPV6;
                type  cml_data_types:CML_ACL_ANY_IPV6_ADDR_T {
                    length "0..255";
                }
                description "";
            } // END of destAddrFZE definition.

            leaf destPortOperFZE  {
                type  cml_data_types:CML_ACL_PORT_OPERATIONS_T;
                description "";
            } // END of destPortOperFZE definition.

            leaf destPortMaxFZE  {
                type  cml_data_types:CML_UINT16_T {
                     range "0..65535";
                }
                description "";
            } // END of destPortMaxFZE definition.

            leaf destPortMinFZE  {
                type  cml_data_types:CML_UINT16_T {
                     range "0..65535";
                }
                description "";
            } // END of destPortMinFZE definition.

            leaf destPortUdpFZE  {
                type  cml_data_types:CML_ACL_UDP_KEYWORD_T;
                description "";
            } // END of destPortUdpFZE definition.

            leaf destPortTcpFZE  {
                type  cml_data_types:CML_ACL_TCP_KEYWORD_T;
                description "";
            } // END of destPortTcpFZE definition.

            leaf icmpMsgFZE  {
                type  cml_data_types:CML_ACL_ICMPV6_OPTIONS_T;
                description "";
            } // END of icmpMsgFZE definition.

            leaf icmpTypeFZE  {
                type  cml_data_types:CML_UINT8_T {
                     range "0..255";
                }
                description "";
            } // END of icmpTypeFZE definition.

            leaf icmpCodeFZE  {
                type  cml_data_types:CML_UINT8_T {
                     range "0..255";
                }
                description "";
            } // END of icmpCodeFZE definition.

            leaf flowLabelFZE  {
                type  cml_data_types:CML_INT32_T {
                     range "0..1048575";
                }
                description "";
            } // END of flowLabelFZE definition.

            leaf fragmentsFZE  {
                type  cml_data_types:CML_INT32_T;
                description "";
            } // END of fragmentsFZE definition.

            leaf dscpFZE  {
                type  cml_data_types:CML_ACL_DSCP_T;
                description "";
            } // END of dscpFZE definition.

            leaf tcpFlagFZE  {
                type  cml_data_types:CML_ACL_TCP_FLAGS_T;
                description "";
            } // END of tcpFlagFZE definition.

            leaf vlanFZE  {
                type  cml_data_types:CML_INT32_T {
                     range "1..4094";
                }
                description "";
            } // END of vlanFZE definition.

        } // End of filterList-list
    } // END of accessListAttr definition.

    grouping  accessMasterIPv4-grouping {
    description
        "accessMasterIPv4";
    container accessMasterIPv4 {
        description
            "accessMasterIPv4";

        list accessListIPv4 {
            key "aclNameIPv4";
            description
                "accessListIPv4";
            leaf aclNameIPv4  {
                type  cml_data_types:CML_STRING_T {
                    length "1..64";
                }
                description "";
            } // END of aclNameIPv4 definition.

            uses accessListAttr;
        } // End of accessListIPv4-list

        list accessListMac {
            key "aclNameMAC";
            description
                "accessListMac";
            leaf aclNameMAC  {
                type  cml_data_types:CML_STRING_T {
                    length "1..64";
                }
                description "";
            } // END of aclNameMAC definition.

            uses accessListAttr;
        } // End of accessListMac-list
    } // END of accessMasterIPv4-container definition.
    } // END of accessMasterIPv4-container definition.

    grouping  accessMasterIPv6-grouping {
    description
        "accessMasterIPv6";
    container accessMasterIPv6 {
        description
            "accessMasterIPv6";

        list accessListIPv6 {
            key "aclNameIPv6";
            description
                "accessListIPv6";
            leaf aclNameIPv6  {
                type  cml_data_types:CML_STRING_T {
                    length "1..64";
                }
                description "";
            } // END of aclNameIPv6 definition.

            uses accessListAttr;
        } // End of accessListIPv6-list
    } // END of accessMasterIPv6-container definition.
    } // END of accessMasterIPv6-container definition.


}
