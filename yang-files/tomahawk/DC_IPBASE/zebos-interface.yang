/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-interface.yang
*
*/

submodule zebos-interface {

    belongs-to  zebos { prefix zebos; }

    import cml_data_types {
        prefix cml_data_types;
    }

    import ietf-inet-types {
        prefix inet;
    }

    import feature_list {
        prefix feature_list;
    }

    include zebos-vrf;
    include zebos-broadcom;
    include zebos-switchportinterface;
    include zebos-lacp;
    include zebos-lag;
    include zebos-lldpv2;
    include zebos-rib;
    include zebos-ospf;
    include zebos-pim4;
    include zebos-dhcpr;
    include zebos-dhcpc;
    include zebos-sflow;
    include zebos-mrib4;
    include zebos-igmp;
    include zebos-igmpsnooping;
    include zebos-mlag;
    include zebos-hqos;
    include zebos-cmm;
    include zebos-aclinterface;
    include zebos-rpf;
    include zebos-trill;
    include zebos-ndd;
    include zebos-rtadv;
    include zebos-nat;
    organization
        "IP Infusion Inc.";

    contact
        "Address: 3965 Freedom Circle, Suite 200, Santa Clara, CA 95054
        Phone: +1 408-400-1900
        E-mail: support@ipinfusion.com
        Web: http://www.ipinfusion.com/";

    description
        "Datamodel for interface object";


    revision "2018-06-21" {
        description " Initial Version.";
        reference "";
    }



    typedef  CML_INTERFACE_OPER_STATUS_T {
        type enumeration {
            enum up {
                value 1;
                description "ready to pass packets";
            }
            enum down {
                value 2;
                description "down state";
            }
            enum testing {
                value 3;
                description "in some test mode";
            }
            enum unknown {
                value 4;
                description "status can not be determined for some reason";
            }
            enum dormant {
                value 5;
                description "not in a condition to pass packets but is instead in a pending state waiting for some external event. ";
            }
            enum notPresent {
                value 6;
                description "some component is missing";
            }
            enum lowerLayerDown {
                value 7;
                description "down due to state of lower-layer interface(s)";
            }
        }
        description "";
        reference "";
    }

    grouping interface-grouping {
    description
        "interface object";
        list interface {
            key "ifName";
            description
                "interface object";
            leaf ifName  {
                type  cml_data_types:CML_STRING_T {
                    length "1..33";
                }
                description "The textual name of the interface. The value of this object should be the name of the interface as assigned by the local device and should be suitable for use in commands entered at the device's `console'. This might be a text name, such as `le0' or a simple port number, such as `1', depending on the interface naming syntax of the device. If several entries in the ifTable together represent a single interface as named by the device, then each will have the same value of ifName. Note that for an agent which responds to SNMP queries concerning an interface on some other (proxied) device, then the value of ifName for such an interface is the proxied device's local name for it. If there is no local name, or this object is otherwise not applicable, then this object contains a zero-length string.";
            } // END of ifName definition.

            leaf interfaceProperties  {
                type  cml_data_types:CML_IFACE_PROP_T;
                config false;
                description "This attribute is used to display interface mapping properties";
            } // END of interfaceProperties definition.

            leaf origifName  {
                if-feature feature_list:HAVE_INTERFACE_NAME_MAPPING;
                type  cml_data_types:CML_STRING_T {
                    length "1..33";
                }
                config false;
                description "This Object is used to Map the Interface Name";
            } // END of origifName definition.

            leaf mappedIfName  {
                type  cml_data_types:CML_STRING_T {
                    length "1..33";
                }
                config false;
                description "This Object is used to set Interface mapped name";
            } // END of mappedIfName definition.

            leaf ifCounterDiscontinuityTime  {
                type  cml_data_types:CML_TIMESTAMP_T;
                config false;
                description "The value of sysUpTime on the most recent occasion at which
            any one or more of this interface's counters suffered a
            discontinuity.  The relevant counters are the specific
            instances associated with this interface of any Counter32 or
            Counter64 object contained in the ifTable or ifXTable.  If
            no such discontinuities have occurred since the last re-
            initialization of the local management subsystem, then this
            object contains a zero value.";
            } // END of ifCounterDiscontinuityTime definition.

            leaf ifIndex  {
                type  cml_data_types:CML_INT32_T;
                config false;
                description "A unique value, greater than zero, for each interface.It is recommended that values are assigned contiguously starting from 1.The value for each interface sub-layer must remain constant at least from one re-initialization of the entity's network management system to the next re-initialization.";
            } // END of ifIndex definition.

            leaf switchportStatus  {
                type  cml_data_types:CML_BOOL_T;
                default false;
                description "This Object is used to set the mode of the Hybrid Switch Router feature to switched only.All interfaces are configured routed by default";
            } // END of switchportStatus definition.

            leaf shutdownFlag  {
                type  cml_data_types:CML_BOOL_T;
                default false;
                description "This Object is used to Set admin state of interface.The testing(3) state indicates that no operational packets can be passed. When a managed system initializes, all interfaces start with ifAdminStatus in the down(2) state. As a result of either explicit management action or per configuration information retained by the managed system, ifAdminStatus is then changed to either the up(1) or testing(3) states (or remains in the down(2) state).";
            } // END of shutdownFlag definition.

            leaf noLearningFlag  {
                if-feature feature_list:HAVE_L2;
                if-feature feature_list:NOT_HAVE_BROADCOM;
                type  cml_data_types:CML_BOOL_T;
                default false;
                description "";
            } // END of noLearningFlag definition.

            leaf multicast  {
                type  cml_data_types:CML_BOOL_T;
                default false;
                description "This Object is used to set multicast flag to interface.The number of packets, delivered by this sub-layer to a higher (sub-)layer, which were addressed to a multicast address at this sub-layer. For a MAC layer protocol, this includes both Group and Functional addresses. Discontinuities in the value of this counter can occur at re-initialization of the management system, and at other times as indicated by the value of ifCounterDiscontinuityTime.";
            } // END of multicast definition.

            leaf ifOperStatus  {
                type  CML_INTERFACE_OPER_STATUS_T;
                config false;
                description "The current operational state of the interface.  The
            testing(3) state indicates that no operational packets can
            be passed.  If ifAdminStatus is down(2) then ifOperStatus
            should be down(2).  If ifAdminStatus is changed to up(1)
            then ifOperStatus should change to up(1) if the interface is
            ready to transmit and receive network traffic; it should
            change to dormant(5) if the interface is waiting for
            external actions (such as a serial line waiting for an
            incoming connection); it should remain in the down(2) state
            if and only if there is a fault that prevents it from going
            to the up(1) state; it should remain in the notPresent(6)
            state if the interface has missing (typically, hardware)
            components.";
            } // END of ifOperStatus definition.

            leaf proxyArp  {
                type  cml_data_types:CML_BOOL_T;
                description "Local proxy ARP is used to resolve MAC addresses to IP addresses in the same Layer 3 network such as, private VLANs that are Layer 2-separated. Local proxy ARP supports all types of interfaces supported by ARP and unnumbered interfaces";
            } // END of proxyArp definition.

            leaf portChannelLoadBal  {
                if-feature feature_list:HAVE_SWFWDR;
                if-feature feature_list:HAVE_LACP;
                type  cml_data_types:CML_LACP_PSC_T;
                description "This Object is used to set LACP port-channel load-balancing and set port selection criteria (PSC) on an interface";
            } // END of portChannelLoadBal definition.

            leaf portChannelMinLinks  {
                if-feature feature_list:HAVE_LACP;
                type  cml_data_types:CML_UINT8_T {
                     range "2..32";
                }
                description "The list of ifIndex's of the E_ports that are members of this Port Channel port";
            } // END of portChannelMinLinks definition.

            leaf stormTotalDiscards  {
                if-feature feature_list:HAVE_BROADCOM;
                if-feature feature_list:HAVE_RATE_LIMIT;
                if-feature feature_list:NOT_HAVE_DUNE;
                type  cml_data_types:CML_COUNTER64_T;
                config false;
                description "Total storm Discards";
            } // END of stormTotalDiscards definition.

            leaf ifMetric  {
                type  cml_data_types:CML_INT32_T;
                config false;
                description "This Object is used to check interface Metric";
            } // END of ifMetric definition.

            leaf mtu  {
                type  cml_data_types:CML_INT32_T {
                     range "64..65536";
                }
                description "This Object is used to set mtu value to interface.The size of the largest packet which can be sent/received on the interface, specified in octets.  For interfaces that are used for transmitting network datagrams, this is the size of the largest network datagram that can be sent on the interface.";
            } // END of mtu definition.

            leaf duplex  {
                type  cml_data_types:CML_DUPLEX_T;
                description "This Object is used to set the duplex mode for each interface";
            } // END of duplex definition.

            leaf defaultDuplex  {
                type  cml_data_types:CML_UINT8_T;
                config false;
                description "This object specifies interface default Duplex";
            } // END of defaultDuplex definition.

            leaf autoNego  {
                type  cml_data_types:CML_INT64_T;
                config false;
                description "This object specifies interface Autonegotiation";
            } // END of autoNego definition.

            leaf defaultAutoNego  {
                type  cml_data_types:CML_UINT8_T;
                config false;
                description "This Flag is used for defaultAutoNego";
            } // END of defaultAutoNego definition.

            leaf linkFlapErrDisable  {
                type  cml_data_types:CML_ENABLE_DISABLE_T;
                default "enable";
                description " This object specifies whether the interface is enabled for link-flap errdisable or not. If this is '0', then interface is not enabled. Otherwise it is enabled.";
            } // END of linkFlapErrDisable definition.

            leaf autonegBitsAdvt  {
                type  cml_data_types:CML_UINT32_T;
                config false;
                description "This Object is used to show Autonegotiation Bits Advit";
            } // END of autonegBitsAdvt definition.

            leaf autonegFaultAdvt  {
                type  cml_data_types:CML_UINT8_T;
                config false;
                description "This Object is used to show Autonegotiation Fault Advt";
            } // END of autonegFaultAdvt definition.

            leaf mdix  {
                type  cml_data_types:CML_UINT32_T;
                config false;
                description "This Object is used to show Medium Dependent Interface Crossover";
            } // END of mdix definition.

            leaf arpAgeingTimeout  {
                if-feature feature_list:NOT_HAVE_NDD;
                type  cml_data_types:CML_UINT32_T {
                     range "1..3000";
                }
                default "3000";
                description "This Object is used to set ARP Ageing timeout in sec and arp age timeout value to interface";
            } // END of arpAgeingTimeout definition.

            leaf slotId  {
                type  cml_data_types:CML_UINT32_T;
                config false;
                description "This Object describes slot Id";
            } // END of slotId definition.

            leaf hwType  {
                type  cml_data_types:CML_HW_TYPE_T;
                config false;
                description "This Object describes HardWare Type";
            } // END of hwType definition.

            leaf hwAddr  {
                type  cml_data_types:CML_STRING_T {
                    length "1..20";
                }
                description "This Object is used to set the mac address for an interface";
            } // END of hwAddr definition.

            leaf hwAddrLen  {
                type  cml_data_types:CML_INT32_T;
                config false;
                description "This Object describes HardWare Address Length";
            } // END of hwAddrLen definition.

            leaf speed  {
                type  cml_data_types:CML_INTERFACE_SPEED_T;
                description "This Object is used to set the interface speed";
            } // END of speed definition.

            leaf defaultSpeed  {
                type  cml_data_types:CML_STRING_T;
                config false;
                description "interface default link speed, bytes/s";
            } // END of defaultSpeed definition.

            leaf maxSpeed  {
                type  cml_data_types:CML_STRING_T;
                config false;
                description "This Object describes interface default max link speed, bytes/s";
            } // END of maxSpeed definition.

            leaf snmpTrapLinkStatus  {
                type  cml_data_types:CML_BOOL_T;
                default false;
                description "This Object is used to set the snmp trap link status in an interface";
            } // END of snmpTrapLinkStatus definition.

            leaf fec  {
                type  cml_data_types:CML_INTF_FEC_T;
                default "off";
                description "This Object is used to set fec to interface";
            } // END of fec definition.

            leaf ifAlias  {
                if-feature feature_list:HAVE_SNMP;
                type  cml_data_types:CML_STRING_T {
                    length "1..33";
                }
                description "This Object is used to describes Alias name for the interface";
            } // END of ifAlias definition.

            leaf bandwidthConfFlags  {
                type  cml_data_types:CML_INT16_T;
                config false;
                description "Has the bandwidth been configured/read from kernel";
            } // END of bandwidthConfFlags definition.

            leaf description  {
                type  cml_data_types:CML_LINE_T {
                    length "1..64";
                }
                description "This Object is used to Set description";
            } // END of description definition.

            leaf esi  {
                if-feature feature_list:HAVE_NVO;
                type  cml_data_types:CML_STRING_T;
                description "";
            } // END of esi definition.

            leaf system-mac  {
                if-feature feature_list:HAVE_NVO;
                type  cml_data_types:CML_MAC_ADDR_T;
                description "This Object is used to describes the Ethernet Segment Identifier";
            } // END of system-mac definition.

            leaf mauDefaultType  {
                if-feature feature_list:HAVE_L2;
                type  cml_data_types:CML_MAUTYPE_T;
                description "This Object is used to set the mau type in an interface";
            } // END of mauDefaultType definition.

            leaf ipDHCPAddr  {
                if-feature feature_list:HAVE_DHCP_CLIENT;
                type  cml_data_types:CML_IPV4_ADDR_T;
                config false;
                description "This Object is used to describes DHCP IP Address";
            } // END of ipDHCPAddr definition.

            leaf ipv6DHCPAddr  {
                if-feature feature_list:HAVE_DHCP_CLIENT;
                if-feature feature_list:HAVE_IPV6;
                type  cml_data_types:CML_IPV6_ADDR_T;
                config false;
                description "This Object is used to describes DHCP IPv6 Address";
            } // END of ipv6DHCPAddr definition.

            leaf ipAddr  {
                type  cml_data_types:CML_STRING_T;
                description "The IPv4 address to which this entry's addressing information pertains";
            } // END of ipAddr definition.

            leaf prefixlen  {
                type  cml_data_types:CML_UINT8_T;
                description "The subnet mask associated with the IPv4 address of this entry. The value of the mask is an IPv4 address with all the network bits set to 1 and all the hosts bits set to 0.";
            } // END of prefixlen definition.

            leaf ipLabel  {
                type  cml_data_types:CML_LINE_T;
                default "NULL";
                description "Label of this address";
            } // END of ipLabel definition.

            leaf unnumberedIpv4  {
                if-feature feature_list:HAVE_NSM_IF_UNNUMBERED;
                type  cml_data_types:CML_STRING_T;
                description "This Object is used to Enable IP processing without an explicit address";
            } // END of unnumberedIpv4 definition.

            leaf remoteAddr  {
                if-feature feature_list:HAVE_NSM_IF_UNNUMBERED;
                type  cml_data_types:CML_STRING_T;
                description "This Object is used to set the remote address of the PPP link";
            } // END of remoteAddr definition.

            leaf unnumberedIpv6  {
                if-feature feature_list:HAVE_NSM_IF_UNNUMBERED;
                if-feature feature_list:HAVE_IPV6;
                type  cml_data_types:CML_STRING_T;
                description "";
            } // END of unnumberedIpv6 definition.

            leaf vrfName  {
                if-feature feature_list:HAVE_VRF;
                type  cml_data_types:CML_STRING_T;
                description "This Object is used to associates an interface with a VRF";
            } // END of vrfName definition.

            leaf vrName  {
                if-feature feature_list:HAVE_VR;
                type  cml_data_types:CML_STRING_T;
                description "This Object is used to associates an interface with a VR";
            } // END of vrName definition.

            leaf loadInterval  {
                if-feature feature_list:HAVE_BROADCOM;
                type  cml_data_types:CML_UINT16_T {
                     range "30..300";
                }
                default "300";
                description "This Object is used to Set load interval";
            } // END of loadInterval definition.

            leaf rdmBwConstraint  {
                if-feature feature_list:HAVE_TE;
                if-feature feature_list:HAVE_DSTE;
                type  cml_data_types:CML_INT64_T;
                config false;
                description "Bandwidth constraint for RDM per class types(bytes per s)";
            } // END of rdmBwConstraint definition.

            leaf teclPriorityBw  {
                if-feature feature_list:HAVE_TE;
                type  cml_data_types:CML_INT64_T;
                config false;
                description "Available bandwidth at priority p, 0 <= p < 8";
            } // END of teclPriorityBw definition.

            leaf bindInfo  {
                type  cml_data_types:CML_BIND_INFO_T;
                config false;
                description "Bind information vrf, mpls_vc, mpls_vc_vlan, vpls, vpls_vlan, vxlan, nvgre";
            } // END of bindInfo definition.

            leaf vrxFlag  {
                if-feature feature_list:HAVE_VRX;
                type  cml_data_types:CML_VRX_FLAG_T;
                config false;
                description "This Object describes the vrx status";
            } // END of vrxFlag definition.

            leaf localSrc  {
                if-feature feature_list:HAVE_VRX;
                type  cml_data_types:CML_LOCAL_FLAG_T;
                config false;
                description "This Object describes the local Source";
            } // END of localSrc definition.

            leaf ifLastChange  {
                type  cml_data_types:CML_TIMETICKS_T;
                config false;
                description "The value of sysUpTime at the time the interface entered
            its current operational state.If the current state was
            entered prior to the last re-initialization of the local
            network management subsystem then this object contains a
            zero value";
            } // END of ifLastChange definition.

            leaf ifLastFlap  {
                type  cml_data_types:CML_DATE_TIME_T;
                config false;
                description "This Object describes the last interface flap";
            } // END of ifLastFlap definition.

            leaf ifLastCounterClear  {
                type  cml_data_types:CML_DATE_TIME_T;
                config false;
                description "This Object describes the last counter clear";
            } // END of ifLastCounterClear definition.

            leaf interfaceType  {
                type  cml_data_types:CML_INTERFACE_TYPE_T;
                config false;
                description "Interface type L2, L3, TDM";
            } // END of interfaceType definition.

            leaf trustState  {
                if-feature feature_list:HAVE_QOS;
                type  cml_data_types:CML_TRUST_STATE_T;
                config false;
                description "This Object describes the trust interface state";
            } // END of trustState definition.

            leaf ipv6Status  {
                if-feature feature_list:HAVE_IPV6;
                type  cml_data_types:CML_BOOL_T;
                config false;
                description "This Object describes the IPv6 capability status";
            } // END of ipv6Status definition.

            leaf ipv6Forwarding  {
                if-feature feature_list:HAVE_IPV6;
                type  cml_data_types:CML_BOOL_T;
                config false;
                description "This Object describes the IPv6 Forwarding";
            } // END of ipv6Forwarding definition.

            leaf ipv4Status  {
                type  cml_data_types:CML_BOOL_T;
                config false;
                description "This Object describes IPv4 capability status";
            } // END of ipv4Status definition.

            leaf mpgIf  {
                if-feature feature_list:HAVE_TFO;
                type  cml_data_types:CML_BOOL_T;
                config false;
                description "This Object describes mpg interface";
            } // END of mpgIf definition.

            leaf tfoLinkType  {
                if-feature feature_list:HAVE_TFO;
                type  cml_data_types:CML_TFO_LINK_TYPE_T;
                config false;
                description "This Object describes interface link type";
            } // END of tfoLinkType definition.

            leaf udldFlushTx  {
                if-feature feature_list:HAVE_UDLD;
                type  cml_data_types:CML_UINT16_T;
                config false;
                description "This Object describes interface udld Flush transmitted ";
            } // END of udldFlushTx definition.

            leaf macLearnLimit  {
                type  cml_data_types:CML_INT32_T;
                config false;
                description "This Object describes mac learning Limit";
            } // END of macLearnLimit definition.

            leaf jitterBuffer  {
                if-feature feature_list:HAVE_TDM_VC;
                type  cml_data_types:CML_UINT16_T {
                     range "1..500";
                }
                default "500";
                description "";
            } // END of jitterBuffer definition.

            leaf payLoadBytes  {
                if-feature feature_list:HAVE_TDM_VC;
                type  cml_data_types:CML_UINT32_T {
                     range "0..32768";
                }
                default "0";
                description "";
            } // END of payLoadBytes definition.

            leaf rtpHeader  {
                if-feature feature_list:HAVE_TDM_VC;
                type  cml_data_types:CML_BOOL_T;
                default false;
                description "";
            } // END of rtpHeader definition.

            leaf portBreakout  {
                if-feature feature_list:HAVE_FLEXPORT;
                type  cml_data_types:CML_NSM_BREAKOUT_TYPE_T;
                description "";
            } // END of portBreakout definition.

            leaf portBundle  {
                if-feature feature_list:HAVE_PORT_BUNDLE;
                if-feature feature_list:NOT_HAVE_TOMAHAWK;
                type  cml_data_types:CML_BOOL_T;
                default false;
                description "";
            } // END of portBundle definition.


            list secondary {
                key "secIpAddr";
                description
                    "Secondary IPv4 Address";
                leaf secIpAddr  {
                    type  cml_data_types:CML_STRING_T;
                    description "The IPv4 address to which this entry's addressing information pertains";
                } // END of secIpAddr definition.

                leaf ipLabel  {
                    type  cml_data_types:CML_LINE_T;
                    default "NULL";
                    description "To specify that an IP address and prefix length will be used by this interface. If the secondary parameter is not specified, this attribute overwrites the primary IP address. If the secondary parameter is specified, this attribute adds a new IP address to the interface. The secondary address cannot be configured in the absence of a primary IP address. The primary address cannot be removed when a secondary address is present.";
                } // END of ipLabel definition.

            } // End of secondary-list

            list ipv6Addr {
                if-feature feature_list:HAVE_IPV6;
                key "ipv6Addr";
                description
                    "IPv6 Address";
                leaf ipv6Addr  {
                    type  cml_data_types:CML_STRING_T;
                    description "This Object is used to describes the IPv6 address to which this entry's addressing information pertains.";
                } // END of ipv6Addr definition.

                leaf anycast  {
                    type  cml_data_types:CML_BOOL_T;
                    default false;
                    description "This Object is used set the IPv6 address of an interface";
                } // END of anycast definition.

            } // End of ipv6Addr-list

            list errorSet {
                if-feature feature_list:HAVE_TDM_VC;
                key "errorSetType";
                description
                    "Error set";
                leaf errorSetType  {
                    type  cml_data_types:CML_ERROR_SET_TYPE_T;
                    description "This Object is used to Set the error-set period";
                } // END of errorSetType definition.

                leaf errorSetPeriod  {
                    type  cml_data_types:CML_UINT32_T {
                         range "2000..10000";
                    }
                    mandatory true;
                    description "This Object describes the Range for setting the error-set period in millisec";
                } // END of errorSetPeriod definition.

            } // End of errorSet-list

            list errorClear {
                if-feature feature_list:HAVE_TDM_VC;
                key "errorClearType";
                description
                    "Error Clear";
                leaf errorClearType  {
                    type  cml_data_types:CML_ERROR_CLEAR_TYPE_T;
                    description "";
                } // END of errorClearType definition.

                leaf errorClearPeriod  {
                    type  cml_data_types:CML_UINT32_T {
                         range "2000..10000";
                    }
                    mandatory true;
                    description "";
                } // END of errorClearPeriod definition.

            } // End of errorClear-list
            container stormControlBcast {
                if-feature feature_list:HAVE_RATE_LIMIT;
                presence "yes";
                description
                    "bcast related commands";
                leaf bcastValue  {
                    type  cml_data_types:CML_RATE_LIMIT_T;
                    mandatory true;
                    description "This Object is used to set the storm control configuration,Set Broadcast Rate Limiting of layer2 Interface";
                } // END of bcastValue definition.

                leaf bcastBitsPerSecondFormat  {
                    type  cml_data_types:CML_RATE_LIMIT_TYPE;
                    description "";
                } // END of bcastBitsPerSecondFormat definition.

                leaf bcastDiscards  {
                    if-feature feature_list:HAVE_HAL;
                    if-feature feature_list:NOT_HAVE_BROADCOM;
                    type  cml_data_types:CML_INT32_T;
                    config false;
                    description "Bcast Storm Discards";
                } // END of bcastDiscards definition.

            } // END of stormControlBcast-container definition.
            container stormControlMcast {
                if-feature feature_list:HAVE_RATE_LIMIT;
                presence "yes";
                description
                    "mcast related commands";
                leaf mcastValue  {
                    type  cml_data_types:CML_RATE_LIMIT_T;
                    mandatory true;
                    description "This Object is used to set the storm control configuration,Set Multicast Rate Limiting of layer2 Interface";
                } // END of mcastValue definition.

                leaf mcastBitsPerSecondFormat  {
                    type  cml_data_types:CML_RATE_LIMIT_TYPE;
                    description "";
                } // END of mcastBitsPerSecondFormat definition.

                leaf mcastDiscards  {
                    if-feature feature_list:HAVE_HAL;
                    if-feature feature_list:NOT_HAVE_BROADCOM;
                    type  cml_data_types:CML_INT32_T;
                    config false;
                    description "Mcast Storm Discards";
                } // END of mcastDiscards definition.

            } // END of stormControlMcast-container definition.
            container stormControlDlfBcast {
                if-feature feature_list:HAVE_RATE_LIMIT;
                presence "yes";
                description
                    "dlfbcast related commands";
                leaf dlfbcastValue  {
                    type  cml_data_types:CML_RATE_LIMIT_T;
                    mandatory true;
                    description "This Object is used to set the storm control configuration,Set DLF Broadcast Rate Limiting of layer2 Interface";
                } // END of dlfbcastValue definition.

                leaf dlfBitsPerSecondFormat  {
                    type  cml_data_types:CML_RATE_LIMIT_TYPE;
                    description "";
                } // END of dlfBitsPerSecondFormat definition.

                leaf dlfDiscards  {
                    if-feature feature_list:HAVE_HAL;
                    if-feature feature_list:NOT_HAVE_BROADCOM;
                    type  cml_data_types:CML_UINT32_T;
                    config false;
                    description "dlf Bcast Storm Discards";
                } // END of dlfDiscards definition.

            } // END of stormControlDlfBcast-container definition.
            container switchportAllowedEthertypes {
                if-feature feature_list:HAVE_BROADCOM;
                if-feature feature_list:HAVE_L2;
                description
                    "Switching characteristics of the Layer2 interface";
                leaf arp  {
                    type  cml_data_types:CML_BOOL_T;
                    description "";
                } // END of arp definition.

                leaf ipv4  {
                    type  cml_data_types:CML_BOOL_T;
                    description "";
                } // END of ipv4 definition.

                leaf ipv6  {
                    type  cml_data_types:CML_BOOL_T;
                    description "";
                } // END of ipv6 definition.

                leaf mpls  {
                    type  cml_data_types:CML_BOOL_T;
                    description "";
                } // END of mpls definition.

                leaf-list ethertypeValue  {
                    type  cml_data_types:CML_STRING_T;
                    description "";
                } // END of ethertypeValue definition.

                leaf log  {
                    type  cml_data_types:CML_BOOL_T;
                    description "";
                } // END of log definition.


                list statistics {
                    if-feature feature_list:HAVE_BROADCOM;
                    if-feature feature_list:HAVE_L2;
                    key "ethertype";
                    config false;
                    description
                        "switchport allowed ethertype statistics per ethertype";
                    leaf ethertype  {
                        type  cml_data_types:CML_SWITCHPORT_ETHERTYPE_T;
                        description "Packet ethertype";
                    } // END of ethertype definition.

                    leaf packets  {
                        type  cml_data_types:CML_COUNTER64_T;
                        description "Packets count";
                    } // END of packets definition.

                    leaf bytes  {
                        type  cml_data_types:CML_COUNTER64_T;
                        description "Bytes count";
                    } // END of bytes definition.

                } // End of statistics-list
            } // END of switchportAllowedEthertypes-container definition.
            container IfFlowControl {
                description
                    "IEEE 802.3x Flow Control";
                leaf flowcontrolRcv  {
                    type  cml_data_types:CML_FLOWCTRL_T;
                    default "off";
                    description "This Object is used to show Flow control on receive";
                } // END of flowcontrolRcv definition.

                leaf flowcontrolSend  {
                    type  cml_data_types:CML_FLOWCTRL_T;
                    default "off";
                    description "This Object is used to show Flow control on send";
                } // END of flowcontrolSend definition.

                leaf flowcontrolRcvOperStatus  {
                    type  cml_data_types:CML_FLOWCTRL_T;
                    config false;
                    description "This Object is used to show Operations status of Flow control on receive";
                } // END of flowcontrolRcvOperStatus definition.

                leaf flowcontrolSendOperStatus  {
                    type  cml_data_types:CML_FLOWCTRL_T;
                    config false;
                    description "This Object is used to show Operations status of Flow control on send";
                } // END of flowcontrolSendOperStatus definition.

                leaf rxPause  {
                    type  cml_data_types:CML_COUNTER64_T;
                    config false;
                    description "Port receive flowcontrol";
                } // END of rxPause definition.

                leaf txPause  {
                    type  cml_data_types:CML_COUNTER64_T;
                    config false;
                    description "Port Send flowcontrol";
                } // END of txPause definition.

            } // END of IfFlowControl-container definition.
            container ifStat {
                config false;
                description
                    "interface Statistics fields";
                leaf rxPackets  {
                    type  cml_data_types:CML_UINT32_T;
                    description "This Object describes Received Packets";
                } // END of rxPackets definition.

                leaf txPackets  {
                    type  cml_data_types:CML_UINT32_T;
                    description "This Object describes Transmitted Packets";
                } // END of txPackets definition.

                leaf rxBytes  {
                    type  cml_data_types:CML_COUNTER64_T;
                    description "This Object describes Received bytes";
                } // END of rxBytes definition.

                leaf txBytes  {
                    type  cml_data_types:CML_COUNTER64_T;
                    description "This Object describes Transmitted bytes";
                } // END of txBytes definition.

                leaf rxerrors  {
                    type  cml_data_types:CML_UINT32_T;
                    description "This Object describes Received errors";
                } // END of rxerrors definition.

                leaf txerrors  {
                    type  cml_data_types:CML_UINT32_T;
                    description "This Object describes Transmitted errors";
                } // END of txerrors definition.

                leaf rxdropped  {
                    type  cml_data_types:CML_UINT32_T;
                    description "This Object describes Received dropped";
                } // END of rxdropped definition.

                leaf txdropped  {
                    type  cml_data_types:CML_UINT32_T;
                    description "This Object describes Transmitted dropped";
                } // END of txdropped definition.

                leaf rxmulticast  {
                    type  cml_data_types:CML_UINT32_T;
                    description "This Object describes Received multicast";
                } // END of rxmulticast definition.

                leaf rxcompressed  {
                    type  cml_data_types:CML_UINT32_T;
                    description "This Object describes Received compressed";
                } // END of rxcompressed definition.

                leaf txcompressed  {
                    type  cml_data_types:CML_UINT32_T;
                    description "This Object describes Transmitted compressed";
                } // END of txcompressed definition.

                leaf collisions  {
                    type  cml_data_types:CML_UINT32_T;
                    description "This Object describes collisions";
                } // END of collisions definition.

                leaf urpfDropped  {
                    type  cml_data_types:CML_UINT32_T;
                    description "";
                } // END of urpfDropped definition.

                leaf rxLengthErrors  {
                    type  cml_data_types:CML_UINT32_T;
                    description "This Object describes Received Length Errors";
                } // END of rxLengthErrors definition.

                leaf rxOverErrors  {
                    type  cml_data_types:CML_UINT32_T;
                    description "This Object describes Received over Errors";
                } // END of rxOverErrors definition.

                leaf rxCrcErrors  {
                    type  cml_data_types:CML_UINT32_T;
                    description "This Object describes Received CRC Errors";
                } // END of rxCrcErrors definition.

                leaf rxFrameErrors  {
                    type  cml_data_types:CML_UINT32_T;
                    description "This Object describes Received Frame Errors";
                } // END of rxFrameErrors definition.

                leaf rxFifoErrors  {
                    type  cml_data_types:CML_UINT32_T;
                    description "This Object describes Received Fifo Errors";
                } // END of rxFifoErrors definition.

                leaf rxMissedErrors  {
                    type  cml_data_types:CML_UINT32_T;
                    description "This Object describes Received Missed Errors";
                } // END of rxMissedErrors definition.

                leaf txAbortedErrors  {
                    type  cml_data_types:CML_UINT32_T;
                    description "This Object describes Transmitted Aborted Errors";
                } // END of txAbortedErrors definition.

                leaf txCarrierErrors  {
                    type  cml_data_types:CML_UINT32_T;
                    description "This Object describes Transmitted Carrier Errors";
                } // END of txCarrierErrors definition.

                leaf txFifoErrors  {
                    type  cml_data_types:CML_UINT32_T;
                    description "This Object describes Transmitted Fifo Errors";
                } // END of txFifoErrors definition.

                leaf txHeartbeatErrors  {
                    type  cml_data_types:CML_UINT32_T;
                    description "This Object describes Transmitted Heart beat Errors";
                } // END of txHeartbeatErrors definition.

                leaf txWindowErrors  {
                    type  cml_data_types:CML_UINT32_T;
                    description "This Object describes Transmitted Window Errors";
                } // END of txWindowErrors definition.

                leaf outErrors  {
                    if-feature feature_list:HAVE_BROADCOM;
                    if-feature feature_list:HAVE_HAL;
                    if-feature feature_list:NOT_HAVE_SWFWDR;
                    type  cml_data_types:CML_COUNTER64_T;
                    description "For packet-oriented interfaces, the number of outbound
            packets that could not be transmitted because of errors.
            For character-oriented or fixed-length interfaces, the
            number of outbound transmission units that could not be
            transmitted because of errors.

            Discontinuities in the value of this counter can occur at
            re-initialization of the management system, and at other
            times as indicated by the value of
            ifCounterDiscontinuityTime.";
                } // END of outErrors definition.

                leaf outDiscards  {
                    if-feature feature_list:HAVE_BROADCOM;
                    if-feature feature_list:HAVE_HAL;
                    if-feature feature_list:NOT_HAVE_SWFWDR;
                    type  cml_data_types:CML_COUNTER64_T;
                    description "The number of outbound packets which were chosen to be
            discarded even though no errors had been detected to prevent
            their being transmitted.  One possible reason for discarding
            such a packet could be to free up buffer space.

            Discontinuities in the value of this counter can occur at
            re-initialization of the management system, and at other
            times as indicated by the value of
            ifCounterDiscontinuityTime.";
                } // END of outDiscards definition.

                leaf outMcPkts  {
                    if-feature feature_list:HAVE_BROADCOM;
                    if-feature feature_list:HAVE_HAL;
                    if-feature feature_list:NOT_HAVE_SWFWDR;
                    type  cml_data_types:CML_COUNTER64_T;
                    description "The total number of packets that higher-level protocols
            requested be transmitted, and which were addressed to a
            multicast address at this sub-layer, including those that
            were discarded or not sent.  For a MAC layer protocol, this
            includes both Group and Functional addresses.

            Discontinuities in the value of this counter can occur at
            re-initialization of the management system, and at other
            times as indicated by the value of
            ifCounterDiscontinuityTime.";
                } // END of outMcPkts definition.

                leaf outUcPkts  {
                    if-feature feature_list:HAVE_BROADCOM;
                    if-feature feature_list:HAVE_HAL;
                    if-feature feature_list:NOT_HAVE_SWFWDR;
                    type  cml_data_types:CML_COUNTER64_T;
                    description "The total number of packets that higher-level protocols
            requested be transmitted, and which were not addressed to a
            multicast or broadcast address at this sub-layer, including
            those that were discarded or not sent.
            Discontinuities in the value of this counter can occur at
            re-initialization of the management system, and at other
            times as indicated by the value of
            ifCounterDiscontinuityTime.";
                } // END of outUcPkts definition.

                leaf inUcPkts  {
                    if-feature feature_list:HAVE_BROADCOM;
                    if-feature feature_list:HAVE_HAL;
                    if-feature feature_list:NOT_HAVE_SWFWDR;
                    type  cml_data_types:CML_COUNTER64_T;
                    description "The number of packets, delivered by this sub-layer to a
            higher (sub-)layer, which were not addressed to a multicast
            or broadcast address at this sub-layer.
            Discontinuities in the value of this counter can occur at
            re-initialization of the management system, and at other
            times as indicated by the value of
            ifCounterDiscontinuityTime.";
                } // END of inUcPkts definition.

                leaf inDiscards  {
                    if-feature feature_list:HAVE_BROADCOM;
                    if-feature feature_list:HAVE_HAL;
                    if-feature feature_list:NOT_HAVE_SWFWDR;
                    type  cml_data_types:CML_COUNTER64_T;
                    description "The number of inbound packets which were chosen to be
            discarded even though no errors had been detected to prevent
            their being deliverable to a higher-layer protocol.  One
            possible reason for discarding such a packet could be to
            free up buffer space.
            Discontinuities in the value of this counter can occur at
            re-initialization of the management system, and at other
            times as indicated by the value of
            ifCounterDiscontinuityTime.";
                } // END of inDiscards definition.

                leaf goodOctetsRcv  {
                    if-feature feature_list:HAVE_BROADCOM;
                    if-feature feature_list:HAVE_HAL;
                    if-feature feature_list:NOT_HAVE_SWFWDR;
                    type  cml_data_types:CML_COUNTER64_T;
                    description "This Object describes Good Octets Received";
                } // END of goodOctetsRcv definition.

                leaf badOctetsRcv  {
                    if-feature feature_list:HAVE_BROADCOM;
                    if-feature feature_list:HAVE_HAL;
                    if-feature feature_list:NOT_HAVE_SWFWDR;
                    type  cml_data_types:CML_COUNTER64_T;
                    description "This Object describes Bad Octets Received";
                } // END of badOctetsRcv definition.

                leaf macTransmitErr  {
                    if-feature feature_list:HAVE_BROADCOM;
                    if-feature feature_list:HAVE_HAL;
                    if-feature feature_list:NOT_HAVE_SWFWDR;
                    type  cml_data_types:CML_COUNTER64_T;
                    description "This Object describes MAC Transmit Error";
                } // END of macTransmitErr definition.

                leaf goodPktsRcv  {
                    if-feature feature_list:HAVE_BROADCOM;
                    if-feature feature_list:HAVE_HAL;
                    if-feature feature_list:NOT_HAVE_SWFWDR;
                    type  cml_data_types:CML_COUNTER64_T;
                    description "This Object describes Good packets Received";
                } // END of goodPktsRcv definition.

                leaf badPktsRcv  {
                    if-feature feature_list:HAVE_BROADCOM;
                    if-feature feature_list:HAVE_HAL;
                    if-feature feature_list:NOT_HAVE_SWFWDR;
                    type  cml_data_types:CML_COUNTER64_T;
                    description "This Object describes Bad packets Received";
                } // END of badPktsRcv definition.

                leaf pktsRcv  {
                    if-feature feature_list:HAVE_BROADCOM;
                    if-feature feature_list:HAVE_HAL;
                    if-feature feature_list:NOT_HAVE_SWFWDR;
                    type  cml_data_types:CML_COUNTER64_T;
                    description "This Object describes Packets Received";
                } // END of pktsRcv definition.

                leaf brdcPktsRcv  {
                    if-feature feature_list:HAVE_BROADCOM;
                    if-feature feature_list:HAVE_HAL;
                    if-feature feature_list:NOT_HAVE_SWFWDR;
                    type  cml_data_types:CML_COUNTER64_T;
                    description "This Object describes Broadcast packets Received";
                } // END of brdcPktsRcv definition.

                leaf mcPktsRcv  {
                    if-feature feature_list:HAVE_BROADCOM;
                    if-feature feature_list:HAVE_HAL;
                    if-feature feature_list:NOT_HAVE_SWFWDR;
                    type  cml_data_types:CML_COUNTER64_T;
                    description "This Object describes multicast packets Received";
                } // END of mcPktsRcv definition.

                leaf pkts64OctetsRcv  {
                    if-feature feature_list:HAVE_BROADCOM;
                    if-feature feature_list:HAVE_HAL;
                    if-feature feature_list:NOT_HAVE_SWFWDR;
                    type  cml_data_types:CML_COUNTER64_T;
                    description "This Object describes packets 64 Octets Received";
                } // END of pkts64OctetsRcv definition.

                leaf pkts65To127OctetsRcv  {
                    if-feature feature_list:HAVE_BROADCOM;
                    if-feature feature_list:HAVE_HAL;
                    if-feature feature_list:NOT_HAVE_SWFWDR;
                    type  cml_data_types:CML_COUNTER64_T;
                    description "This Object describes packets 65 to 127 Octets Received";
                } // END of pkts65To127OctetsRcv definition.

                leaf pkts128To255OctetsRcv  {
                    if-feature feature_list:HAVE_BROADCOM;
                    if-feature feature_list:HAVE_HAL;
                    if-feature feature_list:NOT_HAVE_SWFWDR;
                    type  cml_data_types:CML_COUNTER64_T;
                    description "This Object describes packets 128 to 255 Octets Received";
                } // END of pkts128To255OctetsRcv definition.

                leaf pkts256To511OctetsRcv  {
                    if-feature feature_list:HAVE_BROADCOM;
                    if-feature feature_list:HAVE_HAL;
                    if-feature feature_list:NOT_HAVE_SWFWDR;
                    type  cml_data_types:CML_COUNTER64_T;
                    description "This Object describes packets 256 to 511 Octets Received";
                } // END of pkts256To511OctetsRcv definition.

                leaf pkts512To1023OctetsRcv  {
                    if-feature feature_list:HAVE_BROADCOM;
                    if-feature feature_list:HAVE_HAL;
                    if-feature feature_list:NOT_HAVE_SWFWDR;
                    type  cml_data_types:CML_COUNTER64_T;
                    description "This Object describes packets 512 to 1023 Octets Received";
                } // END of pkts512To1023OctetsRcv definition.

                leaf pkts1024To1518OctetsRcv  {
                    if-feature feature_list:HAVE_BROADCOM;
                    if-feature feature_list:HAVE_HAL;
                    if-feature feature_list:NOT_HAVE_SWFWDR;
                    type  cml_data_types:CML_COUNTER64_T;
                    description "This Object describes packets 1024 to 1518 Octets Received";
                } // END of pkts1024To1518OctetsRcv definition.

                leaf pkts1519To2047OctetsRcv  {
                    if-feature feature_list:HAVE_BROADCOM;
                    if-feature feature_list:HAVE_HAL;
                    if-feature feature_list:NOT_HAVE_SWFWDR;
                    type  cml_data_types:CML_COUNTER64_T;
                    description "This Object describes packets 1519 to 2047 Octets Received";
                } // END of pkts1519To2047OctetsRcv definition.

                leaf pkts2048To4095OctetsRcv  {
                    if-feature feature_list:HAVE_BROADCOM;
                    if-feature feature_list:HAVE_HAL;
                    if-feature feature_list:NOT_HAVE_SWFWDR;
                    type  cml_data_types:CML_COUNTER64_T;
                    description "This Object describes packets 2048 to 4095 Octets Received";
                } // END of pkts2048To4095OctetsRcv definition.

                leaf pkts4096To9216OctetsRcv  {
                    if-feature feature_list:HAVE_BROADCOM;
                    if-feature feature_list:HAVE_HAL;
                    if-feature feature_list:NOT_HAVE_SWFWDR;
                    type  cml_data_types:CML_COUNTER64_T;
                    description "This Object describes packets 4096 to 9216 Octets Received";
                } // END of pkts4096To9216OctetsRcv definition.

                leaf pkts64Octets  {
                    if-feature feature_list:HAVE_BROADCOM;
                    if-feature feature_list:HAVE_HAL;
                    if-feature feature_list:NOT_HAVE_SWFWDR;
                    type  cml_data_types:CML_COUNTER64_T;
                    description "This Object describes packets 64 Octets count";
                } // END of pkts64Octets definition.

                leaf pkts65To127Octets  {
                    if-feature feature_list:HAVE_BROADCOM;
                    if-feature feature_list:HAVE_HAL;
                    if-feature feature_list:NOT_HAVE_SWFWDR;
                    type  cml_data_types:CML_COUNTER64_T;
                    description "This Object describes packets 65 to 127 Octets count";
                } // END of pkts65To127Octets definition.

                leaf pkts128To255Octets  {
                    if-feature feature_list:HAVE_BROADCOM;
                    if-feature feature_list:HAVE_HAL;
                    if-feature feature_list:NOT_HAVE_SWFWDR;
                    type  cml_data_types:CML_COUNTER64_T;
                    description "This Object describes packets 128 to 255 Octets count";
                } // END of pkts128To255Octets definition.

                leaf pkts256To511Octets  {
                    if-feature feature_list:HAVE_BROADCOM;
                    if-feature feature_list:HAVE_HAL;
                    if-feature feature_list:NOT_HAVE_SWFWDR;
                    type  cml_data_types:CML_COUNTER64_T;
                    description "This Object describes packets 256 to 511 Octets count";
                } // END of pkts256To511Octets definition.

                leaf pkts512To1023Octets  {
                    if-feature feature_list:HAVE_BROADCOM;
                    if-feature feature_list:HAVE_HAL;
                    if-feature feature_list:NOT_HAVE_SWFWDR;
                    type  cml_data_types:CML_COUNTER64_T;
                    description "This Object describes packets 512 to 1023 Octets count";
                } // END of pkts512To1023Octets definition.

                leaf pkts1024maxOctets  {
                    if-feature feature_list:HAVE_BROADCOM;
                    if-feature feature_list:HAVE_HAL;
                    if-feature feature_list:NOT_HAVE_SWFWDR;
                    type  cml_data_types:CML_COUNTER64_T;
                    description "This Object describes packets 1024 max Octets count";
                } // END of pkts1024maxOctets definition.

                leaf pkts1519To2047Octets  {
                    if-feature feature_list:HAVE_BROADCOM;
                    if-feature feature_list:HAVE_HAL;
                    if-feature feature_list:NOT_HAVE_SWFWDR;
                    type  cml_data_types:CML_COUNTER64_T;
                    description "This Object describes packets 1519 to 2047 Octets count";
                } // END of pkts1519To2047Octets definition.

                leaf pkts2048To4095Octets  {
                    if-feature feature_list:HAVE_BROADCOM;
                    if-feature feature_list:HAVE_HAL;
                    if-feature feature_list:NOT_HAVE_SWFWDR;
                    type  cml_data_types:CML_COUNTER64_T;
                    description "This Object describes packets 2048 to 4095 Octets count";
                } // END of pkts2048To4095Octets definition.

                leaf pkts4096To9216Octets  {
                    if-feature feature_list:HAVE_BROADCOM;
                    if-feature feature_list:HAVE_HAL;
                    if-feature feature_list:NOT_HAVE_SWFWDR;
                    type  cml_data_types:CML_COUNTER64_T;
                    description "This Object describes packets 4096 to 9216 Octets count";
                } // END of pkts4096To9216Octets definition.

                leaf goodOctetsSent  {
                    if-feature feature_list:HAVE_BROADCOM;
                    if-feature feature_list:HAVE_HAL;
                    if-feature feature_list:NOT_HAVE_SWFWDR;
                    type  cml_data_types:CML_COUNTER64_T;
                    description "This Object describes Good Octets Send";
                } // END of goodOctetsSent definition.

                leaf goodPktsSent  {
                    if-feature feature_list:HAVE_BROADCOM;
                    if-feature feature_list:HAVE_HAL;
                    if-feature feature_list:NOT_HAVE_SWFWDR;
                    type  cml_data_types:CML_COUNTER64_T;
                    description "This Object describes Good Packets Send";
                } // END of goodPktsSent definition.

                leaf excessiveCollisions  {
                    if-feature feature_list:HAVE_BROADCOM;
                    if-feature feature_list:HAVE_HAL;
                    if-feature feature_list:NOT_HAVE_SWFWDR;
                    type  cml_data_types:CML_COUNTER64_T;
                    description "This Object describes Excessive Collisions";
                } // END of excessiveCollisions definition.

                leaf mcPktsSent  {
                    if-feature feature_list:HAVE_BROADCOM;
                    if-feature feature_list:HAVE_HAL;
                    if-feature feature_list:NOT_HAVE_SWFWDR;
                    type  cml_data_types:CML_COUNTER64_T;
                    description "This Object describes multicast Packets Send";
                } // END of mcPktsSent definition.

                leaf brdcPktsSent  {
                    if-feature feature_list:HAVE_BROADCOM;
                    if-feature feature_list:HAVE_HAL;
                    if-feature feature_list:NOT_HAVE_SWFWDR;
                    type  cml_data_types:CML_COUNTER64_T;
                    description "This Object describes broadcast Packets Send";
                } // END of brdcPktsSent definition.

                leaf unrecogMacCntrRcv  {
                    if-feature feature_list:HAVE_BROADCOM;
                    if-feature feature_list:HAVE_HAL;
                    if-feature feature_list:NOT_HAVE_SWFWDR;
                    type  cml_data_types:CML_COUNTER64_T;
                    description "This Object describes unrecognized mac control received";
                } // END of unrecogMacCntrRcv definition.

                leaf fcSent  {
                    if-feature feature_list:HAVE_BROADCOM;
                    if-feature feature_list:HAVE_HAL;
                    if-feature feature_list:NOT_HAVE_SWFWDR;
                    type  cml_data_types:CML_COUNTER64_T;
                    description "This Object describes fc Sent";
                } // END of fcSent definition.

                leaf goodFcRcv  {
                    if-feature feature_list:HAVE_BROADCOM;
                    if-feature feature_list:HAVE_HAL;
                    if-feature feature_list:NOT_HAVE_SWFWDR;
                    type  cml_data_types:CML_COUNTER64_T;
                    description "This Object describes Good Fc Recived";
                } // END of goodFcRcv definition.

                leaf dropEvents  {
                    if-feature feature_list:HAVE_BROADCOM;
                    if-feature feature_list:HAVE_HAL;
                    if-feature feature_list:NOT_HAVE_SWFWDR;
                    type  cml_data_types:CML_COUNTER64_T;
                    description "This Object describes Drop Events";
                } // END of dropEvents definition.

                leaf undersizePkts  {
                    if-feature feature_list:HAVE_BROADCOM;
                    if-feature feature_list:HAVE_HAL;
                    if-feature feature_list:NOT_HAVE_SWFWDR;
                    type  cml_data_types:CML_COUNTER64_T;
                    description "The number of inbound packets discarded whose size are less than
             64 octets (which exclude framing bits, but include the FCS)
             and have a good FCS value.";
                } // END of undersizePkts definition.

                leaf fragmentsPkts  {
                    if-feature feature_list:HAVE_BROADCOM;
                    if-feature feature_list:HAVE_HAL;
                    if-feature feature_list:NOT_HAVE_SWFWDR;
                    type  cml_data_types:CML_COUNTER64_T;
                    description "The number of inbound packets discarded whose size are less than
             64 octets (which exclude framing bits, but include the FCS)
             and have a bad FCS value.";
                } // END of fragmentsPkts definition.

                leaf oversizePkts  {
                    if-feature feature_list:HAVE_BROADCOM;
                    if-feature feature_list:HAVE_HAL;
                    if-feature feature_list:NOT_HAVE_SWFWDR;
                    type  cml_data_types:CML_COUNTER64_T;
                    description "The number of inbound packets whose size are more than maximum
                      transmission unit size.";
                } // END of oversizePkts definition.

                leaf jabberPkts  {
                    if-feature feature_list:HAVE_BROADCOM;
                    if-feature feature_list:HAVE_HAL;
                    if-feature feature_list:NOT_HAVE_SWFWDR;
                    type  cml_data_types:CML_COUNTER64_T;
                    description "The number of inbound packets whose size are more than maximum
            transmission unit size (which excludes framing bits, but include
            FCS) and have a bad FCS value.";
                } // END of jabberPkts definition.

                leaf macRcvError  {
                    if-feature feature_list:HAVE_BROADCOM;
                    if-feature feature_list:HAVE_HAL;
                    if-feature feature_list:NOT_HAVE_SWFWDR;
                    type  cml_data_types:CML_COUNTER64_T;
                    description "This Object describes MAC Reacived Error";
                } // END of macRcvError definition.

                leaf badCrc  {
                    if-feature feature_list:HAVE_BROADCOM;
                    if-feature feature_list:HAVE_HAL;
                    if-feature feature_list:NOT_HAVE_SWFWDR;
                    type  cml_data_types:CML_COUNTER64_T;
                    description "The number of inbound packets which are chosen to be discarded,
                      since the packets have bad or no CRC.";
                } // END of badCrc definition.

                leaf dribble  {
                    if-feature feature_list:HAVE_BROADCOM;
                    if-feature feature_list:HAVE_HAL;
                    if-feature feature_list:NOT_HAVE_SWFWDR;
                    type  cml_data_types:CML_COUNTER64_T;
                    description "This Object describes Dribble";
                } // END of dribble definition.

                leaf collisionsState  {
                    if-feature feature_list:HAVE_BROADCOM;
                    if-feature feature_list:HAVE_HAL;
                    if-feature feature_list:NOT_HAVE_SWFWDR;
                    type  cml_data_types:CML_COUNTER64_T;
                    description "collisions State";
                } // END of collisionsState definition.

                leaf lateCollisions  {
                    if-feature feature_list:HAVE_BROADCOM;
                    if-feature feature_list:HAVE_HAL;
                    if-feature feature_list:NOT_HAVE_SWFWDR;
                    type  cml_data_types:CML_COUNTER64_T;
                    description "This Object describes late Collisions";
                } // END of lateCollisions definition.

                leaf deferredTx  {
                    if-feature feature_list:HAVE_BROADCOM;
                    if-feature feature_list:HAVE_HAL;
                    if-feature feature_list:NOT_HAVE_SWFWDR;
                    type  cml_data_types:CML_COUNTER64_T;
                    description "This Object describes Deferred Transmitted";
                } // END of deferredTx definition.

                leaf badFcRcv  {
                    if-feature feature_list:HAVE_BROADCOM;
                    if-feature feature_list:HAVE_HAL;
                    if-feature feature_list:NOT_HAVE_SWFWDR;
                    type  cml_data_types:CML_COUNTER64_T;
                    description "This Object describes Bad FC Received";
                } // END of badFcRcv definition.

                leaf portInoverflowFrames  {
                    if-feature feature_list:HAVE_BROADCOM;
                    if-feature feature_list:HAVE_HAL;
                    if-feature feature_list:NOT_HAVE_SWFWDR;
                    type  cml_data_types:CML_COUNTER64_T;
                    description "This Object describes port Inoverflow Frames";
                } // END of portInoverflowFrames definition.

                leaf portOutOverflowFrames  {
                    if-feature feature_list:HAVE_BROADCOM;
                    if-feature feature_list:HAVE_HAL;
                    if-feature feature_list:NOT_HAVE_SWFWDR;
                    type  cml_data_types:CML_COUNTER64_T;
                    description "This Object describes port OutOverflow Frames";
                } // END of portOutOverflowFrames definition.

                leaf portInOverflowDiscards  {
                    if-feature feature_list:HAVE_BROADCOM;
                    if-feature feature_list:HAVE_HAL;
                    if-feature feature_list:NOT_HAVE_SWFWDR;
                    type  cml_data_types:CML_COUNTER64_T;
                    description "This Object describes port InOverflow Discards";
                } // END of portInOverflowDiscards definition.

                leaf inFiltered  {
                    if-feature feature_list:HAVE_BROADCOM;
                    if-feature feature_list:HAVE_HAL;
                    if-feature feature_list:NOT_HAVE_SWFWDR;
                    type  cml_data_types:CML_COUNTER64_T;
                    description "This Object describes inFiltered count";
                } // END of inFiltered definition.

                leaf outFiltered  {
                    if-feature feature_list:HAVE_BROADCOM;
                    if-feature feature_list:HAVE_HAL;
                    if-feature feature_list:NOT_HAVE_SWFWDR;
                    type  cml_data_types:CML_COUNTER64_T;
                    description "This Object describes outFiltered count";
                } // END of outFiltered definition.

                leaf mtuExceed  {
                    if-feature feature_list:HAVE_BROADCOM;
                    if-feature feature_list:HAVE_HAL;
                    if-feature feature_list:NOT_HAVE_SWFWDR;
                    type  cml_data_types:CML_COUNTER64_T;
                    description "This Object describes mtu Exceed count";
                } // END of mtuExceed definition.

                leaf inJumbo  {
                    if-feature feature_list:HAVE_BROADCOM;
                    if-feature feature_list:HAVE_HAL;
                    if-feature feature_list:NOT_HAVE_SWFWDR;
                    type  cml_data_types:CML_COUNTER64_T;
                    description "This Object describes inJumbo count";
                } // END of inJumbo definition.

                leaf outJumbo  {
                    if-feature feature_list:HAVE_BROADCOM;
                    if-feature feature_list:HAVE_HAL;
                    if-feature feature_list:NOT_HAVE_SWFWDR;
                    type  cml_data_types:CML_COUNTER64_T;
                    description "This Object describes outJumbo count";
                } // END of outJumbo definition.

                leaf rxPktRate  {
                    if-feature feature_list:HAVE_BROADCOM;
                    if-feature feature_list:HAVE_HAL;
                    if-feature feature_list:NOT_HAVE_SWFWDR;
                    type  cml_data_types:CML_COUNTER64_T;
                    description "This Object describes Recived Packet Rate";
                } // END of rxPktRate definition.

                leaf rxBitRate  {
                    if-feature feature_list:HAVE_BROADCOM;
                    if-feature feature_list:HAVE_HAL;
                    if-feature feature_list:NOT_HAVE_SWFWDR;
                    type  cml_data_types:CML_COUNTER64_T;
                    description "This Object describes Recived BitRate";
                } // END of rxBitRate definition.

                leaf txPktRate  {
                    if-feature feature_list:HAVE_BROADCOM;
                    if-feature feature_list:HAVE_HAL;
                    if-feature feature_list:NOT_HAVE_SWFWDR;
                    type  cml_data_types:CML_COUNTER64_T;
                    description "This Object describes Transmitted packet Rate";
                } // END of txPktRate definition.

                leaf txBitRate  {
                    if-feature feature_list:HAVE_BROADCOM;
                    if-feature feature_list:HAVE_HAL;
                    if-feature feature_list:NOT_HAVE_SWFWDR;
                    type  cml_data_types:CML_COUNTER64_T;
                    description "This Object describes Transmitted BitRate";
                } // END of txBitRate definition.

            } // END of ifStat-container definition.
            container ifProtocolPktStat {
                if-feature feature_list:HAVE_HAL;
                if-feature feature_list:HAVE_BROADCOM;
                if-feature feature_list:NOT_HAVE_DUNE;
                config false;
                description
                    "Display stats for protocol pkts";
                leaf lacp  {
                    type  cml_data_types:CML_UINT32_T;
                    description "LACP Protocol Packets received on the interface";
                } // END of lacp definition.

                leaf stp  {
                    type  cml_data_types:CML_UINT32_T;
                    description "stp protocol ";
                } // END of stp definition.

                leaf lldp  {
                    type  cml_data_types:CML_UINT32_T;
                    description "lldp protocol Packets received on the interface";
                } // END of lldp definition.

                leaf bgp  {
                    type  cml_data_types:CML_UINT32_T;
                    description "bgp protocol Packets received on the interface";
                } // END of bgp definition.

                leaf rip  {
                    type  cml_data_types:CML_UINT32_T;
                    description "rip protocol Packets received on the interface";
                } // END of rip definition.

                leaf ospf  {
                    type  cml_data_types:CML_UINT32_T;
                    description "ospf protocol Packets received on the interface";
                } // END of ospf definition.

                leaf isis  {
                    type  cml_data_types:CML_UINT32_T;
                    description "isis protocol Packets received on the interface";
                } // END of isis definition.

                leaf efm  {
                    type  cml_data_types:CML_UINT32_T;
                    description "efm protocol Packets received on the interface";
                } // END of efm definition.

                leaf slow  {
                    type  cml_data_types:CML_UINT32_T;
                    description "slow protocol Packets received on the interface";
                } // END of slow definition.

                leaf elmi  {
                    type  cml_data_types:CML_UINT32_T;
                    description "elmi protocol Packets received on the interface";
                } // END of elmi definition.

                leaf ldpRsvp  {
                    type  cml_data_types:CML_UINT32_T;
                    description "ldp_rsvp protocol Packets received on the interface";
                } // END of ldpRsvp definition.

                leaf trill  {
                    type  cml_data_types:CML_UINT32_T;
                    description "trill protocol Packets received on the interface";
                } // END of trill definition.

                leaf icmp6  {
                    type  cml_data_types:CML_UINT32_T;
                    description "icmp protocol Packets received on the interface";
                } // END of icmp6 definition.

                leaf arp  {
                    type  cml_data_types:CML_UINT32_T;
                    description "arp protocol Packets received on the interface";
                } // END of arp definition.

                leaf dhcp  {
                    type  cml_data_types:CML_UINT32_T;
                    description "dhcp protocol Packets received on the interface";
                } // END of dhcp definition.

                leaf vxlan  {
                    type  cml_data_types:CML_UINT32_T;
                    description "vxlan protocol Packets received on the interface";
                } // END of vxlan definition.

                leaf igmp  {
                    type  cml_data_types:CML_UINT32_T;
                    description "igmp protocol Packets received on the interface";
                } // END of igmp definition.

                leaf vrrp  {
                    type  cml_data_types:CML_UINT32_T;
                    description "vrrp protocol Packets received on the interface";
                } // END of vrrp definition.

                leaf pim  {
                    type  cml_data_types:CML_UINT32_T;
                    description "pim protocol Packets received on the interface";
                } // END of pim definition.

                leaf eapol  {
                    type  cml_data_types:CML_UINT32_T;
                    description "eapol protocol Packets received on the interface";
                } // END of eapol definition.

                leaf total  {
                    type  cml_data_types:CML_UINT32_T;
                    description "total protocol Packets received on the interface";
                } // END of total definition.

            } // END of ifProtocolPktStat-container definition.
            container IfCapabilities {
                if-feature feature_list:HAVE_HAL;
                config false;
                description
                    "Physical interface capablities";
                leaf speedHalfDuplex  {
                    type  cml_data_types:CML_RAW_STRING_T {
                        pattern "[^ ]*";
                        }
                        description "Interface Speed half duplex capability";
                    } // END of speedHalfDuplex definition.

                    leaf speedFullDuplex  {
                        type  cml_data_types:CML_RAW_STRING_T {
                            pattern "[^ ]*";
                            }
                            description "Interface Speed full duplex capability";
                        } // END of speedFullDuplex definition.

                        leaf pause  {
                            type  cml_data_types:CML_RAW_STRING_T {
                                pattern "[^ ]*";
                                }
                                description "Interface pause Capability";
                            } // END of pause definition.

                            leaf interface  {
                                type  cml_data_types:CML_RAW_STRING_T {
                                    pattern "[^ ]*";
                                    }
                                    description "Interface Capability";
                                } // END of interface definition.

                                leaf medium  {
                                    type  cml_data_types:CML_RAW_STRING_T {
                                        pattern "[^ ]*";
                                        }
                                        description "Interface medium Capability";
                                    } // END of medium definition.

                                    leaf loopback  {
                                        type  cml_data_types:CML_RAW_STRING_T {
                                            pattern "[^ ]*";
                                            }
                                            description "Interface loopback Capability";
                                        } // END of loopback definition.

                                        leaf flags  {
                                            type  cml_data_types:CML_STRING_T;
                                            description "Interface flags Capability";
                                        } // END of flags definition.

                                        leaf eee  {
                                            type  cml_data_types:CML_STRING_T;
                                            description "Interface eee Capability";
                                        } // END of eee definition.

                                        leaf fcmap  {
                                            type  cml_data_types:CML_STRING_T;
                                            description "Interface fcmap Capability";
                                        } // END of fcmap definition.

                                        leaf encap  {
                                            type  cml_data_types:CML_RAW_STRING_T {
                                                pattern "[^ ]*";
                                                }
                                                description "Interface encap Capability";
                                            } // END of encap definition.

                                            leaf fec  {
                                                type  cml_data_types:CML_STRING_T;
                                                description "Interface fec Capability";
                                            } // END of fec definition.

            } // END of IfCapabilities-container definition.
            container IfOBMDropStats {
                if-feature feature_list:HAVE_OBM_DROP_CNTRS;
                config false;
                description
                    "Display OBM Drop stats with reason";
                container totalCount {
                    if-feature feature_list:HAVE_OBM_DROP_CNTRS;
                    config false;
                    description
                        "Hal interface discard reason stats total";
                    leaf HighPriDrops  {
                        type  cml_data_types:CML_COUNTER64_T;
                        description "Packets dropped because of high priority over subscription";
                    } // END of HighPriDrops definition.

                    leaf LowPriDrops  {
                        type  cml_data_types:CML_COUNTER64_T;
                        description "Packets dropped because of low priority over subscription";
                    } // END of LowPriDrops definition.

                    leaf Lossless0Drops  {
                        type  cml_data_types:CML_COUNTER64_T;
                        description "Packets dropped because of Lossless0 over subscription";
                    } // END of Lossless0Drops definition.

                    leaf Lossless1Drops  {
                        type  cml_data_types:CML_COUNTER64_T;
                        description "Packets dropped because of Lossless1 over subscription";
                    } // END of Lossless1Drops definition.

                    leaf TotalObmDrops  {
                        type  cml_data_types:CML_COUNTER64_T;
                        description "Total packets dropped because of over subscription";
                    } // END of TotalObmDrops definition.

                } // END of totalCount-container definition.
                container lastIncrementCount {
                    if-feature feature_list:HAVE_OBM_DROP_CNTRS;
                    config false;
                    description
                        "Interface discard reason stats last";
                    leaf HighPriDrops  {
                        type  cml_data_types:CML_COUNTER64_T;
                        description "Last number of Packets dropped because of high priority over subscription
              This is Updated at every 5sec interval.
            ";
                    } // END of HighPriDrops definition.

                    leaf LowPriDrops  {
                        type  cml_data_types:CML_COUNTER64_T;
                        description "Last number of Packets dropped because of low priority over subscription
              This is Updated at every 5sec interval.
            ";
                    } // END of LowPriDrops definition.

                    leaf Lossless0Drops  {
                        type  cml_data_types:CML_COUNTER64_T;
                        description "Last number of Packets dropped because of lossless0 over subscription
              This is Updated at every 5sec interval.
            ";
                    } // END of Lossless0Drops definition.

                    leaf Lossless1Drops  {
                        type  cml_data_types:CML_COUNTER64_T;
                        description "Last number of Packets dropped because of lossless1 over subscription
              This is Updated at every 5sec interval.
            ";
                    } // END of Lossless1Drops definition.

                    leaf TotalObmDrops  {
                        type  cml_data_types:CML_COUNTER64_T;
                        description "Total last number of packets dropped because of over subscription
              This is Updated at every 5sec interval.
            ";
                    } // END of TotalObmDrops definition.

                } // END of lastIncrementCount-container definition.
                container lastIncrementTime {
                    if-feature feature_list:HAVE_OBM_DROP_CNTRS;
                    config false;
                    description
                        "Interface discard timestamp";
                    leaf HighPriDrops  {
                        type  cml_data_types:CML_DATE_TIME_T;
                        description "Last increment time of OBM high priority dropped packets.
              This is Updated at every 5sec interval.
            ";
                    } // END of HighPriDrops definition.

                    leaf LowPriDrops  {
                        type  cml_data_types:CML_DATE_TIME_T;
                        description "Last increment time of OBM low priority dropped packets.
              This is Updated at every 5sec interval.
            ";
                    } // END of LowPriDrops definition.

                    leaf Lossless0Drops  {
                        type  cml_data_types:CML_DATE_TIME_T;
                        description "Last increment time of OBM lossless0 dropped packets.
              This is Updated at every 5sec interval.
            ";
                    } // END of Lossless0Drops definition.

                    leaf Lossless1Drops  {
                        type  cml_data_types:CML_DATE_TIME_T;
                        description "Last increment time of OBM lossless1 dropped packets.
              This is Updated at every 5sec interval.
            ";
                    } // END of Lossless1Drops definition.

                    leaf TotalObmDrops  {
                        type  cml_data_types:CML_DATE_TIME_T;
                        description "Total last increment time of OBM dropped packets.
              This is Updated at every 5sec interval.
            ";
                    } // END of TotalObmDrops definition.

                } // END of lastIncrementTime-container definition.
            } // END of IfOBMDropStats-container definition.
            container prefixSegment {
                if-feature feature_list:HAVE_SR;
                description
                    "prefix segment";
                leaf sid  {
                    type  cml_data_types:CML_SR_SID_T;
                    description "Segment Route Prefix SID";
                } // END of sid definition.

                leaf expNull  {
                    type  cml_data_types:CML_SR_PREFIX_FLAG_T;
                    description "This Object describes except Null";
                } // END of expNull definition.

                leaf nFlagClear  {
                    type  cml_data_types:CML_SR_N_FLAG_CLEAR_T;
                    description "This Object is used to set n-flag-clear";
                } // END of nFlagClear definition.

            } // END of prefixSegment-container definition.
            container nsmtunnelInterface {
                if-feature feature_list:HAVE_TUNNEL;
                description
                    "interface tunnel related operations";
                leaf tunnelMode  {
                    type  cml_data_types:CML_TUNNEL_MODE_T;
                    default "vxlan";
                    description "";
                } // END of tunnelMode definition.

                leaf nsmTunnel  {
                    type  cml_data_types:CML_IPV4_ADDR_T;
                    description "";
                } // END of nsmTunnel definition.

                leaf tunnelMcastInterface  {
                    type  cml_data_types:CML_STRING_T;
                    description "Configure egress interface for multicast tunnel";
                } // END of tunnelMcastInterface definition.

                leaf tunneldestination  {
                    type  cml_data_types:CML_IPV4_ADDR_T;
                    description "";
                } // END of tunneldestination definition.

                leaf checksum  {
                    type  cml_data_types:CML_BOOL_T;
                    description "";
                } // END of checksum definition.

                leaf tunnelTos  {
                    type  cml_data_types:CML_UINT16_T {
                         range "0..255";
                    }
                    description "";
                } // END of tunnelTos definition.

                leaf tunnelTtl  {
                    type  cml_data_types:CML_UINT16_T {
                         range "1..255";
                    }
                    description "";
                } // END of tunnelTtl definition.

                leaf tunnelPathMtu  {
                    type  cml_data_types:CML_BOOL_T;
                    description "";
                } // END of tunnelPathMtu definition.

                leaf tunnelDmac  {
                    if-feature feature_list:ENABLE_HAL_PATH;
                    type  cml_data_types:CML_STRING_T;
                    description "";
                } // END of tunnelDmac definition.

                leaf tunnelkey  {
                    if-feature feature_list:HAVE_GRE_KEY;
                    type  cml_data_types:CML_TUNNEL_KEY_T;
                    description "";
                } // END of tunnelkey definition.

                leaf tunnelIpv6Mode  {
                    if-feature feature_list:HAVE_TUNNEL_IPV6;
                    type  cml_data_types:CML_TUNNEL_IPV6_MODE_T;
                    default "ipv6ip";
                    description "";
                } // END of tunnelIpv6Mode definition.

            } // END of nsmtunnelInterface-container definition.
            uses ifErrorDiscardCounters;
            uses l2Movement-grouping;
            uses portChannelLoadBalBrcm-grouping;
            uses switchportInterface-grouping;
            uses nsmlacpInterface-grouping;
            uses nsmportInterface-grouping;
            uses nsmPoInterfaceBandwidth-grouping;
            uses lacpInterface-grouping;
            uses lldpv2Interface-grouping;
            uses ribInterface-grouping;
            uses ospfInterface-grouping;
            uses pim4Interface-grouping;
            uses dhcp6interface-grouping;
            uses dhcprelayinterface-grouping;
            uses dhcpClientInterface-grouping;
            uses sflowInterfaceConfigs-grouping;
            uses mrib4Interface-grouping;
            uses mrib4IgmpInterface-grouping;
            uses igmpSnoopInterface-grouping;
            uses mlagAgg-grouping;
            uses qosInterface-grouping;
            uses cmmInterface-grouping;
            uses aclInterface-grouping;
            uses rpfInfo-grouping;
            uses trillinterface-grouping;
            uses nd_interface-grouping;
            uses ndipv6staticnbrentry-grouping;
            uses rtadvInterfaceNdPrefix-grouping;
            uses rtadvInterface-grouping;
            uses nat_interface-grouping;
        } // End of interface-list
    } // END of interface-grouping definition.


    grouping ifIndexList-grouping {
    description
        "interface index details";
        list ifIndexList {
            key "ifIndex";
            config false;
            description
                "interface index details";
            leaf ifIndex  {
                type  cml_data_types:CML_INT32_T;
                description "A unique value, greater than zero, for each interface.It is recommended that values are assigned contiguously starting from 1.The value for each interface sub-layer must remain constant at least from one re-initialization of the entity's network management system to the next re-initialization.";
            } // END of ifIndex definition.

            leaf ifName  {
                type  cml_data_types:CML_LINE_T;
                description "The textual name of the interface. The value of this object should be
            the name of the interface as assigned by the local device and should be suitable
            for use in commands entered at the device's `console'. This might be a text name,
            such as `le0' or a simple port number, such as `1', depending on the interface
            naming syntax of the device. If several entries in the ifTable together represent
            a single interface as named by the device, then each will have the same value of
            ifName. Note that for an agent which responds to SNMP queries concerning an
            interface on some other (proxied) device, then the value of ifName for such an
            interface is the proxied device's local name for it. If there is no local name,
            or this object is otherwise not applicable, then this object contains a zero-length
            string.";
            } // END of ifName definition.

            leaf errDisReason  {
                type  cml_data_types:CML_NSM_ERRDISABLE_STATE_T;
                description "This object specifies the event that caused the interface to be error-disabled. If interface is error-disabled because of lag-mismatch, value of this object is 1. If interface is error-disabled because of stp-bpdu-guard, value of this object is 2. If interface is error-disabled because of link-flap, value of this object is 4.";
            } // END of errDisReason definition.

            leaf aggDownMinLink  {
                type  cml_data_types:CML_BOOL_T;
                description "aggDownMinLink Flag is set then Interface moved to Down state Min Links else move to Up state Min Links";
            } // END of aggDownMinLink definition.

            leaf arpDiscardPackets  {
                if-feature feature_list:HAVE_VXLAN;
                type  cml_data_types:CML_COUNTER64_T;
                description "This Object describes Arp Discard Packets(Applicable only for logical VxLAN-access ports)";
            } // END of arpDiscardPackets definition.

            leaf txArpDiscardPackets  {
                if-feature feature_list:HAVE_VXLAN;
                type  cml_data_types:CML_COUNTER64_T;
                description "This Object describes Arp Out Discard Packets(Applicable only for logical VxLAN-access ports)";
            } // END of txArpDiscardPackets definition.

            leaf rxArpRequestPackets  {
                if-feature feature_list:HAVE_VXLAN;
                type  cml_data_types:CML_COUNTER64_T;
                description "This Object describes Arp request Received Packets(Applicable only for logical VxLAN-access ports)";
            } // END of rxArpRequestPackets definition.

            leaf rxArpReplyPackets  {
                if-feature feature_list:HAVE_VXLAN;
                type  cml_data_types:CML_COUNTER64_T;
                description "This Object describes Arp reply Received Packets(Applicable only for logical VxLAN-access ports)";
            } // END of rxArpReplyPackets definition.

            leaf txArpRequestPackets  {
                if-feature feature_list:HAVE_VXLAN;
                type  cml_data_types:CML_COUNTER64_T;
                description "This Object describes Arp request Transmitted Packets(Applicable only for logical VxLAN-access ports)";
            } // END of txArpRequestPackets definition.

            leaf txArpReplyPackets  {
                if-feature feature_list:HAVE_VXLAN;
                type  cml_data_types:CML_COUNTER64_T;
                description "This Object describes Arp reply Transmitted Packets(Applicable only for logical VxLAN-access ports)";
            } // END of txArpReplyPackets definition.

            leaf ndDiscardPackets  {
                if-feature feature_list:HAVE_VXLAN;
                type  cml_data_types:CML_COUNTER64_T;
                description "This Object describes ND Discard Packets(Applicable only for logical VxLAN-access ports)";
            } // END of ndDiscardPackets definition.

            leaf txNdDiscardPackets  {
                if-feature feature_list:HAVE_VXLAN;
                type  cml_data_types:CML_COUNTER64_T;
                description "This Object describes ND Out Discard Packets(Applicable only for logical VxLAN-access ports)";
            } // END of txNdDiscardPackets definition.

            leaf rxNeighborSolicitationPackets  {
                if-feature feature_list:HAVE_VXLAN;
                type  cml_data_types:CML_COUNTER64_T;
                description "This Object describes ND Solicitaion Received Packets(Applicable only for logical VxLAN-access ports)";
            } // END of rxNeighborSolicitationPackets definition.

            leaf rxNeighborAdvertisementPackets  {
                if-feature feature_list:HAVE_VXLAN;
                type  cml_data_types:CML_COUNTER64_T;
                description "This Object describes ND Advertisement Received Packets(Applicable only for logical VxLAN-access ports)";
            } // END of rxNeighborAdvertisementPackets definition.

            leaf txNeighborSolicitationPackets  {
                if-feature feature_list:HAVE_VXLAN;
                type  cml_data_types:CML_COUNTER64_T;
                description "This Object describes ND Solicitaion Transmitted Packets(Applicable only for logical VxLAN-access ports)";
            } // END of txNeighborSolicitationPackets definition.

            leaf txNeighborAdvertisementPackets  {
                if-feature feature_list:HAVE_VXLAN;
                type  cml_data_types:CML_COUNTER64_T;
                description "This Object describes ND Advertisement Transmitted Packets(Applicable only for logical VxLAN-access ports)";
            } // END of txNeighborAdvertisementPackets definition.

            leaf rxGarpPackets  {
                if-feature feature_list:HAVE_VXLAN;
                type  cml_data_types:CML_COUNTER64_T;
                description "This Object describes Garp Received Packets(Applicable only for logical VxLAN-access ports)";
            } // END of rxGarpPackets definition.

            leaf txGarpPackets  {
                if-feature feature_list:HAVE_VXLAN;
                type  cml_data_types:CML_COUNTER64_T;
                description "This Object describes Garp Transmitted Packets(Applicable only for logical VxLAN-access ports)";
            } // END of txGarpPackets definition.

            leaf rxGnaPackets  {
                if-feature feature_list:HAVE_VXLAN;
                type  cml_data_types:CML_COUNTER64_T;
                description "This Object describes Gna Received Packets(Applicable only for logical VxLAN-access ports)";
            } // END of rxGnaPackets definition.

            leaf txGnaPackets  {
                if-feature feature_list:HAVE_VXLAN;
                type  cml_data_types:CML_COUNTER64_T;
                description "This Object describes Gna Transmitted Packets(Applicable only for logical VxLAN-access ports)";
            } // END of txGnaPackets definition.

        } // End of ifIndexList-list
    } // END of ifIndexList-grouping definition.
    grouping ifErrorDiscardCounters {
        description
            "Grouping for error_counters discard_counters";
        container IfErrorPktStat {
            if-feature feature_list:HAVE_HAL;
            if-feature feature_list:HAVE_BROADCOM;
            if-feature feature_list:NOT_HAVE_DUNE;
            config false;
            description
                "Statistics of error packets received";
            container totalCount {
                if-feature feature_list:HAVE_HAL;
                if-feature feature_list:HAVE_BROADCOM;
                if-feature feature_list:NOT_HAVE_DUNE;
                config false;
                description
                    "Interface error reason stats total";
                leaf badPktsRcv  {
                    type  cml_data_types:CML_COUNTER64_T;
                    description "Rx bad packet receive";
                } // END of badPktsRcv definition.

                leaf undersizePkts  {
                    type  cml_data_types:CML_COUNTER64_T;
                    description "Last inbound packets discarded whose size are less than
             64 octets (which exclude framing bits, but include the FCS)
             and have a good FCS value.
             This is Updated at every 5sec interval.";
                } // END of undersizePkts definition.

                leaf fragmentsPkts  {
                    type  cml_data_types:CML_COUNTER64_T;
                    description "The number of inbound packets discarded whose size are less than
             64 octets (which exclude framing bits, but include the FCS)
             and have a bad FCS value.";
                } // END of fragmentsPkts definition.

                leaf mtuExceed  {
                    type  cml_data_types:CML_COUNTER64_T;
                    description "Rx Oversize Packets";
                } // END of mtuExceed definition.

                leaf jabberPkts  {
                    type  cml_data_types:CML_COUNTER64_T;
                    description "The number of inbound packets whose size are more than maximum
            transmission unit size (which excludes framing bits, but include
            FCS) and have a bad FCS value.";
                } // END of jabberPkts definition.

                leaf badCrc  {
                    type  cml_data_types:CML_COUNTER64_T;
                    description "Last inbound packets which are chosen to be discarded,
            since the packets have bad or no CRC.
            This is Updated at every 5sec interval.";
                } // END of badCrc definition.

            } // END of totalCount-container definition.
            container lastIncrementCount {
                if-feature feature_list:HAVE_HAL;
                if-feature feature_list:HAVE_BROADCOM;
                if-feature feature_list:NOT_HAVE_DUNE;
                config false;
                description
                    "Hal interface error reason stats last";
                leaf badPktsRcv  {
                    type  cml_data_types:CML_COUNTER64_T;
                    description "Rx bad packets";
                } // END of badPktsRcv definition.

                leaf undersizePkts  {
                    type  cml_data_types:CML_COUNTER64_T;
                    description "Last inbound packets discarded whose size are less than
             64 octets (which exclude framing bits, but include the FCS)
             and have a good FCS value.
             This is Updated at every 5sec interval.";
                } // END of undersizePkts definition.

                leaf fragmentsPkts  {
                    type  cml_data_types:CML_COUNTER64_T;
                    description "Last inbound packets discarded whose size are less than
             64 octets (which exclude framing bits, but include the FCS)
             and have a bad FCS value.
             This is Updated at every 5sec interval.";
                } // END of fragmentsPkts definition.

                leaf mtuExceed  {
                    type  cml_data_types:CML_COUNTER64_T;
                    description "Rx Oversize Packets";
                } // END of mtuExceed definition.

                leaf jabberPkts  {
                    type  cml_data_types:CML_COUNTER64_T;
                    description "Last inbound packets whose size are more than maximum
            transmission unit size (which excludes framing bits, but include
            FCS) and have a bad FCS value.
            This is Updated at every 5sec interval.";
                } // END of jabberPkts definition.

                leaf badCrc  {
                    type  cml_data_types:CML_COUNTER64_T;
                    description "Last increment time of Bad CRC packets.
             This is Updated at every 5sec interval.";
                } // END of badCrc definition.

            } // END of lastIncrementCount-container definition.
            container lastIncrementTime {
                if-feature feature_list:HAVE_HAL;
                if-feature feature_list:HAVE_BROADCOM;
                if-feature feature_list:NOT_HAVE_DUNE;
                config false;
                description
                    "Hal error timestamp";
                leaf undersize  {
                    type  cml_data_types:CML_DATE_TIME_T;
                    description "Last increment time of Undersize packets.
             This is Updated at every 5sec interval.";
                } // END of undersize definition.

                leaf fragments  {
                    type  cml_data_types:CML_DATE_TIME_T;
                    description "Last increment time of Fragment error packets.
             This is Updated at every 5sec interval.";
                } // END of fragments definition.

                leaf mtuExceed  {
                    type  cml_data_types:CML_DATE_TIME_T;
                    description "Rx Oversize errors";
                } // END of mtuExceed definition.

                leaf jabber  {
                    type  cml_data_types:CML_DATE_TIME_T;
                    description "Last increment time of Jabber packets.
             This is Updated at every 5sec interval.";
                } // END of jabber definition.

                leaf badCrc  {
                    type  cml_data_types:CML_DATE_TIME_T;
                    description "Last increment time of Bad CRC packets.
                         This is Updated at every 5sec interval.";
                } // END of badCrc definition.

            } // END of lastIncrementTime-container definition.
        } // END of IfErrorPktStat-container definition.
        container IfDiscardStats {
            if-feature feature_list:HAVE_HAL;
            if-feature feature_list:HAVE_BROADCOM;
            if-feature feature_list:NOT_HAVE_DUNE;
            config false;
            description
                "Display Indiscard/Outdiscard stats with reason";
            container totalCount {
                if-feature feature_list:HAVE_HAL;
                if-feature feature_list:HAVE_BROADCOM;
                if-feature feature_list:NOT_HAVE_DUNE;
                config false;
                description
                    "Hal interface discard reason stats total";
                leaf rxPortBlockDrops  {
                    type  cml_data_types:CML_COUNTER64_T;
                    description "The number of packets received when the ingress interface is not in
          STP forwarding state.";
                } // END of rxPortBlockDrops definition.

                leaf rxvlanDiscards  {
                    type  cml_data_types:CML_COUNTER64_T;
                    description "The number of VLAN tagged packets received on a port which is not
           a member of the VLAN or untagged packets received on a trunk port.";
                } // END of rxvlanDiscards definition.

                leaf rxACLQoSDrops  {
                    type  cml_data_types:CML_COUNTER64_T;
                    description "Incoming packets match a field processing entry with a drop or color
          drop action, such as:
           a) User-configured ACL that denies traffic
           b) Service policy with a police action that drops the traffic received
               at a rate higher than the configured limit.";
                } // END of rxACLQoSDrops definition.

                leaf rxPolicyDrops  {
                    type  cml_data_types:CML_COUNTER64_T;
                    description "Inbound packets those are discarded for Device policies violation,
          such as a storm control rate violation.";
                } // END of rxPolicyDrops definition.

                leaf rxIBPDiscards  {
                    type  cml_data_types:CML_COUNTER64_T;
                    description "Inbound packets that are chosen to be discarded with Ingress Back
           Pressure (ingress congestion) when the ingress packet buffer is
           full for an interface.";
                } // END of rxIBPDiscards definition.

                leaf rxEGRPortUnavail  {
                    type  cml_data_types:CML_COUNTER64_T;
                    description "Packets discarded since No output port can be determined for this packet.
          This counter increments along with other counter types in this table
          because it is a catchall for multiple types of discards such as,
            a) VLAN check failed
            b) MTU check failed
            c) ACL/QoS drops
            d) Policy discards
            e) Source MAC is null
            f) Destination IP/source IP address is null
            g) Source MAC and destination MAC address are the same
            h) Forwarding lookup failure";
                } // END of rxEGRPortUnavail definition.

                leaf rxTotalDiscards  {
                    type  cml_data_types:CML_COUNTER64_T;
                    description "Rx total discards";
                } // END of rxTotalDiscards definition.

                leaf txPortBlockDrops  {
                    type  cml_data_types:CML_COUNTER64_T;
                    description "The number of packets discarded when the egress interface is not in
          STP forwarding state.";
                } // END of txPortBlockDrops definition.

                leaf txvlanDiscards  {
                    type  cml_data_types:CML_COUNTER64_T;
                    description "Packets discarded because an invalid VLAN tag is encountered at an
          egress interface.";
                } // END of txvlanDiscards definition.

                leaf txTTLDiscards  {
                    type  cml_data_types:CML_COUNTER64_T;
                    description "Packets discarded because the Time-To Live (TTL) of the outgoing
          packet has passed.";
                } // END of txTTLDiscards definition.

                leaf txUnknownDiscards  {
                    type  cml_data_types:CML_COUNTER64_T;
                    description "Packets discarded for other possible reasons like ACL drop in egress
          or a policer drop in egress. Discards caused by congestion at queues
          and drops at queues are not counted under unknown discards.";
                } // END of txUnknownDiscards definition.

                leaf txUnicastQueueDrops  {
                    type  cml_data_types:CML_COUNTER64_T;
                    description "Packets dropped in the unicast queues because of congestion.";
                } // END of txUnicastQueueDrops definition.

                leaf txMcastQueueDrops  {
                    type  cml_data_types:CML_COUNTER64_T;
                    description "Packets dropped in the multicast queues because of congestion.";
                } // END of txMcastQueueDrops definition.

                leaf txTotalDiscards  {
                    type  cml_data_types:CML_COUNTER64_T;
                    description "Tx Total Discards";
                } // END of txTotalDiscards definition.

            } // END of totalCount-container definition.
            container lastIncrementCount {
                if-feature feature_list:HAVE_HAL;
                if-feature feature_list:HAVE_BROADCOM;
                if-feature feature_list:NOT_HAVE_DUNE;
                config false;
                description
                    "Interface discard reason stats last";
                leaf rxPortBlockDrops  {
                    type  cml_data_types:CML_COUNTER64_T;
                    description "Last number of packets received when the ingress interface is not in
          STP forwarding state.
          This is Updated at every 5sec interval.";
                } // END of rxPortBlockDrops definition.

                leaf rxvlanDiscards  {
                    type  cml_data_types:CML_COUNTER64_T;
                    description "Last number of VLAN tagged packets received on a port which is not
           a member of the VLAN or untagged packets received on a trunk port.
           This is Updated at every 5sec interval.";
                } // END of rxvlanDiscards definition.

                leaf rxACLQoSDrops  {
                    type  cml_data_types:CML_COUNTER64_T;
                    description "Last number Incoming packets discarded due to Acl/Qos.
          This is Updated at every 5sec interval.";
                } // END of rxACLQoSDrops definition.

                leaf rxPolicyDrops  {
                    type  cml_data_types:CML_COUNTER64_T;
                    description "Last Inbound packets those are discarded for Device policies violation,
          such as a storm control rate violation.
          This is Updated at every 5sec interval.";
                } // END of rxPolicyDrops definition.

                leaf rxIBPDiscards  {
                    type  cml_data_types:CML_COUNTER64_T;
                    description "Last Inbound packets that are chosen to be discarded with Ingress Back
           Pressure (ingress congestion) when the ingress packet buffer is
           full for an interface.
           This is Updated at every 5sec interval.";
                } // END of rxIBPDiscards definition.

                leaf rxEGRPortUnavail  {
                    type  cml_data_types:CML_COUNTER64_T;
                    description "Last number of packets discarded in EgrPortUnavail category.
          This is Updated at every 5sec interval.";
                } // END of rxEGRPortUnavail definition.

                leaf rxTotalDiscards  {
                    type  cml_data_types:CML_COUNTER64_T;
                    description "Rx total discards";
                } // END of rxTotalDiscards definition.

                leaf txPortBlockDrops  {
                    type  cml_data_types:CML_COUNTER64_T;
                    description "Last number of packets discarded when the egress interface is not in
          STP forwarding state.
          This is Updated at every 5sec interval.";
                } // END of txPortBlockDrops definition.

                leaf txvlanDiscards  {
                    type  cml_data_types:CML_COUNTER64_T;
                    description "Last number of Packets discarded because of invalid VLAN tag in
          egress interface.
          This is Updated at every 5sec interval.";
                } // END of txvlanDiscards definition.

                leaf txTTLDiscards  {
                    type  cml_data_types:CML_COUNTER64_T;
                    description "Last number of Packets discarded since TTL of the outgoing
          packet has passed.
          This is Updated at every 5sec interval.";
                } // END of txTTLDiscards definition.

                leaf txUnknownDiscards  {
                    type  cml_data_types:CML_COUNTER64_T;
                    description "Last Tx Packets discarded for other possible reasons like ACL drop in egress
          or a policer drop in egress. Discards caused by congestion at queues
          and drops at queues are not counted under unknown discards.
          This is Updated at every 5sec interval.";
                } // END of txUnknownDiscards definition.

                leaf txUnicastQueueDrops  {
                    type  cml_data_types:CML_COUNTER64_T;
                    description "Last Packets dropped in the unicast queues because of congestion.
          This is Updated at every 5sec interval.";
                } // END of txUnicastQueueDrops definition.

                leaf txMcastQueueDrops  {
                    type  cml_data_types:CML_COUNTER64_T;
                    description "Last number of Packets dropped in the multicast queues because
          of congestion.
          This is Updated at every 5sec interval.";
                } // END of txMcastQueueDrops definition.

                leaf txTotalDiscards  {
                    type  cml_data_types:CML_COUNTER64_T;
                    description "Tx Total Discards";
                } // END of txTotalDiscards definition.

            } // END of lastIncrementCount-container definition.
            container lastIncrementTime {
                if-feature feature_list:HAVE_HAL;
                if-feature feature_list:HAVE_BROADCOM;
                if-feature feature_list:NOT_HAVE_DUNE;
                config false;
                description
                    "Interface discard timestamp";
                leaf rxPortBlockDrops  {
                    type  cml_data_types:CML_DATE_TIME_T;
                    description "Last increment time of packets received when interface not in
             forwarding state.
             This is Updated at every 5sec interval.";
                } // END of rxPortBlockDrops definition.

                leaf rxvlanDiscards  {
                    type  cml_data_types:CML_DATE_TIME_T;
                    description "Last increment time of VLAN discarded packets.
             This is Updated at every 5sec interval.";
                } // END of rxvlanDiscards definition.

                leaf rxACLQoSDrops  {
                    type  cml_data_types:CML_DATE_TIME_T;
                    description "Last increment time of Acl/QoS discarded packets.
             This is Updated at every 5sec interval.";
                } // END of rxACLQoSDrops definition.

                leaf rxPolicyDrops  {
                    type  cml_data_types:CML_DATE_TIME_T;
                    description "Last increment time of Policy violation packets.
             This is Updated at every 5sec interval.";
                } // END of rxPolicyDrops definition.

                leaf rxIBPDiscards  {
                    type  cml_data_types:CML_DATE_TIME_T;
                    description "Last increment time of IBP Discards.
             This is Updated at every 5sec interval.";
                } // END of rxIBPDiscards definition.

                leaf rxEGRPortUnavail  {
                    type  cml_data_types:CML_DATE_TIME_T;
                    description "Last increment time of Egress Port Unavailability packets.
             This is Updated at every 5sec interval.";
                } // END of rxEGRPortUnavail definition.

                leaf txPortBlockDrops  {
                    type  cml_data_types:CML_DATE_TIME_T;
                    description "Last increment time of Tx Discards when egress interface is not in
             forwarding state.
             This is Updated at every 5sec interval.";
                } // END of txPortBlockDrops definition.

                leaf txvlanDiscards  {
                    type  cml_data_types:CML_DATE_TIME_T;
                    description "Last increment time of Tx Vlan Discards.
             This is Updated at every 5sec interval.";
                } // END of txvlanDiscards definition.

                leaf txTTLDiscards  {
                    type  cml_data_types:CML_DATE_TIME_T;
                    description "Last increment time of Tx TTL Discards.
             This is Updated at every 5sec interval.";
                } // END of txTTLDiscards definition.

                leaf txUnknownDiscards  {
                    type  cml_data_types:CML_DATE_TIME_T;
                    description "Last increment time of Tx Unknown Discards.
             This is Updated at every 5sec interval.";
                } // END of txUnknownDiscards definition.

                leaf txUnicastQueueDrops  {
                    type  cml_data_types:CML_DATE_TIME_T;
                    description "Last increment time of Tx Unicast queue Discards.
             This is Updated at every 5sec interval.";
                } // END of txUnicastQueueDrops definition.

                leaf txMcastQueueDrops  {
                    type  cml_data_types:CML_DATE_TIME_T;
                    description "Last increment time of Tx Multicast queue Discards.
             This is Updated at every 5sec interval.";
                } // END of txMcastQueueDrops definition.

            } // END of lastIncrementTime-container definition.
        } // END of IfDiscardStats-container definition.
    } // END of ifErrorDiscardCounters definition.

    grouping  ifArbiter-grouping {
    description
        "arbiter to check interface information periodically";
    container ifArbiter {
        if-feature feature_list:HAVE_NSM_IF_ARBITER;
        description
            "arbiter to check interface information periodically";
        leaf ifArbiter  {
            type  cml_data_types:CML_UINT32_T {
                 range "1..65535";
            }
            default "20";
            description "";
        } // END of ifArbiter definition.

    } // END of ifArbiter-container definition.
    } // END of ifArbiter-container definition.

    grouping  nsmMaster-grouping {
    description
        "Global configs for router";
    container nsmMaster {
        description
            "Global configs for router";
        leaf routerId  {
            type  cml_data_types:CML_STRING_T;
            description "";
        } // END of routerId definition.

        leaf enableAutoRouterIdSelection  {
            type  cml_data_types:CML_BOOL_T;
            description "Turn on Automatic Selection of Router ID";
        } // END of enableAutoRouterIdSelection definition.

        leaf enableIpForwarding  {
            type  cml_data_types:CML_BOOL_T;
            description "Turn on IP forwarding";
        } // END of enableIpForwarding definition.

        leaf enableIpv6Forwarding  {
            if-feature feature_list:HAVE_IPV6;
            type  cml_data_types:CML_BOOL_T;
            description "Turn on IPv6 forwarding";
        } // END of enableIpv6Forwarding definition.

        leaf icmpBroadcast  {
            type  cml_data_types:CML_BOOL_T;
            description "Turn on ICMP echo broadcast reply";
        } // END of icmpBroadcast definition.

        leaf hardwareProfilePortMode  {
            if-feature feature_list:HAVE_FLEXPORT;
            type  cml_data_types:CML_NSM_HARDWARE_PORTMODE_T;
            description "This Object is to set port mode";
        } // END of hardwareProfilePortMode definition.

        leaf hardwareProfilePortModeBundle  {
            if-feature feature_list:HAVE_PORT_BUNDLE;
            if-feature feature_list:NOT_HAVE_TOMAHAWK;
            type  cml_data_types:CML_NSM_HARDWARE_PROFILE_PORTMODE_BUNDLE_T;
            description "This Object is to set port bundling/";
        } // END of hardwareProfilePortModeBundle definition.

        leaf mutihomingEnable  {
            if-feature feature_list:HAVE_VXLAN;
            type  cml_data_types:CML_BOOL_T;
            default false;
            description "Enable EVPN multihoming";
        } // END of mutihomingEnable definition.


        list vrf {
            key "vrfName";
            description
                "Virtual routing and forwarding";
            leaf vrfName  {
                type  cml_data_types:CML_STRING_T;
                description "";
            } // END of vrfName definition.

            leaf ipVrfForwarding  {
                type  cml_data_types:CML_BOOL_T;
                description "Turn on IP forwarding";
            } // END of ipVrfForwarding definition.

            leaf ipv6VrfForwarding  {
                if-feature feature_list:HAVE_IPV6;
                type  cml_data_types:CML_BOOL_T;
                description "Turn on IPv6 forwarding";
            } // END of ipv6VrfForwarding definition.

            leaf icmpVrfBroadcast  {
                type  cml_data_types:CML_BOOL_T;
                description "Turn on ICMP echo broadcast reply";
            } // END of icmpVrfBroadcast definition.

        } // End of vrf-list
        container srNsm {
            if-feature feature_list:HAVE_SR;
            description
                "Global Block";
            leaf baseSid  {
                type  cml_data_types:CML_UINT32_T {
                     range "16000..23999";
                }
                description "This is used set Global Block Starting Range";
            } // END of baseSid definition.

            leaf last  {
                type  cml_data_types:CML_UINT32_T {
                     range "16000..23999";
                }
                description "This is used set Global Block End Range";
            } // END of last definition.

        } // END of srNsm-container definition.
        container errdisable {
            description
                "Error Disable Configuration";
            leaf errdisableReason  {
                type  cml_data_types:CML_NSM_ERR_REASON_T;
                description "This object is to enable various errdisable reasons like lag-mismatch, stp-bpdu-guard and link-flap. As the datatype is BITS, 0th bit corresponds to lag-mismatch, 1st bit corresponds to stp-bpdu-guard, 2nd bit corresponds to link-flap";
            } // END of errdisableReason definition.

            leaf errdisableTimeoutInterval  {
                type  cml_data_types:CML_UINT32_T {
                     range "0..1000000";
                }
                default "0";
                description "This object is to configure timeout for errdisable automatic recovery timer";
            } // END of errdisableTimeoutInterval definition.

            leaf linkFlapMaxCount  {
                type  cml_data_types:CML_UINT32_T {
                     range "1..100";
                }
                default "5";
                description "This object is to configure allowed flap count to detect link-flap errdisable";
            } // END of linkFlapMaxCount definition.

            leaf linkFlapTimerInterval  {
                type  cml_data_types:CML_UINT32_T {
                     range "1..1800";
                }
                default "10";
                description " This object is configure timer interval for link-flap timer";
            } // END of linkFlapTimerInterval definition.

        } // END of errdisable-container definition.
        container arpEntry {
            description
                "Arp Entry";

            list staticArpList {
                if-feature feature_list:HAVE_L3;
                if-feature feature_list:NOT_HAVE_NDD;
                key "arpAddr";
                description
                    "static Arp List";
                leaf arpAddr  {
                    type  cml_data_types:CML_IPV4_ADDR_T;
                    description "This Object is to set IP address of the ARP entry";
                } // END of arpAddr definition.

                leaf macAddr  {
                    type  cml_data_types:CML_MAC_ADDR_T;
                    mandatory true;
                    description "To Set Mac (hardware) address of the ARP entry";
                } // END of macAddr definition.

                leaf isArpProxy  {
                    type  cml_data_types:CML_BOOL_T;
                    mandatory true;
                    description "";
                } // END of isArpProxy definition.

            } // End of staticArpList-list

            list ipv6StaticNbrTable {
                if-feature feature_list:HAVE_L3;
                if-feature feature_list:HAVE_IPV6;
                if-feature feature_list:NOT_HAVE_NDD;
                key "nbrAddr";
                description
                    "ipv6 Neighbour Table Static";
                leaf nbrAddr  {
                    type  cml_data_types:CML_IPV6_ADDR_T;
                    description "To Set Neighbors IPv6 address";
                } // END of nbrAddr definition.

                leaf ifName  {
                    type  cml_data_types:CML_STRING_T;
                    mandatory true;
                    description "This Object is used to set Interface name";
                } // END of ifName definition.

                leaf macAddr  {
                    type  cml_data_types:CML_MAC_ADDR_T;
                    mandatory true;
                    description "This Object is used to set MAC (hardware) address";
                } // END of macAddr definition.

            } // End of ipv6StaticNbrTable-list
        } // END of arpEntry-container definition.
    } // END of nsmMaster-container definition.
    } // END of nsmMaster-container definition.

    grouping  cpuInterface-grouping {
    description
        "Description about CPU interface";
    container cpuInterface {
        if-feature feature_list:HAVE_HAL;
        if-feature feature_list:HAVE_BROADCOM;
        if-feature feature_list:NOT_HAVE_DUNE;
        config false;
        description
            "Description about CPU interface";
        container cpuStats {
            if-feature feature_list:HAVE_HAL;
            if-feature feature_list:HAVE_BROADCOM;
            if-feature feature_list:NOT_HAVE_DUNE;
            config false;
            description
                "Statistics of cpu queue";
            leaf rxDiscardPackets  {
                type  cml_data_types:CML_COUNTER64_T;
                description "Last Drop Packet Count";
            } // END of rxDiscardPackets definition.


            list queueStats {
                if-feature feature_list:HAVE_HAL;
                if-feature feature_list:HAVE_BROADCOM;
                if-feature feature_list:NOT_HAVE_DUNE;
                key "queueId";
                config false;
                description
                    "CPU cosq stats";
                leaf queueId  {
                    type  cml_data_types:CML_UINT8_T;
                    description "cpuqueueId is a unique number representing each queue in CPU";
                } // END of queueId definition.

                leaf queueName  {
                    type  cml_data_types:CML_STRING_T;
                    description "Queue Name corresponding to the QueueId.";
                } // END of queueName definition.

                leaf txPkts  {
                    type  cml_data_types:CML_COUNTER64_T;
                    description "The number of outbound packets that are transmitted through the
            queue";
                } // END of txPkts definition.

                leaf txBytes  {
                    type  cml_data_types:CML_COUNTER64_T;
                    description "The number of outbound bytes that are transmitted through the
            queue";
                } // END of txBytes definition.

                leaf droppedPkts  {
                    type  cml_data_types:CML_COUNTER64_T;
                    description "The number of tx packets that are dropped in the
            queue.";
                } // END of droppedPkts definition.

                leaf droppedBytes  {
                    type  cml_data_types:CML_COUNTER64_T;
                    description "The number of tx bytes that are dropped in the
            queue";
                } // END of droppedBytes definition.

                leaf qSizeInBytes  {
                    type  cml_data_types:CML_COUNTER64_T;
                    description "The size of the queue, referred by the  queueId";
                } // END of qSizeInBytes definition.

                container CpuCosqRateStats {
                    if-feature feature_list:HAVE_HAL;
                    if-feature feature_list:HAVE_BROADCOM;
                    if-feature feature_list:NOT_HAVE_DUNE;
                    config false;
                    description
                        "cpu cosq rate stats";
                    leaf txPktRate  {
                        type  cml_data_types:CML_UINT32_T;
                        description "The number of Tx Pkts transmitted from the corresponding CPU queue.";
                    } // END of txPktRate definition.

                    leaf txBitRate  {
                        type  cml_data_types:CML_UINT32_T;
                        description "The number of Tx Bytes transmitted from the corresponding CPU queue.";
                    } // END of txBitRate definition.

                    leaf ratePercent  {
                        type  cml_data_types:CML_INT8_T;
                        description "Percentage of control packets transmitted in the CPU queue.
            Value of -1 indicates rate percentage is not applicable.";
                    } // END of ratePercent definition.

                    leaf lastIncrementCnt  {
                        type  cml_data_types:CML_COUNTER64_T;
                        description "The number of Last Dropped Pkts in the corresponding CPU queue.
            This is Updated at every 5sec interval.";
                    } // END of lastIncrementCnt definition.

                    leaf lastIncrementTime  {
                        type  cml_data_types:CML_DATE_TIME_T;
                        description "Last increment time of Tx Dropped Packets in CPU Queue.
             This is Updated at every 5sec interval.";
                    } // END of lastIncrementTime definition.

                } // END of CpuCosqRateStats-container definition.
            } // End of queueStats-list
        } // END of cpuStats-container definition.
        uses ifErrorDiscardCounters;
    } // END of cpuInterface-container definition.
    } // END of cpuInterface-container definition.


}
