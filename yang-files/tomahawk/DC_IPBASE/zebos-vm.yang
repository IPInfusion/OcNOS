/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-vm.yang
*
*/

submodule zebos-vm {

    belongs-to  zebos { prefix zebos; }

    import cml_data_types {
        prefix cml_data_types;
    }

    import ietf-inet-types {
        prefix inet;
    }

    import feature_list {
        prefix feature_list;
    }

    organization
        "IP Infusion Inc.";

    contact
        "Address: 3965 Freedom Circle, Suite 200, Santa Clara, CA 95054
        Phone: +1 408-400-1900
        E-mail: support@ipinfusion.com
        Web: http://www.ipinfusion.com/";

    description
        "Virtual Machine";


    revision "2018-10-24" {
        description "Adding support for Guest-VM feature.";
        reference "";
    }



    typedef  CML_PROTO_T {
        type enumeration {
            enum tcp {
                value 1;
                description "Give TCP";
            }
            enum udp {
                value 2;
                description "Give UDP";
            }
        }
        description "";
        reference "";
    }

    typedef  CML_VM_OS_TYPE_T {
        type enumeration {
            enum xen {
                value 1;
                description "Give xen";
            }
            enum linux {
                value 2;
                description "Give linux";
            }
            enum hvm {
                value 3;
                description "Give hvm";
            }
            enum exe {
                value 4;
                description "Give exe";
            }
            enum uml {
                value 5;
                description "Give uml";
            }
        }
        description "";
        reference "";
    }

    typedef  CML_VM_OS_VARIANT_T {
        type enumeration {
            enum generic {
                value 1;
                description "Give generic";
            }
            enum fedora {
                value 2;
                description "Give fedora";
            }
            enum rhel {
                value 3;
                description "Give rhel";
            }
            enum ubuntu {
                value 4;
                description "Give ubuntu";
            }
            enum debian {
                value 5;
                description "Give debian";
            }
        }
        description "";
        reference "";
    }

    typedef  CML_VM_VIRT_TYPE_T {
        type enumeration {
            enum kvm {
                value 1;
                description "Give kvm";
            }
            enum qemu {
                value 2;
                description "Give qemu";
            }
        }
        description "";
        reference "";
    }

    grouping vmtemplate-grouping {
    description
        "vmtemplate";
        list vmtemplate {
            if-feature feature_list:HAVE_GUEST_VM;
            key "vmTemplateName";
            description
                "vmtemplate";
            leaf vrId  {
                type  cml_data_types:CML_INT32_T;
                default "0";
                description "";
            } // END of vrId definition.

            leaf vmTemplateName  {
                type  cml_data_types:CML_STRING_T {
                    length "1..16";
                }
                description "";
            } // END of vmTemplateName definition.

            leaf memory  {
                type  cml_data_types:CML_INT32_T {
                     range "128..8192";
                }
                default "128";
                description "Used to set the Memory for Virtual Machine in MB";
            } // END of memory definition.

            leaf osType  {
                type  CML_VM_OS_TYPE_T;
                default "hvm";
                description "Used to set the operating system type of Virtual Machine";
            } // END of osType definition.

            leaf osVariant  {
                type  CML_VM_OS_VARIANT_T;
                default "generic";
                description "Used to set the operating system variant of Virtual Machine";
            } // END of osVariant definition.

            leaf osVirtType  {
                type  CML_VM_VIRT_TYPE_T;
                description "Used to set the virtualization type of Virtual Machine";
            } // END of osVirtType definition.

            leaf diskImage  {
                type  cml_data_types:CML_STRING_T;
                description "Used to set the location of the disk image to boot up Virtual Machine";
            } // END of diskImage definition.

            leaf secondaryDiskImage  {
                type  cml_data_types:CML_STRING_T;
                description "Used to set the location of the secondary disk image to boot up Virtual Machine";
            } // END of secondaryDiskImage definition.

            leaf hostCoreAffinity  {
                type  cml_data_types:CML_VM_AFFINITY_T;
                description "Used to set the core affinity value";
            } // END of hostCoreAffinity definition.

            leaf vcpu  {
                type  cml_data_types:CML_INT8_T {
                     range "1..16";
                }
                default "1";
                description "Used to set the virtual CPU count for Virtual Machine";
            } // END of vcpu definition.


            list vNICList {
                key "vNIC";
                description
                    "vNICList";
                leaf vNIC  {
                    type  cml_data_types:CML_BOOL_T;
                    description "Used to set the virtual NIC ID for Virtual Machine";
                } // END of vNIC definition.

                leaf macAddress  {
                    type  cml_data_types:CML_MAC_ADDR_T;
                    description "Used to set the MAC Address for Virtual Machine";
                } // END of macAddress definition.

                leaf vrfName  {
                    type  cml_data_types:CML_STRING_T {
                        length "1..16";
                    }
                    default "default";
                    description "Used to set the vrf name";
                } // END of vrfName definition.

            } // End of vNICList-list
        } // End of vmtemplate-list
    } // END of vmtemplate-grouping definition.


    grouping vmContList-grouping {
    description
        "vmContList";
        list vmContList {
            if-feature feature_list:HAVE_GUEST_VM;
            key "vmName";
            description
                "vmContList";
            leaf startvm  {
                type  cml_data_types:CML_BOOL_T;
                description "Used to start the guest VM";
            } // END of startvm definition.

            leaf vmName  {
                type  cml_data_types:CML_STRING_T {
                    length "1..16";
                }
                description "Used to set the vrf name";
            } // END of vmName definition.

            leaf vmTemplateName  {
                type  cml_data_types:CML_STRING_T {
                    length "1..16";
                }
                description "Used to set the VM template";
            } // END of vmTemplateName definition.

        } // End of vmContList-list
    } // END of vmContList-grouping definition.


    grouping iptable-grouping {
    description
        "iptable";
        list iptable {
            if-feature feature_list:HAVE_GUEST_VM;
            key "ipTabTempName";
            description
                "iptable";
            leaf ipTabTempName  {
                type  cml_data_types:CML_STRING_T {
                    length "1..16";
                }
                description "";
            } // END of ipTabTempName definition.


            list ipTabRuleStrList {
                key "ipTabRuleStr";
                description
                    "ipTabRuleStrList";
                leaf ipTabRuleStr  {
                    type  cml_data_types:CML_LINE_T;
                    description "Used to set the rules for iptables";
                } // END of ipTabRuleStr definition.

                leaf ipTabrulePos  {
                    type  cml_data_types:CML_INT32_T {
                         range "-1..65535";
                    }
                    mandatory true;
                    description "Used to set the position of the ip-tables rules";
                } // END of ipTabrulePos definition.

            } // End of ipTabRuleStrList-list
        } // End of iptable-list
    } // END of iptable-grouping definition.


    grouping restoreList-grouping {
    description
        "restoreList";
        list restoreList {
            if-feature feature_list:HAVE_GUEST_VM;
            key "vrfName";
            description
                "restoreList";
            leaf vrfName  {
                type  cml_data_types:CML_STRING_T;
                description "Used to set the vrf name";
            } // END of vrfName definition.


            list restoreList {
                key "ipTabTempName";
                description
                    "restoreList";
                leaf ipTabTempName  {
                    type  cml_data_types:CML_STRING_T {
                        length "1..16";
                    }
                    description "Used to set the iptables template";
                } // END of ipTabTempName definition.

                leaf iptables  {
                    type  cml_data_types:CML_BOOL_T;
                    description "This is string not an input";
                } // END of iptables definition.

            } // End of restoreList-list
        } // End of restoreList-list
    } // END of restoreList-grouping definition.


    grouping srcNatList-grouping {
    description
        "srcNatList";
        list srcNatList {
            if-feature feature_list:HAVE_GUEST_VM;
            key "sFromIpAddr";
            description
                "srcNatList";
            leaf sFromIpAddr  {
                type  cml_data_types:CML_STRING_T;
                description "Used to set the from ip address of SNAT";
            } // END of sFromIpAddr definition.

            leaf toIpAddr  {
                type  cml_data_types:CML_STRING_T;
                description "Used to set the to ip address of SNAT";
            } // END of toIpAddr definition.

            leaf vrfName  {
                type  cml_data_types:CML_STRING_T;
                default "default";
                description "Used to set the vrf name";
            } // END of vrfName definition.

        } // End of srcNatList-list
    } // END of srcNatList-grouping definition.


    grouping dstNatList-grouping {
    description
        "dstNatList";
        list dstNatList {
            if-feature feature_list:HAVE_GUEST_VM;
            key "dFromIpAddr";
            description
                "dstNatList";
            leaf dFromIpAddr  {
                type  cml_data_types:CML_STRING_T;
                description "Used to set the from ip address of DNAT";
            } // END of dFromIpAddr definition.


            list vrfNatlist {
                key "vrfName";
                description
                    "vrfNatlist";
                leaf vrfName  {
                    type  cml_data_types:CML_STRING_T;
                    description "Used to set the vrf name";
                } // END of vrfName definition.


                list toNatList {
                    key "toIpAddr";
                    description
                        "toNatList";
                    leaf protocol  {
                        type  CML_PROTO_T;
                        description "Used to set the portocol for DNAT";
                    } // END of protocol definition.

                    leaf toPortNum  {
                        type  cml_data_types:CML_INT32_T {
                             range "-1..65535";
                        }
                        default "-1";
                        description "Used to set the dnat port";
                    } // END of toPortNum definition.

                    leaf fromPortNum  {
                        type  cml_data_types:CML_INT32_T {
                             range "-1..65535";
                        }
                        default "-1";
                        description "Used to set the dnat port";
                    } // END of fromPortNum definition.

                    leaf toIpAddr  {
                        type  cml_data_types:CML_STRING_T;
                        description "Used to set the to ip address of DNAT";
                    } // END of toIpAddr definition.

                } // End of toNatList-list
            } // End of vrfNatlist-list
        } // End of dstNatList-list
    } // END of dstNatList-grouping definition.


    grouping brList-grouping {
    description
        "brList";
        list brList {
            if-feature feature_list:HAVE_GUEST_VM;
            key "brName";
            description
                "brList";
            leaf vrId  {
                type  cml_data_types:CML_INT32_T;
                default "0";
                description "";
            } // END of vrId definition.

            leaf brName  {
                type  cml_data_types:CML_STRING_T {
                    length "1..16";
                }
                description "";
            } // END of brName definition.

            leaf gateWayIpAddr  {
                type  cml_data_types:CML_STRING_T;
                description "";
            } // END of gateWayIpAddr definition.

            leaf dhcpStartIp  {
                type  cml_data_types:CML_STRING_T;
                description "";
            } // END of dhcpStartIp definition.

            leaf dhcpEndIp  {
                type  cml_data_types:CML_STRING_T;
                description "";
            } // END of dhcpEndIp definition.

            leaf leaseMaxVal  {
                type  cml_data_types:CML_UINT32_T {
                     range "10..1000";
                }
                description "";
            } // END of leaseMaxVal definition.

            leaf leaseTime  {
                type  cml_data_types:CML_UINT32_T {
                     range "2..3600";
                }
                description "";
            } // END of leaseTime definition.

            leaf service  {
                type  cml_data_types:CML_BOOL_T;
                description "";
            } // END of service definition.


            list macAddrList {
                key "ipAddr";
                description
                    "macAddrList";
                leaf ipAddr  {
                    type  cml_data_types:CML_STRING_T;
                    description "";
                } // END of ipAddr definition.

                leaf macAddr  {
                    type  cml_data_types:CML_MAC_ADDR_T;
                    mandatory true;
                    description "";
                } // END of macAddr definition.

            } // End of macAddrList-list
        } // End of brList-list
    } // END of brList-grouping definition.

    grouping  debugVmEvents-grouping {
    description
        "debugVmEvents";
    container debugVmEvents {
        description
            "debugVmEvents";
        leaf vmDebugFlag  {
            type  cml_data_types:CML_BOOL_T;
            description "";
        } // END of vmDebugFlag definition.

    } // END of debugVmEvents-container definition.
    } // END of debugVmEvents-container definition.

    grouping  featureVm-grouping {
    description
        "featureVm";
    container featureVm {
        description
            "featureVm";
        leaf vmFlag  {
            type  cml_data_types:CML_BOOL_T;
            description "";
        } // END of vmFlag definition.

    } // END of featureVm-container definition.
    } // END of featureVm-container definition.


}
