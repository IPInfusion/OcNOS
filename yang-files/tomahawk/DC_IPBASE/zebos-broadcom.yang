/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-broadcom.yang
*
*/

submodule zebos-broadcom {

    belongs-to  zebos { prefix zebos; }

    import cml_data_types {
        prefix cml_data_types;
    }

    import ietf-inet-types {
        prefix inet;
    }

    import feature_list {
        prefix feature_list;
    }

    include zebos-vrf;
    organization
        "IP Infusion Inc.";

    contact
        "Address: 3965 Freedom Circle, Suite 200, Santa Clara, CA 95054
        Phone: +1 408-400-1900
        E-mail: support@ipinfusion.com
        Web: http://www.ipinfusion.com/";

    description
        "Datamodel for broadcom object";


    revision "2018-06-21" {
        description " Initial Version.";
        reference "";
    }



    typedef  CML_LIBHWCONF_LACP_PSC_T {
        type enumeration {
            enum dst-mac {
                value 1;
                description "Destination Mac address based load balancing";
            }
            enum src-mac {
                value 2;
                description "Source Mac address based load balancing";
            }
            enum src-dst-mac {
                value 3;
                description "Source and Destination Mac address based load balancing";
            }
            enum src-ip {
                value 4;
                description "Source IP address based load balancing";
            }
            enum dst-ip {
                value 5;
                description "Destination IP address based load balancing";
            }
            enum src-dst-ip {
                value 6;
                description "Source and Destination IP address based load balancing";
            }
            enum rtag7 {
                value 12;
                description "rtag7 hashing based on pkt type";
            }
        }
        description "";
        reference "";
    }    grouping customProfileL2L3 {
        description
            "Attributes for configuring custom profile for tmh or tmh2";
        leaf customL2Bank  {
            type  cml_data_types:CML_UINT8_T {
                 range "1..4";
            }
            description "";
        } // END of customL2Bank definition.

        leaf customL3Bank  {
            type  cml_data_types:CML_UINT8_T {
                 range "1..4";
            }
            description "";
        } // END of customL3Bank definition.

        leaf customDefault  {
            type  cml_data_types:CML_BOOL_T;
            description "";
        } // END of customDefault definition.

    } // END of customProfileL2L3 definition.
    grouping customProfileLpmDefault {
        description
            "Attributes for configuring custom profile for tmh or tmh2";
        leaf customLpmBank  {
            type  cml_data_types:CML_FORWARDING_CUSTOM_PROFILE_LPM_T;
            description "";
        } // END of customLpmBank definition.

    } // END of customProfileLpmDefault definition.
    grouping customProfileVlanDefault {
        description
            "Attributes for configuring custom profile for helix";
        leaf customVlanXlateBank  {
            type  cml_data_types:CML_UINT8_T {
                 range "1..23";
            }
            description "";
        } // END of customVlanXlateBank definition.

        leaf customEpVlanXlateBank  {
            type  cml_data_types:CML_UINT8_T {
                 range "1..23";
            }
            description "";
        } // END of customEpVlanXlateBank definition.

    } // END of customProfileVlanDefault definition.

    grouping  libhwconf-grouping {
    description
        "Global configs for router";
    container libhwconf {
        description
            "Global configs for router";
        leaf DisableCPUCntrlPktVXLAN  {
            if-feature feature_list:HAVE_VXLAN;
            type  cml_data_types:CML_BOOL_T;
            default false;
            description "This Object is to disable the control packets to CPU";
        } // END of DisableCPUCntrlPktVXLAN definition.

        leaf forwardingProfile  {
            if-feature feature_list:HAVE_BCM_UFT;
            if-feature feature_list:NOT_HAVE_DUNE;
            type  cml_data_types:CML_FORWARDING_PROFILE_T;
            description "This Object is to check forwarding profile limit";
        } // END of forwardingProfile definition.

        leaf forwardingProfilelpm  {
            if-feature feature_list:HAVE_BCM_UFT;
            if-feature feature_list:NOT_HAVE_DUNE;
            if-feature feature_list:NOT_HAVE_HELIX4;
            type  cml_data_types:CML_FORWARDING_PROFILE_LPM_T;
            description "";
        } // END of forwardingProfilelpm definition.

        leaf forwardingProfilekaps  {
            if-feature feature_list:HAVE_DUNE;
            if-feature feature_list:HAVE_BCM_UFT;
            type  cml_data_types:CML_PROFILE_T;
            description "This Object is to check forwarding profile limit";
        } // END of forwardingProfilekaps definition.

        leaf hardwareProfileEgressIpv6Acl  {
            if-feature feature_list:HAVE_ACL;
            if-feature feature_list:NOT_HAVE_DUNE;
            type  cml_data_types:CML_ENABLE_DISABLE_T;
            default "enable";
            description "";
        } // END of hardwareProfileEgressIpv6Acl definition.

        leaf hardwareProfileIngressIpv4Acl  {
            if-feature feature_list:HAVE_ACL;
            type  cml_data_types:CML_ENABLE_DISABLE_T;
            default "enable";
            description "set Hardware profile,filter type,ingress ipv4";
        } // END of hardwareProfileIngressIpv4Acl definition.

        leaf hardwareProfileIngressArp  {
            if-feature feature_list:HAVE_ACL;
            if-feature feature_list:NOT_HAVE_DUNE;
            type  cml_data_types:CML_ENABLE_DISABLE_T;
            default "disable";
            description "set Hardware profile,filter type,ingress arp";
        } // END of hardwareProfileIngressArp definition.

        leaf hardwareProfileIngressIpv6  {
            if-feature feature_list:HAVE_ACL;
            if-feature feature_list:NOT_HAVE_DUNE;
            type  cml_data_types:CML_ENABLE_DISABLE_T;
            default "enable";
            description "set Hardware profile,filter type,ingress-ipv6";
        } // END of hardwareProfileIngressIpv6 definition.

        leaf hardwareProfileQosGroup  {
            if-feature feature_list:HAVE_DUNE;
            if-feature feature_list:HAVE_ACL;
            type  cml_data_types:CML_ENABLE_DISABLE_T;
            default "disable";
            description "";
        } // END of hardwareProfileQosGroup definition.

        leaf hardwareProfileEgressIpv4  {
            if-feature feature_list:HAVE_DUNE;
            if-feature feature_list:HAVE_ACL;
            type  cml_data_types:CML_ENABLE_DISABLE_T;
            default "disable";
            description "";
        } // END of hardwareProfileEgressIpv4 definition.

        leaf hardwareProfileEgressL2Group  {
            if-feature feature_list:HAVE_DUNE;
            if-feature feature_list:HAVE_ACL;
            type  cml_data_types:CML_ENABLE_DISABLE_T;
            default "disable";
            description "";
        } // END of hardwareProfileEgressL2Group definition.

        leaf hardwareProfileIngressL2Group  {
            if-feature feature_list:HAVE_DUNE;
            if-feature feature_list:HAVE_ACL;
            type  cml_data_types:CML_ENABLE_DISABLE_T;
            default "disable";
            description "";
        } // END of hardwareProfileIngressL2Group definition.

        leaf hardwareProfilePauseGroup  {
            if-feature feature_list:HAVE_DUNE;
            if-feature feature_list:HAVE_BCM_UFT;
            type  cml_data_types:CML_ENABLE_DISABLE_T;
            default "enable";
            description "";
        } // END of hardwareProfilePauseGroup definition.

        leaf hardwareProfileMicroBfd  {
            if-feature feature_list:HAVE_CUSTOM1_HW_BFD;
            type  cml_data_types:CML_ENABLE_DISABLE_T;
            default "enable";
            description "";
        } // END of hardwareProfileMicroBfd definition.

        leaf hardwareProfileStatisticsIngAcl  {
            if-feature feature_list:HAVE_MPLS_STATS;
            if-feature feature_list:HAVE_DUNE;
            type  cml_data_types:CML_ENABLE_DISABLE_T;
            default "enable";
            description "";
        } // END of hardwareProfileStatisticsIngAcl definition.

        leaf hardwareProfileStatisticsMplsAc  {
            if-feature feature_list:HAVE_MPLS_STATS;
            if-feature feature_list:HAVE_DUNE;
            type  cml_data_types:CML_ENABLE_DISABLE_T;
            default "enable";
            description "";
        } // END of hardwareProfileStatisticsMplsAc definition.

        leaf hardwareProfileStatisticsMplsLsp  {
            if-feature feature_list:HAVE_MPLS_STATS;
            if-feature feature_list:HAVE_DUNE;
            type  cml_data_types:CML_ENABLE_DISABLE_T;
            default "enable";
            description "";
        } // END of hardwareProfileStatisticsMplsLsp definition.

        leaf hardwareProfileStatisticsMplsPwe  {
            if-feature feature_list:HAVE_MPLS_STATS;
            if-feature feature_list:HAVE_DUNE;
            type  cml_data_types:CML_ENABLE_DISABLE_T;
            default "enable";
            description "";
        } // END of hardwareProfileStatisticsMplsPwe definition.

        container forwardingCustomProfile {
            if-feature feature_list:HAVE_TOMAHAWK2;
            if-feature feature_list:HAVE_BCM_UFT;
            description
                "Configures forwarding custom profile for tomahawk2";
            uses customProfileL2L3;
            uses customProfileLpmDefault;
        } // END of forwardingCustomProfile-container definition.
        container forwardingProfileTableLimit {
            if-feature feature_list:HAVE_BCM_UFT;
            config false;
            description
                "Display profile table maximum supported values";
            leaf configuredProfile  {
                if-feature feature_list:NOT_HAVE_DUNE;
                type  cml_data_types:CML_FRWD_PROFILE_T;
                description "User Configured profile";
            } // END of configuredProfile definition.

            leaf forwardingProfile  {
                if-feature feature_list:NOT_HAVE_DUNE;
                type  cml_data_types:CML_FRWD_PROFILE_T;
                description "Profile active in hardware";
            } // END of forwardingProfile definition.


            list KAPS {
                if-feature feature_list:HAVE_DUNE;
                key "profile";
                config false;
                description
                    "KAPS Forwarding Profile";
                leaf profile  {
                    type  cml_data_types:CML_KAPS_FORWADING_PROFILE_T;
                    description "Profile type";
                } // END of profile definition.

                leaf isActive  {
                    type  cml_data_types:CML_BOOL_T;
                    description "Active in hardware";
                } // END of isActive definition.

                leaf publicDbSize  {
                    type  cml_data_types:CML_UINT32_T;
                    description "Public-db : default VRF (VRF = 0)";
                } // END of publicDbSize definition.

                leaf privateDbSize  {
                    type  cml_data_types:CML_UINT32_T;
                    description "Private-db : non-default VRF (VRF != 0)";
                } // END of privateDbSize definition.

            } // End of KAPS-list

            list elkTcam {
                if-feature feature_list:HAVE_DUNE;
                if-feature feature_list:HAVE_ELK_TCAM;
                key "profile";
                config false;
                description
                    "ELK TCAM Forwarding Profile";
                leaf profile  {
                    type  cml_data_types:CML_ELK_TCAM_FORWADING_PROFILE_T;
                    description "Profile type";
                } // END of profile definition.

                leaf isActive  {
                    type  cml_data_types:CML_BOOL_T;
                    description "Active in hardware";
                } // END of isActive definition.

                leaf ipv4DbSize  {
                    type  cml_data_types:CML_UINT32_T;
                    description "IPv4 DB size";
                } // END of ipv4DbSize definition.

                leaf ipv6DbSize  {
                    type  cml_data_types:CML_UINT32_T;
                    description "IPv6 DB size";
                } // END of ipv6DbSize definition.

            } // End of elkTcam-list

            list profileTableSize {
                if-feature feature_list:HAVE_BCM_UFT;
                if-feature feature_list:NOT_HAVE_DUNE;
                key "profile";
                config false;
                description
                    "Forwarding Profile Table";
                leaf profile  {
                    type  cml_data_types:CML_FRWD_PROFILE_T;
                    description "Profile name";
                } // END of profile definition.

                leaf macAddrTable  {
                    type  cml_data_types:CML_INT32_T;
                    description "MAC-Table size";
                } // END of macAddrTable definition.

                leaf hostTableIpv4  {
                    type  cml_data_types:CML_INT32_T;
                    description "Host-Table (UC) IPv4 size";
                } // END of hostTableIpv4 definition.

                leaf hostTableIpv6  {
                    type  cml_data_types:CML_INT32_T;
                    description "Host-Table (UC) IPv6 size";
                } // END of hostTableIpv6 definition.

                leaf prefixTableUCipv4  {
                    type  cml_data_types:CML_INT32_T;
                    description "Prefix-Table (UC) IPv4 size";
                } // END of prefixTableUCipv4 definition.

                leaf prefixTableUCipv6  {
                    type  cml_data_types:CML_INT32_T;
                    description "Prefix-Table (UC) IPv6 size";
                } // END of prefixTableUCipv6 definition.

                leaf prefixTableUCipv6LargerThan64bytes  {
                    if-feature feature_list:NOT_HAVE_HELIX4;
                    type  cml_data_types:CML_INT32_T;
                    description "Prefix-Table (UC) IPv6 (>=65) size";
                } // END of prefixTableUCipv6LargerThan64bytes definition.

                leaf mplsTable  {
                    if-feature feature_list:HAVE_HELIX4;
                    if-feature feature_list:HAVE_MPLS;
                    type  cml_data_types:CML_INT32_T;
                    description "MPLS table size";
                } // END of mplsTable definition.

                leaf vlanXlateTable  {
                    if-feature feature_list:HAVE_HELIX4;
                    type  cml_data_types:CML_INT32_T;
                    description "VLAN xlate table size";
                } // END of vlanXlateTable definition.

                leaf egressVlanXlateTable  {
                    if-feature feature_list:HAVE_HELIX4;
                    type  cml_data_types:CML_INT32_T;
                    description "Egress VLAN xlate table size";
                } // END of egressVlanXlateTable definition.

            } // End of profileTableSize-list
        } // END of forwardingProfileTableLimit-container definition.
        container loadBalance {
            if-feature feature_list:HAVE_BROADCOM;
            if-feature feature_list:NOT_HAVE_DUNE;
            presence "yes";
            description
                "Load Balancing";
            leaf loadBalance  {
                type  cml_data_types:CML_LIBHWCONF_LOADBALANCE;
                mandatory true;
                description "This Object is set loadBalance";
            } // END of loadBalance definition.

            container l2 {
                if-feature feature_list:HAVE_L2;
                description
                    "Load balancing on L2 packet";
                leaf l2destMac  {
                    type  cml_data_types:CML_EMPTY_T;
                    description "Destination Mac address based load balancing";
                } // END of l2destMac definition.

                leaf l2srcMac  {
                    type  cml_data_types:CML_EMPTY_T;
                    description "Source Mac address based load balancing";
                } // END of l2srcMac definition.

                leaf l2etherType  {
                    type  cml_data_types:CML_EMPTY_T;
                    description "Ether-type based load balancing";
                } // END of l2etherType definition.

                leaf l2vlan  {
                    type  cml_data_types:CML_EMPTY_T;
                    description "Vlan based load balancing";
                } // END of l2vlan definition.

            } // END of l2-container definition.
            container l3Ipv4 {
                if-feature feature_list:HAVE_L3;
                description
                    "Load balancing on L2 packet";
                leaf l3srcIpv4  {
                    type  cml_data_types:CML_EMPTY_T;
                    description "Source IPV4 based load balancing";
                } // END of l3srcIpv4 definition.

                leaf l3destIpv4  {
                    type  cml_data_types:CML_EMPTY_T;
                    description "Destination IPV4 based load balancing";
                } // END of l3destIpv4 definition.

                leaf l3srcl4Port  {
                    type  cml_data_types:CML_EMPTY_T;
                    description "Source L4 port based load balancing";
                } // END of l3srcl4Port definition.

                leaf l3destl4Port  {
                    type  cml_data_types:CML_EMPTY_T;
                    description "Destination L4 port based load balancing";
                } // END of l3destl4Port definition.

                leaf l3protocolId  {
                    type  cml_data_types:CML_EMPTY_T;
                    description "Protocol Id based load balancing";
                } // END of l3protocolId definition.

                leaf l3symmetricIpv4  {
                    type  cml_data_types:CML_EMPTY_T;
                    description "Symmetric load balancing";
                } // END of l3symmetricIpv4 definition.

            } // END of l3Ipv4-container definition.
            container l3Ipv6 {
                if-feature feature_list:HAVE_L3;
                description
                    "Load balancing on L2 packet";
                leaf l3srcIpv6  {
                    type  cml_data_types:CML_EMPTY_T;
                    description "Source IPV6 based load balancing";
                } // END of l3srcIpv6 definition.

                leaf l3destIpv6  {
                    type  cml_data_types:CML_EMPTY_T;
                    description "Destination IPV6 based load balancing";
                } // END of l3destIpv6 definition.

                leaf l3srcl6Port  {
                    type  cml_data_types:CML_EMPTY_T;
                    description "Source L4 port based load balancing";
                } // END of l3srcl6Port definition.

                leaf l3destl6Port  {
                    type  cml_data_types:CML_EMPTY_T;
                    description "Destination L4 port based load balancing";
                } // END of l3destl6Port definition.

                leaf l3nextHdr  {
                    type  cml_data_types:CML_EMPTY_T;
                    description "Next Header Field for IPV6";
                } // END of l3nextHdr definition.

                leaf l3symmetricIpv6  {
                    type  cml_data_types:CML_EMPTY_T;
                    description "Symmetric load balancing";
                } // END of l3symmetricIpv6 definition.

            } // END of l3Ipv6-container definition.
            container tunnel {
                if-feature feature_list:HAVE_L3;
                description
                    "Load balancing on L2 packet";
                leaf outerl3Header  {
                    type  cml_data_types:CML_EMPTY_T;
                    description "Usedto set Load balance tunneled packets based on outer header";
                } // END of outerl3Header definition.

            } // END of tunnel-container definition.
            container trill {
                if-feature feature_list:HAVE_TRILLD;
                description
                    "Load balancing on L2 packet";
                leaf trill  {
                    type  cml_data_types:CML_NSM_LOAD_TRILL_T;
                    description "This Object is used to set trill header";
                } // END of trill definition.

            } // END of trill-container definition.
            container hash {
                description
                    "Load balance hash computation";
                leaf hash  {
                    type  cml_data_types:CML_NSM_LOAD_HASH_T;
                    description "This Object is used to set (hash values)CRC";
                } // END of hash definition.

            } // END of hash-container definition.
            container macroflow {
                description
                    "macro-flow based dynamic hash selection";
                leaf macroflow  {
                    type  cml_data_types:CML_EMPTY_T;
                    description "macro-flow based dynamic hash selection";
                } // END of macroflow definition.

            } // END of macroflow-container definition.
            container vxlanL2 {
                if-feature feature_list:HAVE_VXLAN;
                description
                    "Load balancing on vxlan L2 packet";
                leaf vxlandestMac  {
                    type  cml_data_types:CML_EMPTY_T;
                    description "vxlan Destination Mac address based load balancing";
                } // END of vxlandestMac definition.

                leaf vxlansrcMac  {
                    type  cml_data_types:CML_EMPTY_T;
                    description "vxlan Source Mac address based load balancing";
                } // END of vxlansrcMac definition.

            } // END of vxlanL2-container definition.
            container vxlanL3 {
                if-feature feature_list:HAVE_VXLAN;
                description
                    "Load balancing on vxlan L3 packet";
                leaf vxlansrcIp  {
                    type  cml_data_types:CML_EMPTY_T;
                    description "vxlan Source IP";
                } // END of vxlansrcIp definition.

                leaf vxlandestIp  {
                    type  cml_data_types:CML_EMPTY_T;
                    description "vxlan Destination IP";
                } // END of vxlandestIp definition.

                leaf vxlansrcl4Port  {
                    type  cml_data_types:CML_EMPTY_T;
                    description "vxlan Source l4 port";
                } // END of vxlansrcl4Port definition.

                leaf vxlandestl4Port  {
                    type  cml_data_types:CML_EMPTY_T;
                    description "vxlan Destination l4 port";
                } // END of vxlandestl4Port definition.

                leaf vxlanprotocolId  {
                    type  cml_data_types:CML_EMPTY_T;
                    description "vxlan Protocol Id";
                } // END of vxlanprotocolId definition.

            } // END of vxlanL3-container definition.
            container mplsLerL2 {
                if-feature feature_list:HAVE_MPLS;
                description
                    "Load balancing on L2 packet";
                leaf mplsdestMac  {
                    type  cml_data_types:CML_EMPTY_T;
                    description "mpls destination Mac address based load balancing";
                } // END of mplsdestMac definition.

                leaf mplssrcMac  {
                    type  cml_data_types:CML_EMPTY_T;
                    description "mpls source Mac address based load balancing";
                } // END of mplssrcMac definition.

                leaf mplsetherType  {
                    type  cml_data_types:CML_EMPTY_T;
                    description "mpls Ether-type based load balancing";
                } // END of mplsetherType definition.

                leaf mplsvlan  {
                    type  cml_data_types:CML_EMPTY_T;
                    description "mpls Vlan based load balancing";
                } // END of mplsvlan definition.

            } // END of mplsLerL2-container definition.
            container mplsLer {
                if-feature feature_list:HAVE_MPLS;
                description
                    "Load balancing on L2 packet";
                leaf mplssrcIpv6  {
                    type  cml_data_types:CML_EMPTY_T;
                    description "Source IP";
                } // END of mplssrcIpv6 definition.

                leaf mplsdestIpv6  {
                    type  cml_data_types:CML_EMPTY_T;
                    description "Destination IP";
                } // END of mplsdestIpv6 definition.

                leaf mplssrcl4Port  {
                    type  cml_data_types:CML_EMPTY_T;
                    description "Source l4 port";
                } // END of mplssrcl4Port definition.

                leaf mplsdestl4Port  {
                    type  cml_data_types:CML_EMPTY_T;
                    description "Destination l4 port";
                } // END of mplsdestl4Port definition.

                leaf mplsprotocolId  {
                    type  cml_data_types:CML_EMPTY_T;
                    description "Protocol (IPv4)";
                } // END of mplsprotocolId definition.

            } // END of mplsLer-container definition.
            container mpls {
                if-feature feature_list:HAVE_MPLS;
                description
                    "Load balancing for MPLS";
                leaf mplsLabels  {
                    type  cml_data_types:CML_EMPTY_T;
                    description "";
                } // END of mplsLabels definition.

                leaf mplsIpPayload  {
                    type  cml_data_types:CML_EMPTY_T;
                    description "";
                } // END of mplsIpPayload definition.

            } // END of mpls-container definition.
        } // END of loadBalance-container definition.
    } // END of libhwconf-container definition.
    } // END of libhwconf-container definition.

    grouping  l2Movement-grouping {
    description
        "l2Movement";
    container l2Movement {
        description
            "l2Movement";
        leaf allowFirstFrame  {
            if-feature feature_list:NOT_HAVE_DUNE;
            type  cml_data_types:CML_BOOL_T;
            description "This Object is used to allow or drop first frame on L2 movement actions
          ";
        } // END of allowFirstFrame definition.

    } // END of l2Movement-container definition.
    } // END of l2Movement-container definition.

    grouping  portChannelLoadBalBrcm-grouping {
    description
        "portChannelLoadBalBrcm";
    container portChannelLoadBalBrcm {
        if-feature feature_list:NOT_HAVE_DUNE;
        description
            "portChannelLoadBalBrcm";
        leaf portChannelLoadBalBrcm  {
            if-feature feature_list:HAVE_LACP;
            type  CML_LIBHWCONF_LACP_PSC_T;
            description "This Object is used to set LACP port-channel load-balancing and set port selection criteria (PSC) on an interface";
        } // END of portChannelLoadBalBrcm definition.

    } // END of portChannelLoadBalBrcm-container definition.
    } // END of portChannelLoadBalBrcm-container definition.

    grouping  hwTCAMutilization-grouping {
    description
        "TCAM Utilization information";
    container hwTCAMutilization {
        if-feature feature_list:HAVE_ACL;
        config false;
        description
            "TCAM Utilization information";
        leaf warningThresholdLevel  {
            type  cml_data_types:CML_INT32_T;
            description "Warning TCAM threshold level in percentage.
            Value of -1 means the field is not applicable.";
        } // END of warningThresholdLevel definition.

        leaf alertThresholdLevel  {
            type  cml_data_types:CML_INT32_T;
            description "Alert TCAM threshold level in percentage.
            Value of -1 means the field is not applicable.";
        } // END of alertThresholdLevel definition.


        list hwTCAMgroups {
            key "groupId";
            config false;
            description
                "Hardware TCAM group details";
            leaf groupId  {
                type  cml_data_types:CML_UINT32_T;
                description "A unique number corresponding to each TCAM group.";
            } // END of groupId definition.

            leaf groupName  {
                type  cml_data_types:CML_STRING_T;
                description "TCAM group name.";
            } // END of groupName definition.

            leaf groupStatus  {
                type  cml_data_types:CML_BOOL_T;
                description "A flag to indicate if the TCAM group is enabled or not.
              Value of 0 indicates TCAM group is disabled and 1 indicates 
              TCAM group is enabled.";
            } // END of groupStatus definition.

            leaf freeEntries  {
                type  cml_data_types:CML_INT32_T;
                description "Count of free entries in the TCAM group.
              Value of -1 means the field is not applicable.";
            } // END of freeEntries definition.

            leaf usedPercent  {
                type  cml_data_types:CML_INT32_T;
                description "Percentage of entries used in the TCAM group.
              Value of -1 means the field is not applicable.";
            } // END of usedPercent definition.

            leaf usedEntries  {
                type  cml_data_types:CML_INT32_T;
                description "Count of used entries in the TCAM group.
              Value of -1 means the field is not applicable.";
            } // END of usedEntries definition.

            leaf totalEntries  {
                type  cml_data_types:CML_INT32_T;
                description "Count of total entries in the TCAM group.
              Total is summation of dedicated entries and shared entries.
              Value of -1 means the field is not applicable.";
            } // END of totalEntries definition.

            leaf dedicatedEntries  {
                type  cml_data_types:CML_INT32_T;
                description "Count of total entries dedicated to TCAM group.
              Dedicated entries are fixed to the TCAM group and are the
              minimum guaranteed number. Value of -1 means the field
              is not applicable.";
            } // END of dedicatedEntries definition.

            leaf sharedEntries  {
                type  cml_data_types:CML_INT32_T;
                description "Count of entries which are shared across TCAM groups.
              Value of -1 means the field is not applicable.";
            } // END of sharedEntries definition.

        } // End of hwTCAMgroups-list
    } // END of hwTCAMutilization-container definition.
    } // END of hwTCAMutilization-container definition.


}
