/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-dhcpsnooping.yang
*
*/

submodule zebos-dhcpsnooping {

    belongs-to  zebos { prefix zebos; }

    import cml_data_types {
        prefix cml_data_types;
    }

    import feature_list {
        prefix feature_list;
    }

    include zebos-interface;
    include zebos-bridge;
    organization
        "IP Infusion Inc.";

    contact
        "Address: 3965 Freedom Circle, Suite 200, Santa Clara, CA 95054
        Phone: +1 408-400-1900
        E-mail: support@ipinfusion.com
        Web: http://www.ipinfusion.com/";

    description
        "dhcpsnooping_configuration";


    revision "2017-02-27" {
        description "Initial version of dhcpsnooping datamodel.";
    }



    grouping dhcpSnooping-grouping {
        list dhcpSnooping {
            key "bridgeId";
            description
                "dhcp snooping attrs for non default bridge";
            leaf bridgeId  {
                type  cml_data_types:CML_STRING_T {
                    length "1..32";
                }
                description "";
            } // END of bridgeId definition.

            leaf dhcpsEnable  {
                type  cml_data_types:CML_BOOL_T;
                description "";
            } // END of dhcpsEnable definition.

            leaf dhcpRatelimit  {
                type  cml_data_types:CML_STRING_T {
                    length "0..255";
                }
                description "";
            } // END of dhcpRatelimit definition.

            leaf dhcpsVerifyMac  {
                type  cml_data_types:CML_BOOL_T;
                description "";
            } // END of dhcpsVerifyMac definition.

            leaf dhcpsOption82  {
                type  cml_data_types:CML_BOOL_T;
                description "";
            } // END of dhcpsOption82 definition.

            leaf dhcpsStrictVal  {
                type  cml_data_types:CML_BOOL_T;
                description "";
            } // END of dhcpsStrictVal definition.

            leaf vlanRange  {
                type  cml_data_types:CML_STRING_T;
                description "";
            } // END of vlanRange definition.

            leaf daiEnable  {
                type  cml_data_types:CML_BOOL_T;
                description "";
            } // END of daiEnable definition.

            leaf validateFlag  {
                type  cml_data_types:CML_DHCP_VALIDATION_T;
                description "";
            } // END of validateFlag definition.

            leaf arpVlanrange  {
                type  cml_data_types:CML_STRING_T;
                description "";
            } // END of arpVlanrange definition.


            list vlanSourceBindInfo {
                key "vlanId";
                description
                    "vlanSourceBindInfo";
                leaf vlanId  {
                    type  cml_data_types:CML_UINT32_T {
                         range "1..4094";
                    }
                    description "";
                } // END of vlanId definition.


                list macSourceBindInfo {
                    key "macAddr";
                    description
                        "macSourceBindInfo";
                    leaf macAddr  {
                        type  cml_data_types:CML_STRING_T {
                            length "0..255";
                        }
                        description "";
                    } // END of macAddr definition.

                    leaf ifName  {
                        type  cml_data_types:CML_STRING_T {
                            length "0..255";
                        }
                        mandatory true;
                        description "";
                    } // END of ifName definition.

                    leaf ipv4  {
                        type  cml_data_types:CML_IPV4_ADDR_T;
                        description "";
                    } // END of ipv4 definition.

                    leaf ipv6  {
                        type  cml_data_types:CML_IPV6_ADDR_T;
                        description "";
                    } // END of ipv6 definition.

                } // End of macSourceBindInfo-list
            } // End of vlanSourceBindInfo-list

            list vlanDhcpBindInfo {
                key "vlan";
                description
                    "vlanDhcpBindInfo";
                leaf vlan  {
                    type  cml_data_types:CML_UINT32_T {
                         range "1..4094";
                    }
                    description "";
                } // END of vlan definition.


                list macDhcpBindInfo {
                    key "snoopingMacAddr";
                    description
                        "macDhcpBindInfo";
                    leaf snoopingMacAddr  {
                        type  cml_data_types:CML_STRING_T {
                            length "0..255";
                        }
                        description "";
                    } // END of snoopingMacAddr definition.

                    leaf name  {
                        type  cml_data_types:CML_STRING_T {
                            length "0..255";
                        }
                        mandatory true;
                        description "";
                    } // END of name definition.

                    leaf snoopingIpv4  {
                        type  cml_data_types:CML_IPV4_ADDR_T;
                        description "";
                    } // END of snoopingIpv4 definition.

                    leaf snoopingIpv6  {
                        type  cml_data_types:CML_IPV6_ADDR_T;
                        description "";
                    } // END of snoopingIpv6 definition.

                } // End of macDhcpBindInfo-list
            } // End of vlanDhcpBindInfo-list
        } // End of dhcpSnooping-list
    } // END of dhcpSnooping-grouping definition.


    grouping defaultbridgedhcpsnooping-grouping {
        list defaultbridgedhcpsnooping {
            if-feature feature_list:HAVE_DEFAULT_BRIDGE;
            key "bridgeId";
            description
                "Group of dhcp snooping attribute for default bridge";
            leaf bridgeId  {
                type  cml_data_types:CML_STRING_T {
                    length "0..255";
                }
                description "";
            } // END of bridgeId definition.

            leaf dhcpsEnable  {
                type  cml_data_types:CML_BOOL_T;
                description "";
            } // END of dhcpsEnable definition.

            leaf dhcpRatelimit  {
                type  cml_data_types:CML_STRING_T {
                    length "0..255";
                }
                description "";
            } // END of dhcpRatelimit definition.

            leaf dhcpsVerifyMac  {
                type  cml_data_types:CML_BOOL_T;
                description "";
            } // END of dhcpsVerifyMac definition.

            leaf dhcpsOption82  {
                type  cml_data_types:CML_BOOL_T;
                description "";
            } // END of dhcpsOption82 definition.

            leaf dhcpsStrictVal  {
                type  cml_data_types:CML_BOOL_T;
                description "";
            } // END of dhcpsStrictVal definition.

            leaf vlanRange  {
                type  cml_data_types:CML_STRING_T;
                description "";
            } // END of vlanRange definition.

            leaf daiEnable  {
                type  cml_data_types:CML_BOOL_T;
                description "";
            } // END of daiEnable definition.

            leaf validateFlag  {
                type  cml_data_types:CML_DHCP_VALIDATION_T;
                description "";
            } // END of validateFlag definition.

            leaf arpVlanrange  {
                type  cml_data_types:CML_STRING_T;
                description "";
            } // END of arpVlanrange definition.


            list defaultBridgeVlanBindInfo {
                key "vlanId";
                description
                    "defaultBridgeVlanBindInfo";
                leaf vlanId  {
                    type  cml_data_types:CML_UINT32_T {
                         range "1..4094";
                    }
                    description "";
                } // END of vlanId definition.


                list defaultBridgeMacBindInfo {
                    key "macAddr";
                    description
                        "defaultBridgeMacBindInfo";
                    leaf macAddr  {
                        type  cml_data_types:CML_STRING_T {
                            length "0..255";
                        }
                        description "";
                    } // END of macAddr definition.

                    leaf ifName  {
                        type  cml_data_types:CML_STRING_T {
                            length "0..255";
                        }
                        mandatory true;
                        description "";
                    } // END of ifName definition.

                    leaf ipv4  {
                        type  cml_data_types:CML_IPV4_ADDR_T;
                        description "";
                    } // END of ipv4 definition.

                    leaf ipv6  {
                        type  cml_data_types:CML_IPV6_ADDR_T;
                        description "";
                    } // END of ipv6 definition.

                } // End of defaultBridgeMacBindInfo-list
            } // End of defaultBridgeVlanBindInfo-list

            list DefaultBridgeVlanBind {
                key "vlan";
                description
                    "DefaultBridgeVlanBind";
                leaf vlan  {
                    type  cml_data_types:CML_UINT32_T {
                         range "1..4094";
                    }
                    description "";
                } // END of vlan definition.


                list DefaultBridgeMacaddrDhcpSnoopingBindInfo {
                    key "snoopingMacAddr";
                    description
                        "DefaultBridgeMacaddrDhcpSnoopingBindInfo";
                    leaf snoopingMacAddr  {
                        type  cml_data_types:CML_STRING_T {
                            length "0..255";
                        }
                        description "";
                    } // END of snoopingMacAddr definition.

                    leaf name  {
                        type  cml_data_types:CML_STRING_T {
                            length "0..255";
                        }
                        mandatory true;
                        description "";
                    } // END of name definition.

                    leaf snoopingIpv4  {
                        type  cml_data_types:CML_IPV4_ADDR_T;
                        description "";
                    } // END of snoopingIpv4 definition.

                    leaf snoopingIpv6  {
                        type  cml_data_types:CML_IPV6_ADDR_T;
                        description "";
                    } // END of snoopingIpv6 definition.

                } // End of DefaultBridgeMacaddrDhcpSnoopingBindInfo-list
            } // End of DefaultBridgeVlanBind-list
        } // End of defaultbridgedhcpsnooping-list
    } // END of defaultbridgedhcpsnooping-grouping definition.


    grouping dhcp_interface-grouping {
        list dhcp_interface {
            key "ifName";
            description
                "interface commands";
            leaf ifName  {
                type  cml_data_types:CML_STRING_T {
                    length "0..255";
                }
                description "";
            } // END of ifName definition.

            leaf trust  {
                type  cml_data_types:CML_BOOL_T;
                description "";
            } // END of trust definition.

            leaf dhcpSnoopingVlan  {
                type  cml_data_types:CML_BOOL_T;
                description "";
            } // END of dhcpSnoopingVlan definition.

            leaf accessGroupMode  {
                type  cml_data_types:CML_BOOL_T;
                description "";
            } // END of accessGroupMode definition.

        } // End of dhcp_interface-list
    } // END of dhcp_interface-grouping definition.

    grouping  debugDhcpSnooping-grouping {
    container debugDhcpSnooping {
        description
            "debug commands";
        leaf debugTerm  {
            type  cml_data_types:CML_DHCPSNOOP_DEBUG_T;
            description "";
        } // END of debugTerm definition.

        leaf debugConf  {
            type  cml_data_types:CML_DHCPSNOOP_DEBUG_T;
            description "";
        } // END of debugConf definition.

    } // END of debugDhcpSnooping-container definition.
    } // END of debugDhcpSnooping-container definition.


}
