/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-vlan.yang
*
*/

submodule zebos-vlan {

    belongs-to  zebos { prefix zebos; }

    import cml_data_types {
        prefix cml_data_types;
    }

    import feature_list {
        prefix feature_list;
    }

    include zebos-interface;
    organization
        "IP Infusion Inc.";

    contact
        "Address: 3965 Freedom Circle, Suite 200, Santa Clara, CA 95054
        Phone: +1 408-400-1900
        E-mail: support@ipinfusion.com
        Web: http://www.ipinfusion.com/";

    description
        "vlan configuration";


    revision "2018-06-21" {
        description " Initial Version.";
        reference "";
    }



    grouping vlan-grouping {
    description
        "vlan";
        list vlan {
            key "vlanId";
            description
                "vlan";
            leaf vlanName  {
                type  cml_data_types:CML_STRING_T {
                    length "1..32";
                }
                description "";
            } // END of vlanName definition.

            leaf vlanId  {
                type  cml_data_types:CML_RANGE_T {
                    length "1..255";
                }
                description "";
            } // END of vlanId definition.

            leaf vlanType  {
                type  cml_data_types:CML_VLAN_TYPE_T;
                description "";
            } // END of vlanType definition.

            leaf pvlanConfigured  {
                if-feature feature_list:HAVE_PVLAN;
                type  cml_data_types:CML_INT32_T;
                config false;
                description "";
            } // END of pvlanConfigured definition.

            leaf evId  {
                type  cml_data_types:CML_INT8_T;
                config false;
                description "";
            } // END of evId definition.

            leaf ovId  {
                type  cml_data_types:CML_INT8_T;
                config false;
                description "";
            } // END of ovId definition.

            leaf pvlanType  {
                type  cml_data_types:CML_PVLAN_TYPE_T;
                description "";
            } // END of pvlanType definition.

            leaf associateAddRemove  {
                type  cml_data_types:CML_PVLAN_ADD_REMOVE_TYPE_T;
                description "";
            } // END of associateAddRemove definition.

            leaf associateVid  {
                type  cml_data_types:CML_RANGE_T {
                    length "1..255";
                }
                description "";
            } // END of associateVid definition.

            leaf ceVlanFlag  {
                type  cml_data_types:CML_CE_SVLAN_T;
                description "";
            } // END of ceVlanFlag definition.

            leaf preserveCos  {
                type  cml_data_types:CML_OVC_TYPE_T;
                description "";
            } // END of preserveCos definition.

            leaf preserveVlanid  {
                type  cml_data_types:CML_OVC_TYPE_T;
                description "";
            } // END of preserveVlanid definition.

            leaf dscpCos  {
                if-feature feature_list:HAVE_PROVIDER_BRIDGE;
                type  cml_data_types:CML_INT8_T;
                config false;
                description "";
            } // END of dscpCos definition.

            leaf pcpCos  {
                if-feature feature_list:HAVE_PROVIDER_BRIDGE;
                type  cml_data_types:CML_INT8_T;
                config false;
                description "";
            } // END of pcpCos definition.

            leaf pcpDscpFlag  {
                if-feature feature_list:HAVE_PROVIDER_BRIDGE;
                type  cml_data_types:CML_INT8_T;
                config false;
                description "";
            } // END of pcpDscpFlag definition.

            leaf vlanState  {
                type  cml_data_types:CML_VLANSTATE_T;
                mandatory true;
                description "";
            } // END of vlanState definition.

            leaf mtuVal  {
                type  cml_data_types:CML_UINT32_T;
                default "1500";
                description "";
            } // END of mtuVal definition.

            leaf instance  {
                type  cml_data_types:CML_INT32_T;
                config false;
                description "";
            } // END of instance definition.

            leaf primaryVid  {
                if-feature feature_list:HAVE_G8032V2;
                if-feature feature_list:HAVE_G8032;
                type  cml_data_types:CML_INT8_T;
                config false;
                description "";
            } // END of primaryVid definition.

            leaf erpsBitmask  {
                if-feature feature_list:NSM_VLAN_ERPS_CONF;
                type  cml_data_types:CML_INT8_T;
                config false;
                description "";
            } // END of erpsBitmask definition.

            leaf operStatus  {
                if-feature feature_list:NSM_VLAN_ERPS_CONF;
                type  cml_data_types:CML_INT8_T;
                config false;
                description "";
            } // END of operStatus definition.

            leaf bindStatus  {
                if-feature feature_list:HAVE_NVO;
                type  cml_data_types:CML_INT8_T;
                config false;
                description "";
            } // END of bindStatus definition.

            leaf macLearnDisable  {
                type  cml_data_types:CML_INT32_T;
                default "1";
                description "";
            } // END of macLearnDisable definition.

            leaf macLimitMax  {
                type  cml_data_types:CML_INT32_T {
                     range "5..32768";
                }
                description "";
            } // END of macLimitMax definition.

            leaf isAllowed  {
                type  cml_data_types:CML_ALLOWED_FORBIDDEN_T;
                default "forbidden";
                description "";
            } // END of isAllowed definition.

            leaf multicast  {
                type  cml_data_types:CML_BOOL_T;
                default false;
                description "";
            } // END of multicast definition.

            leaf addFlag  {
                type  cml_data_types:CML_ADD_REMOVE_T;
                default "remove";
                description "";
            } // END of addFlag definition.

            leaf ifName  {
                type  cml_data_types:CML_STRING_T {
                    length "0..255";
                }
                description "";
            } // END of ifName definition.

            leaf vlanRuntimeName  {
                type  cml_data_types:CML_STRING_T {
                    length "0..255";
                }
                config false;
                description "";
            } // END of vlanRuntimeName definition.

            leaf taggedInterface  {
                type  cml_data_types:CML_STRING_T {
                    length "0..255";
                }
                config false;
                description "";
            } // END of taggedInterface definition.

            container nsmvlanbmp {
                if-feature feature_list:HAVE_PROVIDER_BRIDGE;
                config false;
                description
                    "nsm vlan bitmap information";
                leaf bitmap  {
                    type  cml_data_types:CML_INT32_T;
                    description "";
                } // END of bitmap definition.

            } // END of nsmvlanbmp-container definition.
        } // End of vlan-list
    } // END of vlan-grouping definition.


    grouping nsmEvcInfo-grouping {
    description
        "nsm evc vlan information";
        list nsmEvcInfo {
            key "evcId";
            description
                "nsm evc vlan information";
            leaf evcId  {
                type  cml_data_types:CML_STRING_T {
                    length "0..255";
                }
                description "";
            } // END of evcId definition.

            leaf evcMaxUni  {
                type  cml_data_types:CML_UINT32_T;
                description "";
            } // END of evcMaxUni definition.

        } // End of nsmEvcInfo-list
    } // END of nsmEvcInfo-grouping definition.


    grouping nsmOvcInfo-grouping {
    description
        "nsm ovc vlan information";
        list nsmOvcInfo {
            key "svlanId";
            description
                "nsm ovc vlan information";
            leaf svlanId  {
                type  cml_data_types:CML_UINT32_T;
                description "";
            } // END of svlanId definition.

            leaf ovcId  {
                type  cml_data_types:CML_STRING_T {
                    length "0..255";
                }
                description "";
            } // END of ovcId definition.

            leaf oepId  {
                type  cml_data_types:CML_STRING_T {
                    length "0..255";
                }
                description "";
            } // END of oepId definition.

            leaf preserveVlan  {
                type  cml_data_types:CML_INT8_T;
                config false;
                description "";
            } // END of preserveVlan definition.

            leaf num_ovcs  {
                type  cml_data_types:CML_INT16_T;
                config false;
                description "";
            } // END of num_ovcs definition.

            leaf ovcMaxUni  {
                type  cml_data_types:CML_UINT32_T;
                description "";
            } // END of ovcMaxUni definition.

        } // End of nsmOvcInfo-list
    } // END of nsmOvcInfo-grouping definition.


    grouping ovcVlanType-grouping {
    description
        "nsm ovc vlan type information";
        list ovcVlanType {
            key "ovcInfo";
            description
                "nsm ovc vlan type information";
            leaf ovcInfo  {
                type  cml_data_types:CML_STRING_T {
                    length "0..255";
                }
                description "";
            } // END of ovcInfo definition.

            leaf ovcVlanType  {
                type  cml_data_types:CML_CE_SVLAN_T;
                description "";
            } // END of ovcVlanType definition.

            leaf-list TypeCos  {
                type  cml_data_types:CML_OVC_TYPE_T;
                description "";
            } // END of TypeCos definition.

            leaf-list TypeVlanid  {
                type  cml_data_types:CML_OVC_TYPE_T;
                description "";
            } // END of TypeVlanid definition.

        } // End of ovcVlanType-list
    } // END of ovcVlanType-grouping definition.


    grouping nsmVlanAccess-grouping {
    description
        "nsmVlanAccess";
        list nsmVlanAccess {
            key "accessMapName";
            description
                "nsmVlanAccess";
            leaf accessMapName  {
                type  cml_data_types:CML_STRING_T {
                    length "1..32";
                }
                description "";
            } // END of accessMapName definition.

            leaf aclCount  {
                type  cml_data_types:CML_INT32_T;
                config false;
                description "";
            } // END of aclCount definition.

            leaf attached  {
                type  cml_data_types:CML_INT32_T;
                config false;
                description "";
            } // END of attached definition.

            leaf ruleCnt  {
                type  cml_data_types:CML_INT32_T;
                config false;
                description "";
            } // END of ruleCnt definition.

            leaf statisticsEntry  {
                type  cml_data_types:CML_INT32_T;
                description "";
            } // END of statisticsEntry definition.

            leaf sequenceNum  {
                type  cml_data_types:CML_UINT32_T {
                     range "1..4294967295";
                }
                mandatory true;
                description "";
            } // END of sequenceNum definition.

            leaf aclType  {
                type  cml_data_types:CML_ACLTYPE_T;
                description "";
            } // END of aclType definition.

            leaf accessGroup  {
                type  cml_data_types:CML_STRING_T {
                    length "0..255";
                }
                description "";
            } // END of accessGroup definition.

            leaf vlanIdCount  {
                type  cml_data_types:CML_STRING_T {
                    length "0..255";
                }
                description "";
            } // END of vlanIdCount definition.

            leaf actionType  {
                type  cml_data_types:CML_ACTIONTYPE_T;
                description "";
            } // END of actionType definition.

            leaf ifName  {
                type  cml_data_types:CML_STRING_T {
                    length "0..255";
                }
                description "";
            } // END of ifName definition.

            leaf vlanAccessEnd  {
                type  cml_data_types:CML_INT32_T;
                description "";
            } // END of vlanAccessEnd definition.

        } // End of nsmVlanAccess-list
    } // END of nsmVlanAccess-grouping definition.


    grouping vlanClassifierRule-grouping {
    description
        "vlanClassifierRule";
        list vlanClassifierRule {
            key "ruleId";
            description
                "vlanClassifierRule";
            leaf type  {
                type  cml_data_types:CML_UINT32_T;
                description "";
            } // END of type definition.

            leaf ruleId  {
                type  cml_data_types:CML_UINT32_T {
                     range "1..256";
                }
                description "";
            } // END of ruleId definition.

            leaf macAddr  {
                type  cml_data_types:CML_STRING_T {
                    length "0..255";
                }
                description "";
            } // END of macAddr definition.

            leaf ipv4Addr  {
                type  cml_data_types:CML_IPV4_PREFIX_T;
                description "";
            } // END of ipv4Addr definition.

            leaf etherType  {
                type  cml_data_types:CML_ETHERTYPE_T;
                description "";
            } // END of etherType definition.

        } // End of vlanClassifierRule-list
    } // END of vlanClassifierRule-grouping definition.


    grouping vlanClassifierGroup-grouping {
    description
        "vlanClassifierGroup";
        list vlanClassifierGroup {
            key "groupId";
            description
                "vlanClassifierGroup";
            leaf groupId  {
                type  cml_data_types:CML_UINT32_T {
                     range "1..16";
                }
                description "";
            } // END of groupId definition.

            leaf ruleId  {
                type  cml_data_types:CML_UINT32_T {
                     range "1..256";
                }
                description "";
            } // END of ruleId definition.

            leaf bind  {
                type  cml_data_types:CML_BIND_T;
                description "";
            } // END of bind definition.


            list vlanClassifierInterface {
                key "ifName";
                description
                    "vlanClassifierInterface";
                leaf ifName  {
                    type  cml_data_types:CML_STRING_T {
                        length "0..255";
                    }
                    description "";
                } // END of ifName definition.

                leaf groupId  {
                    type  cml_data_types:CML_UINT32_T {
                         range "1..16";
                    }
                    description "";
                } // END of groupId definition.

                leaf vlanId  {
                    type  cml_data_types:CML_STRING_T {
                        length "2..4094";
                    }
                    description "";
                } // END of vlanId definition.

            } // End of vlanClassifierInterface-list
        } // End of vlanClassifierGroup-list
    } // END of vlanClassifierGroup-grouping definition.

    grouping  debugConfigMode-grouping {
    description
        "debugConfigMode";
    container debugConfigMode {
        description
            "debugConfigMode";
        leaf configMode  {
            type  cml_data_types:CML_NSM_CONFIG_MODE_T;
            description "";
        } // END of configMode definition.

        leaf configPkt  {
            if-feature feature_list:HAVE_L2;
            type  cml_data_types:CML_NSM_PKT_MGR_T;
            description "";
        } // END of configPkt definition.

    } // END of debugConfigMode-container definition.
    } // END of debugConfigMode-container definition.

    grouping  debugExecMode-grouping {
    description
        "debugExecMode";
    container debugExecMode {
        description
            "debugExecMode";
        leaf ExecMode  {
            type  cml_data_types:CML_NSM_EXEC_MODE_T;
            description "";
        } // END of ExecMode definition.

        leaf ExecPkt  {
            type  cml_data_types:CML_NSM_PKT_MGR_T;
            description "";
        } // END of ExecPkt definition.

        leaf ifName  {
            type  cml_data_types:CML_STRING_T {
                length "0..255";
            }
            description "";
        } // END of ifName definition.

        leaf execStats  {
            type  cml_data_types:CML_UINT32_T;
            description "";
        } // END of execStats definition.

        leaf execErrorStats  {
            type  cml_data_types:CML_EXEC_MSTP_T;
            description "";
        } // END of execErrorStats definition.

        leaf execEnable  {
            type  cml_data_types:CML_ENABLE_DISABLE_T;
            description "";
        } // END of execEnable definition.

    } // END of debugExecMode-container definition.
    } // END of debugExecMode-container definition.


}
