/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : tacacs.yang
*
*/

submodule tacacs {

    belongs-to  ZebOS { prefix ZebOS; }

    import cml_data_types {
        prefix cml_data_types;
    }

    import feature_list {
        prefix feature_list;
    }

    include vrf;
    organization
        "IP Infusion Inc.";

    contact
        "Address: 3965 Freedom Circle, Suite 200, Santa Clara, CA 95054
        Phone: +1 408-400-1900
        E-mail: support@ipinfusion.com
        Web: http://www.ipinfusion.com/";

    description
        "Layer-3 tacacs configurations";


    revision "2017-11-10" {
        description "Modified the CUSTOM_DB trigger for seq-num.";
    }

    revision "2017-10-26" {
        description "Removed CML_FORCE_SET for seqNum attr.";
    }

    revision "2017-10-11" {
        description "Updated the key_enable default value only for CMLSH CLI.";
    }

    revision "2017-10-10" {
        description "Removed unset CLI generation for tacacs-server sequece number.";
    }

    revision "2017-09-21" {
        description "Added sequece number for tacacs-server host addr.";
    }

    revision "2017-06-07" {
        description "Removed tacacs timeout attr and cli sequence. added objectUpdate for 'feature tacacs+ vrf management' command.";
    }

    revision "2017-05-16" {
        description "Updated to hide tacacs timeout.";
    }

    revision "2017-05-11" {
        description "Removed key attr. Updated notif for key.";
    }

    revision "2016-12-27" {
        description "Added snmp oid and documentation tag.";
    }

    revision "2016-10-28" {
        description "Initial version of TAcacs datamodel.";
    }


    grouping  tacacs-grouping {
    container tacacs {
        presence "yes";
        description
            "tacacs related operations";
        leaf vrfName  {
            type  cml_data_types:CML_STRING_T {
                length "0..255";
            }
        } // END of vrfName definition.

        leaf featureTacacs  {
            type  cml_data_types:CML_BOOL_T;
            mandatory true;
            description "feature tacacs+";
        } // END of featureTacacs definition.

        leaf tacacsKeyEnable  {
            if-feature feature_list:HAVE_HOSTPD;
            if-feature feature_list:HAVE_AAA;
            if-feature feature_list:HAVE_TACACS_CLIENT;
            type  cml_data_types:CML_HOSTP_KEY_TYPE_T;
        } // END of tacacsKeyEnable definition.

        leaf tacacsKeyWord  {
            if-feature feature_list:HAVE_HOSTPD;
            if-feature feature_list:HAVE_AAA;
            if-feature feature_list:HAVE_TACACS_CLIENT;
            type  cml_data_types:CML_STRING_T {
                length "0..255";
            }
            description "tacacs-server key";
        } // END of tacacsKeyWord definition.

        leaf debugtacacs  {
            if-feature feature_list:HAVE_HOSTPD;
            if-feature feature_list:HAVE_AAA;
            if-feature feature_list:HAVE_TACACS_CLIENT;
            type  cml_data_types:CML_BOOL_T;
            description "debug tacacs+";
        } // END of debugtacacs definition.

        leaf debugtacacsConfig  {
            if-feature feature_list:HAVE_HOSTPD;
            if-feature feature_list:HAVE_AAA;
            if-feature feature_list:HAVE_TACACS_CLIENT;
            type  cml_data_types:CML_BOOL_T;
            description "Enable/Disable debug";
        } // END of debugtacacsConfig definition.


        list tacacshost {
            key "hostAddr";
            description
                "tacacshost";
            leaf vrfName  {
                type  cml_data_types:CML_STRING_T {
                    length "0..255";
                }
            } // END of vrfName definition.

            leaf hostAddr  {
                type  cml_data_types:CML_STRING_T {
                    length "1..64";
                }
                description "tacacs-server host";
            } // END of hostAddr definition.

            leaf seqNum  {
                if-feature feature_list:HAVE_HOSTPD;
                if-feature feature_list:HAVE_AAA;
                if-feature feature_list:HAVE_TACACS_CLIENT;
                type  cml_data_types:CML_UINT8_T {
                     range "1..8";
                }
                mandatory true;
            } // END of seqNum definition.

            leaf keyEnable  {
                if-feature feature_list:HAVE_HOSTPD;
                if-feature feature_list:HAVE_AAA;
                if-feature feature_list:HAVE_TACACS_CLIENT;
                type  cml_data_types:CML_HOSTP_KEY_TYPE_T;
            } // END of keyEnable definition.

            leaf keyWord  {
                if-feature feature_list:HAVE_HOSTPD;
                if-feature feature_list:HAVE_AAA;
                if-feature feature_list:HAVE_TACACS_CLIENT;
                type  cml_data_types:CML_STRING_T {
                    length "0..255";
                }
            } // END of keyWord definition.

            leaf port  {
                if-feature feature_list:HAVE_HOSTPD;
                if-feature feature_list:HAVE_AAA;
                if-feature feature_list:HAVE_TACACS_CLIENT;
                type  cml_data_types:CML_UINT32_T {
                     range "1025..65535";
                }
            } // END of port definition.

        } // End of tacacshost-list
    } // END of tacacs-container definition.
    } // END of tacacs-container definition.


}
