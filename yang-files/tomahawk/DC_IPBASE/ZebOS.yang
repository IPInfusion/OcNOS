/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ZebOS.yang
*
*/

module ZebOS {

    namespace   "http://www.ipinfusion.com/CMLSchema/ZebOS";

    prefix "ZebOS";

    import cml_data_types {
        prefix cml_data_types;
    }

    include vr;
    include vrf;
    include interface;
    include vlan;
    include switchportinterface;
    include bridge;
    include mstp;
    include lacp;
    include lag;
    include lldpv2;
    include rib;
    include ospf;
    include ospfv3;
    include bgp;
    include oambfd;
    include vrrp;
    include plist;
    include isis;
    include keychain;
    include pim;
    include pim4;
    include vxlan;
    include syslog;
    include snmp;
    include featuredhcp;
    include radius;
    include tacacs;
    include ldap;
    include usermgmt;
    include ssh;
    include telnet;
    include ntp;
    include aaa;
    include dhcpr;
    include dns;
    include dhcpc;
    include sflow;
    include libsyslog;
    include license;
    include pserv;
    include mrib4;
    include igmp;
    include igmpsnooping;
    include routemap;
    include libsnmp;
    include mcec;
    include mlag;
    include hqos;
    include cmm;
    include auth;
    include rip;
    include acl;
    include aclinterface;
    include nsmsnmp;
    include hsl;
    include imi;
    include imiLoggging;
    include linktrack;
    include vlog;
    include ndd;
    include ripng;
    organization
        "IP Infusion Inc.";

    contact
        "Address: 3965 Freedom Circle, Suite 200, Santa Clara, CA 95054
        Phone: +1 408-400-1900
        E-mail: support@ipinfusion.com
        Web: http://www.ipinfusion.com/";

    description
        "ZebOS Managed Object";


    revision "2018-01-02" {
        description "added support for debug nsm and pktmgr.";
    }

    revision "2017-11-27" {
        description "Added CML_RANGE_T data type.";
    }

    revision "2017-11-10" {
        description "Modified the CUSTOM_DB trigger for seq-num.";
    }

    revision "2017-11-09" {
        description "NTP changes.";
    }

    revision "2017-11-03" {
        description "logging level all.";
    }

    revision "2017-11-02" {
        description "update vrId from CLI structure.";
    }

    revision "2017-10-26" {
        description "Removed CML_FORCE_SET for seqNum attr.";
    }

    revision "2017-10-23" {
        description "Console severity 0-5.";
    }

    revision "2017-10-18" {
        description "Made vrf as RDN for NTP.";
    }

    revision "2017-10-11" {
        description "Updated the key_enable default value only for CMLSH CLI.";
    }

    revision "2017-10-10" {
        description "Removed unset CLI generation for tacacs-server sequece number.";
    }

    revision "2017-09-28" {
        description "Added sequece number for tacacs-server host addr.";
    }

    revision "2017-09-19" {
        description "Added attr linkFlapErrDisable in interface datamodel.";
    }

    revision "2017-09-14" {
        description "Added attr errDisReason in interface datamodel.";
    }

    revision "2017-09-13" {
        description "Fix for JIRA-18634.";
    }

    revision "2017-09-04" {
        description "Updated range check for username attr.";
    }

    revision "2017-08-22" {
        description "JIRA-18348.";
    }

    revision "2017-08-09" {
        description "SNMP chnages done for JIRA-18238.";
    }

    revision "2017-08-08" {
        description "Changes done for ARP-ND cache disable..";
    }

    revision "2017-08-07" {
        description "adding custom-db-trigger for HQOS.";
    }

    revision "2017-07-29" {
        description "Changes done for Static MAC only route..";
    }

    revision "2017-07-27" {
        description "Added description to attributes.";
    }

    revision "2017-07-26" {
        description "Added support for more than one format of MAC address.";
    }

    revision "2017-07-24" {
        description "Introduced new cli to display user stats.";
    }

    revision "2017-07-14" {
        description "Added When tag in snmp datamodel..";
    }

    revision "2017-07-11" {
        description "Added FORCE_SET flag for mtu,speed,storm-control..";
    }

    revision "2017-07-10" {
        description "Added the multival support fro hardware-profile filter.";
    }

    revision "2017-07-05" {
        description "Changes done for hold timer for MAC removal.";
    }

    revision "2017-07-04" {
        description "Initial version of IMI datamodel.";
    }

    revision "2017-07-03" {
        description "custom error codes system mgmt modules..";
    }

    revision "2017-06-29" {
        description "Changes done for network side idempotency as JIRA-16106.";
    }

    revision "2017-06-28" {
        description "Changes done for vxlan/evpn statistics as JIRA-16129.";
    }

    revision "2017-06-12" {
        description "snmp-server user commands..";
    }

    revision "2017-06-09" {
        description "DNS configs not appearing in get-config..";
    }

    revision "2017-06-08" {
        description "Added restriction to allow only for admin role.";
    }

    revision "2017-06-07" {
        description "Removed tacacs timeout attr and cli sequence.         added objectUpdate for 'feature tacacs+ vrf management' command..";
    }

    revision "2017-06-06" {
        description "change in CLI range.";
    }

    revision "2017-06-02" {
        description "Datamodel implementation of bfd-firmware command.";
    }

    revision "2017-05-31" {
        description "Added the support of storm-control configuration with absolute value.";
    }

    revision "2017-05-30" {
        description "clear ssh hosts.";
    }

    revision "2017-05-29" {
        description "Data model chnages done for JIRA-16075.";
    }

    revision "2017-05-26" {
        description "Unlock Timeout Attribute.";
    }

    revision "2017-05-23" {
        description "Added startseqnum, increment to support resequence in acl datamodel.";
    }

    revision "2017-05-19" {
        description "Added missing commands and rsa/dsa keys are made objectAction.";
    }

    revision "2017-05-18" {
        description "changes done for JIRA-15803,15881,15882,15836.";
    }

    revision "2017-05-16" {
        description "Updated to hide tacacs timeout, Modified the cli-sequence to cli-command and removed unwanted attrs.";
    }

    revision "2017-05-15" {
        description "secondary ip address is not removed correctly.";
    }

    revision "2017-05-11" {
        description "Modified the cli-sequence to cli-command and removed attrs, Removed key attr. Updated notif for key, Updated notif for cleartext password.";
    }

    revision "2017-05-10" {
        description "Data model chnages done for JIRA-15643.";
    }

    revision "2017-05-04" {
        description "When any attr is removed from payload, unconfigures from backend to update DB..";
    }

    revision "2017-04-29" {
        description "changes for JIRA-15182 and JIRA-15068.";
    }

    revision "2017-04-28" {
        description "changes for mac ageing timeout..";
    }

    revision "2017-04-27" {
        description "Added nsm bcm cli.";
    }

    revision "2017-04-26" {
        description "removed ingress and egress Instance attribute.";
    }

    revision "2017-04-25" {
        description "JIRA-15182 for vxlan data model.";
    }

    revision "2017-04-21" {
        description "ACL rate-limit sFlow.";
    }

    revision "2017-04-20" {
        description "JIRA-15819 for vxlan data model.";
    }

    revision "2017-04-19" {
        description "sflow get api.";
    }

    revision "2017-04-14" {
        description "Added when tag for sflow Interface configurations.";
    }

    revision "2017-04-13" {
        description "changes for mac and arp learning disable for vxlan.";
    }

    revision "2017-04-11" {
        description "Corrected QOS-Inteface hierarchy.";
    }

    revision "2017-04-09" {
        description "changes for JIRA-14761 vxlan data model.";
    }

    revision "2017-04-06" {
        description "changes for JIRA-14587 vxlan data model.";
    }

    revision "2017-03-25" {
        description "Corrected LAG hierarchy.";
    }

    revision "2017-03-24" {
        description "Added switchport allowed ethertype support in interface module.";
    }

    revision "2017-03-21" {
        description "Updated dependecy with interface module in lacp.";
    }

    revision "2017-03-09" {
        description "Changes for acl datamodel.";
    }

    revision "2017-03-05" {
        description "added support for deletion of vlan type.";
    }

    revision "2017-03-03" {
        description "vlaninterface datamodel name has been changed to switchportInterface.";
    }

    revision "2017-02-27" {
        description "added dependentObject for brigdePort.";
    }

    revision "2017-02-25" {
        description "added support for show cml running-config.";
    }

    revision "2017-02-24" {
        description "cliflag added in vlanAccess objectlist.";
    }

    revision "2017-02-23" {
        description "hal statistics attribute added in ifStat container.";
    }

    revision "2017-02-22" {
        description "added bridgeId in bridgePort table, optimising ACL datamodel.";
    }

    revision "2017-02-21" {
        description "private-vlan changes.";
    }

    revision "2017-02-20" {
        description "added run-time attrs in ISIS datamodel.";
    }

    revision "2017-02-14" {
        description "adding missing flag for cli generation.";
    }

    revision "2017-02-13" {
        description "Add the load balance commands.";
    }

    revision "2017-02-11" {
        description "Rip datamodel modifeid.";
    }

    revision "2017-02-10" {
        description "disabling trill bridge creation command.";
    }

    revision "2017-02-08" {
        description "Defect fix for Mcast datamodel.";
    }

    revision "2017-02-07" {
        description "mapped mstp datamodel strcuture with mstpd structure.";
    }

    revision "2017-02-03" {
        description "changes for Mcast datamodel.";
    }

    revision "2017-02-02" {
        description "Defect fixes for isis,pim datamodel.";
    }

    revision "2017-01-31" {
        description "Removed extra attributes from interface datamodel.";
    }

    revision "2017-01-30" {
        description "datamodel adding for HQOS.";
    }

    revision "2017-01-28" {
        description "adding flag for default bridge objectlist in mstp.";
    }

    revision "2017-01-27" {
        description "changes for Debug command.";
    }

    revision "2017-01-25" {
        description "Defect fix in Mcast datamodel.";
    }

    revision "2017-01-23" {
        description "Defect fix in OSPF datamodel.";
    }

    revision "2017-01-20" {
        description "mapped interface datamodel attribute with interface structure.";
    }

    revision "2017-01-19" {
        description "Defect fixes in VRRP datamodel.";
    }

    revision "2017-01-16" {
        description "Ported LDP and RSVP changes from XP-master.";
    }

    revision "2017-01-12" {
        description "auto-populate of default bridge disabled.";
    }

    revision "2017-01-11" {
        description "default bridge command disabled.";
    }

    revision "2017-01-10" {
        description "Defect fixes in OSPF and ISIS datamodel.";
    }

    revision "2017-01-04" {
        description "Changes done to add implicit delete tags.";
    }

    revision "2016-12-30" {
        description "Changes ported from XP-master for vr and vrf.";
    }

    revision "2016-12-29" {
        description "Added support for Routemap SMI auto generation.";
    }

    revision "2016-12-28" {
        description "Added support for Vxlan commands in cmlsh..";
    }

    revision "2016-12-26" {
        description "Added support for LLDPv2 get API.";
    }

    revision "2016-12-22" {
        description "Added support for OSPF SMI auto generation.";
    }

    revision "2016-12-17" {
        description "ISIS redistribute CLI's are changed as per backend CLI's.";
    }

    revision "2016-10-28" {
        description "Top level module includes all ZebOS managed objects.";
    }

    revision "2016-01-29" {
        description "Changes done for ospf getapi and snmp tags.";
    }


    uses lacpSystemPriority-grouping;
    uses lacpdebug-grouping;
    uses oamMpls-grouping;
    uses VrrpDebug-grouping;
    uses hostpsyslog-grouping;
    uses snmp-grouping;
    uses tacacs-grouping;
    uses ldap-grouping;
    uses userDebug-grouping;
    uses ssh-grouping;
    uses telnet-grouping;
    uses sourceNTP-grouping;
    uses debugNTP-grouping;
    uses aaa-grouping;
    uses dhcprelay-grouping;
    uses dhcprelay6-grouping;
    uses dns-grouping;
    uses sflow-grouping;
    uses debugsflow-grouping;
    uses ACLsFlow-grouping;
    uses log-grouping;
    uses pservd-grouping;
    uses igmpConfig-grouping;
    uses snmpVrfName-grouping;
    uses mcecMaster-grouping;
    uses nsmMlag-grouping;
    uses cmmGlobals-grouping;
    uses cmmDmm-grouping;
    uses cmmCpuInfo-grouping;
    uses cmmSysRamTable-grouping;
    uses cmmStackUnitUtilTable-grouping;
    uses cmmSysLedTable-grouping;
    uses cmmSysSwModuleTable-grouping;
    uses cmmAlarmVariable-grouping;
    uses debugdot1x-grouping;
    uses nsmsnmp-grouping;
    uses logginghsl-grouping;
    uses loggingCli-grouping;
    uses memInfo-grouping;
    uses logging_cli-grouping;
    uses logging-grouping;
    uses loggingndd-grouping;
    uses loggingripng-grouping;
    uses vr-grouping;
    uses mstTeBridge-grouping;
    uses backboneBridgePort-grouping;
    uses lldpMaster-grouping;
    uses ospfMaster-grouping;
    uses bgpGlobal-grouping;
    uses hashTableSize-grouping;
    uses bfdSession-grouping;
    uses confModeDebug-grouping;
    uses execModeDebug-grouping;
    uses prefixMaster-grouping;
    uses prefixMaster6-grouping;
    uses usermgmt-grouping;
    uses ntp-grouping;
    uses dhcprelayinterface-grouping;
    uses dhcp6nterface-grouping;
    uses logginglevel-grouping;
    uses cmmStackUnitTable-grouping;
    uses cmmSysPowerSupplyTable-grouping;
    uses cmmSysFanTable-grouping;
    uses cmmSysTemperatureTable-grouping;
    uses cmmSysChipTemperatureTable-grouping;
    uses interfaceTrack-grouping;

    rpc interface-clear-arp-cache {
        input  {
            leaf vrId  {
                type cml_data_types:CML_UINT32_T;
                mandatory true;
            }
        }
    }

    rpc interface-clear-ipv6-neighbors {
        input  {
            leaf vrId  {
                type cml_data_types:CML_UINT32_T;
                mandatory true;
            }
        }
    }

    rpc lag-lacp-snmp-restart {
    }

    rpc rib-clearIpRouteKernel {
        input  {
            leaf vrId  {
                type cml_data_types:CML_UINT32_T;
                mandatory true;
            }
        }
    }

    rpc rib-clearIpKernelRoute {
        input  {
            leaf vrId  {
                type cml_data_types:CML_UINT32_T;
                mandatory true;
            }
        }
    }

    rpc rib-clearIpv6RouteKernel {
        input  {
            leaf vrId  {
                type cml_data_types:CML_UINT32_T;
                mandatory true;
            }
        }
    }

    rpc rib-clearIpRouteAll {
        input  {
            leaf vrId  {
                type cml_data_types:CML_UINT32_T;
                mandatory true;
            }
            leaf starPrint  {
                type cml_data_types:CML_STRING_T;
                mandatory true;
            }
        }
    }

    rpc rib-clearIpRoutePrefix {
        input  {
            leaf vrId  {
                type cml_data_types:CML_UINT32_T;
                mandatory true;
            }
            leaf prefixAddr  {
                type cml_data_types:CML_STRING_T;
                mandatory true;
            }
        }
    }

    rpc rib-clearIpv4RouteAll {
        input  {
            leaf vrId  {
                type cml_data_types:CML_UINT32_T;
                mandatory true;
            }
            leaf starPrint  {
                type cml_data_types:CML_STRING_T;
                mandatory true;
            }
        }
    }

    rpc rib-clearIpv4RoutePrefix {
        input  {
            leaf vrId  {
                type cml_data_types:CML_UINT32_T;
                mandatory true;
            }
            leaf prefixAddr  {
                type cml_data_types:CML_STRING_T;
                mandatory true;
            }
        }
    }

    rpc rib-clearIpv6RouteAll {
        input  {
            leaf vrId  {
                type cml_data_types:CML_UINT32_T;
                mandatory true;
            }
            leaf starPrint  {
                type cml_data_types:CML_STRING_T;
                mandatory true;
            }
        }
    }

    rpc rib-clearIpv6RoutePrefix {
        input  {
            leaf vrId  {
                type cml_data_types:CML_UINT32_T;
                mandatory true;
            }
            leaf prefixIpv6Addr  {
                type cml_data_types:CML_STRING_T;
                mandatory true;
            }
        }
    }

    rpc rib-clearIpVrfRouteAll {
        input  {
            leaf vrId  {
                type cml_data_types:CML_UINT32_T;
                mandatory true;
            }
            leaf vrfName  {
                type cml_data_types:CML_STRING_T;
                mandatory true;
            }
            leaf starPrint  {
                type cml_data_types:CML_STRING_T;
                mandatory true;
            }
        }
    }

    rpc rib-clearIpVrfRoutePrefix {
        input  {
            leaf vrId  {
                type cml_data_types:CML_UINT32_T;
                mandatory true;
            }
            leaf vrfName  {
                type cml_data_types:CML_STRING_T;
                mandatory true;
            }
            leaf prefixAddr  {
                type cml_data_types:CML_STRING_T;
                mandatory true;
            }
        }
    }

    rpc rib-clearIpv4VrfRouteAll {
        input  {
            leaf vrId  {
                type cml_data_types:CML_UINT32_T;
                mandatory true;
            }
            leaf vrfName  {
                type cml_data_types:CML_STRING_T;
                mandatory true;
            }
            leaf starPrint  {
                type cml_data_types:CML_STRING_T;
                mandatory true;
            }
        }
    }

    rpc rib-clearIpv4VrfRoutePrefix {
        input  {
            leaf vrId  {
                type cml_data_types:CML_UINT32_T;
                mandatory true;
            }
            leaf vrfName  {
                type cml_data_types:CML_STRING_T;
                mandatory true;
            }
            leaf prefixAddr  {
                type cml_data_types:CML_STRING_T;
                mandatory true;
            }
        }
    }

    rpc rib-clearIpv6VrdRouteAll {
        input  {
            leaf vrId  {
                type cml_data_types:CML_UINT32_T;
                mandatory true;
            }
            leaf vrfName  {
                type cml_data_types:CML_STRING_T;
                mandatory true;
            }
            leaf starPrint  {
                type cml_data_types:CML_STRING_T;
                mandatory true;
            }
        }
    }

    rpc rib-clearIpv6RoutePrefixVrf {
        input  {
            leaf vrId  {
                type cml_data_types:CML_UINT32_T;
                mandatory true;
            }
            leaf vrfName  {
                type cml_data_types:CML_STRING_T;
                mandatory true;
            }
            leaf prefixIpv6Addr  {
                type cml_data_types:CML_STRING_T;
                mandatory true;
            }
        }
    }

    rpc ospf-restart-ospf-graceful {
        input  {
            leaf vrId  {
                type cml_data_types:CML_UINT32_T;
                mandatory true;
            }
            leaf restartGracePeriod  {
                type cml_data_types:CML_UINT32_T;
                mandatory true;
            }
        }
    }

    rpc ospf-restart-ospf-hitless {
        input  {
            leaf vrId  {
                type cml_data_types:CML_UINT32_T;
                mandatory true;
            }
            leaf hitlessGracePeriod  {
                type cml_data_types:CML_UINT32_T;
                mandatory true;
            }
        }
    }

    rpc ospfv3-ospf-clear {
        input  {
            leaf vrId  {
                type cml_data_types:CML_UINT32_T;
                mandatory true;
            }
            leaf ospfProcess  {
                type cml_data_types:CML_STRING_T;
                mandatory true;
            }
        }
    }

    rpc ospfv3-ospf-restart-hitless {
        input  {
            leaf vrId  {
                type cml_data_types:CML_UINT32_T;
                mandatory true;
            }
            leaf gracePeriod  {
                type cml_data_types:CML_UINT32_T;
                mandatory true;
            }
        }
    }

    rpc ospfv3-ospf-restart {
        input  {
            leaf vrId  {
                type cml_data_types:CML_UINT32_T;
                mandatory true;
            }
            leaf gracePeriod  {
                type cml_data_types:CML_UINT32_T;
                mandatory true;
            }
        }
    }

    rpc ospfv3-ospf-snmp-restart {
    }

    rpc bgp-restartBgp {
        input  {
            leaf vrId  {
                type cml_data_types:CML_UINT32_T;
                mandatory true;
            }
        }
    }

    rpc bgp-clearBgp {
        input  {
            leaf vrId  {
                type cml_data_types:CML_UINT32_T;
                mandatory true;
            }
        }
    }

    rpc vrrp-snmp-restart-vrrp {
    }

    rpc plist-clear-ip-prefix {
        input  {
            leaf vrId  {
                type cml_data_types:CML_UINT32_T;
                mandatory true;
            }
        }
    }

    rpc plist-clear-ip-prefix-by-name {
        input  {
            leaf vrId  {
                type cml_data_types:CML_UINT32_T;
                mandatory true;
            }
            leaf name  {
                type cml_data_types:CML_STRING_T;
                mandatory true;
            }
        }
    }

    rpc plist-clear-ip-prefix-by-prefix {
        input  {
            leaf vrId  {
                type cml_data_types:CML_UINT32_T;
                mandatory true;
            }
            leaf name  {
                type cml_data_types:CML_STRING_T;
                mandatory true;
            }
            leaf prefix  {
                type cml_data_types:CML_STRING_T;
                mandatory true;
            }
        }
    }

    rpc plist-clear-ipv6-prefix {
        input  {
            leaf vrId  {
                type cml_data_types:CML_UINT32_T;
                mandatory true;
            }
        }
    }

    rpc plist-clear-ipv6-prefix-by-name {
        input  {
            leaf vrId  {
                type cml_data_types:CML_UINT32_T;
                mandatory true;
            }
            leaf name  {
                type cml_data_types:CML_STRING_T;
                mandatory true;
            }
        }
    }

    rpc plist-clear-ipv6-prefix-by-prefix {
        input  {
            leaf vrId  {
                type cml_data_types:CML_UINT32_T;
                mandatory true;
            }
            leaf name  {
                type cml_data_types:CML_STRING_T;
                mandatory true;
            }
            leaf prefix  {
                type cml_data_types:CML_STRING_T;
                mandatory true;
            }
        }
    }

    rpc isis-isis-restart {
        input  {
            leaf vrId  {
                type cml_data_types:CML_UINT32_T;
                mandatory true;
            }
            leaf graceCMLSEPperiod  {
                type cml_data_types:CML_UINT16_T;
                mandatory true;
            }
        }
    }

    rpc isis-clear-is-neighbors {
        input  {
            leaf vrId  {
                type cml_data_types:CML_UINT32_T;
                mandatory true;
            }
            leaf SystemID  {
                type cml_data_types:CML_STRING_T;
                mandatory true;
            }
        }
    }

    rpc isis-clear-neighbors {
        input  {
            leaf vrId  {
                type cml_data_types:CML_UINT32_T;
                mandatory true;
            }
        }
    }

    rpc isis-clear-ip-route {
        input  {
            leaf vrId  {
                type cml_data_types:CML_UINT32_T;
                mandatory true;
            }
            leaf isisInstanceTag  {
                type cml_data_types:CML_STRING_T;
                mandatory true;
            }
            leaf ipv4route  {
                type cml_data_types:CML_UINT8_T;
                mandatory true;
            }
        }
    }

    rpc isis-clear-ipv6-route {
        input  {
            leaf vrId  {
                type cml_data_types:CML_UINT32_T;
                mandatory true;
            }
            leaf isisInstanceTag  {
                type cml_data_types:CML_STRING_T;
                mandatory true;
            }
            leaf ipv6route  {
                type cml_data_types:CML_UINT8_T;
                mandatory true;
            }
        }
    }

    rpc isis-isis-proc-clear {
        input  {
            leaf vrId  {
                type cml_data_types:CML_UINT32_T;
                mandatory true;
            }
            leaf isisInstanceTag  {
                type cml_data_types:CML_STRING_T;
                mandatory true;
            }
        }
    }

    rpc isis-isis-clear-counters {
        input  {
            leaf vrId  {
                type cml_data_types:CML_UINT32_T;
                mandatory true;
            }
        }
    }

    rpc isis-clear-interface-counters {
        input  {
            leaf vrId  {
                type cml_data_types:CML_UINT32_T;
                mandatory true;
            }
            leaf ifName  {
                type cml_data_types:CML_STRING_T;
                mandatory true;
            }
        }
    }

    rpc isis-clear-adjacency-all {
        input  {
            leaf vrId  {
                type cml_data_types:CML_UINT32_T;
                mandatory true;
            }
            leaf adjall  {
                type cml_data_types:CML_BOOL_T;
                mandatory true;
            }
            leaf adjvrfname  {
                type cml_data_types:CML_STRING_T;
                mandatory true;
            }
        }
    }

    rpc isis-clear-adjacency-word-all {
        input  {
            leaf vrId  {
                type cml_data_types:CML_UINT32_T;
                mandatory true;
            }
            leaf tagname  {
                type cml_data_types:CML_STRING_T;
                mandatory true;
            }
            leaf adjall  {
                type cml_data_types:CML_BOOL_T;
                mandatory true;
            }
            leaf adjvrfname  {
                type cml_data_types:CML_STRING_T;
                mandatory true;
            }
        }
    }

    rpc isis-clear-adjacency-word-ifname {
        input  {
            leaf vrId  {
                type cml_data_types:CML_UINT32_T;
                mandatory true;
            }
            leaf tagname  {
                type cml_data_types:CML_STRING_T;
                mandatory true;
            }
            leaf tagifname  {
                type cml_data_types:CML_STRING_T;
                mandatory true;
            }
            leaf adjvrfname  {
                type cml_data_types:CML_STRING_T;
                mandatory true;
            }
        }
    }

    rpc isis-clear-adjacency-ifname {
        input  {
            leaf vrId  {
                type cml_data_types:CML_UINT32_T;
                mandatory true;
            }
            leaf adjifname  {
                type cml_data_types:CML_STRING_T;
                mandatory true;
            }
            leaf adjvrfname  {
                type cml_data_types:CML_STRING_T;
                mandatory true;
            }
        }
    }

    rpc isis-clear-adjacency-word-systemid {
        input  {
            leaf vrId  {
                type cml_data_types:CML_UINT32_T;
                mandatory true;
            }
            leaf tagname  {
                type cml_data_types:CML_STRING_T;
                mandatory true;
            }
            leaf tagsystemid  {
                type cml_data_types:CML_STRING_T;
                mandatory true;
            }
            leaf tagvrfname  {
                type cml_data_types:CML_STRING_T;
                mandatory true;
            }
        }
    }

    rpc isis-clear-adjacency-systemid {
        input  {
            leaf vrId  {
                type cml_data_types:CML_UINT32_T;
                mandatory true;
            }
            leaf adjsystemid  {
                type cml_data_types:CML_STRING_T;
                mandatory true;
            }
            leaf adjvrfname  {
                type cml_data_types:CML_STRING_T;
                mandatory true;
            }
        }
    }

    rpc isis-snmp-restart-isis {
    }

    rpc pim-snmp-restart-pim {
    }

    rpc pim4-clear-ip-mroute {
        input  {
            leaf vrId  {
                type cml_data_types:CML_UINT32_T;
                mandatory true;
            }
            leaf vrfName  {
                type cml_data_types:CML_STRING_T;
                mandatory true;
            }
            leaf allFlag  {
                type cml_data_types:CML_BOOL_T;
                mandatory true;
            }
            leaf pimmode  {
                type cml_data_types:CML_UINT8_T;
                mandatory true;
            }
        }
    }

    rpc pim4-clear-ip-mroute-xg {
        input  {
            leaf vrId  {
                type cml_data_types:CML_UINT32_T;
                mandatory true;
            }
            leaf vrfName  {
                type cml_data_types:CML_STRING_T;
                mandatory true;
            }
            leaf mrouteXg  {
                type cml_data_types:CML_STRING_T;
                mandatory true;
            }
        }
    }

    rpc pim4-clear-ip-mroute-sg {
        input  {
            leaf vrId  {
                type cml_data_types:CML_UINT32_T;
                mandatory true;
            }
            leaf vrfName  {
                type cml_data_types:CML_STRING_T;
                mandatory true;
            }
            leaf mrouteGaddr  {
                type cml_data_types:CML_STRING_T;
                mandatory true;
            }
            leaf mrouteSaddr  {
                type cml_data_types:CML_STRING_T;
                mandatory true;
            }
            leaf pimgsmode  {
                type cml_data_types:CML_UINT8_T;
                mandatory true;
            }
        }
    }

    rpc pim4-clear-ip-pim {
        input  {
            leaf vrId  {
                type cml_data_types:CML_UINT32_T;
                mandatory true;
            }
            leaf vrfName  {
                type cml_data_types:CML_STRING_T;
                mandatory true;
            }
            leaf allRp  {
                type cml_data_types:CML_BOOL_T;
                mandatory true;
            }
        }
    }

    rpc pim4-clear-ip-msdp-peer {
        input  {
            leaf vrId  {
                type cml_data_types:CML_UINT32_T;
                mandatory true;
            }
            leaf vrfName  {
                type cml_data_types:CML_STRING_T;
                mandatory true;
            }
            leaf peerAddress  {
                type cml_data_types:CML_STRING_T;
                mandatory true;
            }
        }
    }

    rpc pim4-clear-ip-msdp-sacache {
        input  {
            leaf vrId  {
                type cml_data_types:CML_UINT32_T;
                mandatory true;
            }
            leaf vrfName  {
                type cml_data_types:CML_STRING_T;
                mandatory true;
            }
            leaf saAddress  {
                type cml_data_types:CML_STRING_T;
                mandatory true;
            }
        }
    }

    rpc vxlan-clear-nvo-id-access-port {
        input  {
            leaf vrId  {
                type cml_data_types:CML_UINT32_T;
                mandatory true;
            }
            leaf ifName  {
                type cml_data_types:CML_STRING_T;
                mandatory true;
            }
        }
    }

    rpc vxlan-clear-nvo-id-acess-port-vlan {
        input  {
            leaf vrId  {
                type cml_data_types:CML_UINT32_T;
                mandatory true;
            }
            leaf ifName  {
                type cml_data_types:CML_STRING_T;
                mandatory true;
            }
            leaf vlanId  {
                type cml_data_types:CML_UINT32_T;
                mandatory true;
            }
        }
    }

    rpc vxlan-clear-nvo-id-access-all {
        input  {
            leaf vrId  {
                type cml_data_types:CML_UINT32_T;
                mandatory true;
            }
            leaf clearAllCounter  {
                type cml_data_types:CML_BOOL_T;
                mandatory true;
            }
        }
    }

    rpc vxlan-clear-nvo-id-network-all {
        input  {
            leaf vrId  {
                type cml_data_types:CML_UINT32_T;
                mandatory true;
            }
            leaf clearNetworkAllCounter  {
                type cml_data_types:CML_BOOL_T;
                mandatory true;
            }
        }
    }

    rpc vxlan-clear-nvo-id-network-port {
        input  {
            leaf vrId  {
                type cml_data_types:CML_UINT32_T;
                mandatory true;
            }
            leaf destIpv4  {
                type cml_data_types:CML_STRING_T;
                mandatory true;
            }
        }
    }

    rpc vxlan-clear-nvo-vxlan-mac-stale-entries {
        input  {
            leaf vrId  {
                type cml_data_types:CML_UINT32_T;
                mandatory true;
            }
            leaf vnId  {
                type cml_data_types:CML_UINT32_T;
                mandatory true;
            }
        }
    }

    rpc usermgmt-user {
        input  {
            leaf user  {
                type cml_data_types:CML_STRING_T;
                mandatory true;
            }
        }
    }

    rpc ssh-lengthRSA {
        input  {
            leaf usernameRSA  {
                type cml_data_types:CML_STRING_T;
                mandatory true;
            }
            leaf keyRSA  {
                type cml_data_types:CML_BOOL_T;
                mandatory true;
            }
            leaf lengthRSA  {
                type cml_data_types:CML_INT32_T;
                mandatory true;
            }
            leaf forceRSA  {
                type cml_data_types:CML_BOOL_T;
                mandatory true;
            }
        }
    }

    rpc ssh-keyDSA {
        input  {
            leaf usernameDSA  {
                type cml_data_types:CML_STRING_T;
                mandatory true;
            }
            leaf keyDSA  {
                type cml_data_types:CML_BOOL_T;
                mandatory true;
            }
            leaf forceDSA  {
                type cml_data_types:CML_BOOL_T;
                mandatory true;
            }
        }
    }

    rpc ssh-keyGenRSA {
        input  {
            leaf keyGenRSA  {
                type cml_data_types:CML_BOOL_T;
                mandatory true;
            }
            leaf keyGenlengthRSA  {
                type cml_data_types:CML_UINT32_T;
                mandatory true;
            }
            leaf keyGenforceRSA  {
                type cml_data_types:CML_BOOL_T;
                mandatory true;
            }
            leaf vrfName  {
                type cml_data_types:CML_STRING_T;
                mandatory true;
            }
        }
    }

    rpc ssh-keyDelRSA {
        input  {
            leaf keyDelRSA  {
                type cml_data_types:CML_BOOL_T;
                mandatory true;
            }
            leaf vrfName  {
                type cml_data_types:CML_STRING_T;
                mandatory true;
            }
        }
    }

    rpc ssh-keyGenDSA {
        input  {
            leaf keyGenDSA  {
                type cml_data_types:CML_BOOL_T;
                mandatory true;
            }
            leaf keyGenforceDSA  {
                type cml_data_types:CML_BOOL_T;
                mandatory true;
            }
            leaf vrfName  {
                type cml_data_types:CML_STRING_T;
                mandatory true;
            }
        }
    }

    rpc ssh-keyDelDSA {
        input  {
            leaf keyDelDSA  {
                type cml_data_types:CML_BOOL_T;
                mandatory true;
            }
            leaf vrfName  {
                type cml_data_types:CML_STRING_T;
                mandatory true;
            }
        }
    }

    rpc ssh-keyDelSSHkeys {
        input  {
            leaf keyDelSSHkeys  {
                type cml_data_types:CML_BOOL_T;
                mandatory true;
            }
            leaf vrfName  {
                type cml_data_types:CML_STRING_T;
                mandatory true;
            }
        }
    }

    rpc ssh-clearSSHhosts {
        input  {
            leaf clearSSHhosts  {
                type cml_data_types:CML_BOOL_T;
                mandatory true;
            }
        }
    }

    rpc ntp-sync-retry {
        input  {
            leaf vrf  {
                type cml_data_types:CML_STRING_T;
                mandatory true;
            }
        }
    }

    rpc ntp-clear {
        input  {
            leaf statistics  {
                type cml_data_types:CML_INT32_T;
                mandatory true;
            }
        }
    }

    rpc aaa-lockout {
        input  {
            leaf username  {
                type cml_data_types:CML_STRING_T;
                mandatory true;
            }
        }
    }

    rpc libsyslog-cleardebuglogfile {
    }

    rpc libsyslog-clearlogginglogfile {
    }

    rpc license-licenseget {
        input  {
            leaf sourceCMLSEPinterface  {
                type cml_data_types:CML_STRING_T;
                mandatory true;
            }
            leaf url  {
                type cml_data_types:CML_STRING_T;
                mandatory true;
            }
        }
    }

    rpc license-licenserefresh {
    }

    rpc pserv-clearCores {
        input  {
            leaf clearCore  {
                type cml_data_types:CML_STRING_T;
                mandatory true;
            }
        }
    }

    rpc mrib4-snmp-restart-mrib {
    }

    rpc mrib4-clear-mrib-vrf-all {
        input  {
            leaf vrId  {
                type cml_data_types:CML_UINT32_T;
                mandatory true;
            }
            leaf vrfName  {
                type cml_data_types:CML_STRING_T;
                mandatory true;
            }
            leaf allroute  {
                type cml_data_types:CML_BOOL_T;
                mandatory true;
            }
        }
    }

    rpc mrib4-clear-mrib-grp {
        input  {
            leaf vrId  {
                type cml_data_types:CML_UINT32_T;
                mandatory true;
            }
            leaf vrfName  {
                type cml_data_types:CML_STRING_T;
                mandatory true;
            }
            leaf grpAddr  {
                type cml_data_types:CML_STRING_T;
                mandatory true;
            }
        }
    }

    rpc mrib4-clear-mrib-vrf-src-grp {
        input  {
            leaf vrId  {
                type cml_data_types:CML_UINT32_T;
                mandatory true;
            }
            leaf vrfName  {
                type cml_data_types:CML_STRING_T;
                mandatory true;
            }
            leaf srcAddr  {
                type cml_data_types:CML_STRING_T;
                mandatory true;
            }
            leaf grpAddr  {
                type cml_data_types:CML_STRING_T;
                mandatory true;
            }
        }
    }

    rpc mrib4-clear-mrib-stats-all {
        input  {
            leaf vrId  {
                type cml_data_types:CML_UINT32_T;
                mandatory true;
            }
            leaf vrfName  {
                type cml_data_types:CML_STRING_T;
                mandatory true;
            }
            leaf allroute  {
                type cml_data_types:CML_BOOL_T;
                mandatory true;
            }
        }
    }

    rpc mrib4-clear-mrib-vrf-grp-stats {
        input  {
            leaf vrId  {
                type cml_data_types:CML_UINT32_T;
                mandatory true;
            }
            leaf vrfName  {
                type cml_data_types:CML_STRING_T;
                mandatory true;
            }
            leaf grpAddr  {
                type cml_data_types:CML_STRING_T;
                mandatory true;
            }
        }
    }

    rpc mrib4-clear-mrib-vrf-src-grp-stats {
        input  {
            leaf vrId  {
                type cml_data_types:CML_UINT32_T;
                mandatory true;
            }
            leaf vrfName  {
                type cml_data_types:CML_STRING_T;
                mandatory true;
            }
            leaf srcAddr  {
                type cml_data_types:CML_STRING_T;
                mandatory true;
            }
            leaf grpAddr  {
                type cml_data_types:CML_STRING_T;
                mandatory true;
            }
        }
    }

    rpc igmp-mrib4-igmp-group-clear {
        input  {
            leaf vrfName  {
                type cml_data_types:CML_STRING_T;
                mandatory true;
            }
            leaf groupAddr  {
                type cml_data_types:CML_STRING_T;
                mandatory true;
            }
            leaf ifName  {
                type cml_data_types:CML_STRING_T;
                mandatory true;
            }
        }
    }

    rpc igmp-mrib4-igmp-interface-clear {
        input  {
            leaf vrfName  {
                type cml_data_types:CML_STRING_T;
                mandatory true;
            }
            leaf ifName  {
                type cml_data_types:CML_STRING_T;
                mandatory true;
            }
        }
    }

    rpc igmp-mrib4-igmp-vrfName-clear {
        input  {
            leaf vrfName  {
                type cml_data_types:CML_STRING_T;
                mandatory true;
            }
        }
    }

    rpc igmp-mrib4-igmp-all-group-clear {
        input  {
            leaf vrfName  {
                type cml_data_types:CML_STRING_T;
                mandatory true;
            }
            leaf groupAddr  {
                type cml_data_types:CML_STRING_T;
                mandatory true;
            }
        }
    }

    rpc igmp-mrib4-igmp-group-clear-all {
        input  {
            leaf vrfName  {
                type cml_data_types:CML_STRING_T;
                mandatory true;
            }
            leaf clearAll  {
                type cml_data_types:CML_UINT8_T;
                mandatory true;
            }
        }
    }

    rpc igmpsnooping-igmpsnooping-clear-interface-group {
        input  {
            leaf groupAddr  {
                type cml_data_types:CML_STRING_T;
                mandatory true;
            }
            leaf ifName  {
                type cml_data_types:CML_STRING_T;
                mandatory true;
            }
        }
    }

    rpc igmpsnooping-igmpsnooping-clear-interface {
        input  {
            leaf ifName  {
                type cml_data_types:CML_STRING_T;
                mandatory true;
            }
        }
    }

    rpc igmpsnooping-igmpsnooping-clear-all {
    }

    rpc igmpsnooping-igmpsnooping-clear {
    }

    rpc igmpsnooping-igmpsnooping-clear-group {
        input  {
            leaf groupAddr  {
                type cml_data_types:CML_STRING_T;
                mandatory true;
            }
        }
    }

    rpc mcec-clear-mcec-statistics {
    }

    rpc cmm-clear-ddm-transceiver-alarm {
        input  {
            leaf portNum  {
                type cml_data_types:CML_STRING_T;
                mandatory true;
            }
        }
    }

    rpc auth-snmp-restart {
    }

    rpc rip-rip-restart {
        input  {
            leaf vrId  {
                type cml_data_types:CML_UINT32_T;
                mandatory true;
            }
            leaf gracePeriod  {
                type cml_data_types:CML_UINT32_T;
                mandatory true;
            }
        }
    }

    rpc rip-clear-ip-rip-route {
        input  {
            leaf vrId  {
                type cml_data_types:CML_UINT32_T;
                mandatory true;
            }
            leaf routeCMLSEPtype  {
                type cml_data_types:CML_UINT8_T;
                mandatory true;
            }
        }
    }

    rpc rip-clear-ip-rip-route-prefix {
        input  {
            leaf vrId  {
                type cml_data_types:CML_UINT32_T;
                mandatory true;
            }
            leaf routeCMLSEPtypeCMLSEPpre  {
                type cml_data_types:CML_STRING_T;
                mandatory true;
            }
        }
    }

    rpc rip-clear-ip-rip-route-vrf {
        input  {
            leaf vrId  {
                type cml_data_types:CML_UINT32_T;
                mandatory true;
            }
            leaf vrfName  {
                type cml_data_types:CML_STRING_T;
                mandatory true;
            }
            leaf prefixStr  {
                type cml_data_types:CML_STRING_T;
                mandatory true;
            }
        }
    }

    rpc rip-clear-ip-rip-stat-interf {
        input  {
            leaf vrId  {
                type cml_data_types:CML_UINT32_T;
                mandatory true;
            }
            leaf ifName  {
                type cml_data_types:CML_STRING_T;
                mandatory true;
            }
        }
    }

    rpc rip-snmp-restart-rip {
    }

    rpc imi-clearUser {
        input  {
            leaf vrId  {
                type cml_data_types:CML_UINT32_T;
                mandatory true;
            }
            leaf clearUser  {
                type cml_data_types:CML_STRING_T;
                mandatory true;
            }
        }
    }

    rpc imi-clearLine {
        input  {
            leaf vrId  {
                type cml_data_types:CML_UINT32_T;
                mandatory true;
            }
            leaf clearLine  {
                type cml_data_types:CML_STRING_T;
                mandatory true;
            }
        }
    }

    notification force_unlock {

        description "Notify force unlck from netconf.";

        leaf message {
            type string;
        }
    }

    notification interface-Errdis-Reason {

        description "The interfaceErrdisReason is generated when an interface is error-disabled..";

        leaf ifIndex {
            type string;
        }

        leaf vrId {
            type string;
        }

        leaf errDisReason {
            type string;
        }
    }

    notification agg-Min-Link {

        description "The aggMinLink is generated when a total Active (link-UP) LAG member link count becomes less than the configured min-link count..";

        leaf ifIndex {
            type string;
        }

        leaf vrId {
            type string;
        }

        leaf aggDownMinLink {
            type string;
        }
    }

    notification sflowReceiverTimeoutAlarmMsg {

        description "Notify alarm message.";

        leaf message {
            type string;
        }
    }

    notification cmmAlarmCpuRisingThreshold {

        description "Trap to send information for Rising threshold, threshold interval and CPU Utilisation.";

        leaf cmmSysCpuThresholdInterval {
            type string;
        }

        leaf cmmSysCpuThreshold {
            type string;
        }

        leaf cmmStackUnitCpuUtilization {
            type string;
        }
    }

    notification cmmAlarmFreeMemBlwThreshold {

        description "Trap to send information for Free Memory and Free Memory Threshold.";

        leaf cmmSysRamFreeMem {
            type string;
        }

        leaf cmmSysRamThreshold {
            type string;
        }
    }

    notification cmmAlarmTempHigh {

        description "Set when internal temperature exceeds high alarm level.";

        leaf cmmSysPortIndex {
            type string;
        }

        leaf cmmSysPortType {
            type string;
        }

        leaf cmmSysTemperature {
            type string;
        }

        leaf cmmAlarmVarInteger {
            type string;
        }
    }

    notification cmmAlarmTempLow {

        description "Set when internal temperature is below low alarm level.";

        leaf cmmSysPortIndex {
            type string;
        }

        leaf cmmSysPortType {
            type string;
        }

        leaf cmmSysTemperature {
            type string;
        }

        leaf cmmAlarmVarInteger {
            type string;
        }
    }

    notification cmmWarningTempHigh {

        description "Set when internal temperature exceeds high warning level.";

        leaf cmmSysPortIndex {
            type string;
        }

        leaf cmmSysPortType {
            type string;
        }

        leaf cmmSysTemperature {
            type string;
        }

        leaf cmmAlarmVarInteger {
            type string;
        }
    }

    notification cmmWarningTempLow {

        description "Set when internal temperature is below low warning level.";

        leaf cmmSysPortIndex {
            type string;
        }

        leaf cmmSysPortType {
            type string;
        }

        leaf cmmSysTemperature {
            type string;
        }

        leaf cmmAlarmVarInteger {
            type string;
        }
    }

    notification cmmAlarmVoltageHigh {

        description "Set when internal supply voltage exceeds high alarm level.";

        leaf cmmSysPortIndex {
            type string;
        }

        leaf cmmSysPortType {
            type string;
        }

        leaf cmmSysVoltage {
            type string;
        }

        leaf cmmAlarmVarString {
            type string;
        }
    }

    notification cmmAlarmVoltageLow {

        description "Set when internal supply voltage is below low alarm level.";

        leaf cmmSysPortIndex {
            type string;
        }

        leaf cmmSysPortType {
            type string;
        }

        leaf cmmSysVoltage {
            type string;
        }

        leaf cmmAlarmVarString {
            type string;
        }
    }

    notification cmmWarningVoltageHigh {

        description "Set when internal supply voltage exceeds high warning level..";

        leaf cmmSysPortIndex {
            type string;
        }

        leaf cmmSysPortType {
            type string;
        }

        leaf cmmSysVoltage {
            type string;
        }

        leaf cmmAlarmVarString {
            type string;
        }
    }

    notification cmmWarningVoltageLow {

        description "Set when internal supply voltage is below low warning level.";

        leaf cmmSysPortIndex {
            type string;
        }

        leaf cmmSysPortType {
            type string;
        }

        leaf cmmSysVoltage {
            type string;
        }

        leaf cmmAlarmVarString {
            type string;
        }
    }

    notification cmmAlarmBiasHigh {

        description "Set when TX Bias current exceeds high alarm level.";

        leaf cmmSysPortIndex {
            type string;
        }

        leaf cmmSysPortType {
            type string;
        }

        leaf cmmSysLaserBiasCurrent {
            type string;
        }

        leaf cmmAlarmVarString {
            type string;
        }
    }

    notification cmmAlarmBiasLow {

        description "Set when TX Bias current is below low alarm level.";

        leaf cmmSysPortIndex {
            type string;
        }

        leaf cmmSysPortType {
            type string;
        }

        leaf cmmSysLaserBiasCurrent {
            type string;
        }

        leaf cmmAlarmVarString {
            type string;
        }
    }

    notification cmmWarningBiasHigh {

        description "Set when TX Bias current exceeds high warning level.";

        leaf cmmSysPortIndex {
            type string;
        }

        leaf cmmSysPortType {
            type string;
        }

        leaf cmmSysLaserBiasCurrent {
            type string;
        }

        leaf cmmAlarmVarString {
            type string;
        }
    }

    notification cmmWarningBiasLow {

        description "Set when TX Bias current is below low warning level.";

        leaf cmmSysPortIndex {
            type string;
        }

        leaf cmmSysPortType {
            type string;
        }

        leaf cmmSysRxInputPower {
            type string;
        }

        leaf cmmAlarmVarString {
            type string;
        }
    }

    notification cmmAlarmRxPowerHigh {

        description "Set when Received Power exceeds high alarm level.";

        leaf cmmSysPortIndex {
            type string;
        }

        leaf cmmSysPortType {
            type string;
        }

        leaf cmmSysRxInputPower {
            type string;
        }

        leaf cmmAlarmVarString {
            type string;
        }
    }

    notification cmmAlarmRxPowerLow {

        description "Set when Received Power is below low alarm level.";

        leaf cmmSysPortIndex {
            type string;
        }

        leaf cmmSysPortType {
            type string;
        }

        leaf cmmSysRxInputPower {
            type string;
        }

        leaf cmmAlarmVarString {
            type string;
        }
    }

    notification cmmWarningRxPowerHigh {

        description "Set when Received Power exceeds high warning level..";

        leaf cmmSysPortIndex {
            type string;
        }

        leaf cmmSysPortType {
            type string;
        }

        leaf cmmSysRxInputPower {
            type string;
        }

        leaf cmmAlarmVarString {
            type string;
        }
    }

    notification cmmWarningRxPowerLow {

        description "Set when Received Power is below low warning level.";

        leaf cmmSysPortIndex {
            type string;
        }

        leaf cmmSysPortType {
            type string;
        }

        leaf cmmSysRxInputPower {
            type string;
        }

        leaf cmmAlarmVarString {
            type string;
        }
    }

    notification cmmAlarmTemperatureTooHigh {

        description "Set when Temperature will be above threshold for sensor.";

        leaf cmmSysTemperatureSensorIndex {
            type string;
        }

        leaf cmmAlarmVarInteger {
            type string;
        }

        leaf cmmAlarmVarString {
            type string;
        }
    }

    notification cmmWarningPsuInserted {

        description "Set when Power supply unit is inserted.";

        leaf cmmSysPowerSupplyIndex {
            type string;
        }

        leaf cmmAlarmVarString {
            type string;
        }
    }

    notification cmmWarningPsuRemoved {

        description "Set when Power supply unit is Removed.";

        leaf cmmSysPowerSupplyIndex {
            type string;
        }

        leaf cmmAlarmVarString {
            type string;
        }
    }

    notification cmmWarningPsuFaulty {

        description "Set when Power supply unit is Faulty.";

        leaf cmmSysPowerSupplyIndex {
            type string;
        }

        leaf cmmAlarmVarString {
            type string;
        }
    }

    notification cmmWarningFanTrayInserted {

        description "Set when fan tray is inserted.";

        leaf cmmSysFanTrayNumber {
            type string;
        }

        leaf cmmSysFanRpm {
            type string;
        }

        leaf cmmAlarmVarString {
            type string;
        }
    }

    notification cmmWarningFanTrayRemoved {

        description "Set when fan tray is Removed.";

        leaf cmmSysFanTrayNumber {
            type string;
        }

        leaf cmmAlarmVarString {
            type string;
        }
    }

    notification cmmWarningFanTrayFaulty {

        description "Set when Given Fan Tray Faulty.";

        leaf cmmSysFanTrayNumber {
            type string;
        }

        leaf cmmSysFanIndex {
            type string;
        }

        leaf cmmAlarmVarString {
            type string;
        }
    }

    notification cmmWarningFanTrayRecovered {

        description "Set when Given Fan Tray is recovered.";

        leaf cmmSysFanTrayNumber {
            type string;
        }

        leaf cmmSysFanIndex {
            type string;
        }

        leaf cmmAlarmVarString {
            type string;
        }
    }

    notification cmmWarningFanTrayStall {

        description "Set when Given Fan Tray Stalled.";

        leaf cmmSysFanTrayNumber {
            type string;
        }

        leaf cmmSysFanIndex {
            type string;
        }

        leaf cmmAlarmVarString {
            type string;
        }
    }

    notification cmmWarningFanTrayStallRecovered {

        description "Set when Given Fan Tray is recovered.";

        leaf cmmSysFanTrayNumber {
            type string;
        }

        leaf cmmSysFanIndex {
            type string;
        }

        leaf cmmAlarmVarString {
            type string;
        }
    }

    notification cmmAlarmPowerExceed {

        description "Set when Power will be above threshold.";

        leaf cmmSysPowerSupplyIndex {
            type string;
        }

        leaf cmmSysPSConsumption {
            type string;
        }

        leaf cmmAlarmVarString {
            type string;
        }
    }

    notification cmmAlarmTxPowerHigh {

        description "Set when Transferred Power exceeds high alarm level.";

        leaf cmmSysPortIndex {
            type string;
        }

        leaf cmmSysPortType {
            type string;
        }

        leaf cmmSysTxOutputPower {
            type string;
        }

        leaf cmmAlarmVarString {
            type string;
        }
    }

    notification cmmAlarmTxPowerLow {

        description "Set when Transferred Power is below low alarm level..";

        leaf cmmSysPortIndex {
            type string;
        }

        leaf cmmSysPortType {
            type string;
        }

        leaf cmmSysTxOutputPower {
            type string;
        }

        leaf cmmAlarmVarString {
            type string;
        }
    }

    notification cmmWarningTxPowerHigh {

        description "Set when Transferred Power exceeds high warning level.";

        leaf cmmSysPortIndex {
            type string;
        }

        leaf cmmSysPortType {
            type string;
        }

        leaf cmmSysTxOutputPower {
            type string;
        }

        leaf cmmAlarmVarString {
            type string;
        }
    }

    notification cmmWarningTxPowerLow {

        description "Set when Transferred Power is below low warning level.";

        leaf cmmSysPortIndex {
            type string;
        }

        leaf cmmSysPortType {
            type string;
        }

        leaf cmmSysTxOutputPower {
            type string;
        }

        leaf cmmAlarmVarString {
            type string;
        }
    }

}
