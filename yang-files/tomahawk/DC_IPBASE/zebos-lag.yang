/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-lag.yang
*
*/

submodule zebos-lag {

    belongs-to  zebos { prefix zebos; }

    import cml_data_types {
        prefix cml_data_types;
    }

    import feature_list {
        prefix feature_list;
    }

    organization
        "IP Infusion Inc.";

    contact
        "Address: 3965 Freedom Circle, Suite 200, Santa Clara, CA 95054
        Phone: +1 408-400-1900
        E-mail: support@ipinfusion.com
        Web: http://www.ipinfusion.com/";

    description
        "Layer-2 lacp  configurations";


    revision "2017-03-25" {
        description "Corrected hirerachy.";
    }

    revision "2015-10-21" {
        description "Initial version of datamodel.";
    }


    grouping  lacpSystemPriority-grouping {
    container lacpSystemPriority {
        description
            "lacpSystemPriority";
        leaf systemPriority  {
            type  cml_data_types:CML_UINT32_T {
                 range "1..65535";
            }
            default "32768";
            description "";
        } // END of systemPriority definition.

    } // END of lacpSystemPriority-container definition.
    } // END of lacpSystemPriority-container definition.

    grouping  lacpInterface-grouping {
    container lacpInterface {
        description
            "LACP interface related operations";
        leaf portPriority  {
            type  cml_data_types:CML_UINT32_T {
                 range "1..65535";
            }
            default "32768";
            description "";
        } // END of portPriority definition.

        leaf timeout  {
            type  cml_data_types:CML_LACP_TIMEOUT_T;
            default "long";
            description "";
        } // END of timeout definition.

        leaf bridgeType  {
            type  cml_data_types:CML_LACP_BRIDGETYPE_T;
            default "multicast-group-address";
            description "";
        } // END of bridgeType definition.

        leaf discardConv  {
            if-feature feature_list:HAVE_LACPV2;
            type  cml_data_types:CML_LACP_DISCARD_CONV_T;
            default "disable";
            description "";
        } // END of discardConv definition.

    } // END of lacpInterface-container definition.
    } // END of lacpInterface-container definition.

    grouping  lacpdebug-grouping {
    container lacpdebug {
        description
            "lacpdebug";
        leaf debugLacp  {
            type  cml_data_types:CML_LACP_DEBUG_TYPE_T;
            description "";
        } // END of debugLacp definition.

    } // END of lacpdebug-container definition.
    } // END of lacpdebug-container definition.


}
