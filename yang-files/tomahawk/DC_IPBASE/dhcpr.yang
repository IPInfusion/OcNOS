/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : dhcpr.yang
*
*/

submodule dhcpr {

    belongs-to  ZebOS { prefix ZebOS; }

    import cml_data_types {
        prefix cml_data_types;
    }

    include interface;
    include featuredhcp;
    organization
        "IP Infusion Inc.";

    contact
        "Address: 3965 Freedom Circle, Suite 200, Santa Clara, CA 95054
        Phone: +1 408-400-1900
        E-mail: support@ipinfusion.com
        Web: http://www.ipinfusion.com/";

    description
        "dhcp_relay_configuration";


    revision "2017-05-19" {
        description "Fixed JIRA-14838.";
    }

    revision "2017-05-15" {
        description "Added autoPopulate-custom tag.";
    }

    revision "2016-12-27" {
        description "Added snmp oid.";
    }

    revision "2016-10-28" {
        description "Initial version of dhcpr datamodel.";
    }



    grouping dhcprelayinterface-grouping {
        list dhcprelayinterface {
            key "ifName";
            description
                "DHCP interface related operations";
            leaf ifName  {
                type  cml_data_types:CML_STRING_T {
                    length "0..255";
                }
            } // END of ifName definition.

            leaf-list address  {
                type  cml_data_types:CML_IPV4_ADDR_T;
                description "ip dhcp relay address";
            } // END of address definition.

        } // End of dhcprelayinterface-list
    } // END of dhcprelayinterface-grouping definition.


    grouping dhcp6nterface-grouping {
        list dhcp6nterface {
            key "ifName";
            description
                "DHCP interface related operations";
            leaf ifName  {
                type  cml_data_types:CML_STRING_T {
                    length "0..255";
                }
            } // END of ifName definition.


            list dhcprelayaddress6 {
                key "ipv6address";
                description
                    "dhcprelayaddress6";
                leaf ipv6address  {
                    type  cml_data_types:CML_IPV6_ADDR_T;
                    description "ipv6 dhcp relay address";
                } // END of ipv6address definition.

                leaf interface  {
                    type  cml_data_types:CML_STRING_T {
                        length "0..255";
                    }
                    description "ipv6 dhcp relay address for interface";
                } // END of interface definition.

            } // End of dhcprelayaddress6-list
        } // End of dhcp6nterface-list
    } // END of dhcp6nterface-grouping definition.

    grouping  dhcprelay-grouping {
    container dhcprelay {
        description
            "dhcprelay";
        leaf relay  {
            type  cml_data_types:CML_BOOL_T;
            description "ip dhcp relay";
        } // END of relay definition.

        leaf option  {
            type  cml_data_types:CML_BOOL_T;
            description "ip dhcp relay information option";
        } // END of option definition.

    } // END of dhcprelay-container definition.
    } // END of dhcprelay-container definition.

    grouping  dhcprelay6-grouping {
    container dhcprelay6 {
        description
            "DHCP";
        leaf relay6  {
            type  cml_data_types:CML_BOOL_T;
            description "ipv6 dhcp relay";
        } // END of relay6 definition.

    } // END of dhcprelay6-container definition.
    } // END of dhcprelay6-container definition.


}
