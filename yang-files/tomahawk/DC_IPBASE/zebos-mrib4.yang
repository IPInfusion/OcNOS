/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-mrib4.yang
*
*/

submodule zebos-mrib4 {

    belongs-to  zebos { prefix zebos; }

    import cml_data_types {
        prefix cml_data_types;
    }

    import feature_list {
        prefix feature_list;
    }

    include zebos-vrf;
    organization
        "IP Infusion Inc.";

    contact
        "Address: 3965 Freedom Circle, Suite 200, Santa Clara, CA 95054
        Phone: +1 408-400-1900
        E-mail: support@ipinfusion.com
        Web: http://www.ipinfusion.com/";

    description
        "";


    revision "2018-06-21" {
        description " Initial Version.";
        reference "";
    }



    grouping mrib4Vrf-grouping {
    description
        "mrib4Vrf";
        list mrib4Vrf {
            key "vrfName";
            description
                "mrib4Vrf";
            leaf vrfName  {
                type  cml_data_types:CML_STRING_T {
                    length "0..255";
                }
                description "";
            } // END of vrfName definition.

            leaf setMulticastFlag  {
                type  cml_data_types:CML_BOOL_T;
                default false;
                description "";
            } // END of setMulticastFlag definition.

            leaf configs_flag  {
                type  cml_data_types:CML_UINT32_T;
                config false;
                description "";
            } // END of configs_flag definition.

            leaf rtLimit  {
                type  cml_data_types:CML_UINT32_T {
                     range "1..2147483647";
                }
                description "";
            } // END of rtLimit definition.

            leaf rtThresh  {
                type  cml_data_types:CML_UINT32_T {
                     range "1..2147483647";
                }
                description "";
            } // END of rtThresh definition.

            leaf debugFlag  {
                type  cml_data_types:CML_MRIB4_DEBUG_T;
                description "";
            } // END of debugFlag definition.

            leaf termdebugFlag  {
                type  cml_data_types:CML_MRIB4_DEBUG_T;
                description "";
            } // END of termdebugFlag definition.

            leaf interface_storage_type  {
                type  cml_data_types:CML_UINT32_T;
                config false;
                description "";
            } // END of interface_storage_type definition.

            leaf mrt_entry_count  {
                type  cml_data_types:CML_UINT32_T;
                config false;
                description "";
            } // END of mrt_entry_count definition.

            leaf mrt_entry_sm_count  {
                type  cml_data_types:CML_UINT32_T;
                config false;
                description "";
            } // END of mrt_entry_sm_count definition.

            leaf mrt_entry_dm_count  {
                type  cml_data_types:CML_UINT32_T;
                config false;
                description "";
            } // END of mrt_entry_dm_count definition.

            leaf stat_poll_exptime  {
                type  cml_data_types:CML_STRING_T {
                    length "0..255";
                }
                config false;
                description "";
            } // END of stat_poll_exptime definition.

            leaf num_nocache_recv  {
                type  cml_data_types:CML_UINT32_T;
                config false;
                description "";
            } // END of num_nocache_recv definition.

            leaf num_nocache_sent  {
                type  cml_data_types:CML_UINT32_T;
                config false;
                description "";
            } // END of num_nocache_sent definition.

            leaf num_wrongvif_recv  {
                type  cml_data_types:CML_UINT32_T;
                config false;
                description "";
            } // END of num_wrongvif_recv definition.

            leaf num_wrongvif_sent  {
                type  cml_data_types:CML_UINT32_T;
                config false;
                description "";
            } // END of num_wrongvif_sent definition.

            leaf num_wholepkt_recv  {
                type  cml_data_types:CML_UINT32_T;
                config false;
                description "";
            } // END of num_wholepkt_recv definition.

            leaf num_wholepkt_sent  {
                type  cml_data_types:CML_UINT32_T;
                config false;
                description "";
            } // END of num_wholepkt_sent definition.

            leaf num_imm_stat_sent  {
                type  cml_data_types:CML_UINT32_T;
                config false;
                description "";
            } // END of num_imm_stat_sent definition.

            leaf num_timed_stat_sent  {
                type  cml_data_types:CML_UINT32_T;
                config false;
                description "";
            } // END of num_timed_stat_sent definition.

            leaf num_reg_pkt_sent  {
                type  cml_data_types:CML_UINT32_T;
                config false;
                description "";
            } // END of num_reg_pkt_sent definition.

            leaf reg_ack_recv  {
                type  cml_data_types:CML_UINT32_T;
                config false;
                description "";
            } // END of reg_ack_recv definition.

            leaf reg_nack_recv  {
                type  cml_data_types:CML_UINT32_T;
                config false;
                description "";
            } // END of reg_nack_recv definition.

            leaf rate_nocache_recv  {
                type  cml_data_types:CML_STRING_T {
                    length "0..255";
                }
                config false;
                description "";
            } // END of rate_nocache_recv definition.

            leaf rate_reg_pkt_sent  {
                type  cml_data_types:CML_STRING_T {
                    length "0..255";
                }
                config false;
                description "";
            } // END of rate_reg_pkt_sent definition.


            list mrib_mrt {
                key "mrib_any_src_group";
                config false;
                description
                    "mribCMLSEPmrt";
                leaf mrib_any_src_group  {
                    type  cml_data_types:CML_STRING_T {
                        length "0..255";
                    }
                    description "";
                } // END of mrib_any_src_group definition.

                leaf iif_index  {
                    type  cml_data_types:CML_UINT16_T;
                    description "";
                } // END of iif_index definition.

                leaf rpf_addr  {
                    type  cml_data_types:CML_STRING_T {
                        length "0..255";
                    }
                    description "";
                } // END of rpf_addr definition.

                leaf safi  {
                    type  cml_data_types:CML_STRING_T {
                        length "0..255";
                    }
                    description "";
                } // END of safi definition.

                leaf route_type  {
                    type  cml_data_types:CML_UINT8_T;
                    description "";
                } // END of route_type definition.

                leaf stats_exptime  {
                    type  cml_data_types:CML_STRING_T {
                        length "0..255";
                    }
                    description "";
                } // END of stats_exptime definition.

                leaf pkts_fwd  {
                    type  cml_data_types:CML_UINT32_T;
                    description "";
                } // END of pkts_fwd definition.

                leaf bytes_fwd  {
                    type  cml_data_types:CML_UINT32_T;
                    description "";
                } // END of bytes_fwd definition.

                leaf wrong_if  {
                    type  cml_data_types:CML_UINT32_T;
                    description "";
                } // END of wrong_if definition.


                list olist_vifs {
                    key "if_name";
                    config false;
                    description
                        "olistCMLSEPvifs";
                    leaf if_name  {
                        type  cml_data_types:CML_STRING_T {
                            length "0..255";
                        }
                        description "";
                    } // END of if_name definition.

                    leaf ttl  {
                        type  cml_data_types:CML_UINT8_T;
                        description "";
                    } // END of ttl definition.

                } // End of olist_vifs-list
            } // End of mrib_mrt-list
        } // End of mrib4Vrf-list
    } // END of mrib4Vrf-grouping definition.

    grouping  mrib4Interface-grouping {
    description
        "Mrib4 Interface configs";
    container mrib4Interface {
        description
            "Mrib4 Interface configs";
        leaf ttlThresh  {
            type  cml_data_types:CML_UINT8_T {
                 range "1..255";
            }
            description "";
        } // END of ttlThresh definition.

        leaf LocalAddress  {
            type  cml_data_types:CML_STRING_T {
                length "0..255";
            }
            config false;
            description "";
        } // END of LocalAddress definition.

        leaf RemoteAddress  {
            type  cml_data_types:CML_STRING_T {
                length "0..255";
            }
            config false;
            description "";
        } // END of RemoteAddress definition.

        leaf uptime  {
            type  cml_data_types:CML_STRING_T {
                length "0..255";
            }
            config false;
            description "";
        } // END of uptime definition.

    } // END of mrib4Interface-container definition.
    } // END of mrib4Interface-container definition.


}
