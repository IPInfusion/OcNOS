/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : vrf.yang
*
*/

submodule vrf {

    belongs-to  ZebOS { prefix ZebOS; }

    import cml_data_types {
        prefix cml_data_types;
    }

    import feature_list {
        prefix feature_list;
    }

    organization
        "IP Infusion Inc.";

    contact
        "Address: 3965 Freedom Circle, Suite 200, Santa Clara, CA 95054
        Phone: +1 408-400-1900
        E-mail: support@ipinfusion.com
        Web: http://www.ipinfusion.com/";

    description
        "VPN Routing/Forwarding";


    revision "2016-12-30" {
        description "Changes ported from XP-master.";
    }

    revision "2016-12-28" {
        description "Added support for MAC VRF.";
    }

    revision "2015-10-22" {
        description "Initial draft version.";
    }



    grouping vrf-grouping {
        list vrf {
            key "vrfName";
            description
                "vrf";
            leaf vrfName  {
                type  cml_data_types:CML_STRING_T {
                    length "0..255";
                }
            } // END of vrfName definition.

            leaf macVrf  {
                if-feature feature_list:HAVE_BGP_EVPN;
                type  cml_data_types:CML_BOOL_T;
            } // END of macVrf definition.

            leaf vrfId  {
                type  cml_data_types:CML_UINT32_T;
                config false;
            } // END of vrfId definition.

            leaf fibId  {
                type  cml_data_types:CML_UINT8_T;
                config false;
            } // END of fibId definition.

            leaf description  {
                type  cml_data_types:CML_LINE_T;
            } // END of description definition.

            leaf routerId  {
                type  cml_data_types:CML_STRING_T {
                    length "0..255";
                }
            } // END of routerId definition.

        } // End of vrf-list
    } // END of vrf-grouping definition.


}
