/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : mstp.yang
*
*/

submodule mstp {

    belongs-to  ZebOS { prefix ZebOS; }

    import cml_data_types {
        prefix cml_data_types;
    }

    import feature_list {
        prefix feature_list;
    }

    include interface;
    include vlan;
    organization
        "IP Infusion Inc.";

    contact
        "Address: 3965 Freedom Circle, Suite 200, Santa Clara, CA 95054
        Phone: +1 408-400-1900
        E-mail: support@ipinfusion.com
        Web: http://www.ipinfusion.com/";

    description
        "Layer-2 bridge configurations";


    revision "2017-03-05" {
        description "change to delete mstp vlan instance.";
    }

    revision "2017-02-27" {
        description "added dependentObject for brigdePort.";
    }

    revision "2017-02-21" {
        description "added bridgeId in bridgePort table.";
    }

    revision "2017-02-14" {
        description "adding missing flag for cli generation.";
    }

    revision "2017-02-07" {
        description "mapped mstp datamodel strcuture with mstpd structure.";
    }

    revision "2017-01-28" {
        description "adding flag for default bridge objectlist.";
    }

    revision "2017-01-25" {
        description "fix for installation of spanning-tree commands.";
    }

    revision "2017-01-10" {
        description "changeing parent hierarchy for mstp objectlist.";
    }

    revision "2016-10-29" {
        description "Splited bridge and default-bridge related CLI's as separate objectlist.";
    }



    grouping mstp-grouping {
        list mstp {
            key "instanceId";
            description
                "mstp";
            leaf instanceId  {
                type  cml_data_types:CML_INT32_T {
                     range "1..63";
                }
                description "bridge instance ";
            } // END of instanceId definition.

            leaf lowPort  {
                type  cml_data_types:CML_UINT32_T;
                config false;
            } // END of lowPort definition.

            leaf master  {
                type  cml_data_types:CML_UINT8_T;
                config false;
            } // END of master definition.

            leaf learningEnabled  {
                type  cml_data_types:CML_UINT8_T;
                config false;
            } // END of learningEnabled definition.

            leaf mstiMastered  {
                type  cml_data_types:CML_UINT8_T;
                config false;
            } // END of mstiMastered definition.

            leaf reselect  {
                type  cml_data_types:CML_UINT8_T;
                config false;
            } // END of reselect definition.

            leaf mstpEnabled  {
                type  cml_data_types:CML_UINT8_T;
                config false;
            } // END of mstpEnabled definition.

            leaf mstiBridgeId  {
                type  cml_data_types:CML_STRING_T {
                    length "0..255";
                }
                config false;
            } // END of mstiBridgeId definition.

            leaf recentRoot  {
                type  cml_data_types:CML_UINT32_T;
                config false;
            } // END of recentRoot definition.

            leaf brInstAllRrTimerCntt  {
                type  cml_data_types:CML_UINT32_T;
                config false;
            } // END of brInstAllRrTimerCntt definition.

            leaf mstidesignatedRoot  {
                type  cml_data_types:CML_STRING_T {
                    length "0..255";
                }
                config false;
            } // END of mstidesignatedRoot definition.

            leaf mstiDesignatedBridge  {
                type  cml_data_types:CML_STRING_T {
                    length "0..255";
                }
                config false;
            } // END of mstiDesignatedBridge definition.

            leaf internalRootPathCost  {
                type  cml_data_types:CML_UINT32_T;
                config false;
            } // END of internalRootPathCost definition.

            leaf mstiRootportId  {
                type  cml_data_types:CML_UINT32_T;
                config false;
            } // END of mstiRootportId definition.

            leaf mstiRootPortIfindex  {
                type  cml_data_types:CML_INT32_T;
                config false;
            } // END of mstiRootPortIfindex definition.

            leaf portIndex  {
                type  cml_data_types:CML_INT32_T;
                config false;
            } // END of portIndex definition.

            leaf hopCount  {
                type  cml_data_types:CML_INT32_T;
                config false;
            } // END of hopCount definition.

            leaf tcFlag  {
                type  cml_data_types:CML_STRING_T {
                    length "0..255";
                }
                config false;
            } // END of tcFlag definition.

            leaf insttopologychangedetected  {
                type  cml_data_types:CML_STRING_T {
                    length "0..255";
                }
                config false;
            } // END of insttopologychangedetected definition.

            leaf timeLastTopoChange  {
                type  cml_data_types:CML_STRING_T {
                    length "0..255";
                }
                config false;
            } // END of timeLastTopoChange definition.

            leaf numTopoChanges  {
                type  cml_data_types:CML_INT32_T;
                config false;
            } // END of numTopoChanges definition.

            leaf totalNumTopoChanges  {
                type  cml_data_types:CML_INT32_T;
                config false;
            } // END of totalNumTopoChanges definition.

            leaf tcInitiator  {
                type  cml_data_types:CML_INT32_T;
                config false;
            } // END of tcInitiator definition.

            leaf insttcLastRcvdFrom  {
                type  cml_data_types:CML_STRING_T {
                    length "0..255";
                }
                config false;
            } // END of insttcLastRcvdFrom definition.

            leaf messageAge  {
                if-feature feature_list:HAVE_RPVST_PLUS;
                type  cml_data_types:CML_STRING_T {
                    length "0..255";
                }
                config false;
            } // END of messageAge definition.

            leaf instanceMaxage  {
                if-feature feature_list:HAVE_RPVST_PLUS;
                type  cml_data_types:CML_UINT32_T;
                config false;
            } // END of instanceMaxage definition.

            leaf fwdDelay  {
                if-feature feature_list:HAVE_RPVST_PLUS;
                type  cml_data_types:CML_UINT32_T;
                config false;
            } // END of fwdDelay definition.

            leaf helloTimeInstance  {
                if-feature feature_list:HAVE_RPVST_PLUS;
                type  cml_data_types:CML_UINT32_T;
                config false;
            } // END of helloTimeInstance definition.

            leaf designatedPortid  {
                type  cml_data_types:CML_UINT16_T;
                config false;
            } // END of designatedPortid definition.

            leaf mstipathCost  {
                type  cml_data_types:CML_UINT32_T;
                config false;
            } // END of mstipathCost definition.

            leaf forwarddelayTimer  {
                type  cml_data_types:CML_INT32_T;
                config false;
            } // END of forwarddelayTimer definition.

            leaf messageageTimer  {
                type  cml_data_types:CML_INT32_T;
                config false;
            } // END of messageageTimer definition.

            leaf instcistmessageAge  {
                type  cml_data_types:CML_INT32_T;
                config false;
            } // END of instcistmessageAge definition.

            leaf instanceporttopologyChangetime  {
                type  cml_data_types:CML_INT32_T;
                config false;
            } // END of instanceporttopologyChangetime definition.

            leaf bridgemacAddress  {
                type  cml_data_types:CML_STRING_T {
                    length "0..255";
                }
                config false;
            } // END of bridgemacAddress definition.

            leaf stpmulticastAddress  {
                type  cml_data_types:CML_STRING_T {
                    length "0..255";
                }
                config false;
            } // END of stpmulticastAddress definition.

            leaf instlastTopologychangerecievedfrom  {
                type  cml_data_types:CML_STRING_T {
                    length "0..255";
                }
                config false;
            } // END of instlastTopologychangerecievedfrom definition.

            leaf instancetopologyChange  {
                type  cml_data_types:CML_STRING_T {
                    length "0..255";
                }
                config false;
            } // END of instancetopologyChange definition.

            leaf lasttopologychangeRecievedfrom  {
                type  cml_data_types:CML_STRING_T {
                    length "0..255";
                }
                config false;
            } // END of lasttopologychangeRecievedfrom definition.

            leaf configFormat  {
                type  cml_data_types:CML_INT32_T;
                config false;
            } // END of configFormat definition.

            leaf configName  {
                type  cml_data_types:CML_STRING_T {
                    length "0..255";
                }
                config false;
            } // END of configName definition.

            leaf configRevision  {
                type  cml_data_types:CML_INT32_T;
                config false;
            } // END of configRevision definition.

            leaf configDigest  {
                type  cml_data_types:CML_INT32_T;
                config false;
            } // END of configDigest definition.


            list mstp_interface {
                key "ifName";
                description
                    "Group of mstp attribute having interface property";
                leaf ifName  {
                    type  cml_data_types:CML_STRING_T {
                        length "0..255";
                    }
                    description "bridge-group instance";
                } // END of ifName definition.

                leaf refCount  {
                    type  cml_data_types:CML_STRING_T {
                        length "0..255";
                    }
                    config false;
                } // END of refCount definition.

                leaf typeintf  {
                    type  cml_data_types:CML_UINT8_T;
                    config false;
                } // END of typeintf definition.

                leaf instifIndex  {
                    type  cml_data_types:CML_UINT8_T;
                    config false;
                } // END of instifIndex definition.

                leaf mstiPriority  {
                    type  cml_data_types:CML_INT16_T {
                         range "0..240";
                    }
                    default "128";
                    description "bridge-group instance priority";
                } // END of mstiPriority definition.

                leaf mstiPortId  {
                    type  cml_data_types:CML_UINT8_T;
                    config false;
                } // END of mstiPortId definition.

                leaf mstppathCost  {
                    type  cml_data_types:CML_UINT32_T {
                         range "1..200000000";
                    }
                    default "20000000";
                    description "bridge-group instance path-cost";
                } // END of mstppathCost definition.

                leaf internalRootpathCostintf  {
                    type  cml_data_types:CML_UINT32_T;
                    config false;
                } // END of internalRootpathCostintf definition.

                leaf designatedInternalrootPathcost  {
                    type  cml_data_types:CML_UINT32_T;
                    config false;
                } // END of designatedInternalrootPathcost definition.

                leaf mstiRoot  {
                    type  cml_data_types:CML_STRING_T {
                        length "0..255";
                    }
                    config false;
                } // END of mstiRoot definition.

                leaf designatedBridgePort  {
                    type  cml_data_types:CML_STRING_T {
                        length "0..255";
                    }
                    config false;
                } // END of designatedBridgePort definition.

                leaf designatedInsPortid  {
                    type  cml_data_types:CML_UINT16_T;
                    config false;
                } // END of designatedInsPortid definition.

                leaf messageAgeintf  {
                    type  cml_data_types:CML_UINT32_T;
                    config false;
                } // END of messageAgeintf definition.

                leaf maxAgeintf  {
                    type  cml_data_types:CML_UINT32_T;
                    config false;
                } // END of maxAgeintf definition.

                leaf fwdDelayintf  {
                    type  cml_data_types:CML_UINT32_T;
                    config false;
                } // END of fwdDelayintf definition.

                leaf helloTimeintf  {
                    type  cml_data_types:CML_UINT32_T;
                    config false;
                } // END of helloTimeintf definition.

                leaf hopCountintf  {
                    type  cml_data_types:CML_UINT32_T;
                    config false;
                } // END of hopCountintf definition.

                leaf instrestrictedTCN  {
                    type  cml_data_types:CML_BOOL_T;
                    default false;
                    description "spanning-tree instance restricted-tcn";
                } // END of instrestrictedTCN definition.

                leaf instrestrictedRole  {
                    type  cml_data_types:CML_BOOL_T;
                    default false;
                    description "spanning-tree instance restricted-role";
                } // END of instrestrictedRole definition.

                leaf portstate  {
                    type  cml_data_types:CML_UINT8_T;
                    config false;
                } // END of portstate definition.

                leaf portNextState  {
                    type  cml_data_types:CML_UINT8_T;
                    config false;
                } // END of portNextState definition.

                leaf portInfoType  {
                    type  cml_data_types:CML_UINT8_T;
                    config false;
                } // END of portInfoType definition.

                leaf portRole  {
                    type  cml_data_types:CML_UINT8_T;
                    config false;
                } // END of portRole definition.

                leaf portSelectedRole  {
                    type  cml_data_types:CML_UINT8_T;
                    config false;
                } // END of portSelectedRole definition.

                leaf portTopologyChange  {
                    type  cml_data_types:CML_UINT8_T;
                    config false;
                } // END of portTopologyChange definition.

                leaf portSendProposal  {
                    type  cml_data_types:CML_UINT8_T;
                    config false;
                } // END of portSendProposal definition.

                leaf portreselect  {
                    type  cml_data_types:CML_UINT8_T;
                    config false;
                } // END of portreselect definition.

                leaf portUpdtInfo  {
                    type  cml_data_types:CML_UINT8_T;
                    config false;
                } // END of portUpdtInfo definition.

                leaf portPathcostConfigured  {
                    type  cml_data_types:CML_UINT8_T;
                    config false;
                } // END of portPathcostConfigured definition.

                leaf tcAck  {
                    if-feature feature_list:HAVE_RPVST_PLUS;
                    type  cml_data_types:CML_INT8_T;
                    config false;
                } // END of tcAck definition.

                leaf portNewInfoSstp  {
                    if-feature feature_list:HAVE_RPVST_PLUS;
                    type  cml_data_types:CML_INT8_T;
                    config false;
                } // END of portNewInfoSstp definition.

                leaf portAnyMstiRootport  {
                    if-feature feature_list:HAVE_RPVST_PLUS;
                    type  cml_data_types:CML_INT8_T;
                    config false;
                } // END of portAnyMstiRootport definition.

                leaf portAnyMstiDesigport  {
                    if-feature feature_list:HAVE_RPVST_PLUS;
                    type  cml_data_types:CML_INT8_T;
                    config false;
                } // END of portAnyMstiDesigport definition.

                leaf portConfBpduSent  {
                    type  cml_data_types:CML_INT32_T;
                    config false;
                } // END of portConfBpduSent definition.

                leaf portConfBpduRcvd  {
                    type  cml_data_types:CML_UINT32_T;
                    config false;
                } // END of portConfBpduRcvd definition.

                leaf portTcnBpduSent  {
                    type  cml_data_types:CML_UINT32_T;
                    config false;
                } // END of portTcnBpduSent definition.

                leaf portTcnBpduRcvd  {
                    type  cml_data_types:CML_UINT32_T;
                    config false;
                } // END of portTcnBpduRcvd definition.

                leaf similarbpduCount  {
                    type  cml_data_types:CML_UINT32_T;
                    config false;
                } // END of similarbpduCount definition.

                leaf cistAdminedge  {
                    type  cml_data_types:CML_STRING_T {
                        length "0..255";
                    }
                    config false;
                } // END of cistAdminedge definition.

                leaf cistOperedge  {
                    type  cml_data_types:CML_STRING_T {
                        length "0..255";
                    }
                    config false;
                } // END of cistOperedge definition.

                leaf cistPortrole  {
                    type  cml_data_types:CML_STRING_T {
                        length "0..255";
                    }
                    config false;
                } // END of cistPortrole definition.

                leaf portName  {
                    type  cml_data_types:CML_STRING_T {
                        length "0..255";
                    }
                    config false;
                } // END of portName definition.

                leaf portNumber  {
                    type  cml_data_types:CML_UINT32_T;
                    config false;
                } // END of portNumber definition.

                leaf cistpathCost  {
                    type  cml_data_types:CML_UINT32_T;
                    config false;
                } // END of cistpathCost definition.

                leaf cistPriority  {
                    type  cml_data_types:CML_INT32_T;
                    config false;
                } // END of cistPriority definition.

                leaf cisthelloTime  {
                    type  cml_data_types:CML_INT32_T;
                    config false;
                } // END of cisthelloTime definition.

                leaf cistforwardDelay  {
                    type  cml_data_types:CML_INT32_T;
                    config false;
                } // END of cistforwardDelay definition.

                leaf portspanningTree  {
                    type  cml_data_types:CML_STRING_T {
                        length "0..255";
                    }
                    config false;
                } // END of portspanningTree definition.

                leaf porttopChangeack  {
                    type  cml_data_types:CML_STRING_T {
                        length "0..255";
                    }
                    config false;
                } // END of porttopChangeack definition.

                leaf configPending  {
                    type  cml_data_types:CML_STRING_T {
                        length "0..255";
                    }
                    config false;
                } // END of configPending definition.

                leaf helloTimerstate  {
                    type  cml_data_types:CML_STRING_T {
                        length "0..255";
                    }
                    config false;
                } // END of helloTimerstate definition.

                leaf helloTimervalue  {
                    type  cml_data_types:CML_INT32_T;
                    config false;
                } // END of helloTimervalue definition.

                leaf forwardTimerstate  {
                    type  cml_data_types:CML_STRING_T {
                        length "0..255";
                    }
                    config false;
                } // END of forwardTimerstate definition.

                leaf forwardTimervalue  {
                    type  cml_data_types:CML_INT32_T;
                    config false;
                } // END of forwardTimervalue definition.

                leaf messageTimerstate  {
                    type  cml_data_types:CML_STRING_T {
                        length "0..255";
                    }
                    config false;
                } // END of messageTimerstate definition.

                leaf messageageTimervalue  {
                    type  cml_data_types:CML_INT32_T;
                    config false;
                } // END of messageageTimervalue definition.

                leaf topologychangeTimerstate  {
                    type  cml_data_types:CML_STRING_T {
                        length "0..255";
                    }
                    config false;
                } // END of topologychangeTimerstate definition.

                leaf topologychangeTimervalue  {
                    type  cml_data_types:CML_INT32_T;
                    config false;
                } // END of topologychangeTimervalue definition.

                leaf holdTimerstate  {
                    type  cml_data_types:CML_STRING_T {
                        length "0..255";
                    }
                    config false;
                } // END of holdTimerstate definition.

                leaf holdTimervalue  {
                    type  cml_data_types:CML_INT32_T;
                    config false;
                } // END of holdTimervalue definition.

                leaf portcistnextState  {
                    type  cml_data_types:CML_STRING_T {
                        length "0..255";
                    }
                    config false;
                } // END of portcistnextState definition.

                leaf porttopologyChangetime  {
                    type  cml_data_types:CML_UINT32_T;
                    config false;
                } // END of porttopologyChangetime definition.

                leaf mstiInstancedesignatedRoot  {
                    type  cml_data_types:CML_STRING_T {
                        length "0..255";
                    }
                    config false;
                } // END of mstiInstancedesignatedRoot definition.

                leaf stpMultiCastAddr  {
                    type  cml_data_types:CML_STRING_T {
                        length "0..255";
                    }
                    config false;
                } // END of stpMultiCastAddr definition.

                leaf instanceBridgeMacAddress  {
                    type  cml_data_types:CML_STRING_T {
                        length "0..255";
                    }
                    config false;
                } // END of instanceBridgeMacAddress definition.

                leaf instancetopologyChange  {
                    type  cml_data_types:CML_STRING_T {
                        length "0..255";
                    }
                    config false;
                } // END of instancetopologyChange definition.

                leaf instanceTopologychangedetected  {
                    type  cml_data_types:CML_STRING_T {
                        length "0..255";
                    }
                    config false;
                } // END of instanceTopologychangedetected definition.

                leaf instlastTopologychangerecievedfrom  {
                    type  cml_data_types:CML_STRING_T {
                        length "0..255";
                    }
                    config false;
                } // END of instlastTopologychangerecievedfrom definition.

                leaf runtimevlanId  {
                    type  cml_data_types:CML_STRING_T {
                        length "0..255";
                    }
                    config false;
                } // END of runtimevlanId definition.

                leaf instanceportconfbpduSent  {
                    type  cml_data_types:CML_UINT32_T;
                    config false;
                } // END of instanceportconfbpduSent definition.

                leaf instanceportconfbpduRecieved  {
                    type  cml_data_types:CML_UINT32_T;
                    config false;
                } // END of instanceportconfbpduRecieved definition.

                leaf instanceporttcnbpduSent  {
                    type  cml_data_types:CML_UINT32_T;
                    config false;
                } // END of instanceporttcnbpduSent definition.

                leaf instanceporttcnbpduRecieved  {
                    type  cml_data_types:CML_UINT32_T;
                    config false;
                } // END of instanceporttcnbpduRecieved definition.

                leaf instancetopologychangeInitiator  {
                    type  cml_data_types:CML_INT32_T;
                    config false;
                } // END of instancetopologychangeInitiator definition.

                leaf instancePortNextState  {
                    type  cml_data_types:CML_UINT32_T;
                    config false;
                } // END of instancePortNextState definition.

            } // End of mstp_interface-list
            uses mstpinstance;
        } // End of mstp-list
    } // END of mstp-grouping definition.


    grouping spanInstance-grouping {
        list spanInstance {
            if-feature feature_list:HAVE_DEFAULT_BRIDGE;
            key "instanceId";
            description
                "spanInstance";
            leaf vrId  {
                type  cml_data_types:CML_UINT32_T;
                default "0";
            } // END of vrId definition.

            leaf instanceId  {
                type  cml_data_types:CML_INT32_T {
                     range "1..63";
                }
                description "bridge instance ";
            } // END of instanceId definition.


            list spanningInterface {
                if-feature feature_list:HAVE_DEFAULT_BRIDGE;
                key "ifName";
                description
                    "Group of mstp attribute having interface property";
                leaf bridgeId  {
                    type  cml_data_types:CML_STRING_T {
                        length "0..255";
                    }
                } // END of bridgeId definition.

                leaf ifName  {
                    type  cml_data_types:CML_STRING_T {
                        length "0..255";
                    }
                    description "bridge-group instance";
                } // END of ifName definition.

                leaf mstiPriority  {
                    type  cml_data_types:CML_INT16_T {
                         range "0..240";
                    }
                    default "128";
                    description "bridge-group instance priority";
                } // END of mstiPriority definition.

                leaf mstppathCost  {
                    type  cml_data_types:CML_UINT32_T {
                         range "1..200000000";
                    }
                    default "20000000";
                    description "bridge-group instance path-cost";
                } // END of mstppathCost definition.

            } // End of spanningInterface-list
            uses mstpinstance;
        } // End of spanInstance-list
    } // END of spanInstance-grouping definition.


    grouping mstpSpanningTree-grouping {
        list mstpSpanningTree {
            if-feature feature_list:HAVE_DEFAULT_BRIDGE;
            key "bridgeId";
            description
                "mstpSpanningTree";
            leaf bridgeId  {
                type  cml_data_types:CML_STRING_T {
                    length "0..255";
                }
            } // END of bridgeId definition.

            leaf bridgeShutdown  {
                type  cml_data_types:CML_INT32_T;
                default "1";
            } // END of bridgeShutdown definition.

            leaf forceVersion  {
                type  cml_data_types:CML_INT32_T {
                     range "0..3";
                }
                default "0";
                description "bridge spanning-tree force-version";
            } // END of forceVersion definition.

            leaf pathCostMethod  {
                type  cml_data_types:CML_PATHCOST_METHOD_T;
            } // END of pathCostMethod definition.

            leaf errdisableTimeoutEnable  {
                type  cml_data_types:CML_BOOL_T;
                default false;
                description "bridge spanning-tree errdisable-timeout";
            } // END of errdisableTimeoutEnable definition.

            leaf errdisableTimeoutInterval  {
                type  cml_data_types:CML_INT32_T {
                     range "10..1000000";
                }
                default "300";
                description "bridge spanning-tree errdisable-timeout interval";
            } // END of errdisableTimeoutInterval definition.

            leaf bpduFilter  {
                type  cml_data_types:CML_BOOL_T;
                default false;
            } // END of bpduFilter definition.

            leaf bpduguard  {
                type  cml_data_types:CML_BOOL_T;
                default false;
                description "bridge spanning-tree portfast bpdu-guard";
            } // END of bpduguard definition.

            leaf revisionLevel  {
                type  cml_data_types:CML_UINT16_T {
                     range "0..65535";
                }
                description "bridge revision";
            } // END of revisionLevel definition.

            leaf regionName  {
                type  cml_data_types:CML_STRING_T {
                    length "0..255";
                }
                default "Default";
                description "bridge region";
            } // END of regionName definition.

            uses mstpSpanning;
        } // End of mstpSpanningTree-list
    } // END of mstpSpanningTree-grouping definition.


    grouping mstpbridge-grouping {
        list mstpbridge {
            key "bridgeId";
            description
                "mstpbridge";
            leaf bridgeId  {
                type  cml_data_types:CML_STRING_T {
                    length "0..255";
                }
            } // END of bridgeId definition.

            leaf externalrootPathcost  {
                type  cml_data_types:CML_UINT32_T;
                config false;
            } // END of externalrootPathcost definition.

            leaf cistPortRootid  {
                type  cml_data_types:CML_UINT16_T;
                config false;
            } // END of cistPortRootid definition.

            leaf cistRootPortIfindex  {
                type  cml_data_types:CML_UINT32_T;
                config false;
            } // END of cistRootPortIfindex definition.

            leaf bpduRecvPortIfindex  {
                type  cml_data_types:CML_UINT32_T;
                config false;
            } // END of bpduRecvPortIfindex definition.

            leaf cistMaxAge  {
                type  cml_data_types:CML_UINT32_T;
                config false;
            } // END of cistMaxAge definition.

            leaf brcistMessageAge  {
                type  cml_data_types:CML_UINT32_T;
                config false;
            } // END of brcistMessageAge definition.

            leaf brcistHelloTime  {
                type  cml_data_types:CML_UINT32_T;
                config false;
            } // END of brcistHelloTime definition.

            leaf brcistForwardDelay  {
                type  cml_data_types:CML_UINT32_T;
                config false;
            } // END of brcistForwardDelay definition.

            leaf hopCount  {
                type  cml_data_types:CML_UINT32_T;
                config false;
            } // END of hopCount definition.

            leaf forceVersion  {
                type  cml_data_types:CML_INT32_T {
                     range "0..4";
                }
                default "0";
                description "bridge spanning-tree force-version";
            } // END of forceVersion definition.

            leaf recentRoot  {
                type  cml_data_types:CML_UINT32_T;
                config false;
            } // END of recentRoot definition.

            leaf brAllrrTimerCnt  {
                type  cml_data_types:CML_UINT32_T;
                config false;
            } // END of brAllrrTimerCnt definition.

            leaf learningEnabled  {
                type  cml_data_types:CML_UINT8_T;
                config false;
            } // END of learningEnabled definition.

            leaf bridgeForward  {
                type  cml_data_types:CML_BRIDGE_FORWARD_T;
                description "bridge multiple-spanning-tree";
            } // END of bridgeForward definition.

            leaf topologyChange  {
                type  cml_data_types:CML_UINT8_T;
                config false;
            } // END of topologyChange definition.

            leaf topologychangeDetected  {
                type  cml_data_types:CML_UINT8_T;
                config false;
            } // END of topologychangeDetected definition.

            leaf bridgeEnabled  {
                type  cml_data_types:CML_UINT8_T;
                config false;
            } // END of bridgeEnabled definition.

            leaf isVlanAware  {
                type  cml_data_types:CML_UINT8_T;
                config false;
            } // END of isVlanAware definition.

            leaf reselect  {
                type  cml_data_types:CML_UINT8_T;
                config false;
            } // END of reselect definition.

            leaf ageingTimeIsFwdDelay  {
                type  cml_data_types:CML_UINT8_T;
                config false;
            } // END of ageingTimeIsFwdDelay definition.

            leaf ceBridge  {
                type  cml_data_types:CML_UINT8_T;
                config false;
            } // END of ceBridge definition.

            leaf cnBridge  {
                type  cml_data_types:CML_UINT8_T;
                config false;
            } // END of cnBridge definition.

            leaf isDefault  {
                type  cml_data_types:CML_UINT8_T;
                config false;
            } // END of isDefault definition.

            leaf pathCostMethod  {
                type  cml_data_types:CML_PATHCOST_METHOD_T;
            } // END of pathCostMethod definition.

            leaf portIndex  {
                type  cml_data_types:CML_UINT8_T;
                config false;
            } // END of portIndex definition.

            leaf maxInstances  {
                type  cml_data_types:CML_UINT16_T;
                config false;
            } // END of maxInstances definition.

            leaf numPorts  {
                type  cml_data_types:CML_UINT16_T;
                config false;
            } // END of numPorts definition.

            leaf lasttimeTopologychange  {
                type  cml_data_types:CML_STRING_T {
                    length "0..255";
                }
                config false;
            } // END of lasttimeTopologychange definition.

            leaf numTopoChanges  {
                type  cml_data_types:CML_UINT32_T;
                config false;
            } // END of numTopoChanges definition.

            leaf totalNumTopoChanges  {
                type  cml_data_types:CML_UINT32_T;
                config false;
            } // END of totalNumTopoChanges definition.

            leaf maxAgeCount  {
                type  cml_data_types:CML_UINT32_T;
                config false;
            } // END of maxAgeCount definition.

            leaf bpduguard  {
                type  cml_data_types:CML_BOOL_T;
                default false;
                description "bridge spanning-tree portfast bpdu-guard";
            } // END of bpduguard definition.

            leaf errdisableTimeoutInterval  {
                type  cml_data_types:CML_INT32_T {
                     range "10..1000000";
                }
                default "300";
                description "bridge spanning-tree errdisable-timeout interval";
            } // END of errdisableTimeoutInterval definition.

            leaf errdisableTimeoutEnable  {
                type  cml_data_types:CML_BOOL_T;
                default false;
                description "bridge spanning-tree errdisable-timeout";
            } // END of errdisableTimeoutEnable definition.

            leaf bpduFilter  {
                type  cml_data_types:CML_BOOL_T;
                default false;
            } // END of bpduFilter definition.

            leaf operCisco  {
                type  cml_data_types:CML_UINT8_T;
                config false;
            } // END of operCisco definition.

            leaf topologyType  {
                type  cml_data_types:CML_UINT8_T;
                config false;
            } // END of topologyType definition.

            leaf tcFlag  {
                type  cml_data_types:CML_UINT8_T;
                config false;
            } // END of tcFlag definition.

            leaf tcInitiator  {
                type  cml_data_types:CML_UINT8_T;
                config false;
            } // END of tcInitiator definition.

            leaf tclastRcvdFrom  {
                type  cml_data_types:CML_STRING_T {
                    length "0..255";
                }
                config false;
            } // END of tclastRcvdFrom definition.

            leaf vlanInstanceMap  {
                if-feature feature_list:HAVE_RPVST_PLUS;
                type  cml_data_types:CML_UINT16_T;
                config false;
            } // END of vlanInstanceMap definition.

            leaf custBpduProcess  {
                type  cml_data_types:CML_UINT8_T;
                config false;
            } // END of custBpduProcess definition.

            leaf debug  {
                type  cml_data_types:CML_UINT32_T;
            } // END of debug definition.

            leaf debugStatus  {
                type  cml_data_types:CML_INT32_T;
            } // END of debugStatus definition.

            leaf revisionLevel  {
                type  cml_data_types:CML_UINT16_T {
                     range "0..65535";
                }
                description "bridge revision";
            } // END of revisionLevel definition.

            leaf regionName  {
                type  cml_data_types:CML_STRING_T {
                    length "0..255";
                }
                default "Default";
                description "bridge region";
            } // END of regionName definition.

            leaf vId  {
                type  cml_data_types:CML_STRING_T {
                    length "0..255";
                }
                config false;
            } // END of vId definition.

            leaf bridgePort  {
                type  cml_data_types:CML_STRING_T {
                    length "0..255";
                }
                config false;
            } // END of bridgePort definition.

            leaf cistmstpBridge  {
                type  cml_data_types:CML_STRING_T {
                    length "0..255";
                }
                config false;
            } // END of cistmstpBridge definition.

            leaf cistdesignatedRoot  {
                type  cml_data_types:CML_STRING_T {
                    length "0..255";
                }
                config false;
            } // END of cistdesignatedRoot definition.

            leaf cistBridgeid  {
                type  cml_data_types:CML_STRING_T {
                    length "0..255";
                }
                config false;
            } // END of cistBridgeid definition.

            leaf cistregisteredRoot  {
                type  cml_data_types:CML_STRING_T {
                    length "0..255";
                }
                config false;
            } // END of cistregisteredRoot definition.

            leaf bridgeTopologyChange  {
                type  cml_data_types:CML_STRING_T {
                    length "0..255";
                }
                config false;
            } // END of bridgeTopologyChange definition.

            leaf topologyChangeCount  {
                type  cml_data_types:CML_INT32_T;
                config false;
            } // END of topologyChangeCount definition.

            leaf brType  {
                type  cml_data_types:CML_BRIDGE_TYPE_T;
            } // END of brType definition.

            leaf spaningEnable  {
                type  cml_data_types:CML_INT32_T;
                default "1";
                description "bridge multiple-spanning-tree";
            } // END of spaningEnable definition.

            container routeTable {
                config false;
                description
                    "VLAN tree indexed on vid";
                leaf Id  {
                    type  cml_data_types:CML_UINT32_T;
                } // END of Id definition.

            } // END of routeTable-container definition.
            container mstpConfigInfo {
                config false;
                description
                    "mstp configuration info";
                leaf cfgFormatId  {
                    type  cml_data_types:CML_UINT8_T;
                } // END of cfgFormatId definition.

                leaf cfgName  {
                    type  cml_data_types:CML_STRING_T {
                        length "0..255";
                    }
                } // END of cfgName definition.

                leaf cfgRevisionLvl  {
                    type  cml_data_types:CML_INT16_T;
                } // END of cfgRevisionLvl definition.

                leaf cfgDigest  {
                    type  cml_data_types:CML_STRING_T {
                        length "0..255";
                    }
                } // END of cfgDigest definition.

            } // END of mstpConfigInfo-container definition.
            uses mstpSpanning;
        } // End of mstpbridge-list
    } // END of mstpbridge-grouping definition.


    grouping spanningPort-grouping {
        list spanningPort {
            if-feature feature_list:HAVE_DEFAULT_BRIDGE;
            key "ifName";
            description
                "spanningPort";
            leaf ifName  {
                type  cml_data_types:CML_STRING_T {
                    length "0..255";
                }
            } // END of ifName definition.

            leaf bridgeId  {
                type  cml_data_types:CML_STRING_T {
                    length "0..255";
                }
                default "0";
            } // END of bridgeId definition.

            leaf pathCost  {
                type  cml_data_types:CML_UINT32_T {
                     range "1..200000000";
                }
            } // END of pathCost definition.

        } // End of spanningPort-list
    } // END of spanningPort-grouping definition.


    grouping bridgePort-grouping {
        list bridgePort {
            key "ifName";
            description
                "bridgePort";
            leaf vrId  {
                type  cml_data_types:CML_UINT32_T;
                default "0";
            } // END of vrId definition.

            leaf bridgeId  {
                type  cml_data_types:CML_STRING_T {
                    length "0..255";
                }
            } // END of bridgeId definition.

            leaf devAddr  {
                type  cml_data_types:CML_STRING_T {
                    length "0..255";
                }
                config false;
            } // END of devAddr definition.

            leaf Ifindex  {
                type  cml_data_types:CML_INT32_T;
                config false;
            } // END of Ifindex definition.

            leaf ifName  {
                type  cml_data_types:CML_STRING_T {
                    length "0..255";
                }
            } // END of ifName definition.

            leaf txCount  {
                type  cml_data_types:CML_INT8_T;
                config false;
            } // END of txCount definition.

            leaf totalTxCount  {
                type  cml_data_types:CML_INT32_T;
                config false;
            } // END of totalTxCount definition.

            leaf rxCount  {
                type  cml_data_types:CML_INT8_T;
                config false;
            } // END of rxCount definition.

            leaf forceVersion  {
                type  cml_data_types:CML_INT8_T;
                config false;
            } // END of forceVersion definition.

            leaf infoInternal  {
                type  cml_data_types:CML_INT8_T;
                config false;
            } // END of infoInternal definition.

            leaf rcvdInternal  {
                type  cml_data_types:CML_INT8_T;
                config false;
            } // END of rcvdInternal definition.

            leaf adminp2pMac  {
                type  cml_data_types:CML_LINK_TYPE_T;
                default "point-to-point";
                description "spanning-tree link-type";
            } // END of adminp2pMac definition.

            leaf operp2pmac  {
                type  cml_data_types:CML_INT8_T;
                config false;
            } // END of operp2pmac definition.

            leaf adminEdge  {
                type  cml_data_types:CML_INT8_T;
                config false;
            } // END of adminEdge definition.

            leaf operEdge  {
                type  cml_data_types:CML_INT8_T;
                config false;
            } // END of operEdge definition.

            leaf autoEdge  {
                type  cml_data_types:CML_BOOL_T;
                default false;
                description "spanning-tree autoedge";
            } // END of autoEdge definition.

            leaf portfastConf  {
                type  cml_data_types:CML_PORTEDGE_T;
                default "portfast";
                description "spanning-tree edgeport";
            } // END of portfastConf definition.

            leaf portEnabled  {
                type  cml_data_types:CML_INT8_T;
                config false;
            } // END of portEnabled definition.

            leaf rcvdmstp  {
                type  cml_data_types:CML_INT8_T;
                config false;
            } // END of rcvdmstp definition.

            leaf rcvdstp  {
                type  cml_data_types:CML_INT8_T;
                config false;
            } // END of rcvdstp definition.

            leaf rcvdrstp  {
                type  cml_data_types:CML_INT8_T;
                config false;
            } // END of rcvdrstp definition.

            leaf rcvdspb  {
                type  cml_data_types:CML_INT8_T;
                config false;
            } // END of rcvdspb definition.

            leaf sendmstp  {
                type  cml_data_types:CML_INT8_T;
                config false;
            } // END of sendmstp definition.

            leaf agreednum  {
                type  cml_data_types:CML_INT8_T;
                config false;
            } // END of agreednum definition.

            leaf discAgreedNum  {
                type  cml_data_types:CML_INT8_T;
                config false;
            } // END of discAgreedNum definition.

            leaf agreedMisorder  {
                type  cml_data_types:CML_INT8_T;
                config false;
            } // END of agreedMisorder definition.

            leaf agreeDigestValid  {
                type  cml_data_types:CML_INT8_T;
                config false;
            } // END of agreeDigestValid definition.

            leaf agreedDigestValid  {
                type  cml_data_types:CML_INT8_T;
                config false;
            } // END of agreedDigestValid definition.

            leaf agreeNum  {
                type  cml_data_types:CML_INT8_T;
                config false;
            } // END of agreeNum definition.

            leaf discAgreeNum  {
                type  cml_data_types:CML_INT8_T;
                config false;
            } // END of discAgreeNum definition.

            leaf agreedTopology  {
                type  cml_data_types:CML_INT8_T;
                config false;
            } // END of agreedTopology definition.

            leaf sync  {
                type  cml_data_types:CML_INT8_T;
                config false;
            } // END of sync definition.

            leaf spbAgreementDigest  {
                if-feature feature_list:HAVE_SPBD;
                type  cml_data_types:CML_INT8_T;
                config false;
            } // END of spbAgreementDigest definition.

            leaf tcAck  {
                type  cml_data_types:CML_INT8_T;
                config false;
            } // END of tcAck definition.

            leaf selected  {
                type  cml_data_types:CML_INT8_T;
                config false;
            } // END of selected definition.

            leaf sendProposal  {
                type  cml_data_types:CML_INT8_T;
                config false;
            } // END of sendProposal definition.

            leaf rcvProposal  {
                type  cml_data_types:CML_INT8_T;
                config false;
            } // END of rcvProposal definition.

            leaf reselect  {
                type  cml_data_types:CML_INT8_T;
                config false;
            } // END of reselect definition.

            leaf updtInfo  {
                type  cml_data_types:CML_INT8_T;
                config false;
            } // END of updtInfo definition.

            leaf disputed  {
                type  cml_data_types:CML_INT8_T;
                config false;
            } // END of disputed definition.

            leaf agree  {
                type  cml_data_types:CML_INT8_T;
                config false;
            } // END of agree definition.

            leaf agreed  {
                type  cml_data_types:CML_INT8_T;
                config false;
            } // END of agreed definition.

            leaf configBpduPending  {
                type  cml_data_types:CML_INT8_T;
                config false;
            } // END of configBpduPending definition.

            leaf isL2gp  {
                if-feature feature_list:HAVE_L2GP;
                type  cml_data_types:CML_INT8_T;
                config false;
            } // END of isL2gp definition.

            leaf enableBPDUrx  {
                if-feature feature_list:HAVE_L2GP;
                type  cml_data_types:CML_ENABLEBPDURX_T;
                default "enableBPDUrx";
            } // END of enableBPDUrx definition.

            leaf psuedoRootId  {
                if-feature feature_list:HAVE_L2GP;
                type  cml_data_types:CML_STRING_T {
                    length "0..255";
                }
            } // END of psuedoRootId definition.

            leaf adminBpduguard  {
                type  cml_data_types:CML_BPDU_T;
                default "default";
            } // END of adminBpduguard definition.

            leaf operBpduguard  {
                type  cml_data_types:CML_INT8_T;
                config false;
            } // END of operBpduguard definition.

            leaf adminBpdufilter  {
                type  cml_data_types:CML_BPDU_T;
                default "default";
                description "bridge spanning-tree portfast bpdu-filter";
            } // END of adminBpdufilter definition.

            leaf operBpdufilter  {
                type  cml_data_types:CML_INT8_T;
                config false;
            } // END of operBpdufilter definition.

            leaf adminRootGuard  {
                type  cml_data_types:CML_BOOL_T;
                default false;
                description "spanning-tree guard root";
            } // END of adminRootGuard definition.

            leaf operRootguard  {
                type  cml_data_types:CML_INT8_T;
                config false;
            } // END of operRootguard definition.

            leaf ciscoCfgFormatId  {
                type  cml_data_types:CML_INT8_T;
                config false;
            } // END of ciscoCfgFormatId definition.

            leaf restrictedRole  {
                type  cml_data_types:CML_BOOL_T;
                default false;
                description "spanning-tree restricted-role";
            } // END of restrictedRole definition.

            leaf restrictedDomainRole  {
                type  cml_data_types:CML_BOOL_T;
                default false;
                description "spanning-tree restricted-domain-role";
            } // END of restrictedDomainRole definition.

            leaf restrictedTCN  {
                type  cml_data_types:CML_BOOL_T;
                default false;
                description "spanning-tree restricted-tcn";
            } // END of restrictedTCN definition.

            leaf helloTime  {
                type  cml_data_types:CML_INT32_T {
                     range "1..10";
                }
                default "2";
            } // END of helloTime definition.

            leaf refCount  {
                type  cml_data_types:CML_UINT32_T;
                config false;
            } // END of refCount definition.

            leaf type  {
                type  cml_data_types:CML_UINT32_T;
                config false;
            } // END of type definition.

            leaf portType  {
                type  cml_data_types:CML_UINT32_T;
                config false;
            } // END of portType definition.

            leaf anyMstiRootport  {
                type  cml_data_types:CML_UINT32_T;
                config false;
            } // END of anyMstiRootport definition.

            leaf anyMstiDesigport  {
                type  cml_data_types:CML_UINT32_T;
                config false;
            } // END of anyMstiDesigport definition.

            leaf cistpathCost  {
                type  cml_data_types:CML_UINT32_T;
                config false;
            } // END of cistpathCost definition.

            leaf cistPortid  {
                type  cml_data_types:CML_UINT16_T;
                config false;
            } // END of cistPortid definition.

            leaf cistRoot  {
                type  cml_data_types:CML_STRING_T {
                    length "0..255";
                }
                config false;
            } // END of cistRoot definition.

            leaf cistregisteredRoot  {
                type  cml_data_types:CML_STRING_T {
                    length "0..255";
                }
                config false;
            } // END of cistregisteredRoot definition.

            leaf cistRecvRegisteredRoot  {
                type  cml_data_types:CML_STRING_T {
                    length "0..255";
                }
                config false;
            } // END of cistRecvRegisteredRoot definition.

            leaf cistDesignatedBridge  {
                type  cml_data_types:CML_STRING_T {
                    length "0..255";
                }
                config false;
            } // END of cistDesignatedBridge definition.

            leaf cistExternalRpc  {
                type  cml_data_types:CML_UINT32_T;
                config false;
            } // END of cistExternalRpc definition.

            leaf cistInternalRpc  {
                type  cml_data_types:CML_UINT32_T;
                config false;
            } // END of cistInternalRpc definition.

            leaf cistDesignatedExternalRpc  {
                type  cml_data_types:CML_UINT32_T;
                config false;
            } // END of cistDesignatedExternalRpc definition.

            leaf cistDesignatedInternalRpc  {
                type  cml_data_types:CML_UINT32_T;
                config false;
            } // END of cistDesignatedInternalRpc definition.

            leaf cistDesignatedportId  {
                type  cml_data_types:CML_UINT32_T;
                config false;
            } // END of cistDesignatedportId definition.

            leaf cistMessageAge  {
                type  cml_data_types:CML_INT32_T;
                config false;
            } // END of cistMessageAge definition.

            leaf cistforwardDelay  {
                type  cml_data_types:CML_INT32_T;
                config false;
            } // END of cistforwardDelay definition.

            leaf cisthelloTime  {
                type  cml_data_types:CML_INT32_T;
                config false;
            } // END of cisthelloTime definition.

            leaf hopCount  {
                type  cml_data_types:CML_INT32_T;
                config false;
            } // END of hopCount definition.

            leaf newInfoCist  {
                type  cml_data_types:CML_BOOL_T;
                config false;
            } // END of newInfoCist definition.

            leaf newInfoMsti  {
                type  cml_data_types:CML_BOOL_T;
                config false;
            } // END of newInfoMsti definition.

            leaf criticalBpdu  {
                type  cml_data_types:CML_BOOL_T;
                config false;
            } // END of criticalBpdu definition.

            leaf cistState  {
                type  cml_data_types:CML_STRING_T {
                    length "0..255";
                }
                config false;
            } // END of cistState definition.

            leaf cistNextState  {
                type  cml_data_types:CML_STRING_T {
                    length "0..255";
                }
                config false;
            } // END of cistNextState definition.

            leaf cistInfoType  {
                type  cml_data_types:CML_INT32_T;
                config false;
            } // END of cistInfoType definition.

            leaf cistPortrole  {
                type  cml_data_types:CML_STRING_T {
                    length "0..255";
                }
                config false;
            } // END of cistPortrole definition.

            leaf cistSelectedRole  {
                type  cml_data_types:CML_STRING_T {
                    length "0..255";
                }
                config false;
            } // END of cistSelectedRole definition.

            leaf cistTcState  {
                type  cml_data_types:CML_STRING_T {
                    length "0..255";
                }
                config false;
            } // END of cistTcState definition.

            leaf cistForwardTransition  {
                type  cml_data_types:CML_UINT32_T;
                config false;
            } // END of cistForwardTransition definition.

            leaf svid  {
                type  cml_data_types:CML_INT16_T;
                config false;
            } // END of svid definition.

            leaf spanningTreeDisable  {
                type  cml_data_types:CML_INT8_T;
                config false;
            } // END of spanningTreeDisable definition.

            leaf isid  {
                if-feature feature_list:HAVE_I_BEB;
                type  cml_data_types:CML_INT32_T;
                config false;
            } // END of isid definition.

            leaf pip_port  {
                if-feature feature_list:HAVE_I_BEB;
                type  cml_data_types:CML_INT32_T;
                config false;
            } // END of pip_port definition.

            leaf bvid  {
                if-feature feature_list:HAVE_I_BEB;
                type  cml_data_types:CML_INT32_T;
                config false;
            } // END of bvid definition.

            leaf rpvstEvent  {
                if-feature feature_list:HAVE_RPVST_PLUS;
                type  cml_data_types:CML_INT32_T;
                config false;
            } // END of rpvstEvent definition.

            leaf rpvstBpduType  {
                if-feature feature_list:HAVE_RPVST_PLUS;
                type  cml_data_types:CML_INT32_T;
                config false;
            } // END of rpvstBpduType definition.

            leaf newInfoSstp  {
                if-feature feature_list:HAVE_RPVST_PLUS;
                type  cml_data_types:CML_INT32_T;
                config false;
            } // END of newInfoSstp definition.

            leaf vidTag  {
                if-feature feature_list:HAVE_RPVST_PLUS;
                type  cml_data_types:CML_INT32_T;
                config false;
            } // END of vidTag definition.

            leaf defaultVlan  {
                if-feature feature_list:HAVE_RPVST_PLUS;
                type  cml_data_types:CML_INT32_T;
                config false;
            } // END of defaultVlan definition.

            leaf confBpduSent  {
                type  cml_data_types:CML_INT32_T;
                config false;
            } // END of confBpduSent definition.

            leaf confBpduRcvd  {
                type  cml_data_types:CML_UINT32_T;
                config false;
            } // END of confBpduRcvd definition.

            leaf tcnBpduSent  {
                type  cml_data_types:CML_UINT32_T;
                config false;
            } // END of tcnBpduSent definition.

            leaf tcnBpduRcvd  {
                type  cml_data_types:CML_UINT32_T;
                config false;
            } // END of tcnBpduRcvd definition.

            leaf sourcemacCount  {
                type  cml_data_types:CML_INT32_T;
                config false;
            } // END of sourcemacCount definition.

            leaf similarbpduCount  {
                type  cml_data_types:CML_UINT32_T;
                config false;
            } // END of similarbpduCount definition.

            leaf msgAgeTimerCnt  {
                type  cml_data_types:CML_UINT32_T;
                config false;
            } // END of msgAgeTimerCnt definition.

            leaf totalSrcMacCount  {
                type  cml_data_types:CML_INT32_T;
                config false;
            } // END of totalSrcMacCount definition.

            leaf agg  {
                type  cml_data_types:CML_BOOL_T;
                config false;
            } // END of agg definition.

            leaf portTypeP2p  {
                type  cml_data_types:CML_BOOL_T;
                config false;
            } // END of portTypeP2p definition.

            leaf topologyChange  {
                type  cml_data_types:CML_STRING_T {
                    length "0..255";
                }
                config false;
            } // END of topologyChange definition.

            leaf externalrootPathcost  {
                type  cml_data_types:CML_UINT32_T;
                config false;
            } // END of externalrootPathcost definition.

            leaf bridgeEnabled  {
                type  cml_data_types:CML_STRING_T {
                    length "0..255";
                }
                config false;
            } // END of bridgeEnabled definition.

            leaf cistmstpBridge  {
                type  cml_data_types:CML_STRING_T {
                    length "0..255";
                }
                config false;
            } // END of cistmstpBridge definition.

            leaf cistdesignatedRoot  {
                type  cml_data_types:CML_STRING_T {
                    length "0..255";
                }
                config false;
            } // END of cistdesignatedRoot definition.

            leaf cistBridgeid  {
                type  cml_data_types:CML_STRING_T {
                    length "0..255";
                }
                config false;
            } // END of cistBridgeid definition.

            leaf totalnumberTopologychange  {
                type  cml_data_types:CML_INT32_T;
                config false;
            } // END of totalnumberTopologychange definition.

            leaf maxAgeCount  {
                type  cml_data_types:CML_INT32_T;
                config false;
            } // END of maxAgeCount definition.

            leaf bridgeTopologyChange  {
                type  cml_data_types:CML_STRING_T {
                    length "0..255";
                }
                config false;
            } // END of bridgeTopologyChange definition.

            leaf topologyChangeCount  {
                type  cml_data_types:CML_INT32_T;
                config false;
            } // END of topologyChangeCount definition.

            leaf topologyChangeLastRecv  {
                type  cml_data_types:CML_STRING_T {
                    length "0..255";
                }
                config false;
            } // END of topologyChangeLastRecv definition.

            leaf portName  {
                type  cml_data_types:CML_STRING_T {
                    length "0..255";
                }
                config false;
            } // END of portName definition.

            leaf portNumber  {
                type  cml_data_types:CML_UINT32_T;
                config false;
            } // END of portNumber definition.

            leaf mstipathCost  {
                type  cml_data_types:CML_UINT32_T;
                config false;
            } // END of mstipathCost definition.

            leaf designatedPortid  {
                type  cml_data_types:CML_UINT16_T;
                config false;
            } // END of designatedPortid definition.

            leaf cistPriority  {
                type  cml_data_types:CML_UINT32_T;
                config false;
            } // END of cistPriority definition.

            leaf mstiInstanceRoot  {
                type  cml_data_types:CML_STRING_T {
                    length "0..255";
                }
                config false;
            } // END of mstiInstanceRoot definition.

            leaf maxAgePort  {
                type  cml_data_types:CML_UINT32_T;
                config false;
            } // END of maxAgePort definition.

            leaf helloTimePort  {
                type  cml_data_types:CML_INT32_T;
                config false;
            } // END of helloTimePort definition.

            leaf topologyChangeTimer  {
                type  cml_data_types:CML_INT32_T;
                config false;
            } // END of topologyChangeTimer definition.

            leaf cistPortFast  {
                type  cml_data_types:CML_STRING_T {
                    length "0..255";
                }
                config false;
            } // END of cistPortFast definition.

            leaf bpduGuardState  {
                type  cml_data_types:CML_STRING_T {
                    length "0..255";
                }
                config false;
            } // END of bpduGuardState definition.

            leaf operBpduGuardState  {
                type  cml_data_types:CML_STRING_T {
                    length "0..255";
                }
                config false;
            } // END of operBpduGuardState definition.

            leaf bpduFilterState  {
                type  cml_data_types:CML_STRING_T {
                    length "0..255";
                }
                config false;
            } // END of bpduFilterState definition.

            leaf operBpduFilterState  {
                type  cml_data_types:CML_STRING_T {
                    length "0..255";
                }
                config false;
            } // END of operBpduFilterState definition.

            leaf rootGuardConfigState  {
                type  cml_data_types:CML_STRING_T {
                    length "0..255";
                }
                config false;
            } // END of rootGuardConfigState definition.

            leaf rootGuardState  {
                type  cml_data_types:CML_STRING_T {
                    length "0..255";
                }
                config false;
            } // END of rootGuardState definition.

            leaf version  {
                type  cml_data_types:CML_STRING_T {
                    length "0..255";
                }
                config false;
            } // END of version definition.

            leaf portRecieved  {
                type  cml_data_types:CML_STRING_T {
                    length "0..255";
                }
                config false;
            } // END of portRecieved definition.

            leaf portSend  {
                type  cml_data_types:CML_STRING_T {
                    length "0..255";
                }
                config false;
            } // END of portSend definition.

            leaf portFastCfg  {
                type  cml_data_types:CML_STRING_T {
                    length "0..255";
                }
                config false;
            } // END of portFastCfg definition.

            leaf portFastState  {
                type  cml_data_types:CML_STRING_T {
                    length "0..255";
                }
                config false;
            } // END of portFastState definition.

            leaf pToPstate  {
                type  cml_data_types:CML_STRING_T {
                    length "0..255";
                }
                config false;
            } // END of pToPstate definition.

            leaf pToPCurrentstate  {
                type  cml_data_types:CML_STRING_T {
                    length "0..255";
                }
                config false;
            } // END of pToPCurrentstate definition.

            leaf autoEdgePCfg  {
                type  cml_data_types:CML_STRING_T {
                    length "0..255";
                }
                config false;
            } // END of autoEdgePCfg definition.

            leaf autoEdgetstate  {
                type  cml_data_types:CML_STRING_T {
                    length "0..255";
                }
                config false;
            } // END of autoEdgetstate definition.

            leaf bridgeDesignatedRoot  {
                type  cml_data_types:CML_STRING_T {
                    length "0..255";
                }
                config false;
            } // END of bridgeDesignatedRoot definition.

            leaf portspanningTree  {
                type  cml_data_types:CML_STRING_T {
                    length "0..255";
                }
                config false;
            } // END of portspanningTree definition.

            leaf designatedBridge  {
                type  cml_data_types:CML_STRING_T {
                    length "0..255";
                }
                config false;
            } // END of designatedBridge definition.

            leaf helloTimer  {
                type  cml_data_types:CML_INT32_T;
                config false;
            } // END of helloTimer definition.

            leaf vlanId  {
                type  cml_data_types:CML_UINT16_T {
                     range "2..4094";
                }
            } // END of vlanId definition.

            leaf vlanrestrictedRole  {
                type  cml_data_types:CML_BOOL_T;
                default false;
                description "spanning-tree restricted-role";
            } // END of vlanrestrictedRole definition.

            leaf vlanrestrictedTCN  {
                type  cml_data_types:CML_BOOL_T;
                default false;
                description "spanning-tree restricted-tcn";
            } // END of vlanrestrictedTCN definition.


            list bridgegroup {
                key "bridgeId";
                description
                    "bridgegroup";
                leaf pathCost  {
                    type  cml_data_types:CML_UINT32_T {
                         range "1..200000000";
                    }
                } // END of pathCost definition.

                leaf bridgeId  {
                    type  cml_data_types:CML_STRING_T {
                        length "0..255";
                    }
                } // END of bridgeId definition.

                leaf portPriority  {
                    type  cml_data_types:CML_INT16_T {
                         range "0..240";
                    }
                    default "128";
                    description "bridge-group priority";
                } // END of portPriority definition.

                uses vlanportgrp;
            } // End of bridgegroup-list

            list spanningGroup {
                if-feature feature_list:HAVE_DEFAULT_BRIDGE;
                key "bridgeId";
                description
                    "spanningGroup";
                leaf bridgeId  {
                    type  cml_data_types:CML_STRING_T {
                        length "0..255";
                    }
                } // END of bridgeId definition.

                uses vlanportgrp;
            } // End of spanningGroup-list
        } // End of bridgePort-list
    } // END of bridgePort-grouping definition.


    grouping mstTeBridge-grouping {
        list mstTeBridge {
            if-feature feature_list:HAVE_MSTPD;
            if-feature feature_list:HAVE_PROVIDER_BRIDGE;
            key "bridgeId";
            description
                "mstTeBridge";
            leaf bridgeId  {
                type  cml_data_types:CML_BRIDGE_BACKBONE_ID_T;
            } // END of bridgeId definition.

            leaf temsti  {
                type  cml_data_types:CML_BOOL_T;
            } // END of temsti definition.

            leaf tevlanId  {
                type  cml_data_types:CML_STRING_T {
                    length "0..255";
                }
            } // END of tevlanId definition.

        } // End of mstTeBridge-list
    } // END of mstTeBridge-grouping definition.


    grouping backboneBridge-grouping {
        list backboneBridge {
            key "bridgeId";
            description
                "backboneBridge";
            leaf bridgeId  {
                type  cml_data_types:CML_STRING_T {
                    length "0..255";
                }
            } // END of bridgeId definition.

            leaf priority  {
                type  cml_data_types:CML_UINT32_T {
                     range "0..61440";
                }
                default "32768";
                description "bridge priority";
            } // END of priority definition.

        } // End of backboneBridge-list
    } // END of backboneBridge-grouping definition.


    grouping backboneBridgePort-grouping {
        list backboneBridgePort {
            key "ifName";
            description
                "backbone bridge interface command";
            leaf ifName  {
                type  cml_data_types:CML_STRING_T {
                    length "0..255";
                }
            } // END of ifName definition.

            leaf bridgeId  {
                type  cml_data_types:CML_STRING_T {
                    length "0..255";
                }
            } // END of bridgeId definition.

            leaf portPriority  {
                type  cml_data_types:CML_INT16_T {
                     range "0..240";
                }
                default "128";
                description "bridge-group priority";
            } // END of portPriority definition.

            leaf pathCost  {
                type  cml_data_types:CML_UINT32_T {
                     range "1..200000000";
                }
            } // END of pathCost definition.

        } // End of backboneBridgePort-list
    } // END of backboneBridgePort-grouping definition.


    grouping backboneBridgeInstance-grouping {
        list backboneBridgeInstance {
            key "instanceId";
            description
                "backboneBridgeInstance";
            leaf bridgeId  {
                type  cml_data_types:CML_STRING_T {
                    length "0..255";
                }
                default "backbone";
            } // END of bridgeId definition.

            leaf instanceId  {
                type  cml_data_types:CML_INT32_T {
                     range "1..63";
                }
                description "bridge instance ";
            } // END of instanceId definition.


            list backboneInterface {
                key "ifName";
                description
                    "Group of mstp attribute having interface property";
                leaf bridgeId  {
                    type  cml_data_types:CML_STRING_T {
                        length "0..255";
                    }
                } // END of bridgeId definition.

                leaf ifName  {
                    type  cml_data_types:CML_STRING_T {
                        length "0..255";
                    }
                    description "bridge-group instance";
                } // END of ifName definition.

                leaf mstiPriority  {
                    type  cml_data_types:CML_INT16_T {
                         range "0..240";
                    }
                    default "128";
                    description "bridge-group instance priority";
                } // END of mstiPriority definition.

                leaf mstppathCost  {
                    type  cml_data_types:CML_UINT32_T {
                         range "1..200000000";
                    }
                    default "20000000";
                    description "bridge-group instance path-cost";
                } // END of mstppathCost definition.

            } // End of backboneInterface-list
            uses mstpinstance;
        } // End of backboneBridgeInstance-list
    } // END of backboneBridgeInstance-grouping definition.


    grouping customerSpanningtree-grouping {
        list customerSpanningtree {
            if-feature feature_list:HAVE_PROVIDER_BRIDGE;
            key "ifName";
            description
                "customerSpanningtree";
            leaf ifName  {
                type  cml_data_types:CML_STRING_T {
                    length "0..255";
                }
            } // END of ifName definition.

            leaf cistBridgePriority  {
                type  cml_data_types:CML_UINT32_T {
                     range "0..61440";
                }
                default "61440";
                description "bridge priority";
            } // END of cistBridgePriority definition.

            leaf bridgeMaxAge  {
                type  cml_data_types:CML_INT32_T {
                     range "6..40";
                }
                default "20";
                description "bridge max-age";
            } // END of bridgeMaxAge definition.

            leaf bridgehelloTime  {
                type  cml_data_types:CML_INT32_T {
                     range "1..10";
                }
                default "2";
                description "bridge hello-time";
            } // END of bridgehelloTime definition.

            leaf bridgeforwardDelay  {
                type  cml_data_types:CML_INT32_T {
                     range "4..30";
                }
                default "15";
                description "bridge forward-time";
            } // END of bridgeforwardDelay definition.

            leaf transmitHoldCount  {
                type  cml_data_types:CML_UINT8_T {
                     range "1..10";
                }
                default "6";
                description "bridge transmit-holdcount";
            } // END of transmitHoldCount definition.

            leaf portPriority  {
                type  cml_data_types:CML_INT16_T {
                     range "0..240";
                }
                default "128";
                description "bridge-group priority";
            } // END of portPriority definition.

            leaf providerPortPriority  {
                type  cml_data_types:CML_INT16_T {
                     range "0..240";
                }
                default "128";
                description "bridge-group priority";
            } // END of providerPortPriority definition.

            leaf mstppathCost  {
                type  cml_data_types:CML_UINT32_T {
                     range "1..200000000";
                }
                default "20000000";
                description "bridge-group instance path-cost";
            } // END of mstppathCost definition.

            leaf mstpProviderpathCost  {
                type  cml_data_types:CML_UINT32_T {
                     range "1..200000000";
                }
                default "20000000";
                description "bridge-group instance path-cost";
            } // END of mstpProviderpathCost definition.

            leaf svlanId  {
                type  cml_data_types:CML_UINT16_T {
                     range "1..4094";
                }
            } // END of svlanId definition.

        } // End of customerSpanningtree-list
    } // END of customerSpanningtree-grouping definition.
    grouping mstpinstance {
        description
            "mstpinstance";
        leaf mstiBridgePriority  {
            type  cml_data_types:CML_UINT32_T {
                 range "0..61440";
            }
            default "32768";
            description "bridge instance priority";
        } // END of mstiBridgePriority definition.

        leaf-list vlanId  {
            type  cml_data_types:CML_UINT16_T;
        } // END of vlanId definition.

    } // END of mstpinstance definition.
    grouping mstpSpanning {
        description
            "mstpSpanning";
        leaf bridgeMaxAge  {
            type  cml_data_types:CML_INT32_T {
                 range "6..40";
            }
            default "20";
            description "bridge max-age";
        } // END of bridgeMaxAge definition.

        leaf bridgehelloTime  {
            type  cml_data_types:CML_INT32_T {
                 range "1..10";
            }
            default "2";
            description "bridge hello-time";
        } // END of bridgehelloTime definition.

        leaf bridgeforwardDelay  {
            type  cml_data_types:CML_INT32_T {
                 range "4..30";
            }
            default "15";
            description "bridge forward-time";
        } // END of bridgeforwardDelay definition.

        leaf bridgemaxHops  {
            type  cml_data_types:CML_INT32_T {
                 range "1..40";
            }
            default "20";
            description "bridge max-hops";
        } // END of bridgemaxHops definition.

        leaf cistBridgePriority  {
            type  cml_data_types:CML_UINT32_T {
                 range "0..61440";
            }
            default "32768";
            description "bridge priority";
        } // END of cistBridgePriority definition.

        leaf ageingTime  {
            type  cml_data_types:CML_INT32_T {
                 range "10..1000000";
            }
            default "300";
            description "bridge ageing time";
        } // END of ageingTime definition.

        leaf rpvstFlag  {
            type  cml_data_types:CML_UINT16_T;
        } // END of rpvstFlag definition.

        leaf ageingStatus  {
            type  cml_data_types:CML_BRIDGE_AGEING_STATE;
            description "bridge ageing";
        } // END of ageingStatus definition.

        leaf transmitHoldCount  {
            type  cml_data_types:CML_UINT8_T {
                 range "1..10";
            }
            default "6";
            description "bridge transmit-holdcount";
        } // END of transmitHoldCount definition.

        leaf adminCisco  {
            type  cml_data_types:CML_ENABLE_DISABLE_T;
            default "disable";
            description "bridge cisco-interoperability";
        } // END of adminCisco definition.

        leaf vlanPriority  {
            if-feature feature_list:HAVE_RPVST_PLUS;
            type  cml_data_types:CML_UINT32_T {
                 range "0..61440";
            }
            default "32768";
            description "bridge vlan priority";
        } // END of vlanPriority definition.

        leaf vlanId  {
            type  cml_data_types:CML_UINT16_T {
                 range "2..4094";
            }
        } // END of vlanId definition.

    } // END of mstpSpanning definition.
    grouping vlanportgrp {
        description
            "vlanportgrp";

        list vlanport {
            if-feature feature_list:HAVE_RPVST_PLUS;
            key "vlanId";
            description
                "vlan port commands";
            leaf vlanId  {
                type  cml_data_types:CML_UINT16_T {
                     range "2..4094";
                }
            } // END of vlanId definition.

            leaf vlanportPriority  {
                type  cml_data_types:CML_UINT32_T {
                     range "0..240";
                }
                default "128";
                description "bridge vlan priority";
            } // END of vlanportPriority definition.

            leaf vlanpathCost  {
                type  cml_data_types:CML_UINT32_T {
                     range "1..200000000";
                }
                default "1";
                description "bridge vlan priority";
            } // END of vlanpathCost definition.

        } // End of vlanport-list
    } // END of vlanportgrp definition.


}
