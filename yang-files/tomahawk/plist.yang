/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : plist.yang
*
*/

submodule plist {

    belongs-to  ZebOS { prefix ZebOS; }

    import cml_data_types {
        prefix cml_data_types;
    }

    include vr;
    organization
        "IP Infusion Inc.";

    contact
        "Address: 3965 Freedom Circle, Suite 200, Santa Clara, CA 95054
        Phone: +1 408-400-1900
        E-mail: support@ipinfusion.com
        Web: http://www.ipinfusion.com/";


    revision "2016-12-29" {
        description "OSPF module inclusion.";
    }

    revision "2016-10-20" {
        description "Initial version of plist datamodel.";
    }



    grouping prefixMaster-grouping {
        list prefixMaster {
            key "vrId";
            description
                "Master structure";
            leaf vrId  {
                type  cml_data_types:CML_UINT32_T;
                description "Virtual Router ID";
            } // END of vrId definition.

            leaf seqnum  {
                type  cml_data_types:CML_BOOL_T;
                description "ip prefix-list sequence-number";
            } // END of seqnum definition.


            list ipPrefix {
                key "plistname";
                description
                    "List of struct prefix_list";
                leaf plistname  {
                    type  cml_data_types:CML_STRING_T {
                        length "0..255";
                    }
                    description "ip prefix-list";
                } // END of plistname definition.

                leaf description  {
                    type  cml_data_types:CML_LINE_T;
                    default "NULL";
                    description "ip prefix-list description";
                } // END of description definition.

                leaf count  {
                    type  cml_data_types:CML_INT32_T;
                    config false;
                } // END of count definition.

                leaf rangeCount  {
                    type  cml_data_types:CML_INT32_T;
                    config false;
                } // END of rangeCount definition.


                list ipPrefixEntry {
                    key "seq";
                    description
                        "Each prefix-list's entry";
                    leaf seq  {
                        type  cml_data_types:CML_UINT32_T {
                             range "1..4294967295";
                        }
                    } // END of seq definition.

                    leaf type  {
                        type  cml_data_types:CML_PREFIX_LIST_TYPE;
                        mandatory true;
                    } // END of type definition.

                    leaf network  {
                        type  cml_data_types:CML_IPV4_ADDR_PREFIX_T;
                        mandatory true;
                    } // END of network definition.

                    leaf minPrefixLength  {
                        type  cml_data_types:CML_UINT8_T {
                             range "0..32";
                        }
                        mandatory true;
                    } // END of minPrefixLength definition.

                    leaf maxPrefixLength  {
                        type  cml_data_types:CML_UINT8_T {
                             range "0..32";
                        }
                        mandatory true;
                        description "ip prefix-list network with le and ge";
                    } // END of maxPrefixLength definition.

                    leaf eqPrefixLength  {
                        type  cml_data_types:CML_UINT8_T {
                             range "0..32";
                        }
                        mandatory true;
                        description "ip prefix-list network with eq";
                    } // END of eqPrefixLength definition.

                    leaf any  {
                        type  cml_data_types:CML_BOOL_T;
                        mandatory true;
                        description "ip prefix-list any";
                    } // END of any definition.

                    leaf refCount  {
                        type  cml_data_types:CML_UINT32_T;
                        config false;
                    } // END of refCount definition.

                    leaf hitCount  {
                        type  cml_data_types:CML_UINT32_T;
                        config false;
                    } // END of hitCount definition.

                } // End of ipPrefixEntry-list
            } // End of ipPrefix-list
        } // End of prefixMaster-list
    } // END of prefixMaster-grouping definition.


    grouping prefixMaster6-grouping {
        list prefixMaster6 {
            key "vrId";
            description
                "Master structure of prefix_list";
            leaf vrId  {
                type  cml_data_types:CML_UINT32_T;
                description "Virtual Router ID";
            } // END of vrId definition.

            leaf ipv6Seqnum  {
                type  cml_data_types:CML_BOOL_T;
                description "ipv6 prefix-list sequence-number";
            } // END of ipv6Seqnum definition.


            list ipv6Prefix {
                key "plistname6";
                description
                    "List of struct prefix_list";
                leaf plistname6  {
                    type  cml_data_types:CML_STRING_T {
                        length "0..255";
                    }
                    description "ipv6 prefix-list";
                } // END of plistname6 definition.

                leaf description6  {
                    type  cml_data_types:CML_LINE_T;
                    default "NULL";
                    description "ipv6 prefix-list description";
                } // END of description6 definition.

                leaf count6  {
                    type  cml_data_types:CML_INT32_T;
                    config false;
                } // END of count6 definition.

                leaf rangeCount6  {
                    type  cml_data_types:CML_INT32_T;
                    config false;
                } // END of rangeCount6 definition.


                list ipv6PrefixEntry {
                    key "seq6";
                    description
                        "Each prefix-list's entry";
                    leaf seq6  {
                        type  cml_data_types:CML_UINT32_T {
                             range "1..4294967295";
                        }
                    } // END of seq6 definition.

                    leaf type6  {
                        type  cml_data_types:CML_PREFIX_LIST_TYPE;
                        mandatory true;
                    } // END of type6 definition.

                    leaf network6  {
                        type  cml_data_types:CML_IPV6_PREFIX_T;
                        mandatory true;
                    } // END of network6 definition.

                    leaf minPrefixLength6  {
                        type  cml_data_types:CML_UINT8_T {
                             range "0..128";
                        }
                        mandatory true;
                    } // END of minPrefixLength6 definition.

                    leaf maxPrefixLength6  {
                        type  cml_data_types:CML_UINT8_T {
                             range "0..128";
                        }
                        mandatory true;
                        description "ipv6 prefix-list network";
                    } // END of maxPrefixLength6 definition.

                    leaf any6  {
                        type  cml_data_types:CML_BOOL_T;
                        mandatory true;
                        description "ipv6 prefix-list any";
                    } // END of any6 definition.

                    leaf refCount6  {
                        type  cml_data_types:CML_UINT32_T;
                        config false;
                    } // END of refCount6 definition.

                    leaf hitCount6  {
                        type  cml_data_types:CML_UINT32_T;
                        config false;
                    } // END of hitCount6 definition.

                } // End of ipv6PrefixEntry-list
            } // End of ipv6Prefix-list
        } // End of prefixMaster6-list
    } // END of prefixMaster6-grouping definition.


}
