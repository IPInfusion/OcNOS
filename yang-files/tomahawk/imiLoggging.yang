/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : imiLoggging.yang
*
*/

submodule imiLoggging {

    belongs-to  ZebOS { prefix ZebOS; }

    import cml_data_types {
        prefix cml_data_types;
    }

    organization
        "IP Infusion Inc.";

    contact
        "Address: 3965 Freedom Circle, Suite 200, Santa Clara, CA 95054
        Phone: +1 408-400-1900
        E-mail: support@ipinfusion.com
        Web: http://www.ipinfusion.com/";

    description
        "imi global configs";


    revision "2017-07-03" {
        description "Initial version of imi logging datamodel.";
    }


    grouping  logging_cli-grouping {
    container logging_cli {
        description
            "logging cli";
        leaf logging  {
            type  cml_data_types:CML_BOOL_T;
            description "Logging control";
        } // END of logging definition.

    } // END of logging_cli-container definition.
    } // END of logging_cli-container definition.


}
