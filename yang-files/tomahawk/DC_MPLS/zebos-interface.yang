/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-interface.yang
*
*/

submodule zebos-interface {

    belongs-to  zebos { prefix zebos; }

    import cml_data_types {
        prefix cml_data_types;
    }

    import feature_list {
        prefix feature_list;
    }

    include zebos-vrf;
    include zebos-switchportinterface;
    include zebos-lacp;
    include zebos-lag;
    include zebos-ospf;
    include zebos-sflow;
    include zebos-mlag;
    include zebos-hqos;
    include zebos-aclinterface;
    include zebos-rpf;
    organization
        "IP Infusion Inc.";

    contact
        "Address: 3965 Freedom Circle, Suite 200, Santa Clara, CA 95054
        Phone: +1 408-400-1900
        E-mail: support@ipinfusion.com
        Web: http://www.ipinfusion.com/";

    description
        "Datamodel for interface object";


    revision "2017-09-27" {
        description "added flag for clear arp command.";
    }

    revision "2017-09-18" {
        description "Included feature flags DSTE and MPLS RIB.";
    }

    revision "2017-07-11" {
        description "Added FORCE_SET flag for mtu,speed,storm-control..";
    }

    revision "2017-07-10" {
        description "Added the multival support fro hardware-profile filter.";
    }

    revision "2017-05-31" {
        description "Added the support of storm-control configuration with absolute value.";
    }

    revision "2017-05-18" {
        description "Fix for JIRA-15836.";
    }

    revision "2017-04-28" {
        description "Fix for JIRA-15343. Created dependency.";
    }

    revision "2017-04-24" {
        description "Added nsm bcm cli.";
    }

    revision "2017-03-24" {
        description "Added switchport allowed ethertype support.";
    }

    revision "2017-02-23" {
        description "hal statistics attribute added in ifStat container.";
    }

    revision "2017-02-13" {
        description "Add the load balance commands.";
    }

    revision "2017-01-28" {
        description "Removed extra attributes from datamodel.";
    }

    revision "2017-01-20" {
        description "mapped attribute name with interface structure.";
    }

    revision "2017-01-12" {
        description "adding speed and description command.";
    }

    revision "2017-01-09" {
        description "adding support for auto udpdate of mtu and speed in DB.";
    }



    grouping interface-grouping {
        list interface {
            key "ifName";
            description
                "interface object";
            leaf ifName  {
                type  cml_data_types:CML_STRING_T {
                    length "1..33";
                }
                description "";
            } // END of ifName definition.

            leaf origifName  {
                if-feature feature_list:HAVE_INTERFACE_NAME_MAPPING;
                type  cml_data_types:CML_STRING_T {
                    length "1..33";
                }
                config false;
                description "";
            } // END of origifName definition.

            leaf mappedIfName  {
                type  cml_data_types:CML_STRING_T {
                    length "1..33";
                }
                config false;
                description "";
            } // END of mappedIfName definition.

            leaf ifIndex  {
                type  cml_data_types:CML_INT32_T;
                config false;
                description "";
            } // END of ifIndex definition.

            leaf switchportStatus  {
                type  cml_data_types:CML_BOOL_T;
                default false;
                description "";
            } // END of switchportStatus definition.

            leaf shutdownFlag  {
                type  cml_data_types:CML_BOOL_T;
                default false;
                description "";
            } // END of shutdownFlag definition.

            leaf multicast  {
                type  cml_data_types:CML_BOOL_T;
                default false;
                description "";
            } // END of multicast definition.

            leaf isRunning  {
                type  cml_data_types:CML_BOOL_T;
                config false;
                description "";
            } // END of isRunning definition.

            leaf proxyArp  {
                type  cml_data_types:CML_BOOL_T;
                description "";
            } // END of proxyArp definition.

            leaf portChannelLoadBal  {
                if-feature feature_list:HAVE_LACP;
                type  cml_data_types:CML_LACP_PSC_T;
                description "";
            } // END of portChannelLoadBal definition.

            leaf portChannelMinLinks  {
                if-feature feature_list:HAVE_LACP;
                type  cml_data_types:CML_UINT8_T {
                     range "2..32";
                }
                description "";
            } // END of portChannelMinLinks definition.

            leaf ifMetric  {
                type  cml_data_types:CML_INT32_T;
                config false;
                description "";
            } // END of ifMetric definition.

            leaf mtu  {
                type  cml_data_types:CML_INT32_T {
                     range "64..65536";
                }
                description "";
            } // END of mtu definition.

            leaf duplex  {
                type  cml_data_types:CML_DUPLEX_T;
                description "";
            } // END of duplex definition.

            leaf defaultDuplex  {
                type  cml_data_types:CML_UINT8_T;
                config false;
                description "";
            } // END of defaultDuplex definition.

            leaf autoNego  {
                type  cml_data_types:CML_INT64_T;
                config false;
                description "";
            } // END of autoNego definition.

            leaf defaultAutoNego  {
                type  cml_data_types:CML_UINT8_T;
                config false;
                description "";
            } // END of defaultAutoNego definition.

            leaf flowcontrolRcv  {
                type  cml_data_types:CML_FLOWCTRL_T;
                default "off";
                description "";
            } // END of flowcontrolRcv definition.

            leaf flowcontrolSend  {
                type  cml_data_types:CML_FLOWCTRL_T;
                default "off";
                description "";
            } // END of flowcontrolSend definition.

            leaf autonegBitsAdvt  {
                type  cml_data_types:CML_UINT32_T;
                config false;
                description "";
            } // END of autonegBitsAdvt definition.

            leaf autonegFaultAdvt  {
                type  cml_data_types:CML_UINT8_T;
                config false;
                description "";
            } // END of autonegFaultAdvt definition.

            leaf mdix  {
                type  cml_data_types:CML_UINT32_T;
                config false;
                description "";
            } // END of mdix definition.

            leaf arpAgeingTimeout  {
                type  cml_data_types:CML_UINT32_T {
                     range "1..3000";
                }
                default "3000";
                description "";
            } // END of arpAgeingTimeout definition.

            leaf slotId  {
                type  cml_data_types:CML_UINT32_T;
                config false;
                description "";
            } // END of slotId definition.

            leaf hwType  {
                type  cml_data_types:CML_STRING_T {
                    length "0..255";
                }
                config false;
                description "";
            } // END of hwType definition.

            leaf hwAddr  {
                type  cml_data_types:CML_STRING_T {
                    length "1..20";
                }
                description "";
            } // END of hwAddr definition.

            leaf hwAddrLen  {
                type  cml_data_types:CML_INT32_T;
                config false;
                description "";
            } // END of hwAddrLen definition.

            leaf speed  {
                type  cml_data_types:CML_STRING_T {
                    length "0..255";
                }
                description "";
            } // END of speed definition.

            leaf isAutospeed  {
                if-feature feature_list:HAVE_BROADCOM;
                type  cml_data_types:CML_BOOL_T;
                description "";
            } // END of isAutospeed definition.

            leaf defaultSpeed  {
                type  cml_data_types:CML_STRING_T {
                    length "0..255";
                }
                config false;
                description "interface default link speed, bytes/s";
            } // END of defaultSpeed definition.

            leaf maxSpeed  {
                type  cml_data_types:CML_STRING_T {
                    length "0..255";
                }
                config false;
                description "interface default max link speed, bytes/s";
            } // END of maxSpeed definition.

            leaf bandwidth  {
                if-feature feature_list:HAVE_TE;
                type  cml_data_types:CML_STRING_T {
                    length "0..255";
                }
                default "0";
                description "";
            } // END of bandwidth definition.

            leaf snmpTrapLinkStatus  {
                type  cml_data_types:CML_BOOL_T;
                default false;
                description "";
            } // END of snmpTrapLinkStatus definition.

            leaf fec  {
                type  cml_data_types:CML_INTF_FEC_T;
                default "off";
                description "";
            } // END of fec definition.

            leaf trapLinkup  {
                if-feature feature_list:HAVE_SNMP_AGENT;
                type  cml_data_types:CML_INT32_T;
                config false;
                description "";
            } // END of trapLinkup definition.

            leaf trapLinkdown  {
                if-feature feature_list:HAVE_SNMP_AGENT;
                type  cml_data_types:CML_INT32_T;
                config false;
                description "";
            } // END of trapLinkdown definition.

            leaf ifAlias  {
                if-feature feature_list:HAVE_SNMP;
                type  cml_data_types:CML_STRING_T {
                    length "1..33";
                }
                description "";
            } // END of ifAlias definition.

            leaf bandwidthConfFlags  {
                type  cml_data_types:CML_INT16_T;
                config false;
                description "Has the bandwidth been configured/read from kernel";
            } // END of bandwidthConfFlags definition.

            leaf description  {
                type  cml_data_types:CML_STRING_T {
                    length "0..255";
                }
                description "";
            } // END of description definition.

            leaf esi  {
                if-feature feature_list:HAVE_NVO;
                type  cml_data_types:CML_STRING_T {
                    length "0..255";
                }
                description "";
            } // END of esi definition.

            leaf mauDefaultType  {
                if-feature feature_list:HAVE_L2;
                type  cml_data_types:CML_MAUTYPE_T;
                description "";
            } // END of mauDefaultType definition.

            leaf ipDHCPAddr  {
                if-feature feature_list:HAVE_DHCP_CLIENT;
                type  cml_data_types:CML_STRING_T {
                    length "0..255";
                }
                default "NULL";
                config false;
                description "";
            } // END of ipDHCPAddr definition.

            leaf ipv6DHCPAddr  {
                if-feature feature_list:HAVE_DHCP_CLIENT;
                if-feature feature_list:HAVE_IPV6;
                type  cml_data_types:CML_STRING_T {
                    length "0..255";
                }
                default "NULL";
                config false;
                description "";
            } // END of ipv6DHCPAddr definition.

            leaf ipAddr  {
                type  cml_data_types:CML_STRING_T {
                    length "0..255";
                }
                default "NULL";
                description "";
            } // END of ipAddr definition.

            leaf prefixlen  {
                type  cml_data_types:CML_UINT8_T;
                description "";
            } // END of prefixlen definition.

            leaf ipLabel  {
                type  cml_data_types:CML_STRING_T {
                    length "0..255";
                }
                default "NULL";
                description "";
            } // END of ipLabel definition.

            leaf unnumberedIpv4  {
                if-feature feature_list:HAVE_NSM_IF_UNNUMBERED;
                type  cml_data_types:CML_STRING_T {
                    length "0..255";
                }
                description "";
            } // END of unnumberedIpv4 definition.

            leaf remoteAddr  {
                if-feature feature_list:HAVE_NSM_IF_UNNUMBERED;
                type  cml_data_types:CML_STRING_T {
                    length "0..255";
                }
                description "";
            } // END of remoteAddr definition.

            leaf unnumberedIpv6  {
                if-feature feature_list:HAVE_NSM_IF_UNNUMBERED;
                if-feature feature_list:HAVE_IPV6;
                type  cml_data_types:CML_STRING_T {
                    length "0..255";
                }
                description "";
            } // END of unnumberedIpv6 definition.

            leaf vrfName  {
                if-feature feature_list:HAVE_VRF;
                type  cml_data_types:CML_STRING_T {
                    length "0..255";
                }
                description "";
            } // END of vrfName definition.

            leaf vrName  {
                if-feature feature_list:HAVE_VR;
                type  cml_data_types:CML_STRING_T {
                    length "0..255";
                }
                description "";
            } // END of vrName definition.

            leaf loadInterval  {
                if-feature feature_list:HAVE_BROADCOM;
                type  cml_data_types:CML_UINT16_T {
                     range "30..300";
                }
                default "300";
                description "";
            } // END of loadInterval definition.

            leaf maxReservableBandwidth  {
                if-feature feature_list:HAVE_TE;
                type  cml_data_types:CML_STRING_T {
                    length "0..255";
                }
                default "0";
                description "";
            } // END of maxReservableBandwidth definition.

            leaf rdmBwConstraint  {
                if-feature feature_list:HAVE_TE;
                if-feature feature_list:HAVE_DSTE;
                type  cml_data_types:CML_INT64_T;
                config false;
                description "Bandwidth constraint for RDM per class types(bytes per s)";
            } // END of rdmBwConstraint definition.

            leaf teclPriorityBw  {
                if-feature feature_list:HAVE_TE;
                type  cml_data_types:CML_INT64_T;
                config false;
                description "Available bandwidth at priority p, 0 <= p < 8";
            } // END of teclPriorityBw definition.

            leaf bindInfo  {
                type  cml_data_types:CML_UINT8_T;
                config false;
                description "Bind information vrf, mpls_vc, mpls_vc_vlan, vpls, vpls_vlan, vxlan, nvgre";
            } // END of bindInfo definition.

            leaf bcMode  {
                if-feature feature_list:HAVE_DSTE;
                type  cml_data_types:CML_STRING_T {
                    length "0..255";
                }
                description "";
            } // END of bcMode definition.

            leaf vrxFlag  {
                if-feature feature_list:HAVE_VRX;
                type  cml_data_types:CML_UINT8_T;
                config false;
                description "";
            } // END of vrxFlag definition.

            leaf localSrc  {
                if-feature feature_list:HAVE_VRX;
                type  cml_data_types:CML_UINT8_T;
                config false;
                description "";
            } // END of localSrc definition.

            leaf ifLastChange  {
                type  cml_data_types:CML_STRING_T {
                    length "0..255";
                }
                config false;
                description "";
            } // END of ifLastChange definition.

            leaf ifLastFlap  {
                type  cml_data_types:CML_STRING_T {
                    length "0..255";
                }
                config false;
                description "";
            } // END of ifLastFlap definition.

            leaf ifLastCounterClear  {
                type  cml_data_types:CML_STRING_T {
                    length "0..255";
                }
                config false;
                description "";
            } // END of ifLastCounterClear definition.

            leaf interfaceType  {
                type  cml_data_types:CML_INTERFACE_TYPE_T;
                config false;
                description "Interface type L2, L3, TDM";
            } // END of interfaceType definition.

            leaf trustState  {
                if-feature feature_list:HAVE_QOS;
                type  cml_data_types:CML_INT32_T;
                config false;
                description "";
            } // END of trustState definition.

            leaf ipv6Status  {
                if-feature feature_list:HAVE_IPV6;
                type  cml_data_types:CML_BOOL_T;
                config false;
                description "IPv6 capability status";
            } // END of ipv6Status definition.

            leaf ipv6Forwarding  {
                if-feature feature_list:HAVE_IPV6;
                type  cml_data_types:CML_BOOL_T;
                config false;
                description "";
            } // END of ipv6Forwarding definition.

            leaf ipv4Status  {
                type  cml_data_types:CML_BOOL_T;
                config false;
                description "IPv4 capability status";
            } // END of ipv4Status definition.

            leaf mpgIf  {
                if-feature feature_list:HAVE_TFO;
                type  cml_data_types:CML_UINT64_T;
                config false;
                description "";
            } // END of mpgIf definition.

            leaf tfoLinkType  {
                if-feature feature_list:HAVE_TFO;
                type  cml_data_types:CML_UINT32_T;
                config false;
                description "";
            } // END of tfoLinkType definition.

            leaf udldFlushTx  {
                if-feature feature_list:HAVE_UDLD;
                type  cml_data_types:CML_UINT16_T;
                config false;
                description "";
            } // END of udldFlushTx definition.

            leaf macLearnLimit  {
                type  cml_data_types:CML_INT32_T;
                config false;
                description "";
            } // END of macLearnLimit definition.

            leaf jitterBuffer  {
                if-feature feature_list:HAVE_TDM_VC;
                type  cml_data_types:CML_UINT16_T {
                     range "1..500";
                }
                default "500";
                description "";
            } // END of jitterBuffer definition.

            leaf payLoadBytes  {
                if-feature feature_list:HAVE_TDM_VC;
                type  cml_data_types:CML_UINT32_T {
                     range "0..32768";
                }
                default "0";
                description "";
            } // END of payLoadBytes definition.

            leaf rtpHeader  {
                if-feature feature_list:HAVE_TDM_VC;
                type  cml_data_types:CML_BOOL_T;
                default false;
                description "";
            } // END of rtpHeader definition.

            leaf portBreakout  {
                if-feature feature_list:HAVE_FLEXPORT;
                type  cml_data_types:CML_NSM_BREAKOUT_TYPE_T;
                description "";
            } // END of portBreakout definition.

            leaf portBundle  {
                if-feature feature_list:HAVE_FLEXPORT;
                type  cml_data_types:CML_BOOL_T;
                default false;
                description "";
            } // END of portBundle definition.


            list secondary {
                key "secIpAddr";
                description
                    "Secondary IPv4 Address";
                leaf secIpAddr  {
                    type  cml_data_types:CML_STRING_T {
                        length "0..255";
                    }
                    description "";
                } // END of secIpAddr definition.

                leaf ipLabel  {
                    type  cml_data_types:CML_STRING_T {
                        length "0..255";
                    }
                    default "NULL";
                    description "";
                } // END of ipLabel definition.

            } // End of secondary-list

            list ipv6Addr {
                if-feature feature_list:HAVE_IPV6;
                key "ipv6Addr";
                description
                    "IPv6 Address";
                leaf ipv6Addr  {
                    type  cml_data_types:CML_STRING_T {
                        length "0..255";
                    }
                    description "";
                } // END of ipv6Addr definition.

                leaf anycast  {
                    type  cml_data_types:CML_BOOL_T;
                    default false;
                    description "";
                } // END of anycast definition.

            } // End of ipv6Addr-list

            list bandwidthConstraint {
                if-feature feature_list:HAVE_TE;
                if-feature feature_list:HAVE_DSTE;
                key "constraintName";
                description
                    "Bandwidth constraint per class types (bytes per s)";
                leaf constraintName  {
                    type  cml_data_types:CML_STRING_T {
                        length "0..255";
                    }
                    description "";
                } // END of constraintName definition.

                leaf bandwidthStr  {
                    if-feature feature_list:HAVE_TE;
                    type  cml_data_types:CML_STRING_T {
                        length "0..255";
                    }
                    mandatory true;
                    description "";
                } // END of bandwidthStr definition.

            } // End of bandwidthConstraint-list

            list errorSet {
                if-feature feature_list:HAVE_TDM_VC;
                key "errorSetType";
                description
                    "errorSet";
                leaf errorSetType  {
                    type  cml_data_types:CML_ERROR_SET_TYPE_T;
                    description "";
                } // END of errorSetType definition.

                leaf errorSetPeriod  {
                    type  cml_data_types:CML_UINT32_T {
                         range "2000..10000";
                    }
                    mandatory true;
                    description "";
                } // END of errorSetPeriod definition.

            } // End of errorSet-list

            list errorClear {
                if-feature feature_list:HAVE_TDM_VC;
                key "errorClearType";
                description
                    "errorClear";
                leaf errorClearType  {
                    type  cml_data_types:CML_ERROR_CLEAR_TYPE_T;
                    description "";
                } // END of errorClearType definition.

                leaf errorClearPeriod  {
                    type  cml_data_types:CML_UINT32_T {
                         range "2000..10000";
                    }
                    mandatory true;
                    description "";
                } // END of errorClearPeriod definition.

            } // End of errorClear-list
            container stormControlBcast {
                if-feature feature_list:HAVE_RATE_LIMIT;
                presence "yes";
                description
                    "bcast related commands";
                leaf bcastValue  {
                    type  cml_data_types:CML_RATE_LIMIT_T;
                    mandatory true;
                    description "";
                } // END of bcastValue definition.

                leaf bitsPerSecondFormat  {
                    type  cml_data_types:CML_RATE_LIMIT_TYPE;
                    description "";
                } // END of bitsPerSecondFormat definition.

            } // END of stormControlBcast-container definition.
            container stormControlMcast {
                if-feature feature_list:HAVE_RATE_LIMIT;
                presence "yes";
                description
                    "mcast related commands";
                leaf mcastValue  {
                    type  cml_data_types:CML_RATE_LIMIT_T;
                    mandatory true;
                    description "";
                } // END of mcastValue definition.

                leaf bitsPerSecondFormat  {
                    type  cml_data_types:CML_RATE_LIMIT_TYPE;
                    description "";
                } // END of bitsPerSecondFormat definition.

            } // END of stormControlMcast-container definition.
            container stormControlDlfBcast {
                if-feature feature_list:HAVE_RATE_LIMIT;
                presence "yes";
                description
                    "dlfbcast related commands";
                leaf dlfbcastValue  {
                    type  cml_data_types:CML_RATE_LIMIT_T;
                    mandatory true;
                    description "";
                } // END of dlfbcastValue definition.

                leaf bitsPerSecondFormat  {
                    type  cml_data_types:CML_RATE_LIMIT_TYPE;
                    description "";
                } // END of bitsPerSecondFormat definition.

            } // END of stormControlDlfBcast-container definition.
            container switchportAllowedEthertypes {
                if-feature feature_list:HAVE_BROADCOM;
                if-feature feature_list:HAVE_L2;
                description
                    "Switching characteristics of the Layer2 interface";
                leaf arp  {
                    type  cml_data_types:CML_BOOL_T;
                    description "";
                } // END of arp definition.

                leaf ipv4  {
                    type  cml_data_types:CML_BOOL_T;
                    description "";
                } // END of ipv4 definition.

                leaf ipv6  {
                    type  cml_data_types:CML_BOOL_T;
                    description "";
                } // END of ipv6 definition.

                leaf mpls  {
                    type  cml_data_types:CML_BOOL_T;
                    description "";
                } // END of mpls definition.

                leaf ethertypeValue  {
                    type  cml_data_types:CML_STRING_T {
                        length "0..255";
                    }
                    description "";
                } // END of ethertypeValue definition.

                leaf log  {
                    type  cml_data_types:CML_BOOL_T;
                    description "";
                } // END of log definition.

            } // END of switchportAllowedEthertypes-container definition.
            container ifStat {
                config false;
                description
                    "interface Statistics fields";
                leaf rxPackets  {
                    type  cml_data_types:CML_UINT32_T;
                    description "";
                } // END of rxPackets definition.

                leaf txPackets  {
                    type  cml_data_types:CML_UINT32_T;
                    description "";
                } // END of txPackets definition.

                leaf rxbytes  {
                    type  cml_data_types:CML_UINT64_T;
                    description "";
                } // END of rxbytes definition.

                leaf txbytes  {
                    type  cml_data_types:CML_UINT64_T;
                    description "";
                } // END of txbytes definition.

                leaf rxerrors  {
                    type  cml_data_types:CML_UINT32_T;
                    description "";
                } // END of rxerrors definition.

                leaf txerrors  {
                    type  cml_data_types:CML_UINT32_T;
                    description "";
                } // END of txerrors definition.

                leaf rxdropped  {
                    type  cml_data_types:CML_UINT32_T;
                    description "";
                } // END of rxdropped definition.

                leaf txdropped  {
                    type  cml_data_types:CML_UINT32_T;
                    description "";
                } // END of txdropped definition.

                leaf rxmulticast  {
                    type  cml_data_types:CML_UINT32_T;
                    description "";
                } // END of rxmulticast definition.

                leaf rxcompressed  {
                    type  cml_data_types:CML_UINT32_T;
                    description "";
                } // END of rxcompressed definition.

                leaf txcompressed  {
                    type  cml_data_types:CML_UINT32_T;
                    description "";
                } // END of txcompressed definition.

                leaf collisions  {
                    type  cml_data_types:CML_UINT32_T;
                    description "";
                } // END of collisions definition.

                leaf urpfDropped  {
                    type  cml_data_types:CML_UINT32_T;
                    description "";
                } // END of urpfDropped definition.

                leaf rxLengthErrors  {
                    type  cml_data_types:CML_UINT32_T;
                    description "";
                } // END of rxLengthErrors definition.

                leaf rxOverErrors  {
                    type  cml_data_types:CML_UINT32_T;
                    description "";
                } // END of rxOverErrors definition.

                leaf rxCrcErrors  {
                    type  cml_data_types:CML_UINT32_T;
                    description "";
                } // END of rxCrcErrors definition.

                leaf rxFrameErrors  {
                    type  cml_data_types:CML_UINT32_T;
                    description "";
                } // END of rxFrameErrors definition.

                leaf rxFifoErrors  {
                    type  cml_data_types:CML_UINT32_T;
                    description "";
                } // END of rxFifoErrors definition.

                leaf rxMissedErrors  {
                    type  cml_data_types:CML_UINT32_T;
                    description "";
                } // END of rxMissedErrors definition.

                leaf txAbortedErrors  {
                    type  cml_data_types:CML_UINT32_T;
                    description "";
                } // END of txAbortedErrors definition.

                leaf txCarrierErrors  {
                    type  cml_data_types:CML_UINT32_T;
                    description "";
                } // END of txCarrierErrors definition.

                leaf txFifoErrors  {
                    type  cml_data_types:CML_UINT32_T;
                    description "";
                } // END of txFifoErrors definition.

                leaf txHeartbeatErrors  {
                    type  cml_data_types:CML_UINT32_T;
                    description "";
                } // END of txHeartbeatErrors definition.

                leaf txWindowErrors  {
                    type  cml_data_types:CML_UINT32_T;
                    description "";
                } // END of txWindowErrors definition.

                leaf outErrors  {
                    if-feature feature_list:HAVE_BROADCOM;
                    if-feature feature_list:HAVE_HAL;
                    type  cml_data_types:CML_UINT64_T;
                    description "";
                } // END of outErrors definition.

                leaf outDiscards  {
                    if-feature feature_list:HAVE_BROADCOM;
                    if-feature feature_list:HAVE_HAL;
                    type  cml_data_types:CML_UINT64_T;
                    description "";
                } // END of outDiscards definition.

                leaf outMcPkts  {
                    if-feature feature_list:HAVE_BROADCOM;
                    if-feature feature_list:HAVE_HAL;
                    type  cml_data_types:CML_UINT64_T;
                    description "";
                } // END of outMcPkts definition.

                leaf outUcPkts  {
                    if-feature feature_list:HAVE_BROADCOM;
                    if-feature feature_list:HAVE_HAL;
                    type  cml_data_types:CML_UINT64_T;
                    description "";
                } // END of outUcPkts definition.

                leaf inUcPkts  {
                    if-feature feature_list:HAVE_BROADCOM;
                    if-feature feature_list:HAVE_HAL;
                    type  cml_data_types:CML_UINT64_T;
                    description "";
                } // END of inUcPkts definition.

                leaf inDiscards  {
                    if-feature feature_list:HAVE_BROADCOM;
                    if-feature feature_list:HAVE_HAL;
                    type  cml_data_types:CML_UINT64_T;
                    description "";
                } // END of inDiscards definition.

                leaf goodOctetsRcv  {
                    if-feature feature_list:HAVE_BROADCOM;
                    if-feature feature_list:HAVE_HAL;
                    type  cml_data_types:CML_UINT64_T;
                    description "";
                } // END of goodOctetsRcv definition.

                leaf badOctetsRcv  {
                    if-feature feature_list:HAVE_BROADCOM;
                    if-feature feature_list:HAVE_HAL;
                    type  cml_data_types:CML_UINT64_T;
                    description "";
                } // END of badOctetsRcv definition.

                leaf macTransmitErr  {
                    if-feature feature_list:HAVE_BROADCOM;
                    if-feature feature_list:HAVE_HAL;
                    type  cml_data_types:CML_UINT64_T;
                    description "";
                } // END of macTransmitErr definition.

                leaf goodPktsRcv  {
                    if-feature feature_list:HAVE_BROADCOM;
                    if-feature feature_list:HAVE_HAL;
                    type  cml_data_types:CML_UINT64_T;
                    description "";
                } // END of goodPktsRcv definition.

                leaf badPktsRcv  {
                    if-feature feature_list:HAVE_BROADCOM;
                    if-feature feature_list:HAVE_HAL;
                    type  cml_data_types:CML_UINT64_T;
                    description "";
                } // END of badPktsRcv definition.

                leaf pktsRcv  {
                    if-feature feature_list:HAVE_BROADCOM;
                    if-feature feature_list:HAVE_HAL;
                    type  cml_data_types:CML_UINT64_T;
                    description "";
                } // END of pktsRcv definition.

                leaf brdcPktsRcv  {
                    if-feature feature_list:HAVE_BROADCOM;
                    if-feature feature_list:HAVE_HAL;
                    type  cml_data_types:CML_UINT64_T;
                    description "";
                } // END of brdcPktsRcv definition.

                leaf mcPktsRcv  {
                    if-feature feature_list:HAVE_BROADCOM;
                    if-feature feature_list:HAVE_HAL;
                    type  cml_data_types:CML_UINT64_T;
                    description "";
                } // END of mcPktsRcv definition.

                leaf pkts64OctetsRcv  {
                    if-feature feature_list:HAVE_BROADCOM;
                    if-feature feature_list:HAVE_HAL;
                    type  cml_data_types:CML_UINT64_T;
                    description "";
                } // END of pkts64OctetsRcv definition.

                leaf pkts65127OctetsRcv  {
                    if-feature feature_list:HAVE_BROADCOM;
                    if-feature feature_list:HAVE_HAL;
                    type  cml_data_types:CML_UINT64_T;
                    description "";
                } // END of pkts65127OctetsRcv definition.

                leaf pkts128255OctetsRcv  {
                    if-feature feature_list:HAVE_BROADCOM;
                    if-feature feature_list:HAVE_HAL;
                    type  cml_data_types:CML_UINT64_T;
                    description "";
                } // END of pkts128255OctetsRcv definition.

                leaf pkts256511OctetsRcv  {
                    if-feature feature_list:HAVE_BROADCOM;
                    if-feature feature_list:HAVE_HAL;
                    type  cml_data_types:CML_UINT64_T;
                    description "";
                } // END of pkts256511OctetsRcv definition.

                leaf pkts5121023OctetsRcv  {
                    if-feature feature_list:HAVE_BROADCOM;
                    if-feature feature_list:HAVE_HAL;
                    type  cml_data_types:CML_UINT64_T;
                    description "";
                } // END of pkts5121023OctetsRcv definition.

                leaf pkts10241518OctetsRcv  {
                    if-feature feature_list:HAVE_BROADCOM;
                    if-feature feature_list:HAVE_HAL;
                    type  cml_data_types:CML_UINT64_T;
                    description "";
                } // END of pkts10241518OctetsRcv definition.

                leaf pkts15192047OctetsRcv  {
                    if-feature feature_list:HAVE_BROADCOM;
                    if-feature feature_list:HAVE_HAL;
                    type  cml_data_types:CML_UINT64_T;
                    description "";
                } // END of pkts15192047OctetsRcv definition.

                leaf pkts20484095OctetsRcv  {
                    if-feature feature_list:HAVE_BROADCOM;
                    if-feature feature_list:HAVE_HAL;
                    type  cml_data_types:CML_UINT64_T;
                    description "";
                } // END of pkts20484095OctetsRcv definition.

                leaf pkts40969216OctetsRcv  {
                    if-feature feature_list:HAVE_BROADCOM;
                    if-feature feature_list:HAVE_HAL;
                    type  cml_data_types:CML_UINT64_T;
                    description "";
                } // END of pkts40969216OctetsRcv definition.

                leaf pkts64Octets  {
                    if-feature feature_list:HAVE_BROADCOM;
                    if-feature feature_list:HAVE_HAL;
                    type  cml_data_types:CML_UINT64_T;
                    description "";
                } // END of pkts64Octets definition.

                leaf pkts65127Octets  {
                    if-feature feature_list:HAVE_BROADCOM;
                    if-feature feature_list:HAVE_HAL;
                    type  cml_data_types:CML_UINT64_T;
                    description "";
                } // END of pkts65127Octets definition.

                leaf pkts128255Octets  {
                    if-feature feature_list:HAVE_BROADCOM;
                    if-feature feature_list:HAVE_HAL;
                    type  cml_data_types:CML_UINT64_T;
                    description "";
                } // END of pkts128255Octets definition.

                leaf pkts256511Octets  {
                    if-feature feature_list:HAVE_BROADCOM;
                    if-feature feature_list:HAVE_HAL;
                    type  cml_data_types:CML_UINT64_T;
                    description "";
                } // END of pkts256511Octets definition.

                leaf pkts5121023Octets  {
                    if-feature feature_list:HAVE_BROADCOM;
                    if-feature feature_list:HAVE_HAL;
                    type  cml_data_types:CML_UINT64_T;
                    description "";
                } // END of pkts5121023Octets definition.

                leaf pkts1024maxOctets  {
                    if-feature feature_list:HAVE_BROADCOM;
                    if-feature feature_list:HAVE_HAL;
                    type  cml_data_types:CML_UINT64_T;
                    description "";
                } // END of pkts1024maxOctets definition.

                leaf pkts15192047Octets  {
                    if-feature feature_list:HAVE_BROADCOM;
                    if-feature feature_list:HAVE_HAL;
                    type  cml_data_types:CML_UINT64_T;
                    description "";
                } // END of pkts15192047Octets definition.

                leaf pkts20484095Octets  {
                    if-feature feature_list:HAVE_BROADCOM;
                    if-feature feature_list:HAVE_HAL;
                    type  cml_data_types:CML_UINT64_T;
                    description "";
                } // END of pkts20484095Octets definition.

                leaf pkts40969216Octets  {
                    if-feature feature_list:HAVE_BROADCOM;
                    if-feature feature_list:HAVE_HAL;
                    type  cml_data_types:CML_UINT64_T;
                    description "";
                } // END of pkts40969216Octets definition.

                leaf goodOctetsSent  {
                    if-feature feature_list:HAVE_BROADCOM;
                    if-feature feature_list:HAVE_HAL;
                    type  cml_data_types:CML_UINT64_T;
                    description "";
                } // END of goodOctetsSent definition.

                leaf goodPktsSent  {
                    if-feature feature_list:HAVE_BROADCOM;
                    if-feature feature_list:HAVE_HAL;
                    type  cml_data_types:CML_UINT64_T;
                    description "";
                } // END of goodPktsSent definition.

                leaf excessiveCollisions  {
                    if-feature feature_list:HAVE_BROADCOM;
                    if-feature feature_list:HAVE_HAL;
                    type  cml_data_types:CML_UINT64_T;
                    description "";
                } // END of excessiveCollisions definition.

                leaf mcPktsSent  {
                    if-feature feature_list:HAVE_BROADCOM;
                    if-feature feature_list:HAVE_HAL;
                    type  cml_data_types:CML_UINT64_T;
                    description "";
                } // END of mcPktsSent definition.

                leaf brdcPktsSent  {
                    if-feature feature_list:HAVE_BROADCOM;
                    if-feature feature_list:HAVE_HAL;
                    type  cml_data_types:CML_UINT64_T;
                    description "";
                } // END of brdcPktsSent definition.

                leaf unrecogMacCntrRcv  {
                    if-feature feature_list:HAVE_BROADCOM;
                    if-feature feature_list:HAVE_HAL;
                    type  cml_data_types:CML_UINT64_T;
                    description "";
                } // END of unrecogMacCntrRcv definition.

                leaf fcSent  {
                    if-feature feature_list:HAVE_BROADCOM;
                    if-feature feature_list:HAVE_HAL;
                    type  cml_data_types:CML_UINT64_T;
                    description "";
                } // END of fcSent definition.

                leaf goodFcRcv  {
                    if-feature feature_list:HAVE_BROADCOM;
                    if-feature feature_list:HAVE_HAL;
                    type  cml_data_types:CML_UINT64_T;
                    description "";
                } // END of goodFcRcv definition.

                leaf dropEvents  {
                    if-feature feature_list:HAVE_BROADCOM;
                    if-feature feature_list:HAVE_HAL;
                    type  cml_data_types:CML_UINT64_T;
                    description "";
                } // END of dropEvents definition.

                leaf undersizePkts  {
                    if-feature feature_list:HAVE_BROADCOM;
                    if-feature feature_list:HAVE_HAL;
                    type  cml_data_types:CML_UINT64_T;
                    description "";
                } // END of undersizePkts definition.

                leaf fragmentsPkts  {
                    if-feature feature_list:HAVE_BROADCOM;
                    if-feature feature_list:HAVE_HAL;
                    type  cml_data_types:CML_UINT64_T;
                    description "";
                } // END of fragmentsPkts definition.

                leaf oversizePkts  {
                    if-feature feature_list:HAVE_BROADCOM;
                    if-feature feature_list:HAVE_HAL;
                    type  cml_data_types:CML_UINT64_T;
                    description "";
                } // END of oversizePkts definition.

                leaf jabberPkts  {
                    if-feature feature_list:HAVE_BROADCOM;
                    if-feature feature_list:HAVE_HAL;
                    type  cml_data_types:CML_UINT64_T;
                    description "";
                } // END of jabberPkts definition.

                leaf macRcvError  {
                    if-feature feature_list:HAVE_BROADCOM;
                    if-feature feature_list:HAVE_HAL;
                    type  cml_data_types:CML_UINT64_T;
                    description "";
                } // END of macRcvError definition.

                leaf badCrc  {
                    if-feature feature_list:HAVE_BROADCOM;
                    if-feature feature_list:HAVE_HAL;
                    type  cml_data_types:CML_UINT64_T;
                    description "";
                } // END of badCrc definition.

                leaf dribble  {
                    if-feature feature_list:HAVE_BROADCOM;
                    if-feature feature_list:HAVE_HAL;
                    type  cml_data_types:CML_UINT64_T;
                    description "";
                } // END of dribble definition.

                leaf collisionsState  {
                    if-feature feature_list:HAVE_BROADCOM;
                    if-feature feature_list:HAVE_HAL;
                    type  cml_data_types:CML_UINT64_T;
                    description "";
                } // END of collisionsState definition.

                leaf lateCollisions  {
                    if-feature feature_list:HAVE_BROADCOM;
                    if-feature feature_list:HAVE_HAL;
                    type  cml_data_types:CML_UINT64_T;
                    description "";
                } // END of lateCollisions definition.

                leaf deferredTx  {
                    if-feature feature_list:HAVE_BROADCOM;
                    if-feature feature_list:HAVE_HAL;
                    type  cml_data_types:CML_UINT64_T;
                    description "";
                } // END of deferredTx definition.

                leaf badFcRcv  {
                    if-feature feature_list:HAVE_BROADCOM;
                    if-feature feature_list:HAVE_HAL;
                    type  cml_data_types:CML_UINT64_T;
                    description "";
                } // END of badFcRcv definition.

                leaf portInoverflowFrames  {
                    if-feature feature_list:HAVE_BROADCOM;
                    if-feature feature_list:HAVE_HAL;
                    type  cml_data_types:CML_UINT64_T;
                    description "";
                } // END of portInoverflowFrames definition.

                leaf portOutOverflowFrames  {
                    if-feature feature_list:HAVE_BROADCOM;
                    if-feature feature_list:HAVE_HAL;
                    type  cml_data_types:CML_UINT64_T;
                    description "";
                } // END of portOutOverflowFrames definition.

                leaf portInOverflowDiscards  {
                    if-feature feature_list:HAVE_BROADCOM;
                    if-feature feature_list:HAVE_HAL;
                    type  cml_data_types:CML_UINT64_T;
                    description "";
                } // END of portInOverflowDiscards definition.

                leaf inFiltered  {
                    if-feature feature_list:HAVE_BROADCOM;
                    if-feature feature_list:HAVE_HAL;
                    type  cml_data_types:CML_UINT64_T;
                    description "";
                } // END of inFiltered definition.

                leaf outFiltered  {
                    if-feature feature_list:HAVE_BROADCOM;
                    if-feature feature_list:HAVE_HAL;
                    type  cml_data_types:CML_UINT64_T;
                    description "";
                } // END of outFiltered definition.

                leaf mtuExceed  {
                    if-feature feature_list:HAVE_BROADCOM;
                    if-feature feature_list:HAVE_HAL;
                    type  cml_data_types:CML_UINT64_T;
                    description "";
                } // END of mtuExceed definition.

                leaf inJumbo  {
                    if-feature feature_list:HAVE_BROADCOM;
                    if-feature feature_list:HAVE_HAL;
                    type  cml_data_types:CML_UINT64_T;
                    description "";
                } // END of inJumbo definition.

                leaf outJumbo  {
                    if-feature feature_list:HAVE_BROADCOM;
                    if-feature feature_list:HAVE_HAL;
                    type  cml_data_types:CML_UINT64_T;
                    description "";
                } // END of outJumbo definition.

                leaf rxPktRate  {
                    if-feature feature_list:HAVE_BROADCOM;
                    if-feature feature_list:HAVE_HAL;
                    type  cml_data_types:CML_UINT64_T;
                    description "";
                } // END of rxPktRate definition.

                leaf rxBitRate  {
                    if-feature feature_list:HAVE_BROADCOM;
                    if-feature feature_list:HAVE_HAL;
                    type  cml_data_types:CML_UINT64_T;
                    description "";
                } // END of rxBitRate definition.

                leaf txPktRate  {
                    if-feature feature_list:HAVE_BROADCOM;
                    if-feature feature_list:HAVE_HAL;
                    type  cml_data_types:CML_UINT64_T;
                    description "";
                } // END of txPktRate definition.

                leaf txBitRate  {
                    if-feature feature_list:HAVE_BROADCOM;
                    if-feature feature_list:HAVE_HAL;
                    type  cml_data_types:CML_UINT64_T;
                    description "";
                } // END of txBitRate definition.

            } // END of ifStat-container definition.
            container prefixSegment {
                if-feature feature_list:HAVE_SR;
                description
                    "prefix segment";
                leaf sid  {
                    type  cml_data_types:CML_SR_SID_T;
                    description "";
                } // END of sid definition.

                leaf expNull  {
                    type  cml_data_types:CML_SR_PREFIX_FLAG_T;
                    description "";
                } // END of expNull definition.

                leaf nFlagClear  {
                    type  cml_data_types:CML_SR_N_FLAG_CLEAR_T;
                    description "";
                } // END of nFlagClear definition.

            } // END of prefixSegment-container definition.
            uses switchportInterface-grouping;
            uses nsmlacpInterface-grouping;
            uses nsmportInterface-grouping;
            uses lacpInterface-grouping;
            uses ospfInterface-grouping;
            uses sflowInterfaceConfigs-grouping;
            uses mlagAgg-grouping;
            uses qosInterface-grouping;
            uses aclInterface-grouping;
            uses rpfInfo-grouping;
        } // End of interface-list
    } // END of interface-grouping definition.

    grouping  nsmMaster-grouping {
    container nsmMaster {
        description
            "Global configs for router";
        leaf routerId  {
            type  cml_data_types:CML_STRING_T {
                length "0..255";
            }
            description "";
        } // END of routerId definition.

        leaf hardwareProfileEgressIpv6Acl  {
            if-feature feature_list:HAVE_ACL;
            if-feature feature_list:HAVE_BROADCOM;
            type  cml_data_types:CML_ENABLE_DISABLE_T;
            default "enable";
            description "";
        } // END of hardwareProfileEgressIpv6Acl definition.

        leaf hardwareProfileEgressIpv6Uft  {
            if-feature feature_list:HAVE_BCM_UFT;
            if-feature feature_list:HAVE_BROADCOM;
            type  cml_data_types:CML_ENABLE_DISABLE_T;
            default "enable";
            description "";
        } // END of hardwareProfileEgressIpv6Uft definition.

        leaf hardwareProfileIngressIpv4Uft  {
            if-feature feature_list:HAVE_BCM_UFT;
            if-feature feature_list:HAVE_BROADCOM;
            type  cml_data_types:CML_ENABLE_DISABLE_T;
            default "enable";
            description "";
        } // END of hardwareProfileIngressIpv4Uft definition.

        leaf hardwareProfileIngressIpv4Acl  {
            if-feature feature_list:HAVE_ACL;
            if-feature feature_list:HAVE_BROADCOM;
            type  cml_data_types:CML_ENABLE_DISABLE_T;
            default "enable";
            description "";
        } // END of hardwareProfileIngressIpv4Acl definition.

        leaf hardwareProfileIngressIpv6  {
            if-feature feature_list:HAVE_ACL;
            if-feature feature_list:HAVE_BROADCOM;
            type  cml_data_types:CML_ENABLE_DISABLE_T;
            default "enable";
            description "";
        } // END of hardwareProfileIngressIpv6 definition.

        leaf hardwareProfileQosGroup  {
            if-feature feature_list:HAVE_DUNE;
            if-feature feature_list:HAVE_BCM_UFT;
            if-feature feature_list:HAVE_BROADCOM;
            type  cml_data_types:CML_ENABLE_DISABLE_T;
            default "enable";
            description "";
        } // END of hardwareProfileQosGroup definition.

        leaf hardwareProfileEgressIpv4  {
            if-feature feature_list:HAVE_DUNE;
            if-feature feature_list:HAVE_BCM_UFT;
            if-feature feature_list:HAVE_BROADCOM;
            type  cml_data_types:CML_ENABLE_DISABLE_T;
            default "enable";
            description "";
        } // END of hardwareProfileEgressIpv4 definition.

        leaf hardwareProfileEgressL2Group  {
            if-feature feature_list:HAVE_DUNE;
            if-feature feature_list:HAVE_BCM_UFT;
            if-feature feature_list:HAVE_BROADCOM;
            type  cml_data_types:CML_ENABLE_DISABLE_T;
            default "enable";
            description "";
        } // END of hardwareProfileEgressL2Group definition.

        leaf hardwareProfileIngressL2Group  {
            if-feature feature_list:HAVE_DUNE;
            if-feature feature_list:HAVE_BCM_UFT;
            if-feature feature_list:HAVE_BROADCOM;
            type  cml_data_types:CML_ENABLE_DISABLE_T;
            default "enable";
            description "";
        } // END of hardwareProfileIngressL2Group definition.

        leaf enableIpForwarding  {
            type  cml_data_types:CML_BOOL_T;
            description "";
        } // END of enableIpForwarding definition.

        leaf enableIpv6Forwarding  {
            if-feature feature_list:HAVE_IPV6;
            type  cml_data_types:CML_BOOL_T;
            description "";
        } // END of enableIpv6Forwarding definition.

        leaf icmpBroadcast  {
            type  cml_data_types:CML_BOOL_T;
            description "";
        } // END of icmpBroadcast definition.

        leaf hardwareProfilePortMode  {
            if-feature feature_list:HAVE_FLEXPORT;
            type  cml_data_types:CML_NSM_HARDWARE_PORTMODE_T;
            description "";
        } // END of hardwareProfilePortMode definition.

        leaf hardwareProfilePortModeBundle  {
            if-feature feature_list:HAVE_FLEXPORT;
            type  cml_data_types:CML_NSM_HARDWARE_PROFILE_PORTMODE_BUNDLE_T;
            description "";
        } // END of hardwareProfilePortModeBundle definition.

        leaf forwardingProfile  {
            if-feature feature_list:HAVE_BCM_UFT;
            type  cml_data_types:CML_FORWARDING_PROFILE_T;
            default "l3-profile";
            description "";
        } // END of forwardingProfile definition.

        leaf forwardingProfilelpm  {
            if-feature feature_list:HAVE_BCM_UFT;
            type  cml_data_types:CML_FORWARDING_PROFILE_LPM_T;
            description "";
        } // END of forwardingProfilelpm definition.

        leaf forwardingProfilekaps  {
            if-feature feature_list:HAVE_DUNE;
            if-feature feature_list:HAVE_BCM_UFT;
            type  cml_data_types:CML_PROFILE_T;
            description "";
        } // END of forwardingProfilekaps definition.


        list vrf {
            key "vrfName";
            description
                "vrf";
            leaf vrfName  {
                type  cml_data_types:CML_STRING_T {
                    length "0..255";
                }
                description "";
            } // END of vrfName definition.

            leaf ipVrfForwarding  {
                type  cml_data_types:CML_BOOL_T;
                description "";
            } // END of ipVrfForwarding definition.

            leaf ipv6VrfForwarding  {
                if-feature feature_list:HAVE_IPV6;
                type  cml_data_types:CML_BOOL_T;
                description "";
            } // END of ipv6VrfForwarding definition.

            leaf icmpVrfBroadcast  {
                type  cml_data_types:CML_BOOL_T;
                description "";
            } // END of icmpVrfBroadcast definition.

        } // End of vrf-list
        container srNsm {
            if-feature feature_list:HAVE_SR;
            description
                "srNsm";
            leaf baseSid  {
                type  cml_data_types:CML_UINT32_T {
                     range "16000..23999";
                }
                description "";
            } // END of baseSid definition.

            leaf last  {
                type  cml_data_types:CML_UINT32_T {
                     range "16000..23999";
                }
                description "";
            } // END of last definition.

        } // END of srNsm-container definition.
        container errdisable {
            description
                "Error Disable Configuration";
            leaf errdisableReason  {
                type  cml_data_types:CML_NSM_ERR_REASON_T;
                description "";
            } // END of errdisableReason definition.

            leaf errdisableTimeout  {
                type  cml_data_types:CML_NSM_ERR_DISABLE_TIMEOUT_T;
                default "disable";
                description "";
            } // END of errdisableTimeout definition.

            leaf errdisableTimeoutInterval  {
                type  cml_data_types:CML_UINT32_T {
                     range "10..1000000";
                }
                default "300";
                description "";
            } // END of errdisableTimeoutInterval definition.

            leaf linkFlapMaxCount  {
                type  cml_data_types:CML_UINT32_T {
                     range "1..100";
                }
                default "5";
                description "";
            } // END of linkFlapMaxCount definition.

            leaf linkFlapTimerInterval  {
                type  cml_data_types:CML_UINT32_T {
                     range "1..1800";
                }
                default "10";
                description "";
            } // END of linkFlapTimerInterval definition.

        } // END of errdisable-container definition.
        container arpEntry {
            description
                "arpEntry";

            list staticArpList {
                key "arpAddr";
                description
                    "staticArpList";
                leaf arpAddr  {
                    type  cml_data_types:CML_STRING_T {
                        length "0..255";
                    }
                    description "";
                } // END of arpAddr definition.

                leaf macAddr  {
                    type  cml_data_types:CML_STRING_T {
                        length "0..255";
                    }
                    mandatory true;
                    description "";
                } // END of macAddr definition.

                leaf isArpProxy  {
                    type  cml_data_types:CML_BOOL_T;
                    mandatory true;
                    description "";
                } // END of isArpProxy definition.

            } // End of staticArpList-list

            list ipv6StaticNbrTable {
                if-feature feature_list:HAVE_L3;
                if-feature feature_list:HAVE_IPV6;
                key "nbrAddr";
                description
                    "ipv6StaticNbrTable";
                leaf nbrAddr  {
                    type  cml_data_types:CML_STRING_T {
                        length "0..255";
                    }
                    description "";
                } // END of nbrAddr definition.

                leaf ifName  {
                    type  cml_data_types:CML_STRING_T {
                        length "0..255";
                    }
                    mandatory true;
                    description "";
                } // END of ifName definition.

                leaf macAddr  {
                    type  cml_data_types:CML_STRING_T {
                        length "0..255";
                    }
                    mandatory true;
                    description "";
                } // END of macAddr definition.

            } // End of ipv6StaticNbrTable-list
        } // END of arpEntry-container definition.
    } // END of nsmMaster-container definition.
    } // END of nsmMaster-container definition.

    grouping  loadBalance-grouping {
    container loadBalance {
        if-feature feature_list:HAVE_BROADCOM;
        presence "yes";
        description
            "Load Balancing";
        leaf loadBalance  {
            type  cml_data_types:CML_BOOL_T;
            mandatory true;
            description "";
        } // END of loadBalance definition.

        container l2 {
            if-feature feature_list:HAVE_L2;
            description
                "Load balancing on L2 packet";
            leaf l2destMac  {
                type  cml_data_types:CML_BOOL_T;
                description "";
            } // END of l2destMac definition.

            leaf l2srcMac  {
                type  cml_data_types:CML_BOOL_T;
                description "";
            } // END of l2srcMac definition.

            leaf l2etherType  {
                type  cml_data_types:CML_BOOL_T;
                description "";
            } // END of l2etherType definition.

            leaf l2vlan  {
                type  cml_data_types:CML_BOOL_T;
                description "";
            } // END of l2vlan definition.

        } // END of l2-container definition.
        container l3Ipv4 {
            if-feature feature_list:HAVE_L3;
            description
                "Load balancing on L2 packet";
            leaf l3srcIpv4  {
                type  cml_data_types:CML_BOOL_T;
                description "";
            } // END of l3srcIpv4 definition.

            leaf l3destIpv4  {
                type  cml_data_types:CML_BOOL_T;
                description "";
            } // END of l3destIpv4 definition.

            leaf l3srcl4Port  {
                type  cml_data_types:CML_BOOL_T;
                description "";
            } // END of l3srcl4Port definition.

            leaf l3destl4Port  {
                type  cml_data_types:CML_BOOL_T;
                description "";
            } // END of l3destl4Port definition.

            leaf l3protocolId  {
                type  cml_data_types:CML_BOOL_T;
                description "";
            } // END of l3protocolId definition.

        } // END of l3Ipv4-container definition.
        container l3Ipv6 {
            if-feature feature_list:HAVE_L3;
            description
                "Load balancing on L2 packet";
            leaf l3srcIpv6  {
                type  cml_data_types:CML_BOOL_T;
                description "";
            } // END of l3srcIpv6 definition.

            leaf l3destIpv6  {
                type  cml_data_types:CML_BOOL_T;
                description "";
            } // END of l3destIpv6 definition.

            leaf l3srcl6Port  {
                type  cml_data_types:CML_BOOL_T;
                description "";
            } // END of l3srcl6Port definition.

            leaf l3destl6Port  {
                type  cml_data_types:CML_BOOL_T;
                description "";
            } // END of l3destl6Port definition.

            leaf l3nextHdr  {
                type  cml_data_types:CML_BOOL_T;
                description "";
            } // END of l3nextHdr definition.

        } // END of l3Ipv6-container definition.
        container tunnel {
            if-feature feature_list:HAVE_L3;
            description
                "Load balancing on L2 packet";
            leaf outerl3Header  {
                type  cml_data_types:CML_BOOL_T;
                description "";
            } // END of outerl3Header definition.

        } // END of tunnel-container definition.
        container trill {
            if-feature feature_list:HAVE_TRILLD;
            description
                "Load balancing on L2 packet";
            leaf trill  {
                type  cml_data_types:CML_NSM_LOAD_TRILL_T;
                description "";
            } // END of trill definition.

        } // END of trill-container definition.
        container hash {
            description
                "Load balance hash computation";
            leaf hash  {
                type  cml_data_types:CML_NSM_LOAD_HASH_T;
                description "";
            } // END of hash definition.

        } // END of hash-container definition.
        container macroflow {
            description
                "macro-flow based dynamic hash selection";
            leaf macroflow  {
                type  cml_data_types:CML_BOOL_T;
                description "";
            } // END of macroflow definition.

        } // END of macroflow-container definition.
        container vxlanL2 {
            if-feature feature_list:HAVE_VXLAN;
            description
                "Load balancing on vxlan L2 packet";
            leaf vxlandestMac  {
                type  cml_data_types:CML_BOOL_T;
                description "";
            } // END of vxlandestMac definition.

            leaf vxlansrcMac  {
                type  cml_data_types:CML_BOOL_T;
                description "";
            } // END of vxlansrcMac definition.

        } // END of vxlanL2-container definition.
        container vxlanL3 {
            if-feature feature_list:HAVE_VXLAN;
            description
                "Load balancing on vxlan L3 packet";
            leaf vxlansrcIp  {
                type  cml_data_types:CML_BOOL_T;
                description "";
            } // END of vxlansrcIp definition.

            leaf vxlandestIp  {
                type  cml_data_types:CML_BOOL_T;
                description "";
            } // END of vxlandestIp definition.

            leaf vxlansrcl4Port  {
                type  cml_data_types:CML_BOOL_T;
                description "";
            } // END of vxlansrcl4Port definition.

            leaf vxlandestl4Port  {
                type  cml_data_types:CML_BOOL_T;
                description "";
            } // END of vxlandestl4Port definition.

            leaf vxlanprotocolId  {
                type  cml_data_types:CML_BOOL_T;
                description "";
            } // END of vxlanprotocolId definition.

        } // END of vxlanL3-container definition.
        container mplsLerL2 {
            if-feature feature_list:HAVE_MPLS;
            description
                "Load balancing on L2 packet";
            leaf mplsdestMac  {
                type  cml_data_types:CML_BOOL_T;
                description "";
            } // END of mplsdestMac definition.

            leaf mplssrcMac  {
                type  cml_data_types:CML_BOOL_T;
                description "";
            } // END of mplssrcMac definition.

            leaf mplsetherType  {
                type  cml_data_types:CML_BOOL_T;
                description "";
            } // END of mplsetherType definition.

            leaf mplsvlan  {
                type  cml_data_types:CML_BOOL_T;
                description "";
            } // END of mplsvlan definition.

        } // END of mplsLerL2-container definition.
        container mplsLer {
            if-feature feature_list:HAVE_MPLS;
            description
                "Load balancing on L2 packet";
            leaf mplssrcIpv6  {
                type  cml_data_types:CML_BOOL_T;
                description "";
            } // END of mplssrcIpv6 definition.

            leaf mplsdestIpv6  {
                type  cml_data_types:CML_BOOL_T;
                description "";
            } // END of mplsdestIpv6 definition.

            leaf mplssrcl4Port  {
                type  cml_data_types:CML_BOOL_T;
                description "";
            } // END of mplssrcl4Port definition.

            leaf mplsdestl4Port  {
                type  cml_data_types:CML_BOOL_T;
                description "";
            } // END of mplsdestl4Port definition.

            leaf mplsprotocolId  {
                type  cml_data_types:CML_BOOL_T;
                description "";
            } // END of mplsprotocolId definition.

        } // END of mplsLer-container definition.
    } // END of loadBalance-container definition.
    } // END of loadBalance-container definition.


}
