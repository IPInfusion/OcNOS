/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-mpls.yang
*
*/

submodule zebos-mpls {

    belongs-to  zebos { prefix zebos; }

    import cml_data_types {
        prefix cml_data_types;
    }

    import feature_list {
        prefix feature_list;
    }

    organization
        "IP Infusion Inc.";

    contact
        "Address: 3965 Freedom Circle, Suite 200, Santa Clara, CA 95054
        Phone: +1 408-400-1900
        E-mail: support@ipinfusion.com
        Web: http://www.ipinfusion.com/";

    description
        "";


    revision "2018-06-21" {
        description " Initial Version.";
        reference "";
    }



    grouping svcCustName-grouping {
    description
        "Service mapping related operations";
        list svcCustName {
            key "svcCustName";
            description
                "Service mapping related operations";
            leaf svcCustName  {
                type  cml_data_types:CML_STRING_T {
                    length "0..255";

                    pattern "[a-zA-Z0-9_-]*";
                }
                description "";
            } // END of svcCustName definition.

            leaf allMatchType  {
                type  cml_data_types:CML_BOOL_T;
                description "";
            } // END of allMatchType definition.

            leaf singleTagOuterVlan  {
                type  cml_data_types:CML_RANGE_T {
                    length "1..255";
                }
                description "";
            } // END of singleTagOuterVlan definition.

            leaf doubleTagOvid  {
                type  cml_data_types:CML_UINT16_T {
                     range "2..4094";
                }
                description "";
            } // END of doubleTagOvid definition.

            leaf doubleTagIvid  {
                type  cml_data_types:CML_UINT16_T {
                     range "2..4094";
                }
                description "";
            } // END of doubleTagIvid definition.

            leaf vlanActionPop  {
                type  cml_data_types:CML_MPLS_VLAN_ACTIONTYPE_T;
                description "";
            } // END of vlanActionPop definition.

            leaf vlanActionTranslate  {
                type  cml_data_types:CML_UINT16_T {
                     range "2..4094";
                }
                description "";
            } // END of vlanActionTranslate definition.

            leaf vlanActionPush  {
                type  cml_data_types:CML_UINT16_T {
                     range "2..4094";
                }
                description "";
            } // END of vlanActionPush definition.

            leaf svcTpid  {
                type  cml_data_types:CML_NSM_SVC_TPID_T;
                default "dot1.q";
                description "";
            } // END of svcTpid definition.


            list svcMapList {
                key "svcMapName";
                config false;
                description
                    "svcMapList";
                leaf svcMapName  {
                    type  cml_data_types:CML_STRING_T {
                        length "0..255";
                    }
                    description "";
                } // END of svcMapName definition.

                leaf svcErrorStatus  {
                    type  cml_data_types:CML_STRING_T {
                        length "0..255";
                    }
                    description "";
                } // END of svcErrorStatus definition.

                leaf svcBindIfName  {
                    type  cml_data_types:CML_STRING_T {
                        length "0..255";
                    }
                    description "";
                } // END of svcBindIfName definition.

            } // End of svcMapList-list
        } // End of svcCustName-list
    } // END of svcCustName-grouping definition.


    grouping acGroup-grouping {
    description
        "LDP_vc related operations";
        list acGroup {
            key "acGroup";
            description
                "LDP_vc related operations";
            leaf acGroup  {
                type  cml_data_types:CML_STRING_T {
                    length "0..255";
                }
                description "";
            } // END of acGroup definition.

            leaf groupId  {
                type  cml_data_types:CML_UINT32_T {
                     range "1..4294967295";
                }
                mandatory true;
                description "";
            } // END of groupId definition.

        } // End of acGroup-list
    } // END of acGroup-grouping definition.


    grouping adminGroup-grouping {
    description
        "Administrative Groups";
        list adminGroup {
            key "adminGrpName";
            description
                "Administrative Groups";
            leaf adminGrpName  {
                type  cml_data_types:CML_STRING_T {
                    length "0..255";
                }
                description "";
            } // END of adminGrpName definition.

            leaf adminGroupId  {
                type  cml_data_types:CML_UINT8_T {
                     range "0..31";
                }
                mandatory true;
                description "";
            } // END of adminGroupId definition.

        } // End of adminGroup-list
    } // END of adminGroup-grouping definition.


    grouping vcTable-grouping {
    description
        "LDP_vc related operations";
        list vcTable {
            if-feature feature_list:HAVE_MPLS_VC;
            key "vcName";
            description
                "LDP_vc related operations";
            leaf vcName  {
                type  cml_data_types:CML_STRING_T {
                    length "0..255";
                }
                description "";
            } // END of vcName definition.


            list vcEntry {
                key "vcId";
                description
                    "vcEntry";
                leaf vcId  {
                    type  cml_data_types:CML_UINT32_T {
                         range "1..4294967295";
                    }
                    description "";
                } // END of vcId definition.

                leaf peerAddress  {
                    type  cml_data_types:CML_IPV4_ADDR_T;
                    description "";
                } // END of peerAddress definition.

                leaf peerIpv6Addr  {
                    type  cml_data_types:CML_IPV6_ADDR_T;
                    description "";
                } // END of peerIpv6Addr definition.

                leaf peerGid  {
                    if-feature feature_list:HAVE_MPLS_TP;
                    type  cml_data_types:CML_UINT32_T {
                         range "1..4294967295";
                    }
                    description "";
                } // END of peerGid definition.

                leaf peerAcId  {
                    if-feature feature_list:HAVE_MPLS_TP;
                    type  cml_data_types:CML_UINT32_T {
                         range "1..4294967295";
                    }
                    description "";
                } // END of peerAcId definition.

                leaf CCName  {
                    if-feature feature_list:HAVE_MPLS_TP;
                    type  cml_data_types:CML_STRING_T {
                        length "0..255";
                    }
                    description "";
                } // END of CCName definition.

                leaf ICCName  {
                    if-feature feature_list:HAVE_MPLS_TP;
                    type  cml_data_types:CML_STRING_T {
                        length "0..255";
                    }
                    description "";
                } // END of ICCName definition.

                uses vcTableCommonAttr;
                uses vctableRuntime;
            } // End of vcEntry-list

            list vcFec129Entry {
                if-feature feature_list:HAVE_FEC129;
                key "peerAddress";
                description
                    "vcFec129Entry";
                leaf peerAddress  {
                    type  cml_data_types:CML_IPV4_ADDR_T;
                    description "";
                } // END of peerAddress definition.


                list vcAgiTable {
                    key "agi";
                    description
                        "vcAgiTable";
                    leaf agi  {
                        type  cml_data_types:CML_STRING_T {
                            length "0..255";
                        }
                        description "";
                    } // END of agi definition.


                    list vcSaiiTable {
                        key "saii";
                        description
                            "vcSaiiTable";
                        leaf saii  {
                            type  cml_data_types:CML_STRING_T {
                                length "1..4";
                            }
                            description "";
                        } // END of saii definition.


                        list vcTaiiTable {
                            key "taii";
                            description
                                "vcTaiiTable";
                            leaf taii  {
                                type  cml_data_types:CML_STRING_T {
                                    length "1..4";
                                }
                                description "";
                            } // END of taii definition.

                            uses vcTableCommonAttr;
                        } // End of vcTaiiTable-list
                    } // End of vcSaiiTable-list
                } // End of vcAgiTable-list
            } // End of vcFec129Entry-list
        } // End of vcTable-list
    } // END of vcTable-grouping definition.


    grouping vcMsPwStitch-grouping {
    description
        "virtual circuit related operations";
        list vcMsPwStitch {
            if-feature feature_list:HAVE_MS_PW;
            key "stitchName";
            description
                "virtual circuit related operations";
            leaf stitchName  {
                type  cml_data_types:CML_STRING_T {
                    length "0..255";
                }
                description "";
            } // END of stitchName definition.

            leaf vc1Name  {
                type  cml_data_types:CML_STRING_T {
                    length "0..255";
                }
                mandatory true;
                description "";
            } // END of vc1Name definition.

            leaf vc2Name  {
                type  cml_data_types:CML_STRING_T {
                    length "0..255";
                }
                mandatory true;
                description "";
            } // END of vc2Name definition.

            leaf mtu  {
                type  cml_data_types:CML_UINT16_T {
                     range "0..1500";
                }
                description "";
            } // END of mtu definition.

            leaf ethernet  {
                type  cml_data_types:CML_BOOL_T;
                description "";
            } // END of ethernet definition.

            leaf vlanId  {
                type  cml_data_types:CML_UINT16_T {
                     range "2..4094";
                }
                description "";
            } // END of vlanId definition.

            leaf msPwdescr  {
                type  cml_data_types:CML_STRING_T {
                    length "0..255";
                }
                description "";
            } // END of msPwdescr definition.

            leaf status  {
                type  cml_data_types:CML_BOOL_T;
                config false;
                description "";
            } // END of status definition.

            leaf ms_pw_status  {
                type  cml_data_types:CML_BOOL_T;
                config false;
                description "";
            } // END of ms_pw_status definition.

            container vc1NameRuntime {
                if-feature feature_list:HAVE_MS_PW;
                config false;
                description
                    "vc1NameRuntime";
                uses vcMsPwRuntime;
            } // END of vc1NameRuntime-container definition.
            container vc2NameRuntime {
                if-feature feature_list:HAVE_MS_PW;
                config false;
                description
                    "vc2NameRuntime";
                uses vcMsPwRuntime;
            } // END of vc2NameRuntime-container definition.
        } // End of vcMsPwStitch-list
    } // END of vcMsPwStitch-grouping definition.


    grouping vcFibEntry-grouping {
    description
        "LDP_VC fib related operations";
        list vcFibEntry {
            key "vcId";
            description
                "LDP_VC fib related operations";
            leaf vcId  {
                type  cml_data_types:CML_UINT32_T {
                     range "1..4294967295";
                }
                description "";
            } // END of vcId definition.

            leaf inLabel  {
                type  cml_data_types:CML_UINT32_T {
                     range "16..1048575";
                }
                mandatory true;
                description "";
            } // END of inLabel definition.

            leaf outLabel  {
                type  cml_data_types:CML_UINT32_T {
                     range "16..1048575";
                }
                mandatory true;
                description "";
            } // END of outLabel definition.

            leaf fibNhopStr  {
                type  cml_data_types:CML_IP_ADDR_T {
                    length "0..255";
                }
                description "";
            } // END of fibNhopStr definition.

            leaf fibIfName  {
                type  cml_data_types:CML_STRING_T {
                    length "0..255";
                }
                description "";
            } // END of fibIfName definition.

            leaf ifName  {
                type  cml_data_types:CML_STRING_T {
                    length "0..255";
                }
                mandatory true;
                description "";
            } // END of ifName definition.

            leaf fibTunnelName  {
                if-feature feature_list:HAVE_MPLS_TP;
                type  cml_data_types:CML_STRING_T {
                    length "0..255";
                }
                description "";
            } // END of fibTunnelName definition.

        } // End of vcFibEntry-list
    } // END of vcFibEntry-grouping definition.


    grouping mplsClassType-grouping {
    description
        "mplsClassType";
        list mplsClassType {
            key "classType";
            description
                "mplsClassType";
            leaf classType  {
                type  cml_data_types:CML_STRING_T {
                    length "0..255";
                }
                description "";
            } // END of classType definition.


            list className {
                key "ctName";
                description
                    "className";
                leaf ctName  {
                    type  cml_data_types:CML_STRING_T {
                        length "0..255";
                    }
                    description "";
                } // END of ctName definition.

            } // End of className-list
        } // End of mplsClassType-list
    } // END of mplsClassType-grouping definition.


    grouping teClassList-grouping {
    description
        "teClassList";
        list teClassList {
            key "teClass";
            description
                "teClassList";
            leaf teClass  {
                type  cml_data_types:CML_STRING_T {
                    length "0..255";
                }
                description "";
            } // END of teClass definition.

            leaf ctName  {
                type  cml_data_types:CML_STRING_T {
                    length "0..255";
                }
                mandatory true;
                description "";
            } // END of ctName definition.

            leaf priority  {
                type  cml_data_types:CML_UINT32_T {
                     range "0..7";
                }
                mandatory true;
                description "";
            } // END of priority definition.

        } // End of teClassList-list
    } // END of teClassList-grouping definition.


    grouping mplsBandwidthClass-grouping {
    description
        "mpls bandwidth class";
        list mplsBandwidthClass {
            key "bwClassName";
            description
                "mpls bandwidth class";
            leaf bwClassName  {
                type  cml_data_types:CML_STRING_T {
                    length "0..255";
                }
                description "";
            } // END of bwClassName definition.

            leaf bandwidth  {
                type  cml_data_types:CML_STRING_T {
                    length "0..255";
                }
                description "";
            } // END of bandwidth definition.

            leaf setupPrio  {
                type  cml_data_types:CML_UINT8_T {
                     range "0..7";
                }
                description "";
            } // END of setupPrio definition.

            leaf holdPrio  {
                type  cml_data_types:CML_UINT8_T {
                     range "0..7";
                }
                description "";
            } // END of holdPrio definition.

            leaf classTypeName  {
                if-feature feature_list:HAVE_DSTE;
                type  cml_data_types:CML_STRING_T {
                    length "0..255";
                }
                description "";
            } // END of classTypeName definition.

        } // End of mplsBandwidthClass-list
    } // END of mplsBandwidthClass-grouping definition.


    grouping ftnEntry-cli-grouping {
    description
        "ftnEntryCMLSEPcli";
        list ftnEntry-cli {
            key "fecAddr";
            description
                "ftnEntryCMLSEPcli";
            leaf fecAddr  {
                type  cml_data_types:CML_STRING_T {
                    length "0..255";
                }
                description "";
            } // END of fecAddr definition.

            leaf outLabel  {
                type  cml_data_types:CML_UINT32_T {
                     range "16..52443";
                }
                mandatory true;
                description "";
            } // END of outLabel definition.

            leaf nexthopIpAddr  {
                type  cml_data_types:CML_IPV4_ADDR_T;
                mandatory true;
                description "";
            } // END of nexthopIpAddr definition.

            leaf ftnIfName  {
                type  cml_data_types:CML_STRING_T {
                    length "0..255";
                }
                mandatory true;
                description "";
            } // END of ftnIfName definition.

            leaf ftnIndex  {
                type  cml_data_types:CML_UINT32_T;
                description "";
            } // END of ftnIndex definition.

            uses runtimeFtn;
        } // End of ftnEntry-cli-list
    } // END of ftnEntry-cli-grouping definition.


    grouping ftnEntry-runtime-grouping {
    description
        "ftnEntryCMLSEPruntime";
        list ftnEntry-runtime {
            key "fecAddr";
            config false;
            description
                "ftnEntryCMLSEPruntime";
            leaf fecAddr  {
                type  cml_data_types:CML_STRING_T {
                    length "0..255";
                }
                description "";
            } // END of fecAddr definition.


            list ftnIndex {
                key "ftn_ix";
                config false;
                description
                    "ftnIndex";
                leaf ftn_ix  {
                    type  cml_data_types:CML_UINT32_T;
                    description "";
                } // END of ftn_ix definition.


                list xc-entry {
                    key "xc_ix";
                    config false;
                    description
                        "xcCMLSEPentry";
                    leaf xc_ix  {
                        type  cml_data_types:CML_UINT32_T;
                        description "";
                    } // END of xc_ix definition.

                    leaf inLabel  {
                        type  cml_data_types:CML_UINT32_T;
                        description "";
                    } // END of inLabel definition.

                    container nhlfe-entry {
                        config false;
                        description
                            "nhlfeCMLSEPentry";
                        leaf outLabel  {
                            type  cml_data_types:CML_UINT32_T;
                            description "";
                        } // END of outLabel definition.

                        leaf nexthopIpAddr  {
                            type  cml_data_types:CML_STRING_T {
                                length "0..255";
                            }
                            description "";
                        } // END of nexthopIpAddr definition.

                        leaf outIfName  {
                            type  cml_data_types:CML_STRING_T {
                                length "0..255";
                            }
                            description "";
                        } // END of outIfName definition.

                        uses runtime-nhlfe-entry;
                    } // END of nhlfe-entry-container definition.
                    uses runtime-xc-entry;
                } // End of xc-entry-list
                uses runtimeFtn;
            } // End of ftnIndex-list
        } // End of ftnEntry-runtime-list
    } // END of ftnEntry-runtime-grouping definition.


    grouping ftnTunnelEntry-grouping {
    description
        "ftnTunnelEntry";
        list ftnTunnelEntry {
            if-feature feature_list:NOT_HAVE_MPLS_TUNNEL;
            key "ftnTunnelId";
            description
                "ftnTunnelEntry";
            leaf ftnTunnelId  {
                type  cml_data_types:CML_UINT32_T {
                     range "1..5000";
                }
                description "";
            } // END of ftnTunnelId definition.

            leaf fecAddr  {
                type  cml_data_types:CML_STRING_T {
                    length "0..255";
                }
                mandatory true;
                description "";
            } // END of fecAddr definition.

            leaf outLabel  {
                type  cml_data_types:CML_UINT32_T {
                     range "16..1048575";
                }
                mandatory true;
                description "";
            } // END of outLabel definition.

            leaf nexthopIpAddr  {
                type  cml_data_types:CML_IPV4_ADDR_T;
                mandatory true;
                description "";
            } // END of nexthopIpAddr definition.

            leaf ftnIfName  {
                type  cml_data_types:CML_STRING_T {
                    length "0..255";
                }
                mandatory true;
                description "";
            } // END of ftnIfName definition.

            leaf ftnIndex  {
                type  cml_data_types:CML_UINT32_T;
                description "";
            } // END of ftnIndex definition.

            leaf isPrimary  {
                type  cml_data_types:CML_NSM_VPLS_FTN_ENTRY_T;
                mandatory true;
                description "";
            } // END of isPrimary definition.

        } // End of ftnTunnelEntry-list
    } // END of ftnTunnelEntry-grouping definition.


    grouping ftn6Entry-grouping {
    description
        "ftn6Entry";
        list ftn6Entry {
            if-feature feature_list:NOT_HAVE_MPLS_TUNNEL;
            key "fec6Addr";
            description
                "ftn6Entry";
            leaf ftnTunnelId  {
                type  cml_data_types:CML_UINT32_T {
                     range "1..5000";
                }
                mandatory true;
                description "";
            } // END of ftnTunnelId definition.

            leaf fec6Addr  {
                type  cml_data_types:CML_IPV6_PREFIX_T;
                description "";
            } // END of fec6Addr definition.

            leaf outLabel  {
                type  cml_data_types:CML_UINT32_T {
                     range "16..1048575";
                }
                mandatory true;
                description "";
            } // END of outLabel definition.

            leaf nexthopIpv6Addr  {
                type  cml_data_types:CML_IPV6_ADDR_T;
                mandatory true;
                description "";
            } // END of nexthopIpv6Addr definition.

            leaf ftnIfName  {
                type  cml_data_types:CML_STRING_T {
                    length "0..255";
                }
                mandatory true;
                description "";
            } // END of ftnIfName definition.

            leaf ftnIndex  {
                type  cml_data_types:CML_UINT32_T;
                description "";
            } // END of ftnIndex definition.

            leaf isPrimary  {
                type  cml_data_types:CML_NSM_VPLS_FTN_ENTRY_T;
                mandatory true;
                description "";
            } // END of isPrimary definition.

        } // End of ftn6Entry-list
    } // END of ftn6Entry-grouping definition.


    grouping ilm-runtime-entry-grouping {
    description
        "ilmCMLSEPruntimeCMLSEPentry";
        list ilm-runtime-entry {
            key "inLabel";
            config false;
            description
                "ilmCMLSEPruntimeCMLSEPentry";
            leaf inLabel  {
                type  cml_data_types:CML_UINT32_T;
                description "";
            } // END of inLabel definition.


            list inIfentry {
                key "inIfName";
                config false;
                description
                    "inIfentry";
                leaf inIfName  {
                    type  cml_data_types:CML_STRING_T {
                        length "0..255";
                    }
                    description "";
                } // END of inIfName definition.


                list ilmindex {
                    key "ilmIndex";
                    config false;
                    description
                        "ilmindex";
                    leaf ilmIndex  {
                        type  cml_data_types:CML_UINT32_T;
                        description "";
                    } // END of ilmIndex definition.

                    leaf ilmOwner  {
                        type  cml_data_types:CML_STRING_T {
                            length "0..255";
                        }
                        description "";
                    } // END of ilmOwner definition.

                    leaf lsp_type  {
                        type  cml_data_types:CML_UINT8_T;
                        description "";
                    } // END of lsp_type definition.

                    leaf dscp  {
                        type  cml_data_types:CML_UINT8_T;
                        description "";
                    } // END of dscp definition.

                    leaf row_status  {
                        type  cml_data_types:CML_MPLS_ROW_STATUS_T;
                        description "";
                    } // END of row_status definition.

                    leaf ilm_flag  {
                        type  cml_data_types:CML_STRING_T {
                            length "0..255";
                        }
                        description "";
                    } // END of ilm_flag definition.

                    leaf dscp_exp_map  {
                        type  cml_data_types:CML_STRING_T {
                            length "0..255";
                        }
                        description "";
                    } // END of dscp_exp_map definition.

                    leaf opCode  {
                        type  cml_data_types:CML_NSM_VPLS_OPCODE_T;
                        description "";
                    } // END of opCode definition.

                    leaf popOpCode  {
                        type  cml_data_types:CML_NSM_VPLS_POPOPCODE_T;
                        description "";
                    } // END of popOpCode definition.

                    leaf ilmFecAddr  {
                        type  cml_data_types:CML_STRING_T {
                            length "0..255";
                        }
                        description "";
                    } // END of ilmFecAddr definition.


                    list xc-entry {
                        key "xc_ix";
                        config false;
                        description
                            "xcCMLSEPentry";
                        leaf xc_ix  {
                            type  cml_data_types:CML_UINT32_T;
                            description "";
                        } // END of xc_ix definition.

                        container nhlfe-entry {
                            config false;
                            description
                                "nhlfeCMLSEPentry";
                            leaf outLabel  {
                                type  cml_data_types:CML_UINT32_T;
                                description "";
                            } // END of outLabel definition.

                            leaf ilmNexthopIpAddr  {
                                type  cml_data_types:CML_STRING_T {
                                    length "0..255";
                                }
                                description "";
                            } // END of ilmNexthopIpAddr definition.

                            leaf outIfName  {
                                type  cml_data_types:CML_STRING_T {
                                    length "0..255";
                                }
                                description "";
                            } // END of outIfName definition.

                            uses runtime-nhlfe-entry;
                        } // END of nhlfe-entry-container definition.
                        uses runtime-xc-entry;
                    } // End of xc-entry-list
                } // End of ilmindex-list
            } // End of inIfentry-list
        } // End of ilm-runtime-entry-list
    } // END of ilm-runtime-entry-grouping definition.


    grouping ilmEntry-cli-grouping {
    description
        "ilmEntryCMLSEPcli";
        list ilmEntry-cli {
            key "inLabel";
            description
                "ilmEntryCMLSEPcli";
            leaf inLabel  {
                type  cml_data_types:CML_UINT32_T {
                     range "16..52443";
                }
                description "";
            } // END of inLabel definition.


            list ilmEntryInIF {
                key "inIfName";
                description
                    "ilmEntryInIF";
                leaf ilmOwner  {
                    type  cml_data_types:CML_STRING_T {
                        length "0..255";
                    }
                    config false;
                    description "";
                } // END of ilmOwner definition.

                leaf lsp_type  {
                    type  cml_data_types:CML_UINT8_T;
                    config false;
                    description "";
                } // END of lsp_type definition.

                leaf dscp  {
                    type  cml_data_types:CML_UINT8_T;
                    config false;
                    description "";
                } // END of dscp definition.

                leaf row_status  {
                    type  cml_data_types:CML_MPLS_ROW_STATUS_T;
                    config false;
                    description "";
                } // END of row_status definition.

                leaf ilm_flag  {
                    type  cml_data_types:CML_STRING_T {
                        length "0..255";
                    }
                    config false;
                    description "";
                } // END of ilm_flag definition.

                leaf dscp_exp_map  {
                    type  cml_data_types:CML_STRING_T {
                        length "0..255";
                    }
                    config false;
                    description "";
                } // END of dscp_exp_map definition.

                leaf inIfName  {
                    type  cml_data_types:CML_STRING_T {
                        length "0..255";
                    }
                    description "";
                } // END of inIfName definition.

                leaf opCode  {
                    type  cml_data_types:CML_NSM_VPLS_OPCODE_T;
                    description "";
                } // END of opCode definition.

                leaf popOpCode  {
                    type  cml_data_types:CML_NSM_VPLS_POPOPCODE_T;
                    description "";
                } // END of popOpCode definition.

                leaf outLabel  {
                    type  cml_data_types:CML_UINT32_T {
                         range "16..52443";
                    }
                    description "";
                } // END of outLabel definition.

                leaf outIfName  {
                    type  cml_data_types:CML_STRING_T {
                        length "0..255";
                    }
                    description "";
                } // END of outIfName definition.

                leaf ilmNexthopIpAddr  {
                    type  cml_data_types:CML_IPV4_ADDR_T;
                    description "";
                } // END of ilmNexthopIpAddr definition.

                leaf ilmFecAddr  {
                    type  cml_data_types:CML_STRING_T {
                        length "0..255";
                    }
                    description "";
                } // END of ilmFecAddr definition.

                leaf ilmIndex  {
                    type  cml_data_types:CML_UINT32_T {
                         range "1..4294967295";
                    }
                    description "";
                } // END of ilmIndex definition.

                uses runtime-nhlfe-entry;
            } // End of ilmEntryInIF-list

            list ilm6EntryInIF {
                key "inIfName";
                description
                    "ilm6EntryInIF";
                leaf inIfName  {
                    type  cml_data_types:CML_STRING_T {
                        length "0..255";
                    }
                    description "";
                } // END of inIfName definition.

                leaf ipv6OpCode  {
                    type  cml_data_types:CML_NSM_MPLS_IPV6OPCODE_T;
                    mandatory true;
                    description "";
                } // END of ipv6OpCode definition.

                leaf outLabel  {
                    type  cml_data_types:CML_UINT32_T {
                         range "16..52443";
                    }
                    mandatory true;
                    description "";
                } // END of outLabel definition.

                leaf outIfName  {
                    type  cml_data_types:CML_STRING_T {
                        length "0..255";
                    }
                    mandatory true;
                    description "";
                } // END of outIfName definition.

                leaf ilmNexthopIpv6Addr  {
                    type  cml_data_types:CML_IPV6_ADDR_T;
                    mandatory true;
                    description "";
                } // END of ilmNexthopIpv6Addr definition.

                leaf ilmFec6Addr  {
                    type  cml_data_types:CML_IPV6_PREFIX_T;
                    mandatory true;
                    description "";
                } // END of ilmFec6Addr definition.

                leaf ilmIndex  {
                    type  cml_data_types:CML_UINT32_T {
                         range "1..4294967295";
                    }
                    description "";
                } // END of ilmIndex definition.

            } // End of ilm6EntryInIF-list
        } // End of ilmEntry-cli-list
    } // END of ilmEntry-cli-grouping definition.


    grouping mapRoute-grouping {
    description
        "mpls map route";
        list mapRoute {
            key "routeStr";
            description
                "mpls map route";
            leaf routeStr  {
                type  cml_data_types:CML_STRING_T {
                    length "0..255";
                }
                description "";
            } // END of routeStr definition.

            leaf fecAddr  {
                type  cml_data_types:CML_STRING_T {
                    length "0..255";
                }
                mandatory true;
                description "";
            } // END of fecAddr definition.

        } // End of mapRoute-list
    } // END of mapRoute-grouping definition.


    grouping tpmapRoute-grouping {
    description
        "mpls-tp map route";
        list tpmapRoute {
            if-feature feature_list:HAVE_MPLS_TP;
            key "routeStr";
            description
                "mpls-tp map route";
            leaf routeStr  {
                type  cml_data_types:CML_STRING_T {
                    length "0..255";
                }
                description "";
            } // END of routeStr definition.

            leaf tnlName  {
                if-feature feature_list:HAVE_MPLS_TP;
                type  cml_data_types:CML_STRING_T {
                    length "0..255";
                }
                mandatory true;
                description "";
            } // END of tnlName definition.

        } // End of tpmapRoute-list
    } // END of tpmapRoute-grouping definition.


    grouping labelSpace-grouping {
    description
        "labelSpace";
        list labelSpace {
            key "labelSpace";
            description
                "labelSpace";
            leaf labelSpace  {
                type  cml_data_types:CML_UINT16_T {
                     range "0..60000";
                }
                description "";
            } // END of labelSpace definition.


            list moduleLabelRange {
                key "module";
                description
                    "moduleLabelRange";
                leaf module  {
                    type  cml_data_types:CML_MPLS_MODULE_T;
                    description "";
                } // END of module definition.

                leaf minLabel  {
                    type  cml_data_types:CML_UINT32_T {
                         range "16..1048575";
                    }
                    mandatory true;
                    description "";
                } // END of minLabel definition.

                leaf maxLabel  {
                    type  cml_data_types:CML_UINT32_T {
                         range "16..1048575";
                    }
                    mandatory true;
                    description "";
                } // END of maxLabel definition.

            } // End of moduleLabelRange-list
            container staticLabelRange {
                description
                    "staticLabelRange";
                leaf minLabel  {
                    type  cml_data_types:CML_UINT32_T {
                         range "16..1048575";
                    }
                    mandatory true;
                    description "";
                } // END of minLabel definition.

                leaf maxLabel  {
                    type  cml_data_types:CML_UINT32_T {
                         range "16..1048575";
                    }
                    mandatory true;
                    description "";
                } // END of maxLabel definition.

            } // END of staticLabelRange-container definition.
        } // End of labelSpace-list
    } // END of labelSpace-grouping definition.


    grouping lspTunnel-grouping {
    description
        "lspTunnel";
        list lspTunnel {
            key "ifName";
            description
                "lspTunnel";
            leaf ifName  {
                type  cml_data_types:CML_STRING_T {
                    length "0..255";
                }
                description "";
            } // END of ifName definition.


            list lspTunnelInLabel {
                key "inLabel";
                description
                    "lspTunnelInLabel";
                leaf inLabel  {
                    type  cml_data_types:CML_UINT32_T {
                         range "16..1048575";
                    }
                    description "";
                } // END of inLabel definition.

                leaf outLabel  {
                    type  cml_data_types:CML_UINT32_T {
                         range "16..1048575";
                    }
                    mandatory true;
                    description "";
                } // END of outLabel definition.

                leaf fecAddr  {
                    type  cml_data_types:CML_IPV4_ADDR_PREFIX_T;
                    mandatory true;
                    description "";
                } // END of fecAddr definition.

            } // End of lspTunnelInLabel-list
        } // End of lspTunnel-list
    } // END of lspTunnel-grouping definition.


    grouping l2vpnVpws-grouping {
    description
        "l2vpn VPWS";
        list l2vpnVpws {
            if-feature feature_list:HAVE_MPLS_VC;
            if-feature feature_list:HAVE_UNI_CLI;
            key "l2vpnVpwsName";
            description
                "l2vpn VPWS";
            leaf l2vpnVpwsName  {
                type  cml_data_types:CML_STRING_T {
                    length "0..255";
                }
                description "";
            } // END of l2vpnVpwsName definition.

            leaf protocol  {
                if-feature feature_list:HAVE_MPLS_VC;
                type  cml_data_types:CML_L2VPN_PROTOCOL_T;
                description "";
            } // END of protocol definition.

            leaf rd  {
                if-feature feature_list:HAVE_BGP_VPLS;
                if-feature feature_list:HAVE_SWFWDR;
                type  cml_data_types:CML_STRING_T {
                    length "0..255";
                }
                description "";
            } // END of rd definition.

            leaf routeTarget  {
                if-feature feature_list:HAVE_BGP_VPLS;
                if-feature feature_list:HAVE_SWFWDR;
                type  cml_data_types:CML_STRING_T {
                    length "0..255";
                }
                description "";
            } // END of routeTarget definition.

            leaf shut_down  {
                if-feature feature_list:HAVE_MPLS_VC;
                type  cml_data_types:CML_BOOL_T;
                default true;
                description "";
            } // END of shut_down definition.

            leaf vcId  {
                if-feature feature_list:HAVE_MPLS_VC;
                type  cml_data_types:CML_UINT32_T {
                     range "1..4294967295";
                }
                description "";
            } // END of vcId definition.

        } // End of l2vpnVpws-list
    } // END of l2vpnVpws-grouping definition.


    grouping lsp_dep_up-grouping {
    description
        "lspCMLSEPdepCMLSEPup";
        list lsp_dep_up {
            key "prefix";
            config false;
            description
                "lspCMLSEPdepCMLSEPup";
            leaf prefix  {
                type  cml_data_types:CML_STRING_T {
                    length "0..255";
                }
                description "";
            } // END of prefix definition.

            uses lsp_dep_table;
        } // End of lsp_dep_up-list
    } // END of lsp_dep_up-grouping definition.


    grouping lsp_dep_down-grouping {
    description
        "lspCMLSEPdepCMLSEPdown";
        list lsp_dep_down {
            key "prefix";
            config false;
            description
                "lspCMLSEPdepCMLSEPdown";
            leaf prefix  {
                type  cml_data_types:CML_STRING_T {
                    length "0..255";
                }
                description "";
            } // END of prefix definition.

            uses lsp_dep_table;
        } // End of lsp_dep_down-list
    } // END of lsp_dep_down-grouping definition.
    grouping vctableRuntime {
        description
            "vctableRuntime";
        leaf vcAdminStatus  {
            if-feature feature_list:HAVE_UNI_CLI;
            type  cml_data_types:CML_UINT8_T;
            config false;
            description "";
        } // END of vcAdminStatus definition.

        leaf is_ac_fault  {
            if-feature feature_list:HAVE_BGP_VPLS;
            type  cml_data_types:CML_UINT8_T;
            config false;
            description "";
        } // END of is_ac_fault definition.

        leaf is_bgp_peer_down  {
            if-feature feature_list:HAVE_BGP_VPLS;
            type  cml_data_types:CML_UINT8_T;
            config false;
            description "";
        } // END of is_bgp_peer_down definition.

        leaf vc_type  {
            type  cml_data_types:CML_UINT16_T;
            config false;
            description "";
        } // END of vc_type definition.

        leaf uptime  {
            type  cml_data_types:CML_UINT32_T;
            config false;
            description "";
        } // END of uptime definition.

        leaf last_change  {
            type  cml_data_types:CML_UINT32_T;
            config false;
            description "";
        } // END of last_change definition.

        leaf create_time  {
            type  cml_data_types:CML_UINT32_T;
            config false;
            description "";
        } // END of create_time definition.

        leaf admin_status  {
            type  cml_data_types:CML_UINT8_T;
            config false;
            description "";
        } // END of admin_status definition.

        leaf owner  {
            type  cml_data_types:CML_UINT8_T;
            config false;
            description "";
        } // END of owner definition.

        leaf dn  {
            type  cml_data_types:CML_UINT8_T;
            config false;
            description "";
        } // END of dn definition.

        leaf tunnel_type  {
            type  cml_data_types:CML_UINT8_T;
            config false;
            description "";
        } // END of tunnel_type definition.

        leaf vc_source  {
            type  cml_data_types:CML_UINT8_T;
            config false;
            description "";
        } // END of vc_source definition.

        leaf endpt_type  {
            type  cml_data_types:CML_UINT8_T;
            config false;
            description "";
        } // END of endpt_type definition.

        leaf valid_intrvl_cnt  {
            type  cml_data_types:CML_UINT8_T;
            config false;
            description "";
        } // END of valid_intrvl_cnt definition.

        leaf xc_ix  {
            type  cml_data_types:CML_UINT32_T;
            config false;
            description "";
        } // END of xc_ix definition.

        leaf ftn_xc_ix  {
            type  cml_data_types:CML_UINT32_T;
            config false;
            description "";
        } // END of ftn_xc_ix definition.

        leaf remote_grp_id  {
            type  cml_data_types:CML_UINT32_T;
            config false;
            description "";
        } // END of remote_grp_id definition.

        leaf remote_pw_status  {
            type  cml_data_types:CML_UINT32_T;
            config false;
            description "";
        } // END of remote_pw_status definition.

        leaf pw_status_event_code  {
            type  cml_data_types:CML_UINT32_T;
            config false;
            description "";
        } // END of pw_status_event_code definition.

        leaf pw_status_remote_refresh_timer  {
            type  cml_data_types:CML_UINT32_T;
            config false;
            description "";
        } // END of pw_status_remote_refresh_timer definition.

        leaf state  {
            type  cml_data_types:CML_UINT8_T;
            config false;
            description "";
        } // END of state definition.

        leaf is_provider_port  {
            type  cml_data_types:CML_UINT8_T;
            config false;
            description "";
        } // END of is_provider_port definition.

        leaf pwindex  {
            type  cml_data_types:CML_UINT32_T;
            config false;
            description "";
        } // END of pwindex definition.

        leaf pwtype  {
            type  cml_data_types:CML_UINT16_T;
            config false;
            description "";
        } // END of pwtype definition.

        leaf vccircuit  {
            type  cml_data_types:CML_STRING_T {
                length "0..255";
            }
            config false;
            description "";
        } // END of vccircuit definition.

        leaf svcCust  {
            type  cml_data_types:CML_STRING_T {
                length "0..255";
            }
            config false;
            description "";
        } // END of svcCust definition.


        list svcMatchList {
            key "index";
            config false;
            description
                "svcMatchList";
            leaf index  {
                type  cml_data_types:CML_UINT16_T;
                description "";
            } // END of index definition.

            leaf svcAllMatch  {
                type  cml_data_types:CML_STRING_T {
                    length "0..255";
                }
                description "";
            } // END of svcAllMatch definition.

            leaf svcOvidMatch  {
                type  cml_data_types:CML_UINT16_T;
                description "";
            } // END of svcOvidMatch definition.

            leaf svcIvidMatch  {
                type  cml_data_types:CML_UINT16_T;
                description "";
            } // END of svcIvidMatch definition.

            leaf svcOvidMatchMax  {
                type  cml_data_types:CML_UINT16_T;
                description "";
            } // END of svcOvidMatchMax definition.

        } // End of svcMatchList-list

        list svcActionList {
            key "index";
            config false;
            description
                "svcActionList";
            leaf index  {
                type  cml_data_types:CML_UINT16_T;
                description "";
            } // END of index definition.

            leaf actionType  {
                type  cml_data_types:CML_STRING_T {
                    length "0..255";
                }
                description "";
            } // END of actionType definition.

            leaf actionVal  {
                type  cml_data_types:CML_UINT16_T;
                description "";
            } // END of actionVal definition.

            leaf actionTpid  {
                type  cml_data_types:CML_STRING_T {
                    length "0..255";
                }
                description "";
            } // END of actionTpid definition.

        } // End of svcActionList-list
    } // END of vctableRuntime definition.
    grouping vcTableCommonAttr {
        description
            "vcTableCommonAttr";
        leaf groupName  {
            type  cml_data_types:CML_STRING_T {
                length "0..255";
            }
            description "";
        } // END of groupName definition.

        leaf serviceTpid  {
            type  cml_data_types:CML_NSM_SVC_TPID_T;
            description "";
        } // END of serviceTpid definition.

        leaf groupId  {
            type  cml_data_types:CML_UINT32_T {
                 range "1..4294967295";
            }
            description "";
        } // END of groupId definition.

        leaf controlWord  {
            type  cml_data_types:CML_BOOL_T;
            default false;
            description "";
        } // END of controlWord definition.

        leaf tunnelId  {
            type  cml_data_types:CML_UINT32_T {
                 range "1..65535";
            }
            description "";
        } // END of tunnelId definition.

        leaf tunnelDir  {
            type  cml_data_types:CML_NSM_TUNNEL_DIRECTION_TYPE_T;
            default "forward";
            description "";
        } // END of tunnelDir definition.

        leaf manual  {
            type  cml_data_types:CML_BOOL_T;
            default false;
            description "";
        } // END of manual definition.

        leaf pwStatus  {
            type  cml_data_types:CML_BOOL_T;
            default false;
            description "";
        } // END of pwStatus definition.

        leaf pwStatusRefreshTimer  {
            type  cml_data_types:CML_UINT16_T {
                 range "0..65535";
            }
            default "600";
            description "";
        } // END of pwStatusRefreshTimer definition.

        leaf svlanId  {
            type  cml_data_types:CML_UINT16_T {
                 range "2..4094";
            }
            description "";
        } // END of svlanId definition.

        leaf raw  {
            type  cml_data_types:CML_BOOL_T;
            description "";
        } // END of raw definition.

        leaf tpId  {
            type  cml_data_types:CML_NSM_MPLS_TPID_T;
            description "";
        } // END of tpId definition.

        leaf passive  {
            if-feature feature_list:HAVE_MS_PW;
            type  cml_data_types:CML_BOOL_T;
            default false;
            description "";
        } // END of passive definition.

        leaf vccv  {
            if-feature feature_list:HAVE_VCCV;
            type  cml_data_types:CML_BOOL_T;
            default false;
            description "";
        } // END of vccv definition.

        leaf ccTypes  {
            type  cml_data_types:CML_UINT8_T;
            default "0";
            description "";
        } // END of ccTypes definition.

        leaf bfd  {
            type  cml_data_types:CML_BOOL_T;
            default false;
            description "";
        } // END of bfd definition.

        leaf cvTypes  {
            type  cml_data_types:CML_UINT8_T;
            default "0";
            description "";
        } // END of cvTypes definition.

    } // END of vcTableCommonAttr definition.
    grouping vcMsPwRuntime {
        description
            "vcMsPwRuntime";
        leaf vcId  {
            type  cml_data_types:CML_UINT32_T;
            config false;
            description "";
        } // END of vcId definition.

        leaf peerAddress  {
            type  cml_data_types:CML_STRING_T {
                length "0..255";
            }
            config false;
            description "";
        } // END of peerAddress definition.

        leaf owner  {
            type  cml_data_types:CML_STRING_T {
                length "0..255";
            }
            config false;
            description "";
        } // END of owner definition.

        leaf role  {
            type  cml_data_types:CML_STRING_T {
                length "0..255";
            }
            config false;
            description "";
        } // END of role definition.

        leaf virCircuitType  {
            type  cml_data_types:CML_STRING_T {
                length "0..255";
            }
            config false;
            description "";
        } // END of virCircuitType definition.

    } // END of vcMsPwRuntime definition.
    grouping vcInterfaceCommonAttr {
        description
            "vcInterfaceCommonAttr";
        leaf vcLinkMode  {
            type  cml_data_types:CML_NSM_MPLS_VCLINKMODE_T;
            default "primary";
            description "";
        } // END of vcLinkMode definition.

        leaf innerVlan  {
            type  cml_data_types:CML_UINT16_T {
                 range "1..4094";
            }
            description "";
        } // END of innerVlan definition.

        leaf svlanId  {
            type  cml_data_types:CML_UINT16_T {
                 range "1..4094";
            }
            description "";
        } // END of svlanId definition.

        leaf tpId  {
            type  cml_data_types:CML_NSM_MPLS_TPID_T;
            description "";
        } // END of tpId definition.

    } // END of vcInterfaceCommonAttr definition.
    grouping runtime-nhlfe-entry {
        description
            "runtimeCMLSEPnhlfeCMLSEPentry";
        leaf nhlfe_ix  {
            type  cml_data_types:CML_UINT32_T;
            config false;
            description "";
        } // END of nhlfe_ix definition.

        leaf xc_ix  {
            type  cml_data_types:CML_UINT32_T;
            config false;
            description "";
        } // END of xc_ix definition.

        leaf nhlfeOwner  {
            type  cml_data_types:CML_STRING_T {
                length "0..255";
            }
            config false;
            description "";
        } // END of nhlfeOwner definition.

        leaf rnh_addr  {
            type  cml_data_types:CML_STRING_T {
                length "0..255";
            }
            config false;
            description "";
        } // END of rnh_addr definition.

        leaf tx_bytes  {
            type  cml_data_types:CML_UINT32_T;
            config false;
            description "";
        } // END of tx_bytes definition.

        leaf tc_pkts  {
            type  cml_data_types:CML_UINT32_T;
            config false;
            description "";
        } // END of tc_pkts definition.

        leaf error_pkts  {
            type  cml_data_types:CML_UINT32_T;
            config false;
            description "";
        } // END of error_pkts definition.

        leaf discard_pkts  {
            type  cml_data_types:CML_UINT32_T;
            config false;
            description "";
        } // END of discard_pkts definition.

    } // END of runtime-nhlfe-entry definition.
    grouping runtime-xc-entry {
        description
            "runtimeCMLSEPxcCMLSEPentry";
        leaf xcEntryLFA  {
            type  cml_data_types:CML_STRING_T {
                length "0..255";
            }
            config false;
            description "";
        } // END of xcEntryLFA definition.

        leaf nhlfe_ix  {
            type  cml_data_types:CML_UINT32_T;
            config false;
            description "";
        } // END of nhlfe_ix definition.

        leaf xcOwner  {
            type  cml_data_types:CML_STRING_T {
                length "0..255";
            }
            config false;
            description "";
        } // END of xcOwner definition.

        leaf persistent  {
            type  cml_data_types:CML_BOOL_T;
            config false;
            description "";
        } // END of persistent definition.

        leaf admn_status  {
            type  cml_data_types:CML_MPLS_ADMN_STATUS_T;
            config false;
            description "";
        } // END of admn_status definition.

        leaf opr_status  {
            type  cml_data_types:CML_MPLS_OPR_STATUS_T;
            config false;
            description "";
        } // END of opr_status definition.

    } // END of runtime-xc-entry definition.
    grouping runtimeFtn {
        description
            "runtimeFtn";
        leaf row_status  {
            type  cml_data_types:CML_MPLS_ROW_STATUS_T;
            config false;
            description "";
        } // END of row_status definition.

        leaf owner  {
            type  cml_data_types:CML_STRING_T {
                length "0..255";
            }
            config false;
            description "";
        } // END of owner definition.

        leaf actionType  {
            type  cml_data_types:CML_STRING_T {
                length "0..255";
            }
            config false;
            description "";
        } // END of actionType definition.

        leaf exp_bit  {
            type  cml_data_types:CML_UINT32_T;
            config false;
            description "";
        } // END of exp_bit definition.

        leaf dscp_in  {
            type  cml_data_types:CML_STRING_T {
                length "0..255";
            }
            config false;
            description "";
        } // END of dscp_in definition.

        leaf protected_lsp_id  {
            type  cml_data_types:CML_UINT32_T;
            config false;
            description "";
        } // END of protected_lsp_id definition.

        leaf qos_resrc_id  {
            type  cml_data_types:CML_UINT32_T;
            config false;
            description "";
        } // END of qos_resrc_id definition.

        leaf sz_desc  {
            type  cml_data_types:CML_STRING_T {
                length "0..255";
            }
            config false;
            description "";
        } // END of sz_desc definition.

        leaf tesid  {
            type  cml_data_types:CML_UINT32_T;
            config false;
            description "";
        } // END of tesid definition.

        leaf matched_bytes  {
            type  cml_data_types:CML_UINT32_T;
            config false;
            description "";
        } // END of matched_bytes definition.

        leaf matched_pkts  {
            type  cml_data_types:CML_UINT32_T;
            config false;
            description "";
        } // END of matched_pkts definition.

        leaf tx_bytes  {
            type  cml_data_types:CML_UINT32_T;
            config false;
            description "";
        } // END of tx_bytes definition.

        leaf pushed_pkts  {
            type  cml_data_types:CML_UINT32_T;
            config false;
            description "";
        } // END of pushed_pkts definition.

        leaf bfd_flag  {
            type  cml_data_types:CML_MPLS_BFD_FLAG_T;
            config false;
            description "";
        } // END of bfd_flag definition.

    } // END of runtimeFtn definition.
    grouping lsp_dep_table {
        description
            "lspCMLSEPdepCMLSEPtable";
        leaf type  {
            type  cml_data_types:CML_STRING_T {
                length "0..255";
            }
            config false;
            description "";
        } // END of type definition.

        leaf clist-pointer  {
            type  cml_data_types:CML_STRING_T {
                length "0..255";
            }
            config false;
            description "";
        } // END of clist-pointer definition.

        leaf clist-count  {
            type  cml_data_types:CML_UINT32_T;
            config false;
            description "";
        } // END of clist-count definition.

        leaf clist-prefix  {
            type  cml_data_types:CML_STRING_T {
                length "0..255";
            }
            config false;
            description "";
        } // END of clist-prefix definition.


        list lsp_dep_confirm {
            key "confirm-pointer";
            config false;
            description
                "lspCMLSEPdepCMLSEPconfirm";
            leaf confirm-pointer  {
                type  cml_data_types:CML_STRING_T {
                    length "0..255";
                }
                description "";
            } // END of confirm-pointer definition.

            leaf confirm-type  {
                type  cml_data_types:CML_STRING_T {
                    length "0..255";
                }
                description "";
            } // END of confirm-type definition.

            leaf peerPrefix  {
                type  cml_data_types:CML_STRING_T {
                    length "0..255";
                }
                description "";
            } // END of peerPrefix definition.

            leaf mappedroute  {
                type  cml_data_types:CML_STRING_T {
                    length "0..255";
                }
                description "";
            } // END of mappedroute definition.

            leaf ftnfec  {
                type  cml_data_types:CML_STRING_T {
                    length "0..255";
                }
                description "";
            } // END of ftnfec definition.

            leaf vrffec  {
                type  cml_data_types:CML_STRING_T {
                    length "0..255";
                }
                description "";
            } // END of vrffec definition.

            leaf ilm_ix  {
                type  cml_data_types:CML_UINT32_T;
                description "";
            } // END of ilm_ix definition.

            leaf iif_ix  {
                type  cml_data_types:CML_UINT32_T;
                description "";
            } // END of iif_ix definition.

            leaf in_label  {
                type  cml_data_types:CML_UINT32_T;
                description "";
            } // END of in_label definition.

            leaf vc_id  {
                type  cml_data_types:CML_UINT32_T;
                description "";
            } // END of vc_id definition.

            leaf spokevcid  {
                type  cml_data_types:CML_UINT32_T;
                description "";
            } // END of spokevcid definition.

            leaf vpls_id  {
                type  cml_data_types:CML_UINT32_T;
                description "";
            } // END of vpls_id definition.

        } // End of lsp_dep_confirm-list
    } // END of lsp_dep_table definition.

    grouping  mplsInterface-grouping {
    description
        "mplsInterface";
    container mplsInterface {
        description
            "mplsInterface";
        leaf labelSwitching  {
            type  cml_data_types:CML_UINT16_T {
                 range "0..60000";
            }
            description "";
        } // END of labelSwitching definition.

        leaf vcMode  {
            type  cml_data_types:CML_NSM_MPLS_VCMODE_T;
            description "";
        } // END of vcMode definition.

        leaf vlanId  {
            type  cml_data_types:CML_UINT16_T {
                 range "1..4094";
            }
            description "";
        } // END of vlanId definition.


        list vcEtherInterface {
            key "ifVcName";
            description
                "vcEtherInterface";
            leaf ifVcName  {
                type  cml_data_types:CML_STRING_T {
                    length "0..255";
                }
                description "";
            } // END of ifVcName definition.

            leaf vcType  {
                type  cml_data_types:CML_NSM_MPLS_IF_VCTYPE_T;
                description "";
            } // END of vcType definition.

            leaf EntherVcType  {
                type  cml_data_types:CML_NSM_MPLS_IF_ETHER_VCTYPE_T;
                default "ethernet";
                description "";
            } // END of EntherVcType definition.

            leaf etherAction  {
                type  cml_data_types:NSM_VPLS_ETHER_ACTION_T;
                description "";
            } // END of etherAction definition.

            leaf svcIfName  {
                type  cml_data_types:CML_STRING_T {
                    length "0..255";
                }
                description "";
            } // END of svcIfName definition.

            uses vcInterfaceCommonAttr;
        } // End of vcEtherInterface-list

        list vcVlanInterface {
            key "ifVlanVcName";
            description
                "vcVlanInterface";
            leaf ifVlanVcName  {
                type  cml_data_types:CML_STRING_T {
                    length "0..255";
                }
                description "";
            } // END of ifVlanVcName definition.


            list vcVlan {
                key "vlanId";
                description
                    "vcVlan";
                leaf vlanId  {
                    type  cml_data_types:CML_UINT16_T {
                         range "1..4094";
                    }
                    description "";
                } // END of vlanId definition.

                leaf vlanAction  {
                    type  cml_data_types:NSM_VPLS_VLAN_ACTION_T;
                    description "";
                } // END of vlanAction definition.

                uses vcInterfaceCommonAttr;
            } // End of vcVlan-list
        } // End of vcVlanInterface-list

        list l2vpnVpwsInterface {
            if-feature feature_list:HAVE_UNI_CLI;
            if-feature feature_list:HAVE_MPLS_VC;
            key "l2vpnIfVpwsName";
            description
                "l2vpn-vpws Interface";
            leaf l2vpnIfVpwsName  {
                type  cml_data_types:CML_STRING_T {
                    length "0..255";
                }
                description "";
            } // END of l2vpnIfVpwsName definition.

            leaf vcType  {
                type  cml_data_types:CML_L2VPN_VC_TYPE_T;
                description "";
            } // END of vcType definition.

            leaf vcMode  {
                type  cml_data_types:CML_MPLS_VCLINKMODE_T;
                mandatory true;
                description "";
            } // END of vcMode definition.

        } // End of l2vpnVpwsInterface-list

        list l2vpnVlanVpwsInterface {
            if-feature feature_list:HAVE_UNI_CLI;
            if-feature feature_list:HAVE_MPLS_VC;
            key "l2vpnVlanIfVpwsName";
            description
                "l2vpn-vpws Interface";
            leaf l2vpnVlanIfVpwsName  {
                type  cml_data_types:CML_STRING_T {
                    length "0..255";
                }
                description "";
            } // END of l2vpnVlanIfVpwsName definition.


            list l2vpnVlan {
                key "vlanId";
                description
                    "l2vpnVlan";
                leaf vlanId  {
                    type  cml_data_types:CML_UINT16_T {
                         range "1..4094";
                    }
                    description "";
                } // END of vlanId definition.

                leaf vcMode  {
                    type  cml_data_types:CML_MPLS_VCLINKMODE_T;
                    mandatory true;
                    description "";
                } // END of vcMode definition.

            } // End of l2vpnVlan-list
        } // End of l2vpnVlanVpwsInterface-list
    } // END of mplsInterface-container definition.
    } // END of mplsInterface-container definition.

    grouping  mpls-grouping {
    description
        "mpls";
    container mpls {
        description
            "mpls";
        leaf localPktHandling  {
            type  cml_data_types:CML_BOOL_T;
            description "";
        } // END of localPktHandling definition.

        leaf propagateTtl  {
            type  cml_data_types:CML_BOOL_T;
            description "";
        } // END of propagateTtl definition.

        leaf mplsLog  {
            if-feature feature_list:HAVE_MPLS_FWD;
            type  cml_data_types:CML_NSM_MPLS_LOG_T;
            description "";
        } // END of mplsLog definition.

        leaf enMplsAllInterfaces  {
            type  cml_data_types:CML_BOOL_T;
            description "";
        } // END of enMplsAllInterfaces definition.

        leaf ingressTtlVal  {
            if-feature feature_list:NOT_HAVE_USER_HSL;
            type  cml_data_types:CML_UINT8_T {
                 range "0..255";
            }
            description "";
        } // END of ingressTtlVal definition.

        leaf dste  {
            type  cml_data_types:CML_BOOL_T;
            description "";
        } // END of dste definition.

        leaf egressTtlVal  {
            if-feature feature_list:NOT_HAVE_USER_HSL;
            type  cml_data_types:CML_UINT8_T {
                 range "0..255";
            }
            description "";
        } // END of egressTtlVal definition.

        leaf uniform  {
            type  cml_data_types:CML_BOOL_T;
            description "";
        } // END of uniform definition.

        leaf trapNotify  {
            type  cml_data_types:CML_ENABLE_DISABLE_T;
            default "disable";
            description "";
        } // END of trapNotify definition.


        list classExpBit {
            if-feature feature_list:HAVE_SWFWDR;
            if-feature feature_list:HAVE_DIFFSERV;
            key "supportedClassName";
            description
                "classExpBit";
            leaf supportedClassName  {
                type  cml_data_types:CML_STRING_T {
                    length "0..255";
                }
                description "";
            } // END of supportedClassName definition.

            leaf expbit  {
                type  cml_data_types:CML_UINT8_T {
                     range "0..7";
                }
                description "";
            } // END of expbit definition.

        } // End of classExpBit-list
    } // END of mpls-container definition.
    } // END of mpls-container definition.

    grouping  mplsInterfaceBw-grouping {
    description
        "mplsInterfaceBw";
    container mplsInterfaceBw {
        description
            "mplsInterfaceBw";
        leaf bandwidth  {
            if-feature feature_list:HAVE_TE;
            if-feature feature_list:NOT_IF_BANDWIDTH_INFO;
            type  cml_data_types:CML_STRING_T {
                length "0..255";
            }
            default "0";
            description "";
        } // END of bandwidth definition.

        leaf reservableBandwidthStr  {
            if-feature feature_list:HAVE_TE;
            type  cml_data_types:CML_STRING_T {
                length "0..255";
            }
            description "";
        } // END of reservableBandwidthStr definition.

        leaf-list ifAdminGrpName  {
            if-feature feature_list:HAVE_TE;
            type  cml_data_types:CML_STRING_T {
                length "0..255";
            }
            description "";
        } // END of ifAdminGrpName definition.

        leaf bandwidthConstraintMode  {
            if-feature feature_list:HAVE_TE;
            if-feature feature_list:HAVE_DSTE;
            type  cml_data_types:CML_STRING_T {
                length "0..255";
            }
            description "";
        } // END of bandwidthConstraintMode definition.


        list bandwidthConstraint {
            if-feature feature_list:HAVE_TE;
            if-feature feature_list:HAVE_DSTE;
            key "constraintName";
            description
                "set bandwidth constraint";
            leaf constraintName  {
                type  cml_data_types:CML_STRING_T {
                    length "0..255";
                }
                description "";
            } // END of constraintName definition.

            leaf bandwidthStr  {
                if-feature feature_list:HAVE_TE;
                if-feature feature_list:HAVE_DSTE;
                type  cml_data_types:CML_STRING_T {
                    length "0..255";
                }
                mandatory true;
                description "";
            } // END of bandwidthStr definition.

        } // End of bandwidthConstraint-list
    } // END of mplsInterfaceBw-container definition.
    } // END of mplsInterfaceBw-container definition.

    grouping  rib-ldp-count-grouping {
    description
        "ribCMLSEPldpCMLSEPcount";
    container rib-ldp-count {
        config false;
        description
            "ribCMLSEPldpCMLSEPcount";
        leaf ldp-count  {
            type  cml_data_types:CML_UINT32_T;
            description "";
        } // END of ldp-count definition.


        list rib-ldp {
            key "ldp-rib-index";
            config false;
            description
                "ribCMLSEPldp";
            leaf ldp-rib-index  {
                type  cml_data_types:CML_UINT32_T;
                description "";
            } // END of ldp-rib-index definition.

            leaf sessionAddress  {
                type  cml_data_types:CML_STRING_T {
                    length "0..255";
                }
                description "";
            } // END of sessionAddress definition.

            leaf rib-type  {
                type  cml_data_types:CML_STRING_T {
                    length "0..255";
                }
                description "";
            } // END of rib-type definition.

            leaf peer_label_space  {
                type  cml_data_types:CML_UINT32_T;
                description "";
            } // END of peer_label_space definition.

            leaf ftn-count  {
                type  cml_data_types:CML_UINT32_T;
                description "";
            } // END of ftn-count definition.

            leaf ilm-count  {
                type  cml_data_types:CML_UINT32_T;
                description "";
            } // END of ilm-count definition.

            leaf vc-count  {
                type  cml_data_types:CML_UINT32_T;
                description "";
            } // END of vc-count definition.

            leaf dep-ilm-count  {
                type  cml_data_types:CML_UINT32_T;
                description "";
            } // END of dep-ilm-count definition.

        } // End of rib-ldp-list
    } // END of rib-ldp-count-container definition.
    } // END of rib-ldp-count-container definition.

    grouping  rib-rsvp-count-grouping {
    description
        "ribCMLSEPrsvpCMLSEPcount";
    container rib-rsvp-count {
        config false;
        description
            "ribCMLSEPrsvpCMLSEPcount";
        leaf rsvp-count  {
            type  cml_data_types:CML_UINT32_T;
            description "";
        } // END of rsvp-count definition.


        list rib-rsvp {
            key "rsvp-rib-index";
            config false;
            description
                "ribCMLSEPrsvp";
            leaf rsvp-rib-index  {
                type  cml_data_types:CML_UINT32_T;
                description "";
            } // END of rsvp-rib-index definition.

            leaf trunk_id  {
                type  cml_data_types:CML_UINT32_T;
                description "";
            } // END of trunk_id definition.

            leaf lsp_id  {
                type  cml_data_types:CML_UINT32_T;
                description "";
            } // END of lsp_id definition.

            leaf ingress  {
                type  cml_data_types:CML_STRING_T {
                    length "0..255";
                }
                description "";
            } // END of ingress definition.

            leaf egress  {
                type  cml_data_types:CML_STRING_T {
                    length "0..255";
                }
                description "";
            } // END of egress definition.

            leaf rib-type  {
                type  cml_data_types:CML_STRING_T {
                    length "0..255";
                }
                description "";
            } // END of rib-type definition.

            leaf peer_label_space  {
                type  cml_data_types:CML_UINT32_T;
                description "";
            } // END of peer_label_space definition.

            leaf ftn-count  {
                type  cml_data_types:CML_UINT32_T;
                description "";
            } // END of ftn-count definition.

            leaf ilm-count  {
                type  cml_data_types:CML_UINT32_T;
                description "";
            } // END of ilm-count definition.

        } // End of rib-rsvp-list
    } // END of rib-rsvp-count-container definition.
    } // END of rib-rsvp-count-container definition.


}
