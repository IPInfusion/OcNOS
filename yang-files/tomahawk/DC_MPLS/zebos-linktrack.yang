/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-linktrack.yang
*
*/

submodule zebos-linktrack {

    belongs-to  zebos { prefix zebos; }

    import cml_data_types {
        prefix cml_data_types;
    }

    include zebos-interface;
    organization
        "IP Infusion Inc.";

    contact
        "Address: 3965 Freedom Circle, Suite 200, Santa Clara, CA 95054
        Phone: +1 408-400-1900
        E-mail: support@ipinfusion.com
        Web: http://www.ipinfusion.com/";

    description
        "Interface tracking configurations";


    revision "2018-06-21" {
        description " Initial Version.";
        reference "";
    }



    grouping interfaceTrack-grouping {
    description
        "Interface event tracking";
        list interfaceTrack {
            key "eventOspf";
            description
                "Interface event tracking";
            leaf eventOspf  {
                type  cml_data_types:CML_STRING_T {
                    length "0..255";
                }
                description "";
            } // END of eventOspf definition.

            leaf eventOspfMatch  {
                type  cml_data_types:CML_INT_TRACK_MATCH_TYPE_T;
                mandatory true;
                description "";
            } // END of eventOspfMatch definition.

            leaf-list eventNbr  {
                type  cml_data_types:CML_IPV4_ADDR_T;
                description "";
            } // END of eventNbr definition.


            list actionCost {
                key "actionCostIface";
                description
                    "Interface event tracking";
                leaf actionCostIface  {
                    type  cml_data_types:CML_STRING_T {
                        length "0..255";
                    }
                    description "";
                } // END of actionCostIface definition.

                leaf actionIfaceCost  {
                    type  cml_data_types:CML_UINT32_T {
                         range "1..65535";
                    }
                    mandatory true;
                    description "";
                } // END of actionIfaceCost definition.

            } // End of actionCost-list
        } // End of interfaceTrack-list
    } // END of interfaceTrack-grouping definition.


}
