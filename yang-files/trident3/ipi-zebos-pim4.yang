/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-zebos-pim4.yang
*
*/

submodule ipi-zebos-pim4 {

    belongs-to  ipi-zebos { prefix ipi-zebos; }

    import cml-data-types {
        prefix cml-data-types;
    }

    import feature-list {
        prefix feature-list;
    }

    include ipi-zebos-vrf;
    organization
        "IP Infusion Inc.";

    contact
        "Address: 3965 Freedom Circle, Suite 200, Santa Clara, CA 95054
        Phone: +1 408-400-1900
        E-mail: support@ipinfusion.com
        Web: http://www.ipinfusion.com/";

    description
        "";


    revision "2018-06-21" {
        description " Initial Version.";
        reference "";
    }



    grouping pim4Vrf-grouping {
    description
        "pim4Vrf";
        list pim4Vrf {
            key "vrfName";
            description
                "pim4Vrf";
            leaf vrfName  {
                type  cml-data-types:CML_STRING_T;
                description "";
            } // END of vrfName definition.

            leaf disableRegisterReachFlag  {
                type  cml-data-types:CML_BOOL_T;
                default true;
                description "";
            } // END of disableRegisterReachFlag definition.

            leaf registerRateLimit  {
                type  cml-data-types:CML_UINT16_T {
                     range "1..65535";
                }
                description "";
            } // END of registerRateLimit definition.

            leaf ignoreRpSet  {
                type  cml-data-types:CML_BOOL_T;
                description "";
            } // END of ignoreRpSet definition.

            leaf bidirEnable  {
                if-feature feature-list:HAVE_PIM_BIDIR;
                type  cml-data-types:CML_BOOL_T;
                description "";
            } // END of bidirEnable definition.

            leaf bidirOfferInterval  {
                if-feature feature-list:HAVE_PIM_BIDIR;
                type  cml-data-types:CML_INT32_T {
                     range "1..20000";
                }
                default "100";
                description "";
            } // END of bidirOfferInterval definition.

            leaf bidirIsMsec  {
                if-feature feature-list:HAVE_PIM_BIDIR;
                type  cml-data-types:CML_BOOL_T;
                description "";
            } // END of bidirIsMsec definition.

            leaf bidirOfferLimit  {
                if-feature feature-list:HAVE_PIM_BIDIR;
                type  cml-data-types:CML_UINT32_T {
                     range "4..100";
                }
                description "";
            } // END of bidirOfferLimit definition.

            leaf ssmAclDefaultFlag  {
                type  cml-data-types:CML_PIM_SSM_ACL_TYPE_T;
                description "";
            } // END of ssmAclDefaultFlag definition.

            leaf routerId  {
                type  cml-data-types:CML_IPV4_ADDR_T;
                description "";
            } // END of routerId definition.

            leaf ovrd_rp_cnt  {
                type  cml-data-types:CML_UINT32_T;
                config false;
                description "Count of override configured static RPs";
            } // END of ovrd_rp_cnt definition.

            leaf registerSuppressTime  {
                type  cml-data-types:CML_UINT16_T {
                     range "1..65535";
                }
                description "";
            } // END of registerSuppressTime definition.

            leaf keepalive  {
                type  cml-data-types:CML_UINT16_T;
                config false;
                description "SNMP set or get";
            } // END of keepalive definition.

            leaf registerKeepAliveTime  {
                type  cml-data-types:CML_UINT16_T {
                     range "1..65535";
                }
                description "";
            } // END of registerKeepAliveTime definition.

            leaf sptFlag  {
                type  cml-data-types:CML_BOOL_T;
                description "";
            } // END of sptFlag definition.

            leaf sptName  {
                type  cml-data-types:CML_STRING_T;
                description "";
            } // END of sptName definition.

            leaf sourceAddr  {
                type  cml-data-types:CML_IPV4_IFNAME_T;
                description "";
            } // END of sourceAddr definition.

            leaf acceptAclRegisterName  {
                type  cml-data-types:CML_STRING_T;
                description "";
            } // END of acceptAclRegisterName definition.

            leaf checksumFlag  {
                type  cml-data-types:CML_BOOL_T;
                description "";
            } // END of checksumFlag definition.

            leaf chksumAclName  {
                type  cml-data-types:CML_STRING_T;
                description "";
            } // END of chksumAclName definition.

            leaf joinPruneTime  {
                type  cml-data-types:CML_UINT32_T {
                     range "1..65535";
                }
                description "";
            } // END of joinPruneTime definition.

            leaf mrt_counter_xxrp  {
                type  cml-data-types:CML_UINT32_T;
                config false;
                description "Counters";
            } // END of mrt_counter_xxrp definition.

            leaf mrt_counter_xg  {
                type  cml-data-types:CML_UINT32_T;
                config false;
                description "Counters";
            } // END of mrt_counter_xg definition.

            leaf mrt_counter_sg  {
                type  cml-data-types:CML_UINT32_T;
                config false;
                description "Counters";
            } // END of mrt_counter_sg definition.

            leaf mrt_counter_sgrpt  {
                type  cml-data-types:CML_UINT32_T;
                config false;
                description "Counters";
            } // END of mrt_counter_sgrpt definition.

            leaf mrt_vif_counter_xxrp  {
                type  cml-data-types:CML_UINT32_T;
                config false;
                description "Counters";
            } // END of mrt_vif_counter_xxrp definition.

            leaf mrt_vif_counter_xg  {
                type  cml-data-types:CML_UINT32_T;
                config false;
                description "Counters";
            } // END of mrt_vif_counter_xg definition.

            leaf mrt_vif_counter_sg  {
                type  cml-data-types:CML_UINT32_T;
                config false;
                description "Counters";
            } // END of mrt_vif_counter_sg definition.

            leaf mrt_vif_counter_sgrpt  {
                type  cml-data-types:CML_UINT32_T;
                config false;
                description "Counters";
            } // END of mrt_vif_counter_sgrpt definition.

            leaf pim_out_asserts  {
                if-feature feature-list:HAVE_SNMP;
                type  cml-data-types:CML_UINT32_T;
                config false;
                description "SNMP out assert";
            } // END of pim_out_asserts definition.

            leaf pim_in_asserts  {
                if-feature feature-list:HAVE_SNMP;
                type  cml-data-types:CML_UINT32_T;
                config false;
                description "SNMP in assert";
            } // END of pim_in_asserts definition.


            list pimreg {
                key "regSgPrefix";
                config false;
                description
                    "Register State (at the DR)";
                leaf regSgPrefix  {
                    type  cml-data-types:CML_STRING_T;
                    description "Owning MRT entry";
                } // END of regSgPrefix definition.

                leaf regState  {
                    type  cml-data-types:CML_UINT8_T;
                    description "Register state";
                } // END of regState definition.

                leaf regLastRp  {
                    type  cml-data-types:CML_STRING_T;
                    description "Register Stop timer";
                } // END of regLastRp definition.

                leaf regCurrPkt  {
                    type  cml-data-types:CML_UINT32_T;
                    description "Register rate limiting";
                } // END of regCurrPkt definition.

            } // End of pimreg-list

            list ecmpbundle {
                if-feature feature-list:HAVE_PIM_ECMP_REDIRECT;
                key "bundleName";
                description
                    "ecmpbundle";
                leaf bundleName  {
                    type  cml-data-types:CML_STRING_T;
                    description "";
                } // END of bundleName definition.

                container viflist {
                    config false;
                    description
                        "viflist";
                    leaf ecmpcurnumblks  {
                        type  cml-data-types:CML_UINT32_T;
                        description "Number of blocks";
                    } // END of ecmpcurnumblks definition.

                    leaf ecmpbitmapblk  {
                        type  cml-data-types:CML_UINT32_T;
                        description "points to the map";
                    } // END of ecmpbitmapblk definition.

                } // END of viflist-container definition.
            } // End of ecmpbundle-list

            list pimNexthop {
                key "nexthopDestinationAddress";
                config false;
                description
                    "PIM nexthop cache";
                leaf nexthopDestinationAddress  {
                    type  cml-data-types:CML_STRING_T;
                    description "Owning route node";
                } // END of nexthopDestinationAddress definition.

                leaf nexthopDestType  {
                    type  cml-data-types:CML_UINT32_T;
                    description "Nexthop Status Flags";
                } // END of nexthopDestType definition.

                leaf nheSize  {
                    type  cml-data-types:CML_UINT32_T;
                    description "Nexthop entries";
                } // END of nheSize definition.

                leaf nexthopPreference  {
                    type  cml-data-types:CML_UINT32_T;
                    description "Mcast nexthop reference counter";
                } // END of nexthopPreference definition.

                leaf nexthopMetric  {
                    type  cml-data-types:CML_UINT32_T;
                    description "Metric associated with this next hop";
                } // END of nexthopMetric definition.

                leaf nexthopReferenceCount  {
                    type  cml-data-types:CML_UINT32_T;
                    description "Preference";
                } // END of nexthopReferenceCount definition.

                leaf nexthopRouteType  {
                    type  cml-data-types:CML_UINT8_T;
                    description "Route type of the RPF check route";
                } // END of nexthopRouteType definition.

                leaf nexthopRoutesubType  {
                    type  cml-data-types:CML_UINT8_T;
                    description "iBGP/eBGP used by MSDP";
                } // END of nexthopRoutesubType definition.

                leaf nexthopprefixlen  {
                    type  cml-data-types:CML_UINT8_T;
                    description "Prefix length of the RPF check route";
                } // END of nexthopprefixlen definition.

                leaf nexthopsafi  {
                    if-feature feature-list:HAVE_SNMP;
                    type  cml-data-types:CML_UINT8_T;
                    description "SAFI";
                } // END of nexthopsafi definition.

                leaf nexthopAddress  {
                    type  cml-data-types:CML_STRING_T;
                    description "";
                } // END of nexthopAddress definition.

                leaf nexthopifIndex  {
                    type  cml-data-types:CML_UINT32_T;
                    description "";
                } // END of nexthopifIndex definition.

                leaf nexthopName  {
                    type  cml-data-types:CML_STRING_T;
                    description "";
                } // END of nexthopName definition.


                list nexthop {
                    key "nhgateipv4";
                    config false;
                    description
                        "nhe_list";
                    leaf nhtype  {
                        type  cml-data-types:CML_UINT8_T;
                        description "";
                    } // END of nhtype definition.

                    leaf nhflags  {
                        type  cml-data-types:CML_UINT16_T;
                        description "";
                    } // END of nhflags definition.

                    leaf nhsnmproutetype  {
                        type  cml-data-types:CML_UINT8_T;
                        description "";
                    } // END of nhsnmproutetype definition.

                    leaf nhractivenexthop  {
                        type  cml-data-types:CML_UINT8_T;
                        description "";
                    } // END of nhractivenexthop definition.

                    leaf nhrtype  {
                        type  cml-data-types:CML_UINT8_T;
                        description "";
                    } // END of nhrtype definition.

                    leaf nhrifindex  {
                        type  cml-data-types:CML_UINT8_T;
                        description "";
                    } // END of nhrifindex definition.

                    leaf nhifindex  {
                        type  cml-data-types:CML_UINT8_T;
                        description "";
                    } // END of nhifindex definition.

                    leaf nhbfdifindex  {
                        type  cml-data-types:CML_UINT8_T;
                        description "";
                    } // END of nhbfdifindex definition.

                    leaf nhifname  {
                        type  cml-data-types:CML_STRING_T;
                        description "";
                    } // END of nhifname definition.

                    leaf nhgateipv4  {
                        type  cml-data-types:CML_STRING_T;
                        description "";
                    } // END of nhgateipv4 definition.

                    leaf nhgateipv6  {
                        type  cml-data-types:CML_STRING_T;
                        description "";
                    } // END of nhgateipv6 definition.

                } // End of nexthop-list
                container bgpmsgipv4route {
                    if-feature feature-list:HAVE_PIM_MSDP;
                    config false;
                    description
                        "Will have BGP info to reach the address";
                    leaf bgpprefix  {
                        type  cml-data-types:CML_STRING_T;
                        description "";
                    } // END of bgpprefix definition.

                    leaf bgpprefixlen  {
                        type  cml-data-types:CML_UINT8_T;
                        description "";
                    } // END of bgpprefixlen definition.

                    leaf bgppeeraddr  {
                        type  cml-data-types:CML_STRING_T;
                        description "";
                    } // END of bgppeeraddr definition.

                    leaf bgpifindex  {
                        type  cml-data-types:CML_UINT8_T;
                        description "";
                    } // END of bgpifindex definition.

                    leaf bgpnextHopaddr  {
                        type  cml-data-types:CML_STRING_T;
                        description "";
                    } // END of bgpnextHopaddr definition.

                    leaf bgpascount  {
                        type  cml-data-types:CML_UINT32_T;
                        description "";
                    } // END of bgpascount definition.

                    leaf bgpaspath  {
                        type  cml-data-types:CML_UINT8_T;
                        description "";
                    } // END of bgpaspath definition.

                } // END of bgpmsgipv4route-container definition.
            } // End of pimNexthop-list

            list pimMrt {
                key "mrtprefixsg";
                config false;
                description
                    "Mode independent top-level MRT structure";
                leaf mrtprefixsg  {
                    type  cml-data-types:CML_STRING_T;
                    description "";
                } // END of mrtprefixsg definition.

                leaf mrtprefixlen  {
                    type  cml-data-types:CML_UINT32_T;
                    description "";
                } // END of mrtprefixlen definition.

                leaf mrtmode  {
                    type  cml-data-types:CML_UINT8_T;
                    description "";
                } // END of mrtmode definition.

                leaf mrttype  {
                    type  cml-data-types:CML_UINT8_T;
                    description "";
                } // END of mrttype definition.

                leaf mrtflags  {
                    type  cml-data-types:CML_UINT32_T;
                    description "";
                } // END of mrtflags definition.

                leaf mrtuptime  {
                    type  cml-data-types:CML_STRING_T;
                    description "";
                } // END of mrtuptime definition.

                leaf mrtnhaddr  {
                    type  cml-data-types:CML_STRING_T;
                    description "";
                } // END of mrtnhaddr definition.

                leaf mrtnhifname  {
                    type  cml-data-types:CML_STRING_T;
                    description "";
                } // END of mrtnhifname definition.

                leaf mrtlastrp  {
                    type  cml-data-types:CML_STRING_T;
                    description "";
                } // END of mrtlastrp definition.

                leaf mrtjoinedOlist  {
                    type  cml-data-types:CML_STRING_T;
                    description "";
                } // END of mrtjoinedOlist definition.

                leaf mrtinheritedOlist  {
                    type  cml-data-types:CML_STRING_T;
                    description "";
                } // END of mrtinheritedOlist definition.

                leaf mrtprunedOlist  {
                    type  cml-data-types:CML_STRING_T;
                    description "";
                } // END of mrtprunedOlist definition.

                leaf mrtlocalOlist  {
                    type  cml-data-types:CML_STRING_T;
                    description "";
                } // END of mrtlocalOlist definition.

                leaf mrtsptswitch  {
                    type  cml-data-types:CML_BOOL_T;
                    description "";
                } // END of mrtsptswitch definition.

                leaf mrtOlist  {
                    type  cml-data-types:CML_STRING_T;
                    description "";
                } // END of mrtOlist definition.

                container pimmrtusstatexxrp {
                    config false;
                    description
                        "Upstream (*,*,RP) state";
                    leaf mrtusstate  {
                        type  cml-data-types:CML_STRING_T;
                        description "";
                    } // END of mrtusstate definition.

                    leaf mrtusJttimer  {
                        type  cml-data-types:CML_UINT32_T;
                        description "Join or Prune timer";
                    } // END of mrtusJttimer definition.

                    leaf mrtusLastRpfNbrAddr  {
                        type  cml-data-types:CML_STRING_T;
                        description "Last RPF neighbor";
                    } // END of mrtusLastRpfNbrAddr definition.

                    leaf mrtusLastRpNextHopAddr  {
                        type  cml-data-types:CML_STRING_T;
                        description "Last MRIB.nexthop(RP) Used to generate MRIB.nexthop(RP) changes";
                    } // END of mrtusLastRpNextHopAddr definition.

                } // END of pimmrtusstatexxrp-container definition.
                container pimmrtusstatexg {
                    config false;
                    description
                        "Upstream (*,G) state";
                    leaf mrtusxgstate  {
                        type  cml-data-types:CML_STRING_T;
                        description "";
                    } // END of mrtusxgstate definition.

                    leaf mrtusxgJttimer  {
                        type  cml-data-types:CML_UINT32_T;
                        description "Join or Prune timer";
                    } // END of mrtusxgJttimer definition.

                    leaf mrtusxglastrpfnbraddr  {
                        type  cml-data-types:CML_STRING_T;
                        description "Last RPF neighbor";
                    } // END of mrtusxglastrpfnbraddr definition.

                    leaf mrtusxgKatTimer  {
                        type  cml-data-types:CML_STRING_T;
                        description "(*,G) Keepalive timer";
                    } // END of mrtusxgKatTimer definition.

                    leaf mrtusxgrpusVifName  {
                        type  cml-data-types:CML_STRING_T;
                        description "This vif should always be in the olist. Also can't depend on last_rpf_nbr";
                    } // END of mrtusxgrpusVifName definition.

                    leaf mrtusxgrpusVifId  {
                        type  cml-data-types:CML_INT32_T;
                        description "This vif should always be in the olist. Also can't depend on last_rpf_nbr";
                    } // END of mrtusxgrpusVifId definition.

                } // END of pimmrtusstatexg-container definition.
            } // End of pimMrt-list

            list pimmrtfcr {
                key "mrtfcraddr";
                config false;
                description
                    "The per-source S Forwarding Record in the (*,G) state";
                leaf mrtfcraddr  {
                    type  cml-data-types:CML_STRING_T;
                    description "Address of the source S";
                } // END of mrtfcraddr definition.

                leaf mrtfcrkat  {
                    type  cml-data-types:CML_STRING_T;
                    description "KAT timer for FCR";
                } // END of mrtfcrkat definition.

                leaf mrtfcrinheritedOlist  {
                    type  cml-data-types:CML_STRING_T;
                    description "inherited_olist for each FCR in the (*,G) state";
                } // END of mrtfcrinheritedOlist definition.

            } // End of pimmrtfcr-list

            list staticconf {
                key "staticRpAddr";
                description
                    "List of static RP configuration";
                leaf staticRpAddr  {
                    type  cml-data-types:CML_IPV4_ADDR_T;
                    description "";
                } // END of staticRpAddr definition.

                leaf staticAccessListName  {
                    type  cml-data-types:CML_STRING_T;
                    description "";
                } // END of staticAccessListName definition.

                leaf overrideFlag  {
                    type  cml-data-types:CML_BOOL_T;
                    description "";
                } // END of overrideFlag definition.

                leaf bidirFlag  {
                    if-feature feature-list:HAVE_PIM_BIDIR;
                    type  cml-data-types:CML_BOOL_T;
                    description "";
                } // END of bidirFlag definition.

            } // End of staticconf-list

            list rpset {
                key "rpGrp";
                config false;
                description
                    "PIM static RP tree";
                leaf rpGrp  {
                    type  cml-data-types:CML_STRING_T;
                    description "Group Range Address.";
                } // END of rpGrp definition.

                leaf rpFlags  {
                    type  cml-data-types:CML_STRING_T;
                    description "Flags";
                } // END of rpFlags definition.

                leaf rpfragmentTag  {
                    type  cml-data-types:CML_UINT16_T;
                    description "BSM fragment tag";
                } // END of rpfragmentTag definition.

                leaf rpnumRp  {
                    type  cml-data-types:CML_UINT32_T;
                    description "Number of RPs in this RP set";
                } // END of rpnumRp definition.

                leaf rpsetExptime  {
                    type  cml-data-types:CML_STRING_T;
                    description "";
                } // END of rpsetExptime definition.

            } // End of rpset-list

            list anycastrp {
                key "anycastRendezvousPointAddr";
                description
                    "Anycast-rp structure";
                leaf anycastRendezvousPointAddr  {
                    type  cml-data-types:CML_IPV4_ADDR_T;
                    description "";
                } // END of anycastRendezvousPointAddr definition.

                leaf anycastFlag  {
                    type  cml-data-types:CML_UINT32_T;
                    config false;
                    description "Flags";
                } // END of anycastFlag definition.


                list anycastrpmem {
                    key "memberRendezvousPointAddr";
                    description
                        "Anycast-rp structure";
                    leaf memberRendezvousPointAddr  {
                        type  cml-data-types:CML_IPV4_ADDR_T;
                        description "";
                    } // END of memberRendezvousPointAddr definition.

                } // End of anycastrpmem-list

                list anycastmemberrp {
                    key "memberRpAddr";
                    config false;
                    description
                        "member_rp";
                    leaf memberRpAddr  {
                        type  cml-data-types:CML_STRING_T;
                        description "Member address";
                    } // END of memberRpAddr definition.

                    leaf memberFlag  {
                        type  cml-data-types:CML_UINT32_T;
                        description "Flags";
                    } // END of memberFlag definition.

                } // End of anycastmemberrp-list
            } // End of anycastrp-list

            list rpinfo {
                key "RpinfoAddr";
                config false;
                description
                    "Route table of PIM Bidir";
                leaf RpinfoAddr  {
                    type  cml-data-types:CML_STRING_T;
                    description "";
                } // END of RpinfoAddr definition.

                leaf dfelectionreferencecount  {
                    type  cml-data-types:CML_INT32_T;
                    description "";
                } // END of dfelectionreferencecount definition.

            } // End of rpinfo-list

            list denseMember {
                if-feature feature-list:HAVE_PIM_SMDM;
                key "denseGrp";
                description
                    "To configure explicit dense member";
                leaf denseGrp  {
                    type  cml-data-types:CML_IPV4_ADDR_T;
                    description "";
                } // END of denseGrp definition.

            } // End of denseMember-list
            container pimstat {
                config false;
                description
                    "pimstat";
                leaf join_sent  {
                    type  cml-data-types:CML_UINT32_T;
                    description "";
                } // END of join_sent definition.

                leaf join_rcvd  {
                    type  cml-data-types:CML_UINT32_T;
                    description "";
                } // END of join_rcvd definition.

                leaf reg_pkt_rcvd  {
                    type  cml-data-types:CML_UINT32_T;
                    description "";
                } // END of reg_pkt_rcvd definition.

                leaf reg_null_rcvd  {
                    type  cml-data-types:CML_UINT32_T;
                    description "";
                } // END of reg_null_rcvd definition.

                leaf regstop_sent  {
                    type  cml-data-types:CML_UINT32_T;
                    description "";
                } // END of regstop_sent definition.

                leaf regstop_rcvd  {
                    type  cml-data-types:CML_UINT32_T;
                    description "";
                } // END of regstop_rcvd definition.

            } // END of pimstat-container definition.
            container pimlastassert {
                config false;
                description
                    "SNMP";
                leaf ifindex  {
                    type  cml-data-types:CML_UINT32_T;
                    description "Interface index";
                } // END of ifindex definition.

                leaf group  {
                    type  cml-data-types:CML_STRING_T;
                    description "";
                } // END of group definition.

                leaf source  {
                    type  cml-data-types:CML_STRING_T;
                    description "";
                } // END of source definition.

            } // END of pimlastassert-container definition.
            container pimtrapobjects {
                config false;
                description
                    "SNMP";
                leaf nbr_loss_trap_period  {
                    type  cml-data-types:CML_UINT32_T;
                    description "";
                } // END of nbr_loss_trap_period definition.

                leaf nbr_loss_count  {
                    type  cml-data-types:CML_UINT32_T;
                    description "";
                } // END of nbr_loss_count definition.

                leaf invalid_reg_trap_period  {
                    type  cml-data-types:CML_UINT32_T;
                    description "";
                } // END of invalid_reg_trap_period definition.

                leaf invalid_reg_msgs_rcvd  {
                    type  cml-data-types:CML_UINT32_T;
                    description "";
                } // END of invalid_reg_msgs_rcvd definition.

                leaf invalid_reg_origin  {
                    type  cml-data-types:CML_STRING_T;
                    description "";
                } // END of invalid_reg_origin definition.

                leaf invalid_reg_group  {
                    type  cml-data-types:CML_STRING_T;
                    description "";
                } // END of invalid_reg_group definition.

                leaf invalid_reg_rp  {
                    type  cml-data-types:CML_STRING_T;
                    description "";
                } // END of invalid_reg_rp definition.

                leaf invalid_join_prune_trap_period  {
                    type  cml-data-types:CML_UINT32_T;
                    description "";
                } // END of invalid_join_prune_trap_period definition.

                leaf invalid_join_prune_msgs_rcvd  {
                    type  cml-data-types:CML_UINT32_T;
                    description "";
                } // END of invalid_join_prune_msgs_rcvd definition.

                leaf invalid_join_prune_origin  {
                    type  cml-data-types:CML_STRING_T;
                    description "";
                } // END of invalid_join_prune_origin definition.

                leaf invalid_join_prune_group  {
                    type  cml-data-types:CML_STRING_T;
                    description "";
                } // END of invalid_join_prune_group definition.

                leaf invalid_join_prune_rp  {
                    type  cml-data-types:CML_STRING_T;
                    description "";
                } // END of invalid_join_prune_rp definition.

                leaf rp_mapping_trap_period  {
                    type  cml-data-types:CML_UINT32_T;
                    description "";
                } // END of rp_mapping_trap_period definition.

                leaf rp_mapping_change_count  {
                    type  cml-data-types:CML_UINT32_T;
                    description "";
                } // END of rp_mapping_change_count definition.

                leaf interface_election_trap_period  {
                    type  cml-data-types:CML_UINT32_T;
                    description "";
                } // END of interface_election_trap_period definition.

                leaf interface_election_win_count  {
                    type  cml-data-types:CML_UINT32_T;
                    description "";
                } // END of interface_election_win_count definition.

                leaf invalid_join_prune_grp_mode  {
                    type  cml-data-types:CML_UINT8_T;
                    description "";
                } // END of invalid_join_prune_grp_mode definition.

            } // END of pimtrapobjects-container definition.
            container iamDrList {
                config false;
                description
                    "Bitmap: bit is set if I am DR on the vif";
                leaf curnumblks  {
                    type  cml-data-types:CML_UINT32_T;
                    description "Number of blocks";
                } // END of curnumblks definition.

                leaf bitmapblk  {
                    type  cml-data-types:CML_UINT32_T;
                    description "points to the map";
                } // END of bitmapblk definition.

            } // END of iamDrList-container definition.
            container msdp {
                description
                    "Handle the PIM MSDP API layer which will interact with the external MSDP daemon";
                leaf cflags  {
                    type  cml-data-types:CML_UINT32_T;
                    config false;
                    description "";
                } // END of cflags definition.

                leaf cifname  {
                    type  cml-data-types:CML_STRING_T;
                    description "";
                } // END of cifname definition.

                leaf saeCount  {
                    type  cml-data-types:CML_UINT32_T;
                    config false;
                    description "SAE count";
                } // END of saeCount definition.


                list saCache {
                    key "msdpsrcAddr";
                    description
                        "SA-CACHE";
                    leaf msdpsrcAddr  {
                        type  cml-data-types:CML_IPV4_ADDR_T;
                        description "";
                    } // END of msdpsrcAddr definition.

                    leaf msdpgrpAddr  {
                        type  cml-data-types:CML_IPV4_ADDR_T;
                        mandatory true;
                        description "";
                    } // END of msdpgrpAddr definition.

                    leaf msdpRpAddr  {
                        type  cml-data-types:CML_IPV4_ADDR_T;
                        mandatory true;
                        description "";
                    } // END of msdpRpAddr definition.

                } // End of saCache-list

                list msdpsacacheentry {
                    key "sarpAddr";
                    config false;
                    description
                        "SA-CACHE";
                    leaf sarpAddr  {
                        type  cml-data-types:CML_STRING_T;
                        description "RP addr";
                    } // END of sarpAddr definition.

                    leaf sarpfpeer  {
                        type  cml-data-types:CML_STRING_T;
                        description "The RPF peer which advertised this entry";
                    } // END of sarpfpeer definition.

                    leaf sarpflags  {
                        type  cml-data-types:CML_UINT32_T;
                        description "";
                    } // END of sarpflags definition.

                    leaf sarpuptime  {
                        type  cml-data-types:CML_STRING_T;
                        description "Uptime";
                    } // END of sarpuptime definition.

                    leaf sarpforwardcount  {
                        type  cml-data-types:CML_UINT8_T;
                        description "Prvent cache storms. The RP,S,G entry will be forwarded only twice in a SA Advertisement interval";
                    } // END of sarpforwardcount definition.

                } // End of msdpsacacheentry-list

                list msdpPasswd {
                    if-feature feature-list:HAVE_PIM_MSDP_API;
                    key "PasswdPeerAddr";
                    description
                        "List of MSDP peers and password";
                    leaf PasswdPeerAddr  {
                        type  cml-data-types:CML_IPV4_ADDR_T;
                        description "";
                    } // END of PasswdPeerAddr definition.

                    leaf msdppassword  {
                        type  cml-data-types:CML_STRING_T;
                        mandatory true;
                        description "";
                    } // END of msdppassword definition.

                } // End of msdpPasswd-list

                list msdpPeer {
                    if-feature feature-list:HAVE_PIM_MSDP_API;
                    key "PeerAddr";
                    description
                        "List of MSDP peers";
                    leaf PeerAddr  {
                        type  cml-data-types:CML_IPV4_ADDR_T;
                        description "";
                    } // END of PeerAddr definition.

                    leaf connectSrc  {
                        type  cml-data-types:CML_IPV4_IFNAME_T;
                        description "";
                    } // END of connectSrc definition.

                    leaf meshGrpName  {
                        type  cml-data-types:CML_STRING_T;
                        description "";
                    } // END of meshGrpName definition.

                    leaf prefixList  {
                        type  cml-data-types:CML_STRING_T;
                        description "";
                    } // END of prefixList definition.

                    leaf defaultPeerAddr  {
                        type  cml-data-types:CML_BOOL_T;
                        description "";
                    } // END of defaultPeerAddr definition.

                    leaf Peermeshgrpname  {
                        type  cml-data-types:CML_STRING_T;
                        config false;
                        description " Mesh group name";
                    } // END of Peermeshgrpname definition.

                    leaf peerflags  {
                        type  cml-data-types:CML_UINT32_T;
                        config false;
                        description "";
                    } // END of peerflags definition.

                    leaf peerasno  {
                        type  cml-data-types:CML_UINT32_T;
                        config false;
                        description "AS no from BGP. First time rpf_check logic will initiate a query";
                    } // END of peerasno definition.

                    leaf connretrycount  {
                        type  cml-data-types:CML_UINT32_T;
                        config false;
                        description "MSDP Peer FSM ConnectRetryCounter";
                    } // END of connretrycount definition.

                    leaf sockport  {
                        type  cml-data-types:CML_UINT32_T;
                        config false;
                        description "MSDP Peer Port Number";
                    } // END of sockport definition.

                    leaf peerrole  {
                        type  cml-data-types:CML_UINT32_T;
                        config false;
                        description "Active or Passive role";
                    } // END of peerrole definition.

                    leaf peerstate  {
                        type  cml-data-types:CML_UINT32_T;
                        config false;
                        description "State of current session";
                    } // END of peerstate definition.

                    leaf peeroldstate  {
                        type  cml-data-types:CML_UINT32_T;
                        config false;
                        description "State of current session";
                    } // END of peeroldstate definition.

                    leaf peerdesc  {
                        type  cml-data-types:CML_STRING_T;
                        config false;
                        description "Description of the peer";
                    } // END of peerdesc definition.

                    leaf peerhost  {
                        type  cml-data-types:CML_STRING_T;
                        config false;
                        description "Printable address of the peer";
                    } // END of peerhost definition.

                    leaf peerupdateIf  {
                        type  cml-data-types:CML_STRING_T;
                        config false;
                        description "";
                    } // END of peerupdateIf definition.

                    leaf peerversion  {
                        type  cml-data-types:CML_UINT8_T;
                        config false;
                        description "Peer BGP version";
                    } // END of peerversion definition.

                    leaf peerkeepalivein  {
                        type  cml-data-types:CML_UINT32_T;
                        config false;
                        description "Keepalive input count";
                    } // END of peerkeepalivein definition.

                    leaf peerkeepaliveout  {
                        type  cml-data-types:CML_UINT32_T;
                        config false;
                        description "Keepalive output count";
                    } // END of peerkeepaliveout definition.

                    leaf peerpasswdType  {
                        type  cml-data-types:CML_UINT8_T;
                        config false;
                        description "MSDP peer MD5 authentication setting";
                    } // END of peerpasswdType definition.

                    container peernotifyinfo {
                        config false;
                        description
                            "MSDP Peer Notification Information";
                        leaf peernoterrcode  {
                            type  cml-data-types:CML_UINT16_T;
                            description "";
                        } // END of peernoterrcode definition.

                        leaf peernoterrsubode  {
                            type  cml-data-types:CML_UINT16_T;
                            description "";
                        } // END of peernoterrsubode definition.

                        leaf peernoterrdirsent  {
                            type  cml-data-types:CML_UINT16_T;
                            description "";
                        } // END of peernoterrdirsent definition.

                        leaf peernoterrdlen  {
                            type  cml-data-types:CML_UINT32_T;
                            description "";
                        } // END of peernoterrdlen definition.

                        leaf peernoterrdata  {
                            type  cml-data-types:CML_UINT8_T;
                            description "";
                        } // END of peernoterrdata definition.

                    } // END of peernotifyinfo-container definition.
                } // End of msdpPeer-list
            } // END of msdp-container definition.
            container pimmrtusstatesg {
                config false;
                description
                    " Upstream (S,G) state";
                leaf mrtussgstate  {
                    type  cml-data-types:CML_STRING_T;
                    description "";
                } // END of mrtussgstate definition.

                leaf mrtussgJttimer  {
                    type  cml-data-types:CML_STRING_T;
                    description "Join or Prune timer";
                } // END of mrtussgJttimer definition.

                leaf mrtussglastrpfnbraddr  {
                    type  cml-data-types:CML_STRING_T;
                    description "Last RPF neighbor";
                } // END of mrtussglastrpfnbraddr definition.

                leaf mrtussgKatTimer  {
                    type  cml-data-types:CML_STRING_T;
                    description "(*,G) Keepalive timer";
                } // END of mrtussgKatTimer definition.

                leaf mrtussgsptBit  {
                    type  cml-data-types:CML_BOOL_T;
                    description "SPT bit";
                } // END of mrtussgsptBit definition.

                leaf mrtussgKatPeriod  {
                    type  cml-data-types:CML_UINT16_T;
                    description "(S,G) Keepalive perioed";
                } // END of mrtussgKatPeriod definition.

            } // END of pimmrtusstatesg-container definition.
            container pimmrtusstatesgrpt {
                config false;
                description
                    "Upstream (S,G,rpt) state";
                leaf mrtussgrptstate  {
                    type  cml-data-types:CML_STRING_T;
                    description "";
                } // END of mrtussgrptstate definition.

                leaf mrtussgrptOttimer  {
                    type  cml-data-types:CML_STRING_T;
                    description "(S,G,rpt) Override timer";
                } // END of mrtussgrptOttimer definition.

            } // END of pimmrtusstatesgrpt-container definition.
            container pimbsr {
                description
                    "BSR and C-RP information";
                leaf bsrRole  {
                    type  cml-data-types:CML_STRING_T;
                    config false;
                    description "Role";
                } // END of bsrRole definition.

                leaf bsrState  {
                    type  cml-data-types:CML_STRING_T;
                    config false;
                    description "";
                } // END of bsrState definition.

                leaf bsrInteropSet  {
                    type  cml-data-types:CML_BOOL_T;
                    description "";
                } // END of bsrInteropSet definition.

                leaf bsrifName  {
                    type  cml-data-types:CML_STRING_T;
                    default "NULL";
                    description "";
                } // END of bsrifName definition.

                leaf hashMask  {
                    type  cml-data-types:CML_UINT8_T {
                         range "0..32";
                    }
                    description "";
                } // END of hashMask definition.

                leaf candidatePriority  {
                    type  cml-data-types:CML_UINT8_T {
                         range "0..255";
                    }
                    description "";
                } // END of candidatePriority definition.

                leaf bsrAddress  {
                    type  cml-data-types:CML_STRING_T;
                    config false;
                    description "Bootstrap router's IP address";
                } // END of bsrAddress definition.

                leaf myHashMasklen  {
                    type  cml-data-types:CML_UINT32_T;
                    config false;
                    description "My configured hash mask length";
                } // END of myHashMasklen definition.

                leaf bsrPriority  {
                    type  cml-data-types:CML_UINT32_T;
                    config false;
                    description "Higher value is higher priority";
                } // END of bsrPriority definition.

                leaf bsrUpTime  {
                    type  cml-data-types:CML_STRING_T;
                    config false;
                    description "Uptime";
                } // END of bsrUpTime definition.

                leaf bsrExpiryTime  {
                    type  cml-data-types:CML_STRING_T;
                    config false;
                    description "Expirytime";
                } // END of bsrExpiryTime definition.


                list pimrpset {
                    key "bsrrpgrp";
                    config false;
                    description
                        "Group tree for RP Set";
                    leaf bsrrpgrp  {
                        type  cml-data-types:CML_STRING_T;
                        description "Group Range Address";
                    } // END of bsrrpgrp definition.

                    leaf bsrFlags  {
                        type  cml-data-types:CML_STRING_T;
                        description "Flags";
                    } // END of bsrFlags definition.

                    leaf bsrFragmentTag  {
                        type  cml-data-types:CML_UINT16_T;
                        description "BSM fragment tag";
                    } // END of bsrFragmentTag definition.

                    leaf bsrnumRp  {
                        type  cml-data-types:CML_UINT32_T;
                        description "Number of RPs in this RP set";
                    } // END of bsrnumRp definition.

                    leaf bsrrpsetExptime  {
                        type  cml-data-types:CML_STRING_T;
                        description "";
                    } // END of bsrrpsetExptime definition.


                    list pimrp {
                        key "rpAddr";
                        config false;
                        description
                            "Pointer to the beginning of RP list";
                        leaf rpAddr  {
                            type  cml-data-types:CML_STRING_T;
                            description "Address of RP";
                        } // END of rpAddr definition.

                        leaf rpFrom  {
                            type  cml-data-types:CML_STRING_T;
                            description "From";
                        } // END of rpFrom definition.

                        leaf rpMode  {
                            type  cml-data-types:CML_UINT8_T;
                            description "PIM Mode";
                        } // END of rpMode definition.

                        leaf rpType  {
                            type  cml-data-types:CML_UINT32_T;
                            description "Type of RP entry";
                        } // END of rpType definition.

                        leaf rpFlags  {
                            type  cml-data-types:CML_UINT32_T;
                            description "Flags";
                        } // END of rpFlags definition.

                        leaf rpPriority  {
                            type  cml-data-types:CML_UINT32_T;
                            description "Priority";
                        } // END of rpPriority definition.

                        leaf rpHoldTime  {
                            type  cml-data-types:CML_UINT16_T;
                            description "HoldTime";
                        } // END of rpHoldTime definition.

                        leaf rpUptime  {
                            type  cml-data-types:CML_STRING_T;
                            description "UPtime";
                        } // END of rpUptime definition.

                        leaf rpExptime  {
                            type  cml-data-types:CML_STRING_T;
                            description "ExpireTime";
                        } // END of rpExptime definition.

                        leaf rpRefCnt  {
                            type  cml-data-types:CML_INT32_T;
                            description "Reference count for embedded RP";
                        } // END of rpRefCnt definition.

                    } // End of pimrp-list
                } // End of pimrpset-list

                list pimcrp {
                    key "rpifName";
                    description
                        "List of C-RPs";
                    leaf rpifName  {
                        type  cml-data-types:CML_STRING_T;
                        description "";
                    } // END of rpifName definition.

                    leaf rpbidirFlag  {
                        if-feature feature-list:HAVE_PIM_BIDIR;
                        type  cml-data-types:CML_BOOL_T;
                        description "";
                    } // END of rpbidirFlag definition.

                    leaf groupAccessCtrlListName  {
                        type  cml-data-types:CML_STRING_T;
                        description "";
                    } // END of groupAccessCtrlListName definition.

                    leaf candidateAdvertiseInterval  {
                        type  cml-data-types:CML_INT32_T {
                             range "1..16383";
                        }
                        description "";
                    } // END of candidateAdvertiseInterval definition.

                    leaf rendezvousPointCandidatePriority  {
                        type  cml-data-types:CML_INT32_T {
                             range "0..255";
                        }
                        description "";
                    } // END of rendezvousPointCandidatePriority definition.

                    leaf bsrCandidateRpAddress  {
                        type  cml-data-types:CML_STRING_T;
                        config false;
                        description "C-RP address";
                    } // END of bsrCandidateRpAddress definition.

                    leaf bsrdirConfig  {
                        type  cml-data-types:CML_UINT8_T;
                        config false;
                        description "CRP configuration";
                    } // END of bsrdirConfig definition.

                    leaf bsrdirmode  {
                        type  cml-data-types:CML_UINT8_T;
                        config false;
                        description "Enable or Disable.Used by SNMP for RowStatus";
                    } // END of bsrdirmode definition.

                    leaf bsrAdvertisementInterval  {
                        type  cml-data-types:CML_UINT32_T;
                        config false;
                        description "C-RP Advertisement interval";
                    } // END of bsrAdvertisementInterval definition.

                    leaf bsrcrpHoldtime  {
                        type  cml-data-types:CML_UINT16_T;
                        config false;
                        description "C-RP holdtime";
                    } // END of bsrcrpHoldtime definition.

                    leaf bsrcrpExpTime  {
                        type  cml-data-types:CML_STRING_T;
                        config false;
                        description " C-RP expire time";
                    } // END of bsrcrpExpTime definition.

                    leaf bsrnumgrprange  {
                        type  cml-data-types:CML_UINT16_T;
                        config false;
                        description "C-RP holdtime";
                    } // END of bsrnumgrprange definition.

                    leaf bsrcrpbackoffcnt  {
                        type  cml-data-types:CML_UINT8_T;
                        config false;
                        description "Backoff cnt";
                    } // END of bsrcrpbackoffcnt definition.


                    list crpgrprng {
                        key "bsrcrpPrefix";
                        config false;
                        description
                            "Route table of grp_range";
                        leaf bsrcrpPrefix  {
                            type  cml-data-types:CML_STRING_T;
                            description "Group Range prefix";
                        } // END of bsrcrpPrefix definition.

                    } // End of crpgrprng-list
                } // End of pimcrp-list
            } // END of pimbsr-container definition.
        } // End of pim4Vrf-list
    } // END of pim4Vrf-grouping definition.


    grouping pim4Debug-grouping {
    description
        "pim4Debug";
        list pim4Debug {
            key "vrfName";
            description
                "pim4Debug";
            leaf vrId  {
                type  cml-data-types:CML_UINT32_T;
                default "0";
                description "";
            } // END of vrId definition.

            leaf vrfName  {
                type  cml-data-types:CML_STRING_T;
                description "";
            } // END of vrfName definition.

            leaf temprun  {
                type  cml-data-types:CML_BOOL_T;
                config false;
                description "";
            } // END of temprun definition.

            container debugmsdp {
                if-feature feature-list:HAVE_PIM_MSDP;
                description
                    "debugmsdp";
                leaf debugMsdp  {
                    if-feature feature-list:HAVE_PIM_MSDP;
                    type  cml-data-types:CML_BOOL_T;
                    description "";
                } // END of debugMsdp definition.

                leaf termdebugMsdp  {
                    if-feature feature-list:HAVE_PIM_MSDP;
                    type  cml-data-types:CML_BOOL_T;
                    description "";
                } // END of termdebugMsdp definition.

            } // END of debugmsdp-container definition.
            container debugType {
                description
                    "debugType";
                leaf debugType  {
                    type  cml-data-types:CML_PIM_DEBUG_TYPE_T;
                    description "";
                } // END of debugType definition.

                leaf debugtermType  {
                    type  cml-data-types:CML_PIM_DEBUG_TYPE_T;
                    description "";
                } // END of debugtermType definition.

            } // END of debugType-container definition.
        } // End of pim4Debug-list
    } // END of pim4Debug-grouping definition.

    grouping  pim4Interface-grouping {
    description
        "pim4Interface";
    container pim4Interface {
        description
            "pim4Interface";
        leaf if_index  {
            type  cml-data-types:CML_INT32_T;
            config false;
            description "VIF index When this index is negative, VIF is not yet registered";
        } // END of if_index definition.

        leaf if_config  {
            type  cml-data-types:CML_UINT32_T;
            config false;
            description "Configure";
        } // END of if_config definition.

        leaf if_flags  {
            type  cml-data-types:CML_UINT32_T;
            config false;
            description "Flags";
        } // END of if_flags definition.

        leaf vifExcludeGenIdSetFlag  {
            type  cml-data-types:CML_BOOL_T;
            description "";
        } // END of vifExcludeGenIdSetFlag definition.

        leaf vifBootstrapRouterBorderFlag  {
            type  cml-data-types:CML_BOOL_T;
            description "";
        } // END of vifBootstrapRouterBorderFlag definition.

        leaf vifUnicastBootstrapMechanismSetFlag  {
            type  cml-data-types:CML_BOOL_T;
            description "";
        } // END of vifUnicastBootstrapMechanismSetFlag definition.

        leaf vifMode  {
            type  cml-data-types:CML_PIM_MODE_TYPE_T;
            description "";
        } // END of vifMode definition.

        leaf passiveSet  {
            type  cml-data-types:CML_BOOL_T;
            default false;
            description "";
        } // END of passiveSet definition.

        leaf if_addr  {
            type  cml-data-types:CML_STRING_T;
            config false;
            description "VIF Primary Address";
        } // END of if_addr definition.

        leaf if_addr_global  {
            type  cml-data-types:CML_STRING_T;
            config false;
            description "VIF Primary Address";
        } // END of if_addr_global definition.

        leaf vifHelloInterval  {
            type  cml-data-types:CML_UINT32_T {
                 range "1..18724";
            }
            description "";
        } // END of vifHelloInterval definition.

        leaf hello_holdtime  {
            type  cml-data-types:CML_UINT32_T;
            config false;
            description "Hello holdtime";
        } // END of hello_holdtime definition.

        leaf vifaclNeighborFilterName  {
            type  cml-data-types:CML_STRING_T;
            description "";
        } // END of vifaclNeighborFilterName definition.

        leaf bidirAclNbrFilter  {
            if-feature feature-list:HAVE_PIM_BIDIR;
            type  cml-data-types:CML_STRING_T;
            description "";
        } // END of bidirAclNbrFilter definition.

        leaf bundleBindName  {
            if-feature feature-list:HAVE_PIM_ECMP_REDIRECT;
            type  cml-data-types:CML_STRING_T;
            description "";
        } // END of bundleBindName definition.

        leaf ecm_flow_count  {
            type  cml-data-types:CML_UINT32_T;
            config false;
            description "For ECMP traffic load balancing.The VIF with the least flow count will be chosen for new joins";
        } // END of ecm_flow_count definition.

        leaf dr_addr  {
            type  cml-data-types:CML_STRING_T;
            config false;
            description "VIF DR address";
        } // END of dr_addr definition.

        leaf vifStateRefreshOriginateInterval  {
            type  cml-data-types:CML_UINT16_T {
                 range "1..100";
            }
            description "";
        } // END of vifStateRefreshOriginateInterval definition.

        leaf vif_sr_ttl_min  {
            type  cml-data-types:CML_UINT8_T;
            config false;
            description "VIF SR Message TTL Min. Threshold (# of hops)";
        } // END of vif_sr_ttl_min definition.

        leaf t_effective_prop_dly  {
            type  cml-data-types:CML_INT16_T;
            config false;
            description "SM Effective Propogation Delay";
        } // END of t_effective_prop_dly definition.

        leaf vif_pd  {
            type  cml-data-types:CML_UINT16_T;
            config false;
            description "DM VIF Propagation-delay value (millisec)";
        } // END of vif_pd definition.

        leaf t_effective_ovrd_int  {
            type  cml-data-types:CML_UINT16_T;
            config false;
            description "SM Effective Override interval";
        } // END of t_effective_ovrd_int definition.

        leaf vif_oi  {
            type  cml-data-types:CML_UINT16_T;
            config false;
            description "DM VIF Override-Interval timer value (millisec)";
        } // END of vif_oi definition.

        leaf vif_pi  {
            type  cml-data-types:CML_UINT16_T;
            config false;
            description "DM VIF PruneLimit-Interval timer value(millisec)";
        } // END of vif_pi definition.

        leaf vif_gi  {
            type  cml-data-types:CML_UINT16_T;
            config false;
            description "DM VIF GraftRetry-Interval timer value(millisec)";
        } // END of vif_gi definition.

        leaf trig_hello_delay  {
            type  cml-data-types:CML_UINT16_T;
            config false;
            description "Triggered Hello timer";
        } // END of trig_hello_delay definition.

        leaf jp_tperiodic  {
            type  cml-data-types:CML_UINT16_T;
            config false;
            description "used for jt_timer";
        } // END of jp_tperiodic definition.

        leaf jp_holdtime  {
            type  cml-data-types:CML_UINT16_T;
            config false;
            description "per interface timer intervals, used in jp header";
        } // END of jp_holdtime definition.

        leaf t_override  {
            type  cml-data-types:CML_UINT16_T;
            config false;
            description "Randomized delay to prevent implosion of override messages";
        } // END of t_override definition.

        leaf t_suppressed  {
            type  cml-data-types:CML_UINT16_T;
            config false;
            description "Supression period";
        } // END of t_suppressed definition.

        leaf t_assert_override_int  {
            type  cml-data-types:CML_UINT16_T;
            config false;
            description "Per interface Assert time values";
        } // END of t_assert_override_int definition.

        leaf t_assert_time  {
            type  cml-data-types:CML_UINT16_T;
            config false;
            description "Per interface Assert time values";
        } // END of t_assert_time definition.


        list pimneighbor {
            key "nbr_addr";
            config false;
            description
                "PIM neighbors";
            leaf nbr_addr  {
                type  cml-data-types:CML_STRING_T;
                description "Neighbor's address";
            } // END of nbr_addr definition.

            leaf nbr_flags  {
                type  cml-data-types:CML_UINT32_T;
                description "Neighbor's Flags";
            } // END of nbr_flags definition.

            leaf nbr_uptime  {
                type  cml-data-types:CML_STRING_T;
                description "Neighbors' Uptime";
            } // END of nbr_uptime definition.

            leaf nbr_exptime  {
                type  cml-data-types:CML_STRING_T;
                description "Neighbors' Uptime";
            } // END of nbr_exptime definition.

            leaf nbr_gen_id  {
                type  cml-data-types:CML_UINT32_T;
                description "Neighbors' Generation ID.";
            } // END of nbr_gen_id definition.

            leaf nbr_sr_interval  {
                type  cml-data-types:CML_UINT8_T;
                description "Neighbors' SR Interval (secs)";
            } // END of nbr_sr_interval definition.

            leaf nbr_pd  {
                type  cml-data-types:CML_UINT16_T;
                description "Neighbors' LAN-prune-delay timer value (msecs)";
            } // END of nbr_pd definition.

            leaf nbr_oi  {
                type  cml-data-types:CML_UINT16_T;
                description "Neighbors' Override-Interval timer value (msecs)";
            } // END of nbr_oi definition.

            leaf jp_header_group_count  {
                type  cml-data-types:CML_UINT8_T;
                description "Have to update the no_of_groups while sending";
            } // END of jp_header_group_count definition.

            leaf group_count  {
                type  cml-data-types:CML_UINT8_T;
                description "Have to update the no_of_groups while sending";
            } // END of group_count definition.


            list jpbulkmessage {
                key "bulk_data";
                config false;
                description
                    "Join/Prune Message bulking";
                leaf bulk_data  {
                    type  cml-data-types:CML_STRING_T;
                    description "";
                } // END of bulk_data definition.

                leaf bulk_putp  {
                    type  cml-data-types:CML_INT32_T;
                    description "";
                } // END of bulk_putp definition.

                leaf bulk_getp  {
                    type  cml-data-types:CML_INT32_T;
                    description "";
                } // END of bulk_getp definition.

                leaf bulk_endp  {
                    type  cml-data-types:CML_INT32_T;
                    description "";
                } // END of bulk_endp definition.

                leaf bulk_size  {
                    type  cml-data-types:CML_INT32_T;
                    description "";
                } // END of bulk_size definition.

            } // End of jpbulkmessage-list
            container nbrpimpackethello {
                config false;
                description
                    "Hello variables which will be used for the packet transmission";
                leaf nbrhold_time  {
                    type  cml-data-types:CML_UINT16_T;
                    description "";
                } // END of nbrhold_time definition.

                leaf nbrlan_time  {
                    type  cml-data-types:CML_UINT16_T;
                    description "";
                } // END of nbrlan_time definition.

                leaf nbrpriroity  {
                    type  cml-data-types:CML_UINT32_T;
                    description "";
                } // END of nbrpriroity definition.

                leaf nbroverride_interval  {
                    type  cml-data-types:CML_UINT16_T;
                    description "";
                } // END of nbroverride_interval definition.

                leaf nbrgenid  {
                    type  cml-data-types:CML_UINT32_T;
                    description "";
                } // END of nbrgenid definition.

                leaf nbrrouter_id  {
                    type  cml-data-types:CML_STRING_T;
                    description "";
                } // END of nbrrouter_id definition.

                leaf nbrlocal_id  {
                    type  cml-data-types:CML_UINT32_T;
                    description "";
                } // END of nbrlocal_id definition.


                list nbraddrlist {
                    key "nbrif_addr";
                    config false;
                    description
                        "VIF Secondary Address List";
                    leaf nbrif_addr  {
                        type  cml-data-types:CML_STRING_T;
                        description "";
                    } // END of nbrif_addr definition.

                } // End of nbraddrlist-list
            } // END of nbrpimpackethello-container definition.
        } // End of pimneighbor-list

        list pimvifmember {
            key "vifprefixsg";
            config false;
            description
                "VIF Local Membership Table, Key: (G)";
            leaf vifprefixsg  {
                type  cml-data-types:CML_STRING_T;
                description "The key(G,S) for the table.";
            } // END of vifprefixsg definition.

            leaf vifprefixflags  {
                type  cml-data-types:CML_STRING_T;
                description "";
            } // END of vifprefixflags definition.

            leaf viflags  {
                type  cml-data-types:CML_UINT32_T;
                description "Flags";
            } // END of viflags definition.

            leaf viftype  {
                type  cml-data-types:CML_INT8_T;
                description "Local membership type";
            } // END of viftype definition.

            leaf vifstate  {
                type  cml-data-types:CML_INT8_T;
                description "Local membership state";
            } // END of vifstate definition.


            list srctable {
                key "srcinfo";
                config false;
                description
                    "P-Trie of membership source records";
                leaf srcinfo  {
                    type  cml-data-types:CML_INT32_T;
                    description "P-Trie of membership source records";
                } // END of srcinfo definition.

            } // End of srctable-list
        } // End of pimvifmember-list
        container pimpackethello {
            description
                "Hello variables which will be used for the packet transmission";
            leaf vifHelloHoldTimeInterval  {
                type  cml-data-types:CML_UINT32_T {
                     range "1..65535";
                }
                description "";
            } // END of vifHelloHoldTimeInterval definition.

            leaf vifPropagationDelay  {
                type  cml-data-types:CML_UINT16_T {
                     range "0..32767";
                }
                description "";
            } // END of vifPropagationDelay definition.

            leaf vifDesignatedRouterPriority  {
                type  cml-data-types:CML_UINT32_T {
                     range "0..4294967294";
                }
                description "";
            } // END of vifDesignatedRouterPriority definition.

            leaf override_interval  {
                type  cml-data-types:CML_UINT16_T;
                config false;
                description "";
            } // END of override_interval definition.

            leaf genid  {
                type  cml-data-types:CML_UINT32_T;
                config false;
                description "";
            } // END of genid definition.

            leaf router_id  {
                type  cml-data-types:CML_STRING_T;
                config false;
                description "";
            } // END of router_id definition.

            leaf local_id  {
                type  cml-data-types:CML_UINT32_T;
                config false;
                description "";
            } // END of local_id definition.


            list addrlist {
                key "if_addr";
                config false;
                description
                    "VIF Secondary Address List";
                leaf if_addr  {
                    type  cml-data-types:CML_STRING_T;
                    description "";
                } // END of if_addr definition.

            } // End of addrlist-list
        } // END of pimpackethello-container definition.
    } // END of pim4Interface-container definition.
    } // END of pim4Interface-container definition.


}
