/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-vrrp.yang
*
*/

submodule zebos-vrrp {

    belongs-to  zebos { prefix zebos; }

    import cml_data_types {
        prefix cml_data_types;
    }

    import feature_list {
        prefix feature_list;
    }

    include zebos-interface;
    organization
        "IP Infusion Inc.";

    contact
        "Address: 3965 Freedom Circle, Suite 200, Santa Clara, CA 95054
        Phone: +1 408-400-1900
        E-mail: support@ipinfusion.com
        Web: http://www.ipinfusion.com/";

    description
        "Virtual Router Redundancy Protocol Configurations";


    revision "2018-06-21" {
        description " Initial Version.";
        reference "";
    }



    grouping Vrrp4Instance-grouping {
    description
        "vrrp  related operations";
        list Vrrp4Instance {
            key "vrrpid";
            description
                "vrrp  related operations";
            leaf vrId  {
                type  cml_data_types:CML_UINT32_T;
                default "0";
                description "";
            } // END of vrId definition.

            leaf vrrpid  {
                type  cml_data_types:CML_INT32_T {
                     range "1..255";
                }
                description "";
            } // END of vrrpid definition.


            list vrrp4Interface {
                key "ifName";
                description
                    "vrrp4Interface";
                leaf ifName  {
                    type  cml_data_types:CML_STRING_T {
                        length "0..255";
                    }
                    description "";
                } // END of ifName definition.

                leaf sender_ipv4  {
                    type  cml_data_types:CML_STRING_T {
                        length "0..255";
                    }
                    config false;
                    description "Sender IP address";
                } // END of sender_ipv4 definition.

                leaf primary_addr  {
                    type  cml_data_types:CML_STRING_T {
                        length "0..255";
                    }
                    config false;
                    description "Primary IPv4 address";
                } // END of primary_addr definition.

                leaf adv_src_v4  {
                    type  cml_data_types:CML_STRING_T {
                        length "0..255";
                    }
                    config false;
                    description "Source IPv4 address of advertisement";
                } // END of adv_src_v4 definition.

                leaf ai_vip_v4  {
                    type  cml_data_types:CML_STRING_T {
                        length "0..255";
                    }
                    config false;
                    description "Virtual IP address";
                } // END of ai_vip_v4 definition.

                leaf operational_primary_ipv4  {
                    type  cml_data_types:CML_STRING_T {
                        length "0..255";
                    }
                    config false;
                    description "Operational primary IP address";
                } // END of operational_primary_ipv4 definition.

                leaf operational_master_ipv4  {
                    type  cml_data_types:CML_STRING_T {
                        length "0..255";
                    }
                    config false;
                    description "Operational master IP address";
                } // END of operational_master_ipv4 definition.

                leaf v2compatible  {
                    type  cml_data_types:CML_BOOL_T;
                    default false;
                    description "";
                } // END of v2compatible definition.

                leaf virtualip  {
                    type  cml_data_types:CML_IPV4_ADDR_T;
                    description "";
                } // END of virtualip definition.

                leaf conf_owner  {
                    type  cml_data_types:CML_BOOL_T;
                    description "";
                } // END of conf_owner definition.

                leaf operationalip  {
                    type  cml_data_types:CML_IPV4_ADDR_T;
                    description "";
                } // END of operationalip definition.

                uses vrrp_configurations;
            } // End of vrrp4Interface-list
        } // End of Vrrp4Instance-list
    } // END of Vrrp4Instance-grouping definition.


    grouping Vrrp6Instance-grouping {
    description
        "vrrp  related operations";
        list Vrrp6Instance {
            key "vrrp6id";
            description
                "vrrp  related operations";
            leaf vrId  {
                type  cml_data_types:CML_UINT32_T;
                default "0";
                description "";
            } // END of vrId definition.

            leaf vrrp6id  {
                type  cml_data_types:CML_INT32_T {
                     range "1..255";
                }
                description "";
            } // END of vrrp6id definition.


            list vrrp6Interface {
                key "ifName";
                description
                    "vrrp6Interface";
                leaf ifName  {
                    type  cml_data_types:CML_STRING_T {
                        length "0..255";
                    }
                    description "";
                } // END of ifName definition.

                leaf virtualip6  {
                    type  cml_data_types:CML_IPV6_ADDR_T;
                    description "";
                } // END of virtualip6 definition.

                leaf owner6  {
                    type  cml_data_types:CML_BOOL_T;
                    description "";
                } // END of owner6 definition.

                leaf operationalip6  {
                    type  cml_data_types:CML_IPV6_ADDR_T;
                    description "";
                } // END of operationalip6 definition.

                leaf operational_primary_ipv6  {
                    type  cml_data_types:CML_STRING_T {
                        length "0..255";
                    }
                    config false;
                    description "Operational primary IP address";
                } // END of operational_primary_ipv6 definition.

                leaf operational_master_ipv6  {
                    type  cml_data_types:CML_STRING_T {
                        length "0..255";
                    }
                    config false;
                    description "Operational master IP address";
                } // END of operational_master_ipv6 definition.

                leaf adv_src_6  {
                    type  cml_data_types:CML_STRING_T {
                        length "0..255";
                    }
                    config false;
                    description "Source IPv6 address of advertisement";
                } // END of adv_src_6 definition.

                leaf ai_vip_v6  {
                    type  cml_data_types:CML_STRING_T {
                        length "0..255";
                    }
                    config false;
                    description "Virtual IPv6 address";
                } // END of ai_vip_v6 definition.

                uses vrrp_configurations;
            } // End of vrrp6Interface-list
        } // End of Vrrp6Instance-list
    } // END of Vrrp6Instance-grouping definition.
    grouping vrrp_configurations {
        description
            "vrrpCMLSEPconfigurations";
        leaf circuitifName  {
            type  cml_data_types:CML_STRING_T {
                length "0..255";
            }
            description "";
        } // END of circuitifName definition.

        leaf prioritydelta  {
            type  cml_data_types:CML_UINT8_T {
                 range "1..253";
            }
            description "";
        } // END of prioritydelta definition.

        leaf enable  {
            type  cml_data_types:CML_ENABLE_DISABLE_T;
            description "";
        } // END of enable definition.

        leaf preemptmode  {
            type  cml_data_types:CML_VRRP_PREEMPT_MODE_T;
            default "true";
            description "";
        } // END of preemptmode definition.

        leaf priority  {
            type  cml_data_types:CML_UINT8_T {
                 range "1..254";
            }
            description "";
        } // END of priority definition.

        leaf switchback  {
            type  cml_data_types:CML_INT32_T {
                 range "1..500000";
            }
            description "";
        } // END of switchback definition.

        leaf advertiseinterval  {
            type  cml_data_types:CML_INT32_T {
                 range "5..4095";
            }
            default "100";
            description "";
        } // END of advertiseinterval definition.

        leaf acceptmode  {
            type  cml_data_types:CML_VRRP_ACCEPT_MODE_T;
            default "false";
            description "";
        } // END of acceptmode definition.

        leaf multicastMembership  {
            type  cml_data_types:CML_VRRP_MEMEBER_STATE;
            config false;
            description "state of Multicast membership on interface";
        } // END of multicastMembership definition.

        leaf vrrp_old_mac  {
            type  cml_data_types:CML_STRING_T {
                length "0..255";
            }
            config false;
            description "Old Mac for each VRRP session";
        } // END of vrrp_old_mac definition.

        leaf prev_state  {
            type  cml_data_types:CML_VRRP_STATE_T;
            config false;
            description "Previous State.";
        } // END of prev_state definition.

        leaf state  {
            type  cml_data_types:CML_VRRP_STATE_T;
            config false;
            description "vrrp state";
        } // END of state definition.

        leaf af_type  {
            type  cml_data_types:CML_INT8_T;
            config false;
            description "Address family";
        } // END of af_type definition.

        leaf oper_ip_status  {
            type  cml_data_types:CML_INT32_T;
            config false;
            description "";
        } // END of oper_ip_status definition.

        leaf ifindex  {
            type  cml_data_types:CML_INT32_T;
            config false;
            description "Interface. (ifindex)";
        } // END of ifindex definition.

        leaf owner  {
            type  cml_data_types:CML_BOOL_T;
            config false;
            description "flag for oper_pri_ip";
        } // END of owner definition.

        leaf run_priority  {
            type  cml_data_types:CML_INT16_T;
            config false;
            description "Priority";
        } // END of run_priority definition.

        leaf switch_back_delay_timer  {
            type  cml_data_types:CML_INT32_T;
            config false;
            description "Countdown timer for switch_back_delay";
        } // END of switch_back_delay_timer definition.

        leaf master_adv_int  {
            type  cml_data_types:CML_INT32_T;
            config false;
            description "Adv interval received from the master";
        } // END of master_adv_int definition.

        leaf vmac_mbyte_word  {
            type  cml_data_types:CML_STRING_T {
                length "0..255";
            }
            config false;
            description "Virtual Mac";
        } // END of vmac_mbyte_word definition.

        leaf timer  {
            type  cml_data_types:CML_INT32_T;
            config false;
            description "Countdown timer";
        } // END of timer definition.

        leaf vip_status  {
            type  cml_data_types:CML_BOOL_T;
            config false;
            description "Flags for virtual-ip";
        } // END of vip_status definition.

        leaf shutdown_flag  {
            type  cml_data_types:CML_BOOL_T;
            config false;
            description "Flags for shutdown flag";
        } // END of shutdown_flag definition.

        leaf skew_time  {
            type  cml_data_types:CML_INT32_T;
            config false;
            description "Skew time";
        } // END of skew_time definition.

        leaf master_down_int  {
            type  cml_data_types:CML_INT32_T;
            config false;
            description "Master down interval";
        } // END of master_down_int definition.

        leaf num_ip_addrs  {
            type  cml_data_types:CML_INT32_T;
            config false;
            description "Number of IP addresses";
        } // END of num_ip_addrs definition.

        leaf link_addr_deleted  {
            type  cml_data_types:CML_BOOL_T;
            config false;
            description "VRRP Link address";
        } // END of link_addr_deleted definition.

        leaf mc_status  {
            type  cml_data_types:CML_BOOL_T;
            config false;
            description " VRRP Circuit Failover machine status";
        } // END of mc_status definition.

        leaf mc_down_cnt  {
            type  cml_data_types:CML_INT32_T;
            config false;
            description " VRRP Circuit Failover machine down count";
        } // END of mc_down_cnt definition.

        leaf pri_zero_pkts_sent  {
            type  cml_data_types:CML_BOOL_T;
            config false;
            description "VRRP Circuit Failover priority";
        } // END of pri_zero_pkts_sent definition.

        leaf admin_state  {
            type  cml_data_types:CML_UINT8_T;
            config false;
            description "SNMP variables (admin_state)";
        } // END of admin_state definition.

        leaf rowstatus  {
            type  cml_data_types:CML_INT32_T;
            config false;
            description "SNMP variables";
        } // END of rowstatus definition.

        leaf primary_ipaddr_flag  {
            type  cml_data_types:CML_INT32_T;
            config false;
            description "SNMP variables";
        } // END of primary_ipaddr_flag definition.

        leaf storage_type  {
            type  cml_data_types:CML_INT32_T;
            config false;
            description "SNMP variables";
        } // END of storage_type definition.

        leaf accept_vip_installed  {
            type  cml_data_types:CML_INT32_T;
            config false;
            description "flag for Keeps track if non-owner installs VIP in accept mode";
        } // END of accept_vip_installed definition.

        leaf stats_become_master  {
            type  cml_data_types:CML_INT32_T;
            config false;
            description "Times state transitioned to master";
        } // END of stats_become_master definition.

        leaf stats_advt_rcvd  {
            type  cml_data_types:CML_INT32_T;
            config false;
            description " Advt rcvd";
        } // END of stats_advt_rcvd definition.

        leaf stats_advt_int_errors  {
            type  cml_data_types:CML_INT32_T;
            config false;
            description "Advt rcvd with wrong interval";
        } // END of stats_advt_int_errors definition.

        leaf stats_ip_ttl_errors  {
            type  cml_data_types:CML_INT32_T;
            config false;
            description "No. pkts rcvd with ttl != 255";
        } // END of stats_ip_ttl_errors definition.

        leaf stats_pri_zero_pkts_rcvd  {
            type  cml_data_types:CML_INT32_T;
            config false;
            description "No. pkts rcvd with priority=0";
        } // END of stats_pri_zero_pkts_rcvd definition.

        leaf stats_pri_zero_pkts_sent  {
            type  cml_data_types:CML_INT32_T;
            config false;
            description " No. pkts sent with priority=0";
        } // END of stats_pri_zero_pkts_sent definition.

        leaf stats_invalid_type_pkts_rcvd  {
            type  cml_data_types:CML_INT32_T;
            config false;
            description "No. pkts rcvd with invalid type";
        } // END of stats_invalid_type_pkts_rcvd definition.

        leaf stats_addr_list_errors  {
            type  cml_data_types:CML_INT32_T;
            config false;
            description "No. pkts rcvd with addr mismatch";
        } // END of stats_addr_list_errors definition.

        leaf stats_invalid_auth_type  {
            type  cml_data_types:CML_INT32_T;
            config false;
            description "No. pkts rcvd with unknown auth type";
        } // END of stats_invalid_auth_type definition.

        leaf stats_auth_type_mismatch  {
            type  cml_data_types:CML_INT32_T;
            config false;
            description "No. pkts rcvd with auth type mismatch";
        } // END of stats_auth_type_mismatch definition.

        leaf stats_ip_cnt_mismatch  {
            type  cml_data_types:CML_INT32_T;
            config false;
            description "No. of pkts rcvd with mismatch in Ip address count";
        } // END of stats_ip_cnt_mismatch definition.

        leaf stats_pkt_len_errors  {
            type  cml_data_types:CML_INT32_T;
            config false;
            description "Total num of pkts rcvd with pkt length less than length of VRRP header";
        } // END of stats_pkt_len_errors definition.

        leaf stats_disc_time  {
            type  cml_data_types:CML_UINT32_T;
            config false;
            description "Discontinuity Time";
        } // END of stats_disc_time definition.

        leaf mc_up_events  {
            type  cml_data_types:CML_INT32_T;
            config false;
            description "Monitored circuit up event";
        } // END of mc_up_events definition.

        leaf mc_down_events  {
            type  cml_data_types:CML_INT32_T;
            config false;
            description "Monitored circuit down event";
        } // END of mc_down_events definition.

        leaf new_master_reason  {
            type  cml_data_types:CML_INT32_T;
            config false;
            description "Reason to transit to the master";
        } // END of new_master_reason definition.

        leaf new_master_reason_next  {
            type  cml_data_types:CML_INT32_T;
            config false;
            description "Reason to transit that is to set";
        } // END of new_master_reason_next definition.

        leaf init_msg_code  {
            type  cml_data_types:CML_VRRP_INIT_MSG_CODE_T;
            config false;
            description "Vrrp init message types";
        } // END of init_msg_code definition.

        leaf garp_pkt_delay  {
            type  cml_data_types:CML_INT32_T;
            config false;
            description "Garp packet display";
        } // END of garp_pkt_delay definition.

        leaf garp_snd_flag  {
            type  cml_data_types:CML_BOOL_T;
            config false;
            description "Garp send flag";
        } // END of garp_snd_flag definition.

        container vrrp_advt_info {
            config false;
            description
                "Holds the VRRP Packet information";
            leaf ver_type  {
                type  cml_data_types:CML_UINT8_T;
                description "Version and Type";
            } // END of ver_type definition.

            leaf advert_vrid  {
                type  cml_data_types:CML_UINT8_T;
                description "VrId";
            } // END of advert_vrid definition.

            leaf advert_priority  {
                type  cml_data_types:CML_UINT8_T;
                description "Priority";
            } // END of advert_priority definition.

            leaf advert_num_ip_addrs  {
                type  cml_data_types:CML_UINT8_T;
                description "Number of IP addresses to backup";
            } // END of advert_num_ip_addrs definition.

            leaf advert_auth_type  {
                type  cml_data_types:CML_UINT8_T;
                description "Auth type";
            } // END of advert_auth_type definition.

            leaf advert_advt_int  {
                type  cml_data_types:CML_UINT8_T;
                description "Advertisement interval";
            } // END of advert_advt_int definition.

            leaf advert_cksum  {
                type  cml_data_types:CML_INT32_T;
                description "VRRP Checksum";
            } // END of advert_cksum definition.

            leaf advert_ipv4_address  {
                type  cml_data_types:CML_STRING_T {
                    length "0..255";
                }
                description "Virtual IP address";
            } // END of advert_ipv4_address definition.

            leaf advert_ipv6_address  {
                type  cml_data_types:CML_STRING_T {
                    length "0..255";
                }
                description "Virtual IPv6 address";
            } // END of advert_ipv6_address definition.

            leaf advert_auth_data  {
                type  cml_data_types:CML_STRING_T {
                    length "0..255";
                }
                description "Auth data";
            } // END of advert_auth_data definition.

        } // END of vrrp_advt_info-container definition.
    } // END of vrrp_configurations definition.

    grouping  vrrp-grouping {
    description
        "Virtual Router Redundancy Protocol Configurations";
    container vrrp {
        description
            "Virtual Router Redundancy Protocol Configurations";
        leaf vmac  {
            type  cml_data_types:CML_VRRP_VMAC_T;
            default "enable";
            description "";
        } // END of vmac definition.

        leaf compatible  {
            type  cml_data_types:CML_VRRP_VMAC_T;
            default "disable";
            description "";
        } // END of compatible definition.

        leaf notificationcntl  {
            type  cml_data_types:CML_INT32_T;
            config false;
            description "Flag For Trap Generation";
        } // END of notificationcntl definition.

        leaf sess_tbl_max  {
            type  cml_data_types:CML_INT32_T;
            config false;
            description "Instance table max value";
        } // END of sess_tbl_max definition.

        leaf sess_tbl_cnt  {
            type  cml_data_types:CML_INT32_T;
            config false;
            description "Instance table count value";
        } // END of sess_tbl_cnt definition.

        leaf vrrp_v4_sess_cnt  {
            type  cml_data_types:CML_UINT16_T;
            config false;
            description "IPv4 Session count";
        } // END of vrrp_v4_sess_cnt definition.

        leaf vrrp_v6_sess_cnt  {
            type  cml_data_types:CML_UINT16_T;
            config false;
            description "IPv6 Session count";
        } // END of vrrp_v6_sess_cnt definition.

        leaf vrrp_asso_tbl_max  {
            type  cml_data_types:CML_INT32_T;
            config false;
            description "Instance table associate max value";
        } // END of vrrp_asso_tbl_max definition.

        leaf vrrp_asso_tbl_cnt  {
            type  cml_data_types:CML_INT32_T;
            config false;
            description "Instance table associate count value";
        } // END of vrrp_asso_tbl_cnt definition.

        leaf vrrp_sock  {
            type  cml_data_types:CML_INT32_T;
            config false;
            description "Send/Recv socket (sock)";
        } // END of vrrp_sock definition.

        leaf vrrp_sock_net  {
            type  cml_data_types:CML_INT32_T;
            config false;
            description "VRRP forwarding (layer 2) sockets (sock_net)";
        } // END of vrrp_sock_net definition.

        leaf vrrp_sock_promisc  {
            type  cml_data_types:CML_INT32_T;
            config false;
            description "(sock_promisc)";
        } // END of vrrp_sock_promisc definition.

        leaf vrrp_sock_garp  {
            type  cml_data_types:CML_INT32_T;
            config false;
            description "(sock_garp)";
        } // END of vrrp_sock_garp definition.

        leaf sock_vrrp  {
            type  cml_data_types:CML_INT32_T;
            config false;
            description "(sock_vrrp)";
        } // END of sock_vrrp definition.

        leaf proto_err_reason  {
            type  cml_data_types:CML_INT32_T;
            config false;
            description "(proto_err_reason)";
        } // END of proto_err_reason definition.

        leaf sock_pf_ndadvt  {
            if-feature feature_list:HAVE_IPV6;
            type  cml_data_types:CML_INT32_T;
            config false;
            description "sock PF_PACKET for sending neighbor advrt (sock_pf_ndadvt)";
        } // END of sock_pf_ndadvt definition.

        leaf ipv6_sock  {
            if-feature feature_list:HAVE_IPV6;
            type  cml_data_types:CML_INT32_T;
            config false;
            description "(vrrp->ipv6_sock)";
        } // END of ipv6_sock definition.

        leaf icmpv6_sock  {
            if-feature feature_list:HAVE_IPV6;
            type  cml_data_types:CML_INT32_T;
            config false;
            description "(vrrp->icmppv6_sock)";
        } // END of icmpv6_sock definition.

    } // END of vrrp-container definition.
    } // END of vrrp-container definition.

    grouping  VrrpDebug-grouping {
    description
        "vrrp debug commands";
    container VrrpDebug {
        description
            "vrrp debug commands";
        leaf debugflag  {
            type  cml_data_types:CML_VRRP_DEBUG_T;
            description "";
        } // END of debugflag definition.

        leaf termDebugflag  {
            type  cml_data_types:CML_VRRP_DEBUG_T;
            description "";
        } // END of termDebugflag definition.

    } // END of VrrpDebug-container definition.
    } // END of VrrpDebug-container definition.


}
