/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-zebos-license.yang
*
*/

submodule ipi-zebos-license {

    belongs-to  ipi-zebos { prefix ipi-zebos; }

    import cml-data-types {
        prefix cml-data-types;
    }

    import feature-list {
        prefix feature-list;
    }

    include ipi-zebos-vrf;
    organization
        "IP Infusion Inc.";

    contact
        "Address: 3965 Freedom Circle, Suite 200, Santa Clara, CA 95054
        Phone: +1 408-400-1900
        E-mail: support@ipinfusion.com
        Web: http://www.ipinfusion.com/";

    description
        "license configurations";


    revision "2018-06-21" {
        description " Initial Version.";
        reference "";
    }


    grouping  licenseServer-grouping {
    description
        "licenseServer";
    container licenseServer {
        description
            "licenseServer";
        leaf serverUrl  {
            type  cml-data-types:CML_STRING_T;
            description "";
        } // END of serverUrl definition.

        leaf vrfName  {
            type  cml-data-types:CML_STRING_T;
            description "";
        } // END of vrfName definition.

    } // END of licenseServer-container definition.
    } // END of licenseServer-container definition.

    grouping  licenseInfo-grouping {
    description
        "license information";
    container licenseInfo {
        config false;
        description
            "license information";
        leaf slotCount  {
            if-feature feature-list:HAVE_COHERENT_OPTICS;
            type  cml-data-types:CML_UINT32_T;
            description "license slot count";
        } // END of slotCount definition.

        leaf licenseStatus  {
            type  cml-data-types:CML_STRING_T;
            description "license log message for all clients";
        } // END of licenseStatus definition.

        leaf licenseMsg  {
            type  cml-data-types:CML_RAW_STRING_T;
            description "license log message for all clients";
        } // END of licenseMsg definition.

        leaf serviceEndDate  {
            type  cml-data-types:CML_STRING_T;
            description "service end date";
        } // END of serviceEndDate definition.

        leaf remainingDays  {
            type  cml-data-types:CML_INT32_T;
            description "remaining days to license expiry or remaining lease";
        } // END of remainingDays definition.

        leaf deviceSoftware  {
            type  cml-data-types:CML_STRING_T;
            description "Device software";
        } // END of deviceSoftware definition.

        leaf nodeIdentifier  {
            type  cml-data-types:CML_STRING_T;
            description "Node id";
        } // END of nodeIdentifier definition.

        leaf validity  {
            type  cml-data-types:CML_STRING_T;
            description "Validity of license";
        } // END of validity definition.

        leaf type  {
            type  cml-data-types:CML_RAW_STRING_T;
            description "License Type";
        } // END of type definition.

    } // END of licenseInfo-container definition.
    } // END of licenseInfo-container definition.


}
