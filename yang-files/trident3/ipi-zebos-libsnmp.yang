/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-zebos-libsnmp.yang
*
*/

submodule ipi-zebos-libsnmp {

    belongs-to  ipi-zebos { prefix ipi-zebos; }

    import cml-data-types {
        prefix cml-data-types;
    }

    import feature-list {
        prefix feature-list;
    }

    include ipi-zebos-vrf;
    organization
        "IP Infusion Inc.";

    contact
        "Address: 3965 Freedom Circle, Suite 200, Santa Clara, CA 95054
        Phone: +1 408-400-1900
        E-mail: support@ipinfusion.com
        Web: http://www.ipinfusion.com/";

    description
        "snmp trap configurations";


    revision "2018-06-21" {
        description " Initial Version.";
        reference "";
    }


    grouping  snmpTrap-grouping {
    description
        "snmp-server trap configuration common for all modules";
    container snmpTrap {
        if-feature feature-list:HAVE_SNMP_AGENT;
        description
            "snmp-server trap configuration common for all modules";
        leaf-list traps  {
            type  cml-data-types:SNMP_TRAP_OPTIONS_T;
            description "";
        } // END of traps definition.

    } // END of snmpTrap-container definition.
    } // END of snmpTrap-container definition.

    grouping  debugAgentx-grouping {
    description
        "debugging for agentx";
    container debugAgentx {
        if-feature feature-list:HAVE_AGENTX;
        description
            "debugging for agentx";
        leaf debug  {
            type  cml-data-types:CML_AGENTX_DEBUG_TYPE_T;
            description "";
        } // END of debug definition.

    } // END of debugAgentx-container definition.
    } // END of debugAgentx-container definition.


}
