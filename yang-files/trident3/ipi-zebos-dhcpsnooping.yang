/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-zebos-dhcpsnooping.yang
*
*/

submodule ipi-zebos-dhcpsnooping {

    belongs-to  ipi-zebos { prefix ipi-zebos; }

    import cml-data-types {
        prefix cml-data-types;
    }

    import feature-list {
        prefix feature-list;
    }

    include ipi-zebos-interface;
    include ipi-zebos-bridge;
    organization
        "IP Infusion Inc.";

    contact
        "Address: 3965 Freedom Circle, Suite 200, Santa Clara, CA 95054
        Phone: +1 408-400-1900
        E-mail: support@ipinfusion.com
        Web: http://www.ipinfusion.com/";

    description
        "dhcpsnooping_configuration";


    revision "2018-06-21" {
        description " Initial Version.";
        reference "";
    }



    grouping dhcpSnooping-grouping {
    description
        "dhcp snooping attrs for non default bridge";
        list dhcpSnooping {
            key "bridgeId";
            description
                "dhcp snooping attrs for non default bridge";
            leaf bridgeId  {
                type  cml-data-types:CML_STRING_T {
                    length "1..32";
                }
                description "";
            } // END of bridgeId definition.

            leaf dhcpsEnable  {
                type  cml-data-types:CML_BOOL_T;
                description "";
            } // END of dhcpsEnable definition.

            leaf dhcpRatelimit  {
                type  cml-data-types:CML_STRING_T;
                description "";
            } // END of dhcpRatelimit definition.

            leaf dhcpsVerifyMac  {
                type  cml-data-types:CML_BOOL_T;
                description "";
            } // END of dhcpsVerifyMac definition.

            leaf dhcpsOption82  {
                type  cml-data-types:CML_BOOL_T;
                description "";
            } // END of dhcpsOption82 definition.

            leaf dhcpsWritedelay  {
                type  cml-data-types:CML_STRING_T;
                description "";
            } // END of dhcpsWritedelay definition.

            leaf dhcpsStrictVal  {
                type  cml-data-types:CML_BOOL_T;
                description "";
            } // END of dhcpsStrictVal definition.

            leaf vlanRange  {
                type  cml-data-types:CML_RANGE_T;
                description "";
            } // END of vlanRange definition.

            leaf daiEnable  {
                type  cml-data-types:CML_BOOL_T;
                description "";
            } // END of daiEnable definition.

            leaf validateFlag  {
                type  cml-data-types:CML_DHCP_VALIDATION_T;
                description "";
            } // END of validateFlag definition.

            leaf arpVlanrange  {
                type  cml-data-types:CML_RANGE_T;
                description "";
            } // END of arpVlanrange definition.


            list vlanSourceBindInfo {
                key "vlanId";
                description
                    "vlanSourceBindInfo";
                leaf vlanId  {
                    type  cml-data-types:CML_UINT32_T {
                         range "1..4094";
                    }
                    description "";
                } // END of vlanId definition.


                list macSourceBindInfo {
                    key "macAddr";
                    description
                        "macSourceBindInfo";
                    leaf macAddr  {
                        type  cml-data-types:CML_MAC_ADDR_T {
                            pattern "[0-9a-fA-F]{4}\\.[0-9a-f]{4}\\.[0-9a-f]{4}";
                            }
                            description "";
                        } // END of macAddr definition.

                        leaf ifName  {
                            type  cml-data-types:CML_STRING_T;
                            mandatory true;
                            description "";
                        } // END of ifName definition.

                        leaf ipv4  {
                            type  cml-data-types:CML_IPV4_ADDR_T;
                            description "";
                        } // END of ipv4 definition.

                        leaf ipv6  {
                            type  cml-data-types:CML_IPV6_ADDR_T;
                            description "";
                        } // END of ipv6 definition.

                } // End of macSourceBindInfo-list
            } // End of vlanSourceBindInfo-list

            list vlanDhcpBindInfo {
                key "vlan";
                description
                    "vlanDhcpBindInfo";
                leaf vlan  {
                    type  cml-data-types:CML_UINT32_T {
                         range "1..4094";
                    }
                    description "";
                } // END of vlan definition.


                list macDhcpBindInfo {
                    key "snoopingMacAddr";
                    description
                        "macDhcpBindInfo";
                    leaf snoopingMacAddr  {
                        type  cml-data-types:CML_MAC_ADDR_T {
                            pattern "[0-9a-fA-F]{4}\\.[0-9a-f]{4}\\.[0-9a-f]{4}";
                            }
                            description "";
                        } // END of snoopingMacAddr definition.

                        leaf name  {
                            type  cml-data-types:CML_STRING_T;
                            mandatory true;
                            description "";
                        } // END of name definition.

                        leaf snoopingIpv4  {
                            type  cml-data-types:CML_IPV4_ADDR_T;
                            description "";
                        } // END of snoopingIpv4 definition.

                        leaf snoopingIpv6  {
                            type  cml-data-types:CML_IPV6_ADDR_T;
                            description "";
                        } // END of snoopingIpv6 definition.

                } // End of macDhcpBindInfo-list
            } // End of vlanDhcpBindInfo-list
        } // End of dhcpSnooping-list
    } // END of dhcpSnooping-grouping definition.


    grouping defaultbridgedhcpsnooping-grouping {
    description
        "Group of dhcp snooping attribute for default bridge";
        list defaultbridgedhcpsnooping {
            if-feature feature-list:HAVE_DEFAULT_BRIDGE;
            key "bridgeId";
            description
                "Group of dhcp snooping attribute for default bridge";
            leaf bridgeId  {
                type  cml-data-types:CML_STRING_T;
                description "";
            } // END of bridgeId definition.

            leaf dhcpsEnable  {
                type  cml-data-types:CML_BOOL_T;
                description "";
            } // END of dhcpsEnable definition.

            leaf dhcpRatelimit  {
                type  cml-data-types:CML_STRING_T;
                description "";
            } // END of dhcpRatelimit definition.

            leaf dhcpsVerifyMac  {
                type  cml-data-types:CML_BOOL_T;
                description "";
            } // END of dhcpsVerifyMac definition.

            leaf dhcpsOption82  {
                type  cml-data-types:CML_BOOL_T;
                description "";
            } // END of dhcpsOption82 definition.

            leaf dhcpsWritedelay  {
                type  cml-data-types:CML_STRING_T;
                description "";
            } // END of dhcpsWritedelay definition.

            leaf dhcpsStrictVal  {
                type  cml-data-types:CML_BOOL_T;
                description "";
            } // END of dhcpsStrictVal definition.

            leaf vlanRange  {
                type  cml-data-types:CML_RANGE_T;
                description "";
            } // END of vlanRange definition.

            leaf daiEnable  {
                type  cml-data-types:CML_BOOL_T;
                description "";
            } // END of daiEnable definition.

            leaf validateFlag  {
                type  cml-data-types:CML_DHCP_VALIDATION_T;
                description "";
            } // END of validateFlag definition.

            leaf arpVlanrange  {
                type  cml-data-types:CML_RANGE_T;
                description "";
            } // END of arpVlanrange definition.


            list defaultBridgeVlanBindInfo {
                key "vlanId";
                description
                    "defaultBridgeVlanBindInfo";
                leaf vlanId  {
                    type  cml-data-types:CML_UINT32_T {
                         range "1..4094";
                    }
                    description "";
                } // END of vlanId definition.


                list defaultBridgeMacBindInfo {
                    key "macAddr";
                    description
                        "defaultBridgeMacBindInfo";
                    leaf macAddr  {
                        type  cml-data-types:CML_MAC_ADDR_T {
                            pattern "[0-9a-fA-F]{4}\\.[0-9a-f]{4}\\.[0-9a-f]{4}";
                            }
                            description "";
                        } // END of macAddr definition.

                        leaf ifName  {
                            type  cml-data-types:CML_STRING_T;
                            mandatory true;
                            description "";
                        } // END of ifName definition.

                        leaf ipv4  {
                            type  cml-data-types:CML_IPV4_ADDR_T;
                            description "";
                        } // END of ipv4 definition.

                        leaf ipv6  {
                            type  cml-data-types:CML_IPV6_ADDR_T;
                            description "";
                        } // END of ipv6 definition.

                } // End of defaultBridgeMacBindInfo-list
            } // End of defaultBridgeVlanBindInfo-list

            list DefaultBridgeVlanBind {
                key "vlan";
                description
                    "DefaultBridgeVlanBind";
                leaf vlan  {
                    type  cml-data-types:CML_UINT32_T {
                         range "1..4094";
                    }
                    description "";
                } // END of vlan definition.


                list DefaultBridgeMacaddrDhcpSnoopingBindInfo {
                    key "snoopingMacAddr";
                    description
                        "DefaultBridgeMacaddrDhcpSnoopingBindInfo";
                    leaf snoopingMacAddr  {
                        type  cml-data-types:CML_MAC_ADDR_T {
                            pattern "[0-9a-fA-F]{4}\\.[0-9a-f]{4}\\.[0-9a-f]{4}";
                            }
                            description "";
                        } // END of snoopingMacAddr definition.

                        leaf name  {
                            type  cml-data-types:CML_STRING_T;
                            mandatory true;
                            description "";
                        } // END of name definition.

                        leaf snoopingIpv4  {
                            type  cml-data-types:CML_IPV4_ADDR_T;
                            description "";
                        } // END of snoopingIpv4 definition.

                        leaf snoopingIpv6  {
                            type  cml-data-types:CML_IPV6_ADDR_T;
                            description "";
                        } // END of snoopingIpv6 definition.

                } // End of DefaultBridgeMacaddrDhcpSnoopingBindInfo-list
            } // End of DefaultBridgeVlanBind-list
        } // End of defaultbridgedhcpsnooping-list
    } // END of defaultbridgedhcpsnooping-grouping definition.


    grouping dhcp_interface-grouping {
    description
        "interface commands";
        list dhcp_interface {
            key "ifName";
            description
                "interface commands";
            leaf ifName  {
                type  cml-data-types:CML_STRING_T;
                description "";
            } // END of ifName definition.

            leaf trust  {
                type  cml-data-types:CML_BOOL_T;
                description "";
            } // END of trust definition.

            leaf dhcpSnoopingVlan  {
                type  cml-data-types:CML_BOOL_T;
                description "";
            } // END of dhcpSnoopingVlan definition.

            leaf accessGroupMode  {
                type  cml-data-types:CML_BOOL_T;
                description "";
            } // END of accessGroupMode definition.

        } // End of dhcp_interface-list
    } // END of dhcp_interface-grouping definition.

    grouping  debugDhcpSnooping-grouping {
    description
        "debug commands";
    container debugDhcpSnooping {
        description
            "debug commands";
        leaf debugTerm  {
            type  cml-data-types:CML_DHCPSNOOP_DEBUG_T;
            description "";
        } // END of debugTerm definition.

        leaf debugConf  {
            type  cml-data-types:CML_DHCPSNOOP_DEBUG_T;
            description "";
        } // END of debugConf definition.

    } // END of debugDhcpSnooping-container definition.
    } // END of debugDhcpSnooping-container definition.


}
