/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-zebos-ospf.yang
*
*/

submodule ipi-zebos-ospf {

    belongs-to  ipi-zebos { prefix ipi-zebos; }

    import cml-data-types {
        prefix cml-data-types;
    }

    import feature-list {
        prefix feature-list;
    }

    include ipi-zebos-vrf;
    include ipi-zebos-vrf;
    organization
        "IP Infusion Inc.";

    contact
        "Address: 3965 Freedom Circle, Suite 200, Santa Clara, CA 95054
        Phone: +1 408-400-1900
        E-mail: support@ipinfusion.com
        Web: http://www.ipinfusion.com/";

    description
        "Layer-3 ospf configurations";


    revision "2018-06-21" {
        description " Initial Version.";
        reference "";
    }



    grouping ospf-grouping {
    description
        "OSPF attributes for each ospf process id";
        list ospf {
            key "ospfProcessId";
            description
                "OSPF attributes for each ospf process id";
            leaf ospfUpTime  {
                type  cml-data-types:CML_STRING_T;
                config false;
                description "OSPF Up Time";
            } // END of ospfUpTime definition.

            leaf ddCountIn  {
                type  cml-data-types:CML_UINT16_T;
                config false;
                description "Number of received database descripton packet";
            } // END of ddCountIn definition.

            leaf ddCountOut  {
                type  cml-data-types:CML_UINT16_T;
                config false;
                description "Number of sent database descripton packet";
            } // END of ddCountOut definition.

            leaf externalLsaCount  {
                type  cml-data-types:CML_INT32_T;
                config false;
                description "Number of external (Type 5) lsa";
            } // END of externalLsaCount definition.

            leaf externalLsaChecksum  {
                type  cml-data-types:CML_STRING_T;
                config false;
                description "External LSA Checksum";
            } // END of externalLsaChecksum definition.

            leaf opaqueLsaCount  {
                type  cml-data-types:CML_INT32_T;
                config false;
                description "Number of opaque lsa";
            } // END of opaqueLsaCount definition.

            leaf opaqueLsaChecksum  {
                type  cml-data-types:CML_STRING_T;
                config false;
                description "Opaque LSA Checksum";
            } // END of opaqueLsaChecksum definition.

            leaf nonDefaulExternalLsaCount  {
                type  cml-data-types:CML_INT32_T;
                config false;
                description "Number of non default external lsa";
            } // END of nonDefaulExternalLsaCount definition.

            leaf lsdbExceedOverflowInterval  {
                type  cml-data-types:CML_UINT32_T;
                config false;
                description "Exceed Over flow interval for link state database";
            } // END of lsdbExceedOverflowInterval definition.

            leaf lsaOriginateCount  {
                type  cml-data-types:CML_UINT32_T;
                config false;
                description "Number of originated lsa";
            } // END of lsaOriginateCount definition.

            leaf lsaRecievedCount  {
                type  cml-data-types:CML_UINT32_T;
                config false;
                description "Number of recieved lsa";
            } // END of lsaRecievedCount definition.

            leaf areaCount  {
                type  cml-data-types:CML_INT32_T;
                config false;
                description "Number of area present";
            } // END of areaCount definition.

            leaf dsteStatus  {
                if-feature feature-list:HAVE_DSTE;
                type  cml-data-types:CML_STRING_T;
                config false;
                description "Destinition status";
            } // END of dsteStatus definition.

            leaf ospfPacketSendBuffer  {
                type  cml-data-types:CML_UINT32_T;
                config false;
                description "Buffer Size";
            } // END of ospfPacketSendBuffer definition.

            leaf ospfLsaBuffer  {
                type  cml-data-types:CML_UINT32_T;
                config false;
                description "Buffer Size";
            } // END of ospfLsaBuffer definition.

            leaf ospfPacketUnusedCount  {
                type  cml-data-types:CML_UINT32_T;
                config false;
                description "Number of unused ospf packet";
            } // END of ospfPacketUnusedCount definition.

            leaf ospfTotalPacketUnusedCount  {
                type  cml-data-types:CML_UINT32_T;
                config false;
                description "Number of total unused ospf packet";
            } // END of ospfTotalPacketUnusedCount definition.

            leaf ospfStatsUpTime  {
                type  cml-data-types:CML_STRING_T;
                config false;
                description "OSPF Stats Up Time";
            } // END of ospfStatsUpTime definition.

            leaf ospfRouterIdChanges  {
                type  cml-data-types:CML_UINT32_T;
                config false;
                description "OSPF Router ID";
            } // END of ospfRouterIdChanges definition.

            leaf ospfDRElectionCounter  {
                type  cml-data-types:CML_UINT32_T;
                config false;
                description "Designated router election counter";
            } // END of ospfDRElectionCounter definition.

            leaf ospfOlderLsaReceived  {
                type  cml-data-types:CML_UINT32_T;
                config false;
                description "Number of older recieved lsa";
            } // END of ospfOlderLsaReceived definition.

            leaf ospfNbrStateChangeCount  {
                type  cml-data-types:CML_UINT32_T;
                config false;
                description "Number of ospf neighbor change";
            } // END of ospfNbrStateChangeCount definition.

            leaf ospfNbrExpirationCount  {
                type  cml-data-types:CML_UINT32_T;
                config false;
                description "Neighborship Expired Count";
            } // END of ospfNbrExpirationCount definition.

            leaf ospfNbrBadLsReqsCount  {
                type  cml-data-types:CML_UINT32_T;
                config false;
                description "Number of badlsreq";
            } // END of ospfNbrBadLsReqsCount definition.

            leaf ospfNbrSeqNumMismatchCount  {
                type  cml-data-types:CML_UINT32_T;
                config false;
                description "Number of NbrSeqNumMismatch";
            } // END of ospfNbrSeqNumMismatchCount definition.

            leaf ospfSpfFull  {
                type  cml-data-types:CML_UINT32_T;
                config false;
                description "OSPF Spf Full";
            } // END of ospfSpfFull definition.

            leaf ospfSpfSummary  {
                type  cml-data-types:CML_UINT32_T;
                config false;
                description "OSPF Spf Summary";
            } // END of ospfSpfSummary definition.

            leaf ospfSpfExternal  {
                type  cml-data-types:CML_UINT32_T;
                config false;
                description "OSPF Spf External";
            } // END of ospfSpfExternal definition.

            leaf defaultRouterId  {
                type  cml-data-types:CML_STRING_T;
                config false;
                description "Default router ID";
            } // END of defaultRouterId definition.

            leaf ospfProcessId  {
                type  cml-data-types:CML_UINT16_T {
                     range "0..65535";
                }
                description "OSPF process ID";
            } // END of ospfProcessId definition.

            leaf vrfName  {
                type  cml-data-types:CML_STRING_T;
                description "VRF Name";
            } // END of vrfName definition.

            leaf routerId  {
                type  cml-data-types:CML_IPV4_ADDR_T;
                description "The router identifier";
            } // END of routerId definition.

            leaf floodReduction  {
                type  cml-data-types:CML_BOOL_T;
                description "Flood Reduction";
            } // END of floodReduction definition.

            leaf isCompitableRfc1583  {
                type  cml-data-types:CML_BOOL_T;
                description "TRUE will set and FALSE will unset";
            } // END of isCompitableRfc1583 definition.

            leaf isdbSummary  {
                type  cml-data-types:CML_BOOL_T;
                description "Whether Database Summary Enabled/Disabled";
            } // END of isdbSummary definition.

            leaf bfdEnabled  {
                if-feature feature-list:HAVE_BFD;
                type  cml-data-types:CML_BOOL_T;
                description "To enable Bidirectional Forwarding Detection (BFD)";
            } // END of bfdEnabled definition.

            leaf cspfEnabled  {
                if-feature feature-list:HAVE_OSPF_CSPF;
                type  cml-data-types:CML_BOOL_T;
                description "Whether cspf Enabled/Disabled";
            } // END of cspfEnabled definition.

            leaf cspfTieBreak  {
                if-feature feature-list:HAVE_OSPF_CSPF;
                type  cml-data-types:CML_OSPF6_CSPF_TYPE_T;
                description "To set the CSPF (Constrained Shortest Path First) tie-break method";
            } // END of cspfTieBreak definition.

            leaf cspfDefRetryInterval  {
                if-feature feature-list:HAVE_OSPF_CSPF;
                type  cml-data-types:CML_UINT16_T {
                     range "1..3600";
                }
                description "CSPF Default Retry Interval";
            } // END of cspfDefRetryInterval definition.

            leaf cspfBetterProtection  {
                if-feature feature-list:HAVE_GMPLS;
                if-feature feature-list:HAVE_OSPF_CSPF;
                type  cml-data-types:CML_BOOL_T;
                description "Whether cspfBetterProtection Enabled/Disabled";
            } // END of cspfBetterProtection definition.

            leaf vrfLiteEnable  {
                if-feature feature-list:HAVE_VRF_OSPF;
                type  cml-data-types:CML_BOOL_T;
                description "vrfLite Enabled/Disabled";
            } // END of vrfLiteEnable definition.

            leaf logAdjacencyDebugType  {
                type  cml-data-types:CML_STRING_T;
                description "Debug Option for log-adjacency-changes";
            } // END of logAdjacencyDebugType definition.

            leaf shutDown  {
                type  cml-data-types:CML_BOOL_T;
                description "ShutDown";
            } // END of shutDown definition.

            leaf areaBorderType  {
                type  cml-data-types:CML_OSPF_ABR_TYPE_T;
                description "OSPF Area Border Router Type";
            } // END of areaBorderType definition.

            leaf spfMinDelay  {
                type  cml-data-types:CML_UINT32_T {
                     range "0..2147483647";
                }
                default "500";
                description "The minimum delay in milliseconds between receiving a change to SPF calculation.Default minimum delay: 500 milliseconds";
            } // END of spfMinDelay definition.

            leaf spfMaxDelay  {
                type  cml-data-types:CML_UINT32_T {
                     range "0..2147483647";
                }
                default "50000";
                description "The maximum delay in milliseconds between receiving a change to SPF calculation.Default maximum delay: 50000 milliseconds (50 seconds)";
            } // END of spfMaxDelay definition.

            leaf throttleTimersStartDelay  {
                type  cml-data-types:CML_UINT32_T {
                     range "0..600000";
                }
                default "0";
                description "Start interval: The minimum delay in milliseconds for the generation of LSAs. The first instance of LSA is always generated immediately upon a local OSPF topology change.The generation of the next LSA is not before the start interval.Default start interval: 0 milliseconds";
            } // END of throttleTimersStartDelay definition.

            leaf throttleMinInterval  {
                type  cml-data-types:CML_UINT32_T {
                     range "1..600000";
                }
                default "5000";
                description "Hold interval: The hold time in milliseconds. This value is used to calculate the subsequent rate limiting times for LSA generation.Default hold interval: 5000 milliseconds";
            } // END of throttleMinInterval definition.

            leaf throttleTimersMaxDelay  {
                type  cml-data-types:CML_UINT32_T {
                     range "1..600000";
                }
                default "5000";
                description "Maximum interval: The maximum wait time in milliseconds between generation of the same LSA.Default maximum interval: 5000 milliseconds";
            } // END of throttleTimersMaxDelay definition.

            leaf lsaMinArrival  {
                type  cml-data-types:CML_UINT32_T {
                     range "0..600000";
                }
                default "1000";
                description "minimum time interval in between two dupicate lsa. Default value is 1000 miliseconds (1 sec)";
            } // END of lsaMinArrival definition.

            leaf referenceBandwidth  {
                type  cml-data-types:CML_INT32_T {
                     range "1..4294967";
                }
                default "100";
                description "Reference Bandwidth";
            } // END of referenceBandwidth definition.

            leaf maxDBDescriptor  {
                type  cml-data-types:CML_UINT16_T {
                     range "1..65535";
                }
                default "64";
                description "Maximum Database Descriptor";
            } // END of maxDBDescriptor definition.

            leaf restartMethod  {
                if-feature feature-list:HAVE_RESTART;
                type  cml-data-types:CML_BOOL_T;
                description "Restart Method";
            } // END of restartMethod definition.

            leaf restartMethodlls  {
                if-feature feature-list:HAVE_RESTART;
                type  cml-data-types:CML_BOOL_T;
                description "Restart Method lls";
            } // END of restartMethodlls definition.

            leaf isCapabilityOpaque  {
                if-feature feature-list:HAVE_OPAQUE_LSA;
                type  cml-data-types:CML_BOOL_T;
                description "True if opaque capable else set to false";
            } // END of isCapabilityOpaque definition.

            leaf isCapabilityTe  {
                if-feature feature-list:HAVE_OSPF_TE;
                type  cml-data-types:CML_OSPF_CAPABILITY_TE_T;
                description "True if set else false";
            } // END of isCapabilityTe definition.

            leaf metricValue  {
                type  cml-data-types:CML_UINT32_T {
                     range "1..16777214";
                }
                default "2";
                description "Metric Value";
            } // END of metricValue definition.

            leaf lsdbExternalLimit  {
                if-feature feature-list:HAVE_OSPF_DB_OVERFLOW;
                type  cml-data-types:CML_UINT32_T {
                     range "0..2147483647";
                }
                description "LSDB External Limit";
            } // END of lsdbExternalLimit definition.

            leaf exitOverflowInterval  {
                if-feature feature-list:HAVE_OSPF_DB_OVERFLOW;
                type  cml-data-types:CML_UINT32_T {
                     range "0..65535";
                }
                default "0";
                description "Exit Overflow Interval: Default value set to 0";
            } // END of exitOverflowInterval definition.

            leaf lsdbLimit  {
                type  cml-data-types:CML_UINT32_T {
                     range "0..4294967294";
                }
                description "LSDB Limit";
            } // END of lsdbLimit definition.

            leaf lsdbLimitType  {
                type  cml-data-types:CML_OSPF_ACTION_TYPE_T;
                default "hard";
                description "lsdb Limit Type: default type is hard";
            } // END of lsdbLimitType definition.

            leaf maxAreaLimit  {
                type  cml-data-types:CML_UINT32_T {
                     range "1..4294967294";
                }
                description "Maximim configurted area limit";
            } // END of maxAreaLimit definition.

            leaf ospfmaxUnusePackets  {
                type  cml-data-types:CML_UINT32_T {
                     range "0..65535";
                }
                default "200";
                description "Maximum unused ospf packet value: default value is 200";
            } // END of ospfmaxUnusePackets definition.

            leaf lsaunuseMax  {
                type  cml-data-types:CML_UINT16_T {
                     range "0..65535";
                }
                description "Unused Maximum LSA";
            } // END of lsaunuseMax definition.

            leaf refreshTimer  {
                type  cml-data-types:CML_UINT32_T {
                     range "10..1800";
                }
                default "10";
                description "Interval in which updated lsa will be flooded again";
            } // END of refreshTimer definition.

            leaf isP2pRfcIncompatible  {
                type  cml-data-types:CML_BOOL_T;
                description "True if set else false";
            } // END of isP2pRfcIncompatible definition.

            leaf isFrrSet  {
                if-feature feature-list:HAVE_OSPF_LFA;
                type  cml-data-types:CML_BOOL_T;
                description "True if set else false";
            } // END of isFrrSet definition.

            leaf srMpls  {
                if-feature feature-list:HAVE_SR_MPLS;
                type  cml-data-types:CML_BOOL_T;
                description "True if set else false";
            } // END of srMpls definition.

            leaf ospfsrgbBase  {
                type  cml-data-types:CML_INT32_T {
                     range "16000..23999";
                }
                description "Segment-Routing global block base value";
            } // END of ospfsrgbBase definition.

            leaf ospfsrgbRangeSize  {
                if-feature feature-list:HAVE_SR_MPLS;
                type  cml-data-types:CML_INT32_T {
                     range "16000..23999";
                }
                description "Segment-Routing global block range size";
            } // END of ospfsrgbRangeSize definition.

            leaf adminDistance  {
                type  cml-data-types:CML_INT32_T {
                     range "1..255";
                }
                description "Administrative Distance";
            } // END of adminDistance definition.


            list ospfInterfaceNeighbor {
                key "ospfNbrIfname";
                config false;
                description
                    "ospfInterfaceNeighbor";
                leaf ospfNbrIfname  {
                    type  cml-data-types:CML_STRING_T;
                    description "Interface Name";
                } // END of ospfNbrIfname definition.

                leaf ospfAreaId  {
                    type  cml-data-types:CML_STRING_T;
                    description "Area ID";
                } // END of ospfAreaId definition.


                list ospfNeighborRuntime {
                    key "ospfNbrRouterId";
                    config false;
                    description
                        "ospfNeighborRuntime";
                    leaf ospfNbrRouterId  {
                        type  cml-data-types:CML_STRING_T;
                        description "Router ID";
                    } // END of ospfNbrRouterId definition.

                    leaf ospfNbrOptions  {
                        type  cml-data-types:CML_STRING_T;
                        description "OSPF Neighbor Option Field";
                    } // END of ospfNbrOptions definition.

                    leaf ospfNeighborState  {
                        type  cml-data-types:CML_STRING_T;
                        description "OSPF Neighbor State";
                    } // END of ospfNeighborState definition.

                    leaf ospfNbrEvents  {
                        type  cml-data-types:CML_UINT32_T;
                        description "OSPF Neighbor Events";
                    } // END of ospfNbrEvents definition.

                    leaf ospfNbrAddressLessIndex  {
                        type  cml-data-types:CML_UINT32_T;
                        description "OSPF Neighbor Address Index";
                    } // END of ospfNbrAddressLessIndex definition.

                    leaf ospfNbrLsRetransQLen  {
                        type  cml-data-types:CML_UINT32_T;
                        description "OSPF Neighbor Retransmit Queue Length";
                    } // END of ospfNbrLsRetransQLen definition.

                    leaf ospfNbmaNbrPermanence  {
                        type  cml-data-types:CML_UINT32_T;
                        description "OSPF Nbma Neighbor Permanence";
                    } // END of ospfNbmaNbrPermanence definition.

                    leaf ospfNbrHelloSuppressed  {
                        type  cml-data-types:CML_UINT32_T;
                        description "OSPF Neighbor Hello Suppressed";
                    } // END of ospfNbrHelloSuppressed definition.

                    leaf ospfNbrRestartHelperStatus  {
                        if-feature feature-list:HAVE_RESTART;
                        type  cml-data-types:CML_UINT32_T;
                        description "OSPF Neighbor Restart Helper Status";
                    } // END of ospfNbrRestartHelperStatus definition.

                    leaf ospfNbrRestartHelperAge  {
                        if-feature feature-list:HAVE_RESTART;
                        type  cml-data-types:CML_UINT32_T;
                        description "OSPF Neighbor Restart Helper Age";
                    } // END of ospfNbrRestartHelperAge definition.

                    leaf ospfNbrRestartHelperExitReason  {
                        if-feature feature-list:HAVE_RESTART;
                        type  cml-data-types:CML_UINT32_T;
                        description "OSPF Neighbor Restart Helper Exit Reason";
                    } // END of ospfNbrRestartHelperExitReason definition.

                    leaf ospfLsDbCount  {
                        type  cml-data-types:CML_UINT32_T;
                        description "ospf LSDB count";
                    } // END of ospfLsDbCount definition.

                    leaf ospfLsRequestCount  {
                        type  cml-data-types:CML_UINT32_T;
                        description "Number of Link State Request";
                    } // END of ospfLsRequestCount definition.

                    leaf ospfLsRetransmitCount  {
                        type  cml-data-types:CML_UINT32_T;
                        description "Number of Link State retransmission";
                    } // END of ospfLsRetransmitCount definition.

                    leaf llsOptions  {
                        if-feature feature-list:HAVE_RESTART;
                        type  cml-data-types:CML_STRING_T;
                        description "lls Options";
                    } // END of llsOptions definition.

                    leaf llsExtendedOption  {
                        if-feature feature-list:HAVE_RESTART;
                        type  cml-data-types:CML_STRING_T;
                        description "lls Extended Option";
                    } // END of llsExtendedOption definition.

                    leaf lastOobResyncTime  {
                        if-feature feature-list:HAVE_RESTART;
                        type  cml-data-types:CML_STRING_T;
                        description "Last Oob Resync Time";
                    } // END of lastOobResyncTime definition.

                    leaf oobResyncTimeout  {
                        if-feature feature-list:HAVE_RESTART;
                        type  cml-data-types:CML_STRING_T;
                        description "oob Resync Timeout";
                    } // END of oobResyncTimeout definition.

                    leaf deadTimerDueTime  {
                        type  cml-data-types:CML_STRING_T;
                        description "Dead Timer Due Time";
                    } // END of deadTimerDueTime definition.

                    leaf ospfPollTimerDueIn  {
                        type  cml-data-types:CML_STRING_T;
                        description "OSPF Poll Timer Due-In";
                    } // END of ospfPollTimerDueIn definition.

                    leaf ospfNeighborUpTime  {
                        type  cml-data-types:CML_STRING_T;
                        description "Neighbor Up Time";
                    } // END of ospfNeighborUpTime definition.

                    leaf ospfCryptSeqNum  {
                        if-feature feature-list:HAVE_MD5;
                        type  cml-data-types:CML_UINT32_T;
                        description "Crypto Sequence Number";
                    } // END of ospfCryptSeqNum definition.

                    leaf ospfDesignatedRouter  {
                        type  cml-data-types:CML_STRING_T;
                        description "OSPF Designated Router";
                    } // END of ospfDesignatedRouter definition.

                    leaf ospfBackDesignatedRouter  {
                        type  cml-data-types:CML_STRING_T;
                        description "OSPF Back-Up Designated Router";
                    } // END of ospfBackDesignatedRouter definition.

                    leaf threadInactivityTimer  {
                        type  cml-data-types:CML_ON_OFF_T;
                        description "Thread Inactivity Timer";
                    } // END of threadInactivityTimer definition.

                    leaf threadDBdescRetransmission  {
                        type  cml-data-types:CML_ON_OFF_T;
                        description "Thread DataBase description Retransmission";
                    } // END of threadDBdescRetransmission definition.

                    leaf threadLinkStateRqstRetransmission  {
                        type  cml-data-types:CML_ON_OFF_T;
                        description "Thread for LinkState Request Retransmission";
                    } // END of threadLinkStateRqstRetransmission definition.

                    leaf threadLinkStateUpdateRetransmission  {
                        type  cml-data-types:CML_ON_OFF_T;
                        description "Thread for LinkState Update Retransmission";
                    } // END of threadLinkStateUpdateRetransmission definition.

                    leaf ospfNeighborPriority  {
                        type  cml-data-types:CML_UINT32_T;
                        description "OSPF Neighbor Priority";
                    } // END of ospfNeighborPriority definition.

                } // End of ospfNeighborRuntime-list
            } // End of ospfInterfaceNeighbor-list

            list passiveInterface {
                key "passiveIfName";
                description
                    "OSPF Passive Interface list";
                leaf passiveIfName  {
                    type  cml-data-types:CML_STRING_T;
                    description "Passive Interface Name";
                } // END of passiveIfName definition.

                leaf-list passiveIfAddr  {
                    type  cml-data-types:CML_IPV4_ADDR_T;
                    description "Passive Interface Address";
                } // END of passiveIfAddr definition.

            } // End of passiveInterface-list

            list frr_pref {
                if-feature feature-list:HAVE_OSPF_LFA;
                key "frrPrefIndex";
                description
                    "Keeps user preferences, lower index in the array is higher priority";
                leaf frrPrefIndex  {
                    type  cml-data-types:CML_UINT32_T {
                         range "1..10";
                    }
                    description "FRR Preference Index";
                } // END of frrPrefIndex definition.

                leaf frrPrefVal  {
                    if-feature feature-list:HAVE_OSPF_LFA;
                    type  cml-data-types:CML_OSPF_FRR_TIE_BREAK_VAL_T;
                    mandatory true;
                    description "FRR Preference Value";
                } // END of frrPrefVal definition.

            } // End of frr_pref-list

            list srcDistance {
                key "distprefix";
                description
                    "srcDistance";
                leaf distprefix  {
                    type  cml-data-types:CML_IPV4_ADDR_PREFIX_T;
                    description "OSPF Administrative Distance in IPv4 Format";
                } // END of distprefix definition.

                leaf aclDistance  {
                    type  cml-data-types:CML_UINT8_T {
                         range "1..255";
                    }
                    description "acl Distance";
                } // END of aclDistance definition.

                leaf accessListName  {
                    type  cml-data-types:CML_STRING_T;
                    mandatory true;
                    description "Access List";
                } // END of accessListName definition.

            } // End of srcDistance-list

            list topsrTrunk {
                if-feature feature-list:HAVE_SR_MPLS;
                key "topsrTrunkName";
                description
                    "List of all Segment Routing trunks enabled for this OSPF Instance";
                leaf topsrTrunkName  {
                    type  cml-data-types:CML_STRING_T;
                    description "Segment Routing trunk name for this OSPF Instance";
                } // END of topsrTrunkName definition.

            } // End of topsrTrunk-list

            list distributeList {
                if-feature feature-list:HAVE_ACL;
                key "distAccessListName";
                description
                    "Distribute list for OSPF Protocol";
                leaf distAccessListName  {
                    type  cml-data-types:CML_STRING_T;
                    description "Distribute Access list for OSPF Protocol";
                } // END of distAccessListName definition.

                leaf ospfDistIn  {
                    type  cml-data-types:CML_BOOL_T;
                    description "OSPF Distribute In";
                } // END of ospfDistIn definition.


                list distributeListProtocol {
                    key "ospfdistProtocol";
                    description
                        "Distribute list for OSPF Protocol";
                    leaf ospfdistProtocol  {
                        type  cml-data-types:CML_OSPF_DIST_ROUTE_SOURCE_TYPE_T;
                        description "Distribute Protocol for OSPF";
                    } // END of ospfdistProtocol definition.

                } // End of distributeListProtocol-list

                list distributeListOspf {
                    key "ospfdistOspfProtocol";
                    description
                        "Distribute list for OSPF Protocol";
                    leaf ospfdistOspfProtocol  {
                        type  cml-data-types:CML_INT32_T {
                             range "1..65535";
                        }
                        description "Redistribute other Routing Protocols into OSPF Routing Table";
                    } // END of ospfdistOspfProtocol definition.

                } // End of distributeListOspf-list
            } // End of distributeList-list

            list redistributeisis {
                key "isisProcessId";
                description
                    "reditribute isis routes to ospf process id";
                leaf isisProcessId  {
                    type  cml-data-types:CML_STRING_T;
                    description "ISIS Process Id";
                } // END of isisProcessId definition.

                leaf redistOspfMetricType  {
                    type  cml-data-types:CML_OSPF_METRIC_TYPE_T;
                    default "2";
                    description "Redistribute OSPF Metric Type";
                } // END of redistOspfMetricType definition.

                leaf redistOspfMetricValue  {
                    type  cml-data-types:CML_INT32_T {
                         range "0..16777214";
                    }
                    description "Redistribute OSPF Metric Value";
                } // END of redistOspfMetricValue definition.

                leaf redistOspfTag  {
                    type  cml-data-types:CML_UINT32_T {
                         range "0..4294967295";
                    }
                    description "Redistribute OSPF Tag value";
                } // END of redistOspfTag definition.

                leaf ospfrouteMapName  {
                    type  cml-data-types:CML_STRING_T;
                    description "OSPF Route Map Name";
                } // END of ospfrouteMapName definition.

            } // End of redistributeisis-list

            list redistributeProc {
                key "secondaryOspfProcessId";
                description
                    "reditribute routes internally to other ospf process id";
                leaf secondaryOspfProcessId  {
                    type  cml-data-types:CML_INT32_T {
                         range "1..65535";
                    }
                    description "OSPF Process ID";
                } // END of secondaryOspfProcessId definition.

                leaf redistOspfMetricType  {
                    type  cml-data-types:CML_OSPF_METRIC_TYPE_T;
                    default "2";
                    description "Redistribute OSPF Metric Type";
                } // END of redistOspfMetricType definition.

                leaf redistOspfMetricValue  {
                    type  cml-data-types:CML_INT32_T {
                         range "0..16777214";
                    }
                    description "Redistribute OSPF Metric Value";
                } // END of redistOspfMetricValue definition.

                leaf redistOspfTag  {
                    type  cml-data-types:CML_UINT32_T {
                         range "0..4294967295";
                    }
                    description "Redistribute OSPF Tag";
                } // END of redistOspfTag definition.

                leaf ospfrouteMapName  {
                    type  cml-data-types:CML_STRING_T;
                    description "OSPF Route Map Name";
                } // END of ospfrouteMapName definition.

            } // End of redistributeProc-list

            list redistribute {
                key "routeSourceType";
                description
                    "redistribute routes to external process (bgp/static etc.)";
                leaf routeSourceType  {
                    type  cml-data-types:CML_OSPF_ROUTE_SOURCE_TYPE_T;
                    description "Source type of OSPF Route";
                } // END of routeSourceType definition.

                leaf redistMetricType  {
                    type  cml-data-types:CML_OSPF_METRIC_TYPE_T;
                    description "Redistribute Metric Type";
                } // END of redistMetricType definition.

                leaf redistMetricValue  {
                    type  cml-data-types:CML_INT32_T {
                         range "0..16777214";
                    }
                    description "Redistribute Metric Value";
                } // END of redistMetricValue definition.

                leaf redistTag  {
                    type  cml-data-types:CML_UINT32_T {
                         range "0..4294967295";
                    }
                    description "Redistribute Tag value";
                } // END of redistTag definition.

                leaf routeMapName  {
                    type  cml-data-types:CML_STRING_T;
                    description "Route Map Name";
                } // END of routeMapName definition.

            } // End of redistribute-list

            list neighbor {
                key "neighborIpAddr";
                description
                    "ospf neighbour";
                leaf neighborIpAddr  {
                    type  cml-data-types:CML_IPV4_ADDR_T;
                    description "ospf neighbour IP Address";
                } // END of neighborIpAddr definition.

                leaf neighborCost  {
                    type  cml-data-types:CML_UINT16_T {
                         range "1..65535";
                    }
                    default "10";
                    description "Neighbor Cost";
                } // END of neighborCost definition.

                leaf ospfNbmaNbrStatus  {
                    type  cml-data-types:CML_OSPF_NBMA_ROW_STATUS;
                    description "OSPF neighbor status in NBMA Network";
                } // END of ospfNbmaNbrStatus definition.

                container nbrOptions {
                    description
                        "nbrOptions";
                    leaf neighborStaticPriority  {
                        type  cml-data-types:CML_UINT8_T {
                             range "0..255";
                        }
                        default "0";
                        description "Neighbor Static Priority";
                    } // END of neighborStaticPriority definition.

                    leaf neighborPollInterval  {
                        type  cml-data-types:CML_INT32_T {
                             range "1..2147483647";
                        }
                        default "120";
                        description "Neighbor Poll Interval";
                    } // END of neighborPollInterval definition.

                } // END of nbrOptions-container definition.
            } // End of neighbor-list

            list summary {
                key "summaryAddr";
                description
                    "ospf summary";
                leaf summaryAddr  {
                    type  cml-data-types:CML_IPV4_PREFIX_T;
                    description "OSPF Summary Address";
                } // END of summaryAddr definition.

                leaf summaryAddressNotAdvertise  {
                    type  cml-data-types:CML_BOOL_T;
                    description "Whether summaryAddressNotAdvertise Set as Enabled/Disabled";
                } // END of summaryAddressNotAdvertise definition.

                leaf addressTag  {
                    type  cml-data-types:CML_UINT32_T {
                         range "0..4294967295";
                    }
                    description "Address Tag";
                } // END of addressTag definition.

            } // End of summary-list

            list area {
                key "areaId";
                description
                    "ospf area";
                leaf AreaInterfaceCount  {
                    type  cml-data-types:CML_INT32_T;
                    config false;
                    description "Number of Interface in an OSPF Area";
                } // END of AreaInterfaceCount definition.

                leaf AreaNeighborCount  {
                    type  cml-data-types:CML_INT32_T;
                    config false;
                    description "Number of OSPF Neighbor";
                } // END of AreaNeighborCount definition.

                leaf spfLastExexTime  {
                    type  cml-data-types:CML_STRING_T;
                    config false;
                    description "Last SPF executed time";
                } // END of spfLastExexTime definition.

                leaf spfExecCount  {
                    type  cml-data-types:CML_UINT32_T;
                    config false;
                    description "Number od SPF Execution";
                } // END of spfExecCount definition.

                leaf areaLsaCount  {
                    type  cml-data-types:CML_INT32_T;
                    config false;
                    description "Number od LSA";
                } // END of areaLsaCount definition.

                leaf areaLsaChecksum  {
                    type  cml-data-types:CML_STRING_T;
                    config false;
                    description "LSA Checksum";
                } // END of areaLsaChecksum definition.

                leaf nssaTranslatorCount  {
                    if-feature feature-list:HAVE_NSSA;
                    type  cml-data-types:CML_INT32_T;
                    config false;
                    description "NSSA Translator Count";
                } // END of nssaTranslatorCount definition.

                leaf nssaTranslatorState  {
                    if-feature feature-list:HAVE_NSSA;
                    type  cml-data-types:CML_STRING_T;
                    config false;
                    description "NSSA Translator State";
                } // END of nssaTranslatorState definition.

                leaf areaId  {
                    type  cml-data-types:CML_OSPF_AREA_T;
                    description "Area Id";
                } // END of areaId definition.

                leaf areaAuthType  {
                    type  cml-data-types:CML_OSPF_AREA_AUTHENTICATION_TYPE_T;
                    description "Area Authentication Type";
                } // END of areaAuthType definition.

                leaf areaShortcutType  {
                    type  cml-data-types:CML_OSPF_AREA_SHORTCUT_TYPE_T;
                    default "default";
                    description "Area Shortcut Type";
                } // END of areaShortcutType definition.

                leaf areaCost  {
                    type  cml-data-types:CML_UINT32_T {
                         range "0..16777215";
                    }
                    default "1";
                    description "Area Cost";
                } // END of areaCost definition.

                leaf exportListName  {
                    if-feature feature-list:HAVE_ACL;
                    type  cml-data-types:CML_STRING_T;
                    default "NULL";
                    description "Export List";
                } // END of exportListName definition.

                leaf importListName  {
                    if-feature feature-list:HAVE_ACL;
                    type  cml-data-types:CML_STRING_T;
                    default "NULL";
                    description "Import List";
                } // END of importListName definition.


                list Stub {
                    key "isStubArea";
                    description
                        "ospf area stub configuration";
                    leaf isStubArea  {
                        type  cml-data-types:CML_OSPF_STUB_T;
                        description "Whether isStubArea Set as Enabled/Disabled";
                    } // END of isStubArea definition.

                    leaf stubAreaNoSummary  {
                        type  cml-data-types:CML_BOOL_T;
                        description "Whether stubAreaNoSummary Set as Enabled/Disabled";
                    } // END of stubAreaNoSummary definition.

                } // End of Stub-list

                list Nssa {
                    if-feature feature-list:HAVE_NSSA;
                    key "isNssaArea";
                    description
                        "ospf area stub configuration";
                    leaf isNssaArea  {
                        type  cml-data-types:CML_OSPF_NSSA_T;
                        description "Nssa OSPF Area";
                    } // END of isNssaArea definition.

                    leaf nssaStabilityInterval  {
                        type  cml-data-types:CML_INT32_T {
                             range "0..2147483647";
                        }
                        default "40";
                        description "NSSA Stability Interval in Seconds";
                    } // END of nssaStabilityInterval definition.

                    leaf nssaTranslatorRole  {
                        type  cml-data-types:CML_OSPF_TRANSLATOR_ROLE_T;
                        default "candidate";
                        description "NSSA-ABR Translator Role";
                    } // END of nssaTranslatorRole definition.

                    leaf nssaDefaultOriginMetric  {
                        type  cml-data-types:CML_INT32_T {
                             range "0..16777214";
                        }
                        default "0";
                        description "NSSA Default Origin Metric";
                    } // END of nssaDefaultOriginMetric definition.

                    leaf nssaDefaultOriginMetricType  {
                        type  cml-data-types:CML_INT32_T {
                             range "1..2";
                        }
                        default "2";
                        description "NSSA Default Origin Metric Type";
                    } // END of nssaDefaultOriginMetricType definition.

                    leaf isNssaNoDist  {
                        type  cml-data-types:CML_BOOL_T;
                        description "Whether isNssaNoDist Set as Enabled/Disabled";
                    } // END of isNssaNoDist definition.

                    leaf isNssaDefaultOriginate  {
                        type  cml-data-types:CML_BOOL_T;
                        description "Whether isNssaDefaultOriginate Set as Enabled/Disabled";
                    } // END of isNssaDefaultOriginate definition.

                    leaf nssaAreaNoSummary  {
                        type  cml-data-types:CML_BOOL_T;
                        description "Whether nssaAreaNoSummary Set as Enabled/Disabled";
                    } // END of nssaAreaNoSummary definition.

                    leaf nssarouteMap  {
                        type  cml-data-types:CML_STRING_T;
                        description "NSSA Route Map";
                    } // END of nssarouteMap definition.

                } // End of Nssa-list

                list filterPrefixList {
                    if-feature feature-list:HAVE_ACL;
                    key "prefixType";
                    description
                        "filterPrefixList";
                    leaf prefixName  {
                        type  cml-data-types:CML_NONEMPTY_STRING_T;
                        mandatory true;
                        description "Prefix Name";
                    } // END of prefixName definition.

                    leaf prefixType  {
                        type  cml-data-types:CML_OSPF_AREA_FILTER_LIST_PREFIX_T;
                        description "Prefix Type";
                    } // END of prefixType definition.

                } // End of filterPrefixList-list

                list filterAccessList {
                    if-feature feature-list:HAVE_ACL;
                    key "accessType";
                    description
                        "filterAccessList";
                    leaf accessName  {
                        type  cml-data-types:CML_NONEMPTY_STRING_T;
                        mandatory true;
                        description "Filter Access Name";
                    } // END of accessName definition.

                    leaf accessType  {
                        type  cml-data-types:CML_OSPF_AREA_FILTER_LIST_PREFIX_T;
                        description "Filter Access Type";
                    } // END of accessType definition.

                } // End of filterAccessList-list

                list hostAddr {
                    key "hostIpAddr";
                    description
                        "ospf host entries";
                    leaf hostIpAddr  {
                        type  cml-data-types:CML_IPV4_ADDR_T;
                        description "OSPF host IP Address";
                    } // END of hostIpAddr definition.

                    leaf hostEntryCost  {
                        type  cml-data-types:CML_INT32_T {
                             range "0..65535";
                        }
                        default "0";
                        description "OSPF host entry cost";
                    } // END of hostEntryCost definition.

                } // End of hostAddr-list

                list network {
                    key "networkPrefix";
                    description
                        "ospf network";
                    leaf networkPrefix  {
                        type  cml-data-types:CML_IPV4_PREFIX_T;
                        description "OPSF network prefix";
                    } // END of networkPrefix definition.

                    leaf InstanceId  {
                        if-feature feature-list:HAVE_OSPF_MULTI_INST;
                        type  cml-data-types:CML_INT16_T {
                             range "0..255";
                        }
                        description "OSPF Instance ID";
                    } // END of InstanceId definition.

                } // End of network-list

                list virtLink {
                    key "peerId";
                    description
                        "ospf virtual link";
                    leaf peerId  {
                        type  cml-data-types:CML_IPV4_ADDR_T;
                        description "ospf virtual link peer Address Identification";
                    } // END of peerId definition.

                    leaf vlinkAuthType  {
                        type  cml-data-types:CML_OSPF_VLINK_AUTH_TYPE_T;
                        default "authentication-null";
                        description "Virtual Link Authentication Type";
                    } // END of vlinkAuthType definition.

                    leaf vlinkMsgDigestKeyId  {
                        type  cml-data-types:CML_UINT8_T {
                             range "1..255";
                        }
                        description "Virtual Link Message Digest Key Id";
                    } // END of vlinkMsgDigestKeyId definition.

                    leaf vlinkMsgDigestKey  {
                        type  cml-data-types:CML_MD5_PASSWORD_T;
                        description "Virtual Link Message Digest Key";
                    } // END of vlinkMsgDigestKey definition.

                    leaf vlinkAuthKey  {
                        type  cml-data-types:CML_MD5_PASSWORD_T;
                        description "Virtual Link Authentication Key";
                    } // END of vlinkAuthKey definition.

                    leaf vlinkRetransIntvl  {
                        type  cml-data-types:CML_INT32_T {
                             range "1..3600";
                        }
                        default "5";
                        description "virtual link Retransmit Interval";
                    } // END of vlinkRetransIntvl definition.

                    leaf vlinkTransmitDelay  {
                        type  cml-data-types:CML_INT32_T {
                             range "1..3600";
                        }
                        default "1";
                        description "Virtual Link Transmit Delay";
                    } // END of vlinkTransmitDelay definition.

                    leaf vlinkHelloInterval  {
                        type  cml-data-types:CML_INT32_T {
                             range "1..65535";
                        }
                        default "10";
                        description "Virtual Link Hello Interval";
                    } // END of vlinkHelloInterval definition.

                    leaf vlinkDeadIntervalConf  {
                        type  cml-data-types:CML_INT32_T {
                             range "1..65535";
                        }
                        description "Virtual Link Dead Interval";
                    } // END of vlinkDeadIntervalConf definition.

                    leaf vlinkDeadInterval  {
                        type  cml-data-types:CML_INT32_T;
                        config false;
                        description "Virtual link dead interval is the interval during which no packets are received and after which the router acknowledges a neighboring router as down. This run time attribute will be displayed only when vlinkDeadIntervalConf is not configured explicitly.";
                    } // END of vlinkDeadInterval definition.

                    leaf vlinkWaitInterval  {
                        type  cml-data-types:CML_INT32_T;
                        config false;
                        description "Wait Timer Interval";
                    } // END of vlinkWaitInterval definition.

                    leaf vlinkName  {
                        type  cml-data-types:CML_STRING_T;
                        config false;
                        description "Virtual Link Name";
                    } // END of vlinkName definition.

                    leaf vlinkStatus  {
                        type  cml-data-types:CML_OSPF_VLINK_STATUS_T;
                        config false;
                        description "Virtual Link Status";
                    } // END of vlinkStatus definition.

                    leaf vlinkInterface  {
                        type  cml-data-types:CML_STRING_T;
                        config false;
                        description "Virtual Link Interface";
                    } // END of vlinkInterface definition.

                    leaf vlinkLocalAddress  {
                        type  cml-data-types:CML_STRING_T;
                        config false;
                        description "Virtual Link Local address";
                    } // END of vlinkLocalAddress definition.

                    leaf vlinkRemoteAddress  {
                        type  cml-data-types:CML_STRING_T;
                        config false;
                        description "Virtual Link Remote address";
                    } // END of vlinkRemoteAddress definition.

                    leaf vlinkHelloDue  {
                        type  cml-data-types:CML_STRING_T;
                        config false;
                        description "Virtual Link Hello due";
                    } // END of vlinkHelloDue definition.

                    leaf vlinkInterfaceState  {
                        type  cml-data-types:CML_OSPF_VLINK_INTERFACE_STATE_T;
                        config false;
                        description "Virtual Link Interface State";
                    } // END of vlinkInterfaceState definition.

                    leaf vlinkAdjState  {
                        type  cml-data-types:CML_OSPF_VLINK_ADJ_STATE_T;
                        config false;
                        description "Virtual Link Adjacency state";
                    } // END of vlinkAdjState definition.

                    container vlinkbfd {
                        description
                            "Bidirectional Forwarding Detection";
                        leaf vlinkFallOverBfd  {
                            if-feature feature-list:HAVE_BFD;
                            type  cml-data-types:CML_BOOL_T;
                            description "Virtual Link Fallover BFD";
                        } // END of vlinkFallOverBfd definition.

                    } // END of vlinkbfd-container definition.
                } // End of virtLink-list

                list areaRange {
                    key "rangeId";
                    description
                        "ospf range";
                    leaf rangeId  {
                        type  cml-data-types:CML_IPV4_PREFIX_T;
                        description "OSPF Range ID";
                    } // END of rangeId definition.

                    leaf rangeAdvertise  {
                        type  cml-data-types:CML_OSPF_AREA_RANGE_ADVERTISE_T;
                        description "OSPF Area Range Advertise";
                    } // END of rangeAdvertise definition.

                    leaf substituteAddr  {
                        type  cml-data-types:CML_IPV4_ADDR_PREFIX_T;
                        description "Substitute Address";
                    } // END of substituteAddr definition.

                } // End of areaRange-list
            } // End of area-list
            container defaultInformation {
                presence "yes";
                description
                    "Default external route Information";
                leaf defaultInformationOriginate  {
                    type  cml-data-types:CML_OSPF_DEFAULT_INFO_T;
                    mandatory true;
                    description "Default Information Originate";
                } // END of defaultInformationOriginate definition.

                leaf metric  {
                    type  cml-data-types:CML_UINT32_T {
                         range "0..16777214";
                    }
                    description "Distance from source to Destinition";
                } // END of metric definition.

                leaf metricType  {
                    type  cml-data-types:CML_OSPF_METRIC_TYPE_T;
                    description "Metric Type";
                } // END of metricType definition.

                leaf routeMap  {
                    type  cml-data-types:CML_STRING_T;
                    description "Route Map";
                } // END of routeMap definition.

                leaf alwaysSet  {
                    type  cml-data-types:CML_BOOL_T;
                    description "Whether alwaysSet Enabled/Disabled ";
                } // END of alwaysSet definition.

            } // END of defaultInformation-container definition.
            container distance {
                description
                    "Define an administrative distance";
                leaf distanceIntra  {
                    type  cml-data-types:CML_UINT32_T {
                         range "1..255";
                    }
                    description "Intra Area Routes Administrative Distance";
                } // END of distanceIntra definition.

                leaf distanceInter  {
                    type  cml-data-types:CML_UINT32_T {
                         range "1..255";
                    }
                    description "Inter Area Routes Administrative Distance";
                } // END of distanceInter definition.

                leaf distanceExternal  {
                    type  cml-data-types:CML_UINT32_T {
                         range "1..255";
                    }
                    description "External Routes Administrative Distance";
                } // END of distanceExternal definition.

            } // END of distance-container definition.
            container domain-id {
                description
                    "domainCMLSEPid";
                leaf domainPrimaryAddr  {
                    if-feature feature-list:HAVE_VRF_OSPF;
                    type  cml-data-types:CML_IPV4_ADDR_T;
                    description "Domain Primary Address";
                } // END of domainPrimaryAddr definition.

                leaf domainNull  {
                    if-feature feature-list:HAVE_VRF_OSPF;
                    type  cml-data-types:CML_STRING_T;
                    description "Domain ID: Null";
                } // END of domainNull definition.

                leaf domainType  {
                    if-feature feature-list:HAVE_VRF_OSPF;
                    type  cml-data-types:CML_OSPF_DOMAIN_TYPE_T;
                    description "Domain ID Type";
                } // END of domainType definition.

                leaf domainHexValue  {
                    if-feature feature-list:HAVE_VRF_OSPF;
                    type  cml-data-types:CML_STRING_T;
                    description "OSPF Domain ID Type Hex Format";
                } // END of domainHexValue definition.

                leaf domainTypeSecondary  {
                    if-feature feature-list:HAVE_VRF_OSPF;
                    type  cml-data-types:CML_BOOL_T;
                    description "OSPF Secondary Domain ID Type in Hex Format";
                } // END of domainTypeSecondary definition.


                list domainIdSecondary {
                    if-feature feature-list:HAVE_VRF_OSPF;
                    key "domainSecondaryAddr";
                    description
                        "domainIdSecondary";
                    leaf domainSecondaryAddr  {
                        type  cml-data-types:CML_IPV4_ADDR_T;
                        description "Domain Secondary Address";
                    } // END of domainSecondaryAddr definition.

                } // End of domainIdSecondary-list
            } // END of domain-id-container definition.
            uses TrafficStats;
        } // End of ospf-list
    } // END of ospf-grouping definition.


    grouping teLinkOspf-grouping {
    description
        "teLinkOspf";
        list teLinkOspf {
            if-feature feature-list:HAVE_GMPLS;
            if-feature feature-list:HAVE_OSPF_TE;
            key "teName";
            description
                "teLinkOspf";
            leaf teName  {
                type  cml-data-types:CML_STRING_T;
                description "TE Link Name";
            } // END of teName definition.

            leaf teLinkOspfInstance  {
                type  cml-data-types:CML_UINT16_T {
                     range "0..65535";
                }
                description "TE Link OSPF Instance";
            } // END of teLinkOspfInstance definition.

            leaf teLinkAreaId  {
                type  cml-data-types:CML_OSPF_AREA_T;
                description "TE Link OSPF Area Id";
            } // END of teLinkAreaId definition.

            leaf teLinkTEMetric  {
                if-feature feature-list:HAVE_OSPF_TE;
                if-feature feature-list:HAVE_GMPLS;
                type  cml-data-types:CML_UINT32_T {
                     range "1..65535";
                }
                default "1";
                description "TE Link Metric Value";
            } // END of teLinkTEMetric definition.

            leaf telinkLocalEnable  {
                if-feature feature-list:HAVE_GMPLS;
                if-feature feature-list:HAVE_OSPF_TE;
                type  cml-data-types:CML_BOOL_T;
                description "Enable if set else disable";
            } // END of telinkLocalEnable definition.

        } // End of teLinkOspf-list
    } // END of teLinkOspf-grouping definition.
    grouping ipOspfCmds {
        description
            "ip ospf command attributes";
        leaf ifAuthTypeAddr  {
            type  cml-data-types:CML_OSPF_AUTH_TYPE_T;
            description "OSPF Authentication Type";
        } // END of ifAuthTypeAddr definition.

        leaf ospfIfAdminStat  {
            type  cml-data-types:CML_OSPF_IF_STATE;
            description "Interface Admin Stat";
        } // END of ospfIfAdminStat definition.

        leaf ospfIfAreaId  {
            if-feature feature-list:HAVE_OSPF_MULTI_INST;
            type  cml-data-types:CML_STRING_T;
            description "Interface Area ID";
        } // END of ospfIfAreaId definition.

        leaf ifStatus  {
            if-feature feature-list:HAVE_OSPF_MULTI_INST;
            type  cml-data-types:CML_OSPF_ROW_STATUS;
            description "Interface Status";
        } // END of ifStatus definition.

        leaf ospfIfMulticastForwarding  {
            if-feature feature-list:HAVE_OSPF_MULTI_INST;
            type  cml-data-types:CML_UINT32_T;
            description "OSPF Interface Multicast Forwarding";
        } // END of ospfIfMulticastForwarding definition.

        leaf ospfIfDemand  {
            if-feature feature-list:HAVE_OSPF_MULTI_INST;
            type  cml-data-types:CML_UINT32_T;
            description "no of packets unused";
        } // END of ospfIfDemand definition.

        leaf ospfAddressLessIf  {
            type  cml-data-types:CML_UINT32_T;
            config false;
            description "OSPF Address LessIf";
        } // END of ospfAddressLessIf definition.

        leaf ospfIfState  {
            type  cml-data-types:CML_UINT32_T;
            config false;
            description "Interface State";
        } // END of ospfIfState definition.

        leaf ospfIfEvents  {
            type  cml-data-types:CML_UINT32_T;
            config false;
            description "OSPF Interface Events";
        } // END of ospfIfEvents definition.

        leaf ospfIfLsaCount  {
            type  cml-data-types:CML_UINT32_T;
            config false;
            description "OSPF Interface Lsa Count";
        } // END of ospfIfLsaCount definition.

        leaf ospfIfLsaCksumSum  {
            type  cml-data-types:CML_UINT32_T;
            config false;
            description "OSPF Interface Lsa CksumSum";
        } // END of ospfIfLsaCksumSum definition.

        leaf ospfIfDesignatedRouter  {
            type  cml-data-types:CML_STRING_T;
            config false;
            description "OSPF Designated Router";
        } // END of ospfIfDesignatedRouter definition.

        leaf ospfIfBackupDesignatedRouter  {
            type  cml-data-types:CML_STRING_T;
            config false;
            description "OSPF Back-up Designated Router";
        } // END of ospfIfBackupDesignatedRouter definition.

        leaf ospfIfDesignatedRouterId  {
            type  cml-data-types:CML_STRING_T;
            config false;
            description "OSPF If Designated Router-Id";
        } // END of ospfIfDesignatedRouterId definition.

        leaf ospfIfBackupDesignatedRouterId  {
            type  cml-data-types:CML_STRING_T;
            config false;
            description "OSPF If Back-up Designated Router-Id";
        } // END of ospfIfBackupDesignatedRouterId definition.

        leaf ifPriorityAddr  {
            type  cml-data-types:CML_UINT8_T {
                 range "0..255";
            }
            default "1";
            description "interface Priority value";
        } // END of ifPriorityAddr definition.

        leaf ifCostAddr  {
            type  cml-data-types:CML_UINT32_T {
                 range "1..65535";
            }
            default "10";
            description "Interface cost";
        } // END of ifCostAddr definition.

        leaf ifDeadIntervalAddr  {
            type  cml-data-types:CML_UINT32_T;
            config false;
            description "Interface ospf dead interval is the time during which the router waits to receive an OSPF hello packet from the neighbor before declaring the neighbor down. This attribute will be displayed only when ifDeadIntervalAddrConf is not configured explicitly";
        } // END of ifDeadIntervalAddr definition.

        leaf ifDeadIntervalAddrConf  {
            type  cml-data-types:CML_UINT32_T {
                 range "1..65535";
            }
            description "Interface DeadInterval";
        } // END of ifDeadIntervalAddrConf definition.

        leaf ifHelloIntervalAddr  {
            type  cml-data-types:CML_UINT32_T {
                 range "1..65535";
            }
            default "10";
            description "Interface HelloInterval";
        } // END of ifHelloIntervalAddr definition.

        leaf ifRetransmitIntervalAddr  {
            type  cml-data-types:CML_UINT32_T {
                 range "1..65535";
            }
            default "5";
            description "Interface Retransmit Interval";
        } // END of ifRetransmitIntervalAddr definition.

        leaf ifTransmitDelayAddr  {
            type  cml-data-types:CML_UINT32_T {
                 range "1..3600";
            }
            default "1";
            description "Interface TransmitDelay value";
        } // END of ifTransmitDelayAddr definition.

        leaf ifDatabaseFilterAddr  {
            type  cml-data-types:CML_BOOL_T;
            description "Whether ifDatabaseFilter is Enabled/Disabled";
        } // END of ifDatabaseFilterAddr definition.

        leaf isMtuIgnoreAddr  {
            type  cml-data-types:CML_BOOL_T;
            description "Whether isMtuIgnoreAddr Set as Enabled/Disabled";
        } // END of isMtuIgnoreAddr definition.

        leaf ifResyncTimeoutAddr  {
            type  cml-data-types:CML_UINT32_T {
                 range "1..65535";
            }
            default "40";
            description "Interface Resync Timeout";
        } // END of ifResyncTimeoutAddr definition.

    } // END of ipOspfCmds definition.
    grouping TrafficStats {
        description
            "Runtime attrs of TrafficStats";
        leaf trafficTimeStamp  {
            type  cml-data-types:CML_STRING_T;
            config false;
            description "Traffic Time Stamp";
        } // END of trafficTimeStamp definition.

        leaf totalStatsIn  {
            type  cml-data-types:CML_INT32_T;
            config false;
            description "Total Stats In";
        } // END of totalStatsIn definition.

        leaf totalStatsOut  {
            type  cml-data-types:CML_INT32_T;
            config false;
            description "Total Stats Out";
        } // END of totalStatsOut definition.

        leaf errorsDropIn  {
            type  cml-data-types:CML_INT32_T;
            config false;
            description "Errors Drop In";
        } // END of errorsDropIn definition.

        leaf errorsDropOut  {
            type  cml-data-types:CML_INT32_T;
            config false;
            description "Errors Drop Out";
        } // END of errorsDropOut definition.

        leaf errorsHellosIn  {
            type  cml-data-types:CML_INT32_T;
            config false;
            description "Errors Hellos In";
        } // END of errorsHellosIn definition.

        leaf dbdsIn  {
            type  cml-data-types:CML_INT32_T;
            config false;
            description "dbdsIn";
        } // END of dbdsIn definition.

        leaf lsreqIn  {
            type  cml-data-types:CML_INT32_T;
            config false;
            description "ls Request In";
        } // END of lsreqIn definition.

        leaf lsuIn  {
            type  cml-data-types:CML_INT32_T;
            config false;
            description "lsu In";
        } // END of lsuIn definition.

        leaf lsacksIn  {
            type  cml-data-types:CML_INT32_T;
            config false;
            description "ls acks In";
        } // END of lsacksIn definition.

        leaf unknownIn  {
            type  cml-data-types:CML_INT32_T;
            config false;
            description "unknown In";
        } // END of unknownIn definition.

        leaf unknownOut  {
            type  cml-data-types:CML_INT32_T;
            config false;
            description "unknown Out";
        } // END of unknownOut definition.

        leaf badVersion  {
            type  cml-data-types:CML_INT32_T;
            config false;
            description "Bad Version";
        } // END of badVersion definition.

        leaf badCrc  {
            type  cml-data-types:CML_INT32_T;
            config false;
            description "Bad Crc";
        } // END of badCrc definition.

        leaf invalidSrc  {
            type  cml-data-types:CML_INT32_T;
            config false;
            description "Invalid Source";
        } // END of invalidSrc definition.

        leaf invalidDSt  {
            type  cml-data-types:CML_INT32_T;
            config false;
            description "Invalid Destination";
        } // END of invalidDSt definition.

        leaf noNbr  {
            type  cml-data-types:CML_INT32_T;
            config false;
            description "No Neighbor";
        } // END of noNbr definition.

        leaf passive  {
            type  cml-data-types:CML_INT32_T;
            config false;
            description "Passive";
        } // END of passive definition.

        leaf wrongArea  {
            type  cml-data-types:CML_INT32_T;
            config false;
            description "Wrong Area";
        } // END of wrongArea definition.

        leaf pktLength  {
            type  cml-data-types:CML_INT32_T;
            config false;
            description "Packet Length";
        } // END of pktLength definition.

        leaf badAuth  {
            type  cml-data-types:CML_INT32_T;
            config false;
            description "Bad Authentication";
        } // END of badAuth definition.

        leaf statsHelloIn  {
            type  cml-data-types:CML_INT32_T;
            config false;
            description "Stats Hello-In";
        } // END of statsHelloIn definition.

        leaf statsDbDescIn  {
            type  cml-data-types:CML_INT32_T;
            config false;
            description "Stats Database Description In";
        } // END of statsDbDescIn definition.

        leaf statsLsReqIn  {
            type  cml-data-types:CML_INT32_T;
            config false;
            description "Stats Ls Req-In";
        } // END of statsLsReqIn definition.

        leaf statsLsUpdIn  {
            type  cml-data-types:CML_INT32_T;
            config false;
            description "Stats Ls Update-In";
        } // END of statsLsUpdIn definition.

        leaf statsLsAckIn  {
            type  cml-data-types:CML_INT32_T;
            config false;
            description "Stats Ls Ack-In";
        } // END of statsLsAckIn definition.

        leaf statsHelloOut  {
            type  cml-data-types:CML_INT32_T;
            config false;
            description "Stats Hello Out";
        } // END of statsHelloOut definition.

        leaf statsDbDescOut  {
            type  cml-data-types:CML_INT32_T;
            config false;
            description "Stats Db Desc-Out";
        } // END of statsDbDescOut definition.

        leaf statsLsReqOut  {
            type  cml-data-types:CML_INT32_T;
            config false;
            description "Stats Ls Req-Out";
        } // END of statsLsReqOut definition.

        leaf statsLsUpdOut  {
            type  cml-data-types:CML_INT32_T;
            config false;
            description "Stats Ls Update-Out";
        } // END of statsLsUpdOut definition.

        leaf statsLsAckOut  {
            type  cml-data-types:CML_INT32_T;
            config false;
            description "Stats Ls Acknowledge-Out";
        } // END of statsLsAckOut definition.

    } // END of TrafficStats definition.

    grouping  ospfMaster-grouping {
    description
        "OSPF Master commands";
    container ospfMaster {
        description
            "OSPF Master commands";
        leaf multiInstanceSet  {
            if-feature feature-list:HAVE_OSPF_MULTI_INST;
            type  cml-data-types:CML_BOOL_T;
            description "OSPF instance";
        } // END of multiInstanceSet definition.

        leaf graceperiod  {
            if-feature feature-list:HAVE_RESTART;
            type  cml-data-types:CML_UINT16_T {
                 range "2..1800";
            }
            description "Grace period in seconds";
        } // END of graceperiod definition.

        leaf-list helperId  {
            type  cml-data-types:CML_IPV4_ADDR_T;
            description "Helper policy (Never, Only reload, Only Upgrade)";
        } // END of helperId definition.


        list srPath {
            if-feature feature-list:HAVE_SR_MPLS;
            key "ospfsrPathName";
            description
                "List for paths for Segment Routing";
            leaf ospfsrPathName  {
                type  cml-data-types:CML_STRING_T;
                description "Path Name for Segment Routing";
            } // END of ospfsrPathName definition.


            list srPathEro {
                if-feature feature-list:HAVE_SR_MPLS;
                key "hopAddr";
                description
                    "List of hops";
                leaf hopAddr  {
                    type  cml-data-types:CML_IPV4_ADDR_T;
                    description "Hop address";
                } // END of hopAddr definition.


                list srPathEronext {
                    if-feature feature-list:HAVE_SR_MPLS;
                    key "hopnbrAddr";
                    description
                        "List of hops";
                    leaf hopnbrAddr  {
                        type  cml-data-types:CML_IPV4_ADDR_T;
                        description "Hop neighbor Address";
                    } // END of hopnbrAddr definition.

                } // End of srPathEronext-list
            } // End of srPathEro-list
        } // End of srPath-list

        list srTrunk {
            if-feature feature-list:HAVE_SR_MPLS;
            key "ospfsrTrunkName";
            description
                "Hash table to store ingress trunks only";
            leaf ospfsrTrunkName  {
                type  cml-data-types:CML_STRING_T;
                description "Segment Routing Trunk Name";
            } // END of ospfsrTrunkName definition.

            leaf Tegress  {
                if-feature feature-list:HAVE_SR_MPLS;
                type  cml-data-types:CML_IPV4_ADDR_T;
                description "Tunnel Egress";
            } // END of Tegress definition.

            leaf TrunkPathName  {
                if-feature feature-list:HAVE_SR_MPLS;
                type  cml-data-types:CML_STRING_T;
                description "Trunk Path Name";
            } // END of TrunkPathName definition.

        } // End of srTrunk-list
        container ospfDebugConf {
            description
                "OSPF global debug flags";
            leaf ospfDebugConfAllType  {
                type  cml-data-types:CML_BOOL_T;
                description "All Type of Debugging Options for OSPF";
            } // END of ospfDebugConfAllType definition.

            leaf ospfPacketDebugConfType  {
                type  cml-data-types:CML_OSPF_PACKET_TYPE_T;
                description "Debug Option for OSPF Packet";
            } // END of ospfPacketDebugConfType definition.

            leaf ospfEventFlagsConf  {
                type  cml-data-types:CML_OSPF_DEBUG_EVENT_TYPE_T;
                description "Debug Option for OSPF Event";
            } // END of ospfEventFlagsConf definition.

            leaf ospfIfsmFlagsConf  {
                type  cml-data-types:CML_OSPF_DEBUG_IFSM_T;
                description "Debug Option for Interface Finite State Machine";
            } // END of ospfIfsmFlagsConf definition.

            leaf ospfNfsmFlagsConf  {
                type  cml-data-types:CML_OSPF_DEBUG_NFSM_T;
                description "Debug Option for OSPF Neighbor Finite State Machine";
            } // END of ospfNfsmFlagsConf definition.

            leaf ospfLsaFlagsConf  {
                type  cml-data-types:CML_OSPF_DEBUG_LSA_T;
                description "Debug Option for Link State Advertisement";
            } // END of ospfLsaFlagsConf definition.

            leaf ospfNsmFlagsConf  {
                type  cml-data-types:CML_OSPF_DEBUG_NSM_T;
                description "Debug Option for OSPF NSM Information";
            } // END of ospfNsmFlagsConf definition.

            leaf ospfRibFlagsConf  {
                if-feature feature-list:HAVE_RIBD;
                type  cml-data-types:CML_OSPF_DEBUG_RIB_T;
                description "Debug Option for OSPF RIB Information";
            } // END of ospfRibFlagsConf definition.

            leaf ospfBfdFlagsConf  {
                if-feature feature-list:HAVE_BFD;
                type  cml-data-types:CML_BOOL_T;
                description "Debug Option for OSPF BFD Information";
            } // END of ospfBfdFlagsConf definition.

            leaf ospfRtCalcflagsConf  {
                type  cml-data-types:CML_OSPF_DEBUG_ROUTE_T;
                description "Debug Option for OSPF Route Calculation";
            } // END of ospfRtCalcflagsConf definition.

            leaf ospfDatabaseTimerflagsConf  {
                type  cml-data-types:CML_BOOL_T;
                description "OSPF Database Timer Flags";
            } // END of ospfDatabaseTimerflagsConf definition.

            leaf ospfRedistributeFlagsConf  {
                type  cml-data-types:CML_OSPF_DEBUG_REDIST_T;
                description "OSPF Redistribute Flags";
            } // END of ospfRedistributeFlagsConf definition.

            leaf ospfGracefulRestartFlagsConf  {
                type  cml-data-types:CML_OSPF_DEBUG_GRACEFUL_T;
                description "ospf Graceful Restart Flags";
            } // END of ospfGracefulRestartFlagsConf definition.

            leaf ospfPolicyFlagsConf  {
                type  cml-data-types:CML_BOOL_T;
                description "OSPF Policy Flags";
            } // END of ospfPolicyFlagsConf definition.

            leaf ospfRetransmissionFlagsConf  {
                type  cml-data-types:CML_BOOL_T;
                description "OSPF Retransmission Flags";
            } // END of ospfRetransmissionFlagsConf definition.

            leaf ospfLfaRouteFlagsConf  {
                if-feature feature-list:HAVE_OSPF_LFA;
                type  cml-data-types:CML_BOOL_T;
                description "OSPF Lfa Route Flags";
            } // END of ospfLfaRouteFlagsConf definition.

            leaf ospfHaFlagsConf  {
                if-feature feature-list:HAVE_OSPF_SSO;
                type  cml-data-types:CML_BOOL_T;
                description "OSPF Ha Flags";
            } // END of ospfHaFlagsConf definition.

            leaf debugospfSrFlagsConf  {
                if-feature feature-list:HAVE_SR_MPLS;
                type  cml-data-types:CML_BOOL_T;
                description "Debug OSPF SR Flags";
            } // END of debugospfSrFlagsConf definition.

            leaf ospfCspfDebugEventsConf  {
                if-feature feature-list:HAVE_OSPF_CSPF;
                type  cml-data-types:CML_BOOL_T;
                description "OSPF Cspf Debug Events";
            } // END of ospfCspfDebugEventsConf definition.

            leaf ospfCspfDebugHexdumpConf  {
                if-feature feature-list:HAVE_OSPF_CSPF;
                type  cml-data-types:CML_BOOL_T;
                description "OSPF Cspf Debug Hexdump";
            } // END of ospfCspfDebugHexdumpConf definition.

        } // END of ospfDebugConf-container definition.
        container ospfDebug {
            description
                "OSPF global debug flags";
            leaf ospfDebugAllType  {
                type  cml-data-types:CML_BOOL_T;
                description "Debug Option for OSPF is Enabled/Disabled";
            } // END of ospfDebugAllType definition.

            leaf ospfPacketDebugType  {
                type  cml-data-types:CML_OSPF_PACKET_TYPE_T;
                description "Debug Option for OSPF Packet";
            } // END of ospfPacketDebugType definition.

            leaf ospfEventFlags  {
                type  cml-data-types:CML_OSPF_DEBUG_EVENT_TYPE_T;
                description "Debug Option for OSPF Event";
            } // END of ospfEventFlags definition.

            leaf ospfIfsmFlags  {
                type  cml-data-types:CML_OSPF_DEBUG_IFSM_T;
                description "Debug Option for IFSM";
            } // END of ospfIfsmFlags definition.

            leaf ospfNfsmFlags  {
                type  cml-data-types:CML_OSPF_DEBUG_NFSM_T;
                description "Debug Option for NFSM";
            } // END of ospfNfsmFlags definition.

            leaf ospfLsaFlags  {
                type  cml-data-types:CML_OSPF_DEBUG_LSA_T;
                description "Debug Option for OSPF LSA";
            } // END of ospfLsaFlags definition.

            leaf ospfNsmFlags  {
                type  cml-data-types:CML_OSPF_DEBUG_NSM_T;
                description "Debug Option for OSPF NSM Information";
            } // END of ospfNsmFlags definition.

            leaf ospfRibFlags  {
                if-feature feature-list:HAVE_RIBD;
                type  cml-data-types:CML_OSPF_DEBUG_RIB_T;
                description "Debug Option for OSPF RIB Information";
            } // END of ospfRibFlags definition.

            leaf ospfBfdFlags  {
                if-feature feature-list:HAVE_BFD;
                type  cml-data-types:CML_BOOL_T;
                description "Debug Option for OSPF BFD Information";
            } // END of ospfBfdFlags definition.

            leaf ospfRtCalcflags  {
                type  cml-data-types:CML_OSPF_DEBUG_ROUTE_T;
                description "Debug Option for OSPF Route Calculation";
            } // END of ospfRtCalcflags definition.

            leaf ospfDatabaseTimerflags  {
                type  cml-data-types:CML_BOOL_T;
                description "OSPF Database rate-limiting Timer";
            } // END of ospfDatabaseTimerflags definition.

            leaf ospfRedistributeFlags  {
                type  cml-data-types:CML_OSPF_DEBUG_REDIST_T;
                description "Debug Option for OSPF Redistribute Information";
            } // END of ospfRedistributeFlags definition.

            leaf ospfGracefulRestartFlags  {
                type  cml-data-types:CML_OSPF_DEBUG_GRACEFUL_T;
                description "Debug Option for OSPF Graceful Restart";
            } // END of ospfGracefulRestartFlags definition.

            leaf ospfPolicyFlags  {
                type  cml-data-types:CML_BOOL_T;
                description "Debug Option for OSPF Policy Flags";
            } // END of ospfPolicyFlags definition.

            leaf ospfRetransmissionFlags  {
                type  cml-data-types:CML_BOOL_T;
                description "Debug Option for OSPF Retransmission";
            } // END of ospfRetransmissionFlags definition.

            leaf ospfLfaRouteFlags  {
                if-feature feature-list:HAVE_OSPF_LFA;
                type  cml-data-types:CML_BOOL_T;
                description "Debug Option for OSPF Loop-free Alternate Path";
            } // END of ospfLfaRouteFlags definition.

            leaf ospfHaFlags  {
                if-feature feature-list:HAVE_OSPF_SSO;
                type  cml-data-types:CML_BOOL_T;
                description "Debug option for HA";
            } // END of ospfHaFlags definition.

            leaf ospfSrFlags  {
                if-feature feature-list:HAVE_SR_MPLS;
                type  cml-data-types:CML_BOOL_T;
                description "Debug Option for OSPF Segment Routing";
            } // END of ospfSrFlags definition.

            leaf ospfCspfDebugEvents  {
                if-feature feature-list:HAVE_OSPF_CSPF;
                type  cml-data-types:CML_BOOL_T;
                description "Debug Option for OSPF CSPF Event Flags";
            } // END of ospfCspfDebugEvents definition.

            leaf ospfCspfDebugHexdump  {
                if-feature feature-list:HAVE_OSPF_CSPF;
                type  cml-data-types:CML_BOOL_T;
                description "Debug Option for OSPF CSPF hexdump Flags";
            } // END of ospfCspfDebugHexdump definition.

        } // END of ospfDebug-container definition.
        container helperPolicy {
            description
                "Helper policy for Graceful Restart";
            leaf MaxGracePeriod  {
                type  cml-data-types:CML_UINT16_T {
                     range "2..1800";
                }
                description "Maximum grace period in seconds";
            } // END of MaxGracePeriod definition.

        } // END of helperPolicy-container definition.
    } // END of ospfMaster-container definition.
    } // END of ospfMaster-container definition.

    grouping  ospfInterface-grouping {
    description
        "OSPF interface related operations";
    container ospfInterface {
        description
            "OSPF interface related operations";
        leaf ifTEMetric  {
            if-feature feature-list:HAVE_OSPF_TE;
            type  cml-data-types:CML_UINT32_T {
                 range "1..65535";
            }
            default "1";
            description "The minimum delay in milliseconds between accepting the same LSA from neighbors";
        } // END of ifTEMetric definition.

        leaf ospfholddown  {
            if-feature feature-list:HAVE_LDPD;
            type  cml-data-types:CML_UINT32_T {
                 range "1..2147483";
            }
            default "70000";
            description "OSPF hold down time in milliseconds";
        } // END of ospfholddown definition.

        leaf ifBfdEnable  {
            if-feature feature-list:HAVE_BFD;
            type  cml-data-types:CML_OSPF_BFD_STATE;
            description "To enable Bidirectional Forwarding Detection";
        } // END of ifBfdEnable definition.

        leaf ifNetworkType  {
            type  cml-data-types:CML_OSPF_NETWORK_T;
            description "Interface Network Type";
        } // END of ifNetworkType definition.

        leaf ifMtu  {
            type  cml-data-types:CML_UINT16_T {
                 range "576..65535";
            }
            default "576";
            description "Interface MTU size";
        } // END of ifMtu definition.

        leaf ifDisableAll  {
            type  cml-data-types:CML_BOOL_T;
            description "Whether ifDisableAll Set as Enabled/Disabled";
        } // END of ifDisableAll definition.

        leaf fastRerouteIfSet  {
            if-feature feature-list:HAVE_OSPF_LFA;
            type  cml-data-types:CML_BOOL_T;
            description "Whether fastRerouteIfSet Set as Enabled/Disabled";
        } // END of fastRerouteIfSet definition.

        leaf ifFloodReduction  {
            type  cml-data-types:CML_BOOL_T;
            description "Whether ifFloodReduction Set as Enabled/Disabled";
        } // END of ifFloodReduction definition.

        leaf ifDemandCircuit  {
            if-feature feature-list:HAVE_OSPF_OD;
            if-feature feature-list:HAVE_OSPF_MULTI_INST;
            type  cml-data-types:CML_BOOL_T;
            description "Whether Interface Demand Circuit Set as Enabled/Disabled";
        } // END of ifDemandCircuit definition.


        list ospfMultiAreaProcess {
            if-feature feature-list:HAVE_OSPF_MULTI_AREA;
            key "ospfProcess";
            description
                "OSPF multi-area configs";
            leaf ospfProcess  {
                type  cml-data-types:CML_UINT16_T {
                     range "0..65535";
                }
                description "OSPF Process ID";
            } // END of ospfProcess definition.


            list ospfMultiArea {
                if-feature feature-list:HAVE_OSPF_MULTI_AREA;
                key "multiAreaId";
                description
                    "OSPF multi-area configs";
                leaf multiAreaId  {
                    type  cml-data-types:CML_OSPF_AREA_T;
                    description "OSPF Multi-Area ID";
                } // END of multiAreaId definition.

                leaf neighborAddr  {
                    type  cml-data-types:CML_IPV4_ADDR_T;
                    description "Neighbor Address";
                } // END of neighborAddr definition.

            } // End of ospfMultiArea-list
        } // End of ospfMultiAreaProcess-list

        list ospfInterfaceAddr {
            key "ipOspfAddr";
            description
                "OSPF interface addr related operations";
            leaf ipOspfAddr  {
                type  cml-data-types:CML_IPV4_ADDR_T;
                description "OSPF Interface Address";
            } // END of ipOspfAddr definition.


            list ospfInterfaceMessageDigestKey {
                key "msgDigestKeyIdAddr";
                description
                    "OSPF message-digest-key related operations";
                leaf msgDigestKeyIdAddr  {
                    type  cml-data-types:CML_UINT32_T {
                         range "1..255";
                    }
                    description "Message Digest Key Id";
                } // END of msgDigestKeyIdAddr definition.

                leaf msgDigestKeyEncryptionAddr  {
                    type  cml-data-types:CML_OSPF_MD5_T;
                    description "Message Digest Key Encryption Address";
                } // END of msgDigestKeyEncryptionAddr definition.

                leaf msgifAuthKeyAddr  {
                    type  cml-data-types:CML_MD5_PASSWORD_T;
                    description "Message interface Authentication Key Address";
                } // END of msgifAuthKeyAddr definition.

                leaf msgifAuthEncryptKeyAddr  {
                    type  cml-data-types:CML_MD5_PASSWORD_T;
                    description "Msg if Auth Encrypt Key Address";
                } // END of msgifAuthEncryptKeyAddr definition.

            } // End of ospfInterfaceMessageDigestKey-list
            container Authkey {
                description
                    "Enable authentication-key on this interface";
                leaf ifAuthKeyAddr  {
                    type  cml-data-types:CML_MD5_PASSWORD_T;
                    description "Interface Authentication key Address";
                } // END of ifAuthKeyAddr definition.

                leaf authKeyEncryptionAddr  {
                    type  cml-data-types:CML_OSPF_MD5_T;
                    description "Authentication key Encription Address";
                } // END of authKeyEncryptionAddr definition.

            } // END of Authkey-container definition.
            uses ipOspfCmds;
        } // End of ospfInterfaceAddr-list
        container ipOspfInterface {
            description
                "ip OSPF interface addr related operations";

            list ospfInterfaceMessageDigestKey {
                key "msgDigestKeyIdAddr";
                description
                    "OSPF message-digest-key related operations";
                leaf msgDigestKeyIdAddr  {
                    type  cml-data-types:CML_UINT32_T {
                         range "1..255";
                    }
                    description "Message Digest Key ID value";
                } // END of msgDigestKeyIdAddr definition.

                leaf msgDigestKeyEncryptionAddr  {
                    type  cml-data-types:CML_OSPF_MD5_T;
                    description "Message Digest Key Encryption Address";
                } // END of msgDigestKeyEncryptionAddr definition.

                leaf msgifAuthKeyAddr  {
                    type  cml-data-types:CML_MD5_PASSWORD_T;
                    description "Message Interface AuthKey Address";
                } // END of msgifAuthKeyAddr definition.

                leaf msgifAuthEncryptKeyAddr  {
                    type  cml-data-types:CML_MD5_PASSWORD_T;
                    description "Message interface Auth Encrypt Key Address";
                } // END of msgifAuthEncryptKeyAddr definition.

            } // End of ospfInterfaceMessageDigestKey-list
            container Authkey {
                description
                    "Enable authentication-key on this interface";
                leaf ifAuthKeyAddr  {
                    type  cml-data-types:CML_MD5_PASSWORD_T;
                    description "Interface Authentication key address";
                } // END of ifAuthKeyAddr definition.

                leaf authKeyEncryptionAddr  {
                    type  cml-data-types:CML_OSPF_MD5_T;
                    description "Auth Key Encryption Address";
                } // END of authKeyEncryptionAddr definition.

            } // END of Authkey-container definition.
            uses ipOspfCmds;
        } // END of ipOspfInterface-container definition.
        uses TrafficStats;
    } // END of ospfInterface-container definition.
    } // END of ospfInterface-container definition.


}
