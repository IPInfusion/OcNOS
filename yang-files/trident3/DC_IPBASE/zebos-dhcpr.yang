/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-dhcpr.yang
*
*/

submodule zebos-dhcpr {

    belongs-to  zebos { prefix zebos; }

    import cml_data_types {
        prefix cml_data_types;
    }

    organization
        "IP Infusion Inc.";

    contact
        "Address: 3965 Freedom Circle, Suite 200, Santa Clara, CA 95054
        Phone: +1 408-400-1900
        E-mail: support@ipinfusion.com
        Web: http://www.ipinfusion.com/";

    description
        "dhcp_relay_configuration";


    revision "2018-06-21" {
        description " Initial Version.";
        reference "";
    }



    grouping dhcp6interface-grouping {
    description
        "DHCP interface related operations";
        list dhcp6interface {
            key "ipv6address";
            description
                "DHCP interface related operations";
            leaf ipv6address  {
                type  cml_data_types:CML_IPV6_ADDR_T;
                description "";
            } // END of ipv6address definition.

            leaf interface  {
                type  cml_data_types:CML_STRING_T;
                description "";
            } // END of interface definition.

        } // End of dhcp6interface-list
    } // END of dhcp6interface-grouping definition.

    grouping  linkSelection-grouping {
    description
        "linkSelection";
    container linkSelection {
        description
            "linkSelection";
        leaf ipAddress  {
            type  cml_data_types:CML_IPV4_ADDR_T;
            description "Enable link selection sub-option (5) in the option-82 in DHCP packet";
        } // END of ipAddress definition.

    } // END of linkSelection-container definition.
    } // END of linkSelection-container definition.

    grouping  dhcprelay-grouping {
    description
        "dhcprelay";
    container dhcprelay {
        description
            "dhcprelay";
        leaf relay  {
            type  cml_data_types:CML_BOOL_T;
            description "";
        } // END of relay definition.

        leaf option  {
            type  cml_data_types:CML_BOOL_T;
            description "";
        } // END of option definition.

        leaf ipAddress  {
            type  cml_data_types:CML_IPV4_ADDR_T;
            description "Enable link selection sub-option (5) in the option-82 in DHCP packet";
        } // END of ipAddress definition.

    } // END of dhcprelay-container definition.
    } // END of dhcprelay-container definition.

    grouping  dhcprelayinterface-grouping {
    description
        "DHCP interface related operations";
    container dhcprelayinterface {
        description
            "DHCP interface related operations";
        leaf-list address  {
            type  cml_data_types:CML_IPV4_ADDR_T;
            description "";
        } // END of address definition.

        leaf remoteId  {
            type  cml_data_types:CML_STRING_T {
                length "1..255";
            }
            description "";
        } // END of remoteId definition.

    } // END of dhcprelayinterface-container definition.
    } // END of dhcprelayinterface-container definition.

    grouping  dhcprelay6-grouping {
    description
        "DHCP";
    container dhcprelay6 {
        description
            "DHCP";
        leaf relay6  {
            type  cml_data_types:CML_BOOL_T;
            description "";
        } // END of relay6 definition.

    } // END of dhcprelay6-container definition.
    } // END of dhcprelay6-container definition.


}
