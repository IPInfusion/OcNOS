/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-lag.yang
*
*/

submodule zebos-lag {

    belongs-to  zebos { prefix zebos; }

    import cml_data_types {
        prefix cml_data_types;
    }

    import feature_list {
        prefix feature_list;
    }

    organization
        "IP Infusion Inc.";

    contact
        "Address: 3965 Freedom Circle, Suite 200, Santa Clara, CA 95054
        Phone: +1 408-400-1900
        E-mail: support@ipinfusion.com
        Web: http://www.ipinfusion.com/";

    description
        "Layer-2 lacp  configurations";


    revision "2018-06-21" {
        description " Initial Version.";
        reference "";
    }

    grouping linkState {
        description
            "link state runtime flags";
        leaf activity  {
            type  cml_data_types:CML_UINT8_T;
            config false;
            description "";
        } // END of activity definition.

        leaf timeout  {
            type  cml_data_types:CML_UINT8_T;
            config false;
            description "";
        } // END of timeout definition.

        leaf aggregation  {
            type  cml_data_types:CML_UINT8_T;
            config false;
            description "";
        } // END of aggregation definition.

        leaf synchronization  {
            type  cml_data_types:CML_UINT8_T;
            config false;
            description "";
        } // END of synchronization definition.

        leaf collecting  {
            type  cml_data_types:CML_UINT8_T;
            config false;
            description "";
        } // END of collecting definition.

        leaf distributing  {
            type  cml_data_types:CML_UINT8_T;
            config false;
            description "";
        } // END of distributing definition.

        leaf defaulted  {
            type  cml_data_types:CML_UINT8_T;
            config false;
            description "";
        } // END of defaulted definition.

        leaf expired  {
            type  cml_data_types:CML_UINT8_T;
            config false;
            description "";
        } // END of expired definition.

    } // END of linkState definition.

    grouping  lacpMaster-grouping {
    description
        "lacp master runtime attributes";
    container lacpMaster {
        description
            "lacp master runtime attributes";
        leaf dummy  {
            type  cml_data_types:CML_UINT8_T;
            description "";
        } // END of dummy definition.


        list lacpAggregator {
            key "aggIndex";
            config false;
            description
                "lacp aggregator runtime attributes";
            leaf aggIndex  {
                type  cml_data_types:CML_UINT16_T;
                description "";
            } // END of aggIndex definition.

            leaf aggregatorName  {
                type  cml_data_types:CML_STRING_T;
                description "";
            } // END of aggregatorName definition.

            leaf aggId  {
                type  cml_data_types:CML_UINT32_T;
                description "";
            } // END of aggId definition.

            leaf aggregatorType  {
                type  cml_data_types:CML_AGGREGATOR_TYPE_T;
                description "";
            } // END of aggregatorType definition.

            leaf aggregatorMacAddress  {
                type  cml_data_types:CML_MAC_ADDR_T;
                description "";
            } // END of aggregatorMacAddress definition.

            leaf actorAdminAggregatorKey  {
                type  cml_data_types:CML_UINT16_T;
                description "";
            } // END of actorAdminAggregatorKey definition.

            leaf actorOperAggregatorKey  {
                type  cml_data_types:CML_STRING_T;
                description "";
            } // END of actorOperAggregatorKey definition.

            leaf actorSystemPriority  {
                type  cml_data_types:CML_STRING_T;
                description "";
            } // END of actorSystemPriority definition.

            leaf actorSystem  {
                type  cml_data_types:CML_MAC_ADDR_T;
                description "";
            } // END of actorSystem definition.

            leaf receiveLinkCount  {
                type  cml_data_types:CML_UINT32_T;
                description "";
            } // END of receiveLinkCount definition.

            leaf transmitLinkCount  {
                type  cml_data_types:CML_UINT32_T;
                description "";
            } // END of transmitLinkCount definition.

            leaf individualAggregator  {
                type  cml_data_types:CML_UINT8_T;
                description "";
            } // END of individualAggregator definition.

            leaf aggregatorReady  {
                type  cml_data_types:CML_UINT8_T;
                description "";
            } // END of aggregatorReady definition.

            leaf partnerSystemPriority  {
                type  cml_data_types:CML_STRING_T;
                description "";
            } // END of partnerSystemPriority definition.

            leaf partnerSystem  {
                type  cml_data_types:CML_MAC_ADDR_T;
                description "";
            } // END of partnerSystem definition.

            leaf partnerOperAggregatorKey  {
                type  cml_data_types:CML_STRING_T;
                description "";
            } // END of partnerOperAggregatorKey definition.

            leaf mlagId  {
                if-feature feature_list:HAVE_MLAG;
                type  cml_data_types:CML_UINT16_T;
                description "";
            } // END of mlagId definition.

            leaf neighPartnerSystem  {
                if-feature feature_list:HAVE_MCEC;
                type  cml_data_types:CML_MAC_ADDR_T;
                description "";
            } // END of neighPartnerSystem definition.

            leaf neighPartnerSystemPriority  {
                if-feature feature_list:HAVE_MCEC;
                type  cml_data_types:CML_UINT16_T;
                description "";
            } // END of neighPartnerSystemPriority definition.

            leaf neighPartnerAggKey  {
                if-feature feature_list:HAVE_MCEC;
                type  cml_data_types:CML_UINT16_T;
                description "";
            } // END of neighPartnerAggKey definition.


            list lacpLink {
                key "aggLinkIndex";
                config false;
                description
                    "lacp link runtime attributes";
                leaf aggLinkIndex  {
                    type  cml_data_types:CML_INT32_T;
                    description "";
                } // END of aggLinkIndex definition.

                leaf lacpLinkName  {
                    type  cml_data_types:CML_STRING_T;
                    description "";
                } // END of lacpLinkName definition.

                leaf linkActorPortNumber  {
                    type  cml_data_types:CML_UINT32_T;
                    description "";
                } // END of linkActorPortNumber definition.

                leaf linkSyncState  {
                    type  cml_data_types:CML_UINT8_T;
                    description "";
                } // END of linkSyncState definition.

                leaf rcvState  {
                    type  cml_data_types:CML_LACP_RCV_STATE_T;
                    description "";
                } // END of rcvState definition.

                leaf periodicTxState  {
                    type  cml_data_types:CML_LACP_PERIODIC_TX_STATE_T;
                    description "";
                } // END of periodicTxState definition.

                leaf muxMachineState  {
                    type  cml_data_types:CML_LACP_MUX_STATE_T;
                    description "";
                } // END of muxMachineState definition.

                leaf linkActorSystem  {
                    type  cml_data_types:CML_MAC_ADDR_T;
                    description "";
                } // END of linkActorSystem definition.

                leaf actorSystemPriority  {
                    type  cml_data_types:CML_STRING_T;
                    description "";
                } // END of actorSystemPriority definition.

                leaf actorPortNumber  {
                    type  cml_data_types:CML_UINT16_T;
                    description "";
                } // END of actorPortNumber definition.

                leaf actorPortPriority  {
                    type  cml_data_types:CML_STRING_T;
                    description "";
                } // END of actorPortPriority definition.

                leaf actorAdminPortKey  {
                    type  cml_data_types:CML_STRING_T;
                    description "";
                } // END of actorAdminPortKey definition.

                leaf actorOperPortKey  {
                    type  cml_data_types:CML_STRING_T;
                    description "";
                } // END of actorOperPortKey definition.

                leaf partnerAdminSystem  {
                    type  cml_data_types:CML_MAC_ADDR_T;
                    description "";
                } // END of partnerAdminSystem definition.

                leaf partnerOperSystem  {
                    type  cml_data_types:CML_MAC_ADDR_T;
                    description "";
                } // END of partnerOperSystem definition.

                leaf partnerOperKey  {
                    type  cml_data_types:CML_STRING_T;
                    description "";
                } // END of partnerOperKey definition.

                leaf partnerAdminSystemPriority  {
                    type  cml_data_types:CML_STRING_T;
                    description "";
                } // END of partnerAdminSystemPriority definition.

                leaf partnerOperSystemPriority  {
                    type  cml_data_types:CML_STRING_T;
                    description "";
                } // END of partnerOperSystemPriority definition.

                leaf partnerAdminPortNumber  {
                    type  cml_data_types:CML_UINT16_T;
                    description "";
                } // END of partnerAdminPortNumber definition.

                leaf partnerOperPortNumber  {
                    type  cml_data_types:CML_UINT16_T;
                    description "";
                } // END of partnerOperPortNumber definition.

                leaf partnerAdminPortPriority  {
                    type  cml_data_types:CML_STRING_T;
                    description "";
                } // END of partnerAdminPortPriority definition.

                leaf partnerOperPortPriority  {
                    type  cml_data_types:CML_STRING_T;
                    description "";
                } // END of partnerOperPortPriority definition.

                leaf lacpduSentCount  {
                    type  cml_data_types:CML_UINT32_T;
                    description "";
                } // END of lacpduSentCount definition.

                leaf lacpduRecvCount  {
                    type  cml_data_types:CML_UINT16_T;
                    description "";
                } // END of lacpduRecvCount definition.

                leaf mpduRecvCount  {
                    type  cml_data_types:CML_UINT32_T;
                    description "";
                } // END of mpduRecvCount definition.

                leaf mpduSentCount  {
                    type  cml_data_types:CML_UINT32_T;
                    description "";
                } // END of mpduSentCount definition.

                leaf pcktSentErrCount  {
                    type  cml_data_types:CML_UINT32_T;
                    description "";
                } // END of pcktSentErrCount definition.

                leaf pcktRecvErrCount  {
                    type  cml_data_types:CML_UINT32_T;
                    description "";
                } // END of pcktRecvErrCount definition.

                leaf mpduResponseRecvCount  {
                    type  cml_data_types:CML_UINT32_T;
                    description "";
                } // END of mpduResponseRecvCount definition.

                leaf mpduResponseSentCount  {
                    type  cml_data_types:CML_UINT32_T;
                    description "";
                } // END of mpduResponseSentCount definition.

                leaf protocolDa  {
                    if-feature feature_list:HAVE_LACPV2;
                    type  cml_data_types:CML_PROTOCOL_DEST_ADDR_TYPE_T;
                    description "";
                } // END of protocolDa definition.

                leaf actorVersion  {
                    if-feature feature_list:HAVE_LACPV2;
                    type  cml_data_types:CML_UINT32_T;
                    description "";
                } // END of actorVersion definition.

                leaf partnerLacpduVersionNumber  {
                    if-feature feature_list:HAVE_LACPV2;
                    type  cml_data_types:CML_UINT32_T;
                    description "";
                } // END of partnerLacpduVersionNumber definition.

                container lacpLinkCsfcd {
                    if-feature feature_list:HAVE_LACPV2;
                    config false;
                    description
                        "link csfcd runtime attributes";
                    leaf partnerActparSync  {
                        type  cml_data_types:CML_BOOL_T;
                        description "";
                    } // END of partnerActparSync definition.

                    leaf actparSync  {
                        type  cml_data_types:CML_BOOL_T;
                        description "";
                    } // END of actparSync definition.

                    leaf longLacpduTransmit  {
                        type  cml_data_types:CML_BOOL_T;
                        description "";
                    } // END of longLacpduTransmit definition.

                } // END of lacpLinkCsfcd-container definition.
                container actorOperState {
                    config false;
                    description
                        "link actor operation states";
                    uses linkState;
                } // END of actorOperState-container definition.
                container actorAdminState {
                    config false;
                    description
                        "link actor admin states";
                    uses linkState;
                } // END of actorAdminState-container definition.
                container partnerOperState {
                    config false;
                    description
                        "link partner operation states";
                    uses linkState;
                } // END of partnerOperState-container definition.
                container partnerAdminState {
                    config false;
                    description
                        "link partner admin states";
                    uses linkState;
                } // END of partnerAdminState-container definition.
                container lacpLinkInterface {
                    config false;
                    description
                        "link inteface runtime attributes";
                    leaf lacpAdminKey  {
                        type  cml_data_types:CML_UINT16_T;
                        description "";
                    } // END of lacpAdminKey definition.

                } // END of lacpLinkInterface-container definition.
            } // End of lacpLink-list
        } // End of lacpAggregator-list
        container lacpSystemPriority {
            description
                "LACP System Identifier";
            leaf systemPriority  {
                type  cml_data_types:CML_UINT32_T {
                     range "0..65535";
                }
                default "32768";
                description "";
            } // END of systemPriority definition.

            leaf systemId  {
                type  cml_data_types:CML_MAC_ADDR_T;
                config false;
                description "";
            } // END of systemId definition.

        } // END of lacpSystemPriority-container definition.
    } // END of lacpMaster-container definition.
    } // END of lacpMaster-container definition.

    grouping  lacpInterface-grouping {
    description
        "LACP interface related operations";
    container lacpInterface {
        description
            "LACP interface related operations";
        leaf portPriority  {
            type  cml_data_types:CML_UINT32_T {
                 range "1..65535";
            }
            default "32768";
            description "";
        } // END of portPriority definition.

        leaf timeout  {
            type  cml_data_types:CML_LACP_TIMEOUT_T;
            default "long";
            description "";
        } // END of timeout definition.

        leaf bridgeType  {
            if-feature feature_list:HAVE_LACPV2;
            type  cml_data_types:CML_LACP_BRIDGETYPE_T;
            default "multicast-group-address";
            description "";
        } // END of bridgeType definition.

        leaf discardConv  {
            if-feature feature_list:HAVE_LACPV2;
            type  cml_data_types:CML_LACP_DISCARD_CONV_T;
            default "disable";
            description "";
        } // END of discardConv definition.

        leaf forceUp  {
            type  cml_data_types:CML_BOOL_T;
            default false;
            description "";
        } // END of forceUp definition.

    } // END of lacpInterface-container definition.
    } // END of lacpInterface-container definition.

    grouping  lacpdebug-grouping {
    description
        "lacpdebug";
    container lacpdebug {
        description
            "lacpdebug";
        leaf debugLacp  {
            type  cml_data_types:CML_LACP_DEBUG_TYPE_T;
            description "";
        } // END of debugLacp definition.

    } // END of lacpdebug-container definition.
    } // END of lacpdebug-container definition.


}
