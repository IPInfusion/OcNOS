/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-sflow.yang
*
*/

submodule zebos-sflow {

    belongs-to  zebos { prefix zebos; }

    import cml_data_types {
        prefix cml_data_types;
    }

    import feature_list {
        prefix feature_list;
    }

    organization
        "IP Infusion Inc.";

    contact
        "Address: 3965 Freedom Circle, Suite 200, Santa Clara, CA 95054
        Phone: +1 408-400-1900
        E-mail: support@ipinfusion.com
        Web: http://www.ipinfusion.com/";

    description
        "sflow configurations";


    revision "2018-06-21" {
        description " Initial Version.";
        reference "";
    }


    grouping  sflow-grouping {
    description
        "sflow";
    container sflow {
        presence "yes";
        description
            "sflow";
        leaf sflowInstance  {
            type  cml_data_types:CML_BOOL_T;
            mandatory true;
            description "If more than one sFlow sampler is available for this SFlowDataSource then individual samplers are distinguished using the SFlowInstance variable. The value of SFlowInstance ranges from 1..n where n is the number of samplers associated with this SFlowDataSource";
        } // END of sflowInstance definition.

        leaf sflowVersion  {
            type  cml_data_types:CML_STRING_T;
            config false;
            description "Uniquely identifies the version and implementation of this MIB.The MIB Version willchange with each revision of the SFLOW MIB.Management entities must check the MIB Version and not attempt to manage agents with MIB Versions greater than that for which they were designed.";
        } // END of sflowVersion definition.

        leaf sflowAgentIp  {
            if-feature feature_list:HAVE_SFLOW;
            type  cml_data_types:CML_IPV4_ADDR_T;
            description "The IP address associated with this agent. In the case of a multi-homed agent, this should be the loopback address of the agent. The sFlowAgent address must provide SNMP connectivity to the agent. The address should be an invariant that does not change as interfaces are reconfigured, enabled, disabled,added or removed. A manager should be able to use the sFlowAgentAddress as a unique key that will identify this agent over extended periods of time so that a history can be maintained.";
        } // END of sflowAgentIp definition.

        leaf collectorIP  {
            if-feature feature_list:HAVE_SFLOW;
            type  cml_data_types:CML_IPV4_ADDR_T;
            description "The IP address of the sFlow collector.If set to 0.0.0.0 no sFlow datagrams will be sent.";
        } // END of collectorIP definition.

        leaf port  {
            if-feature feature_list:HAVE_SFLOW;
            type  cml_data_types:CML_INT32_T {
                 range "1024..65535";
            }
            description "The destination port for sFlow datagrams.";
        } // END of port definition.

        leaf receiverTimeout  {
            if-feature feature_list:HAVE_SFLOW;
            type  cml_data_types:CML_INT32_T {
                 range "0..2147483647";
            }
            description "The time (in seconds) remaining before the sampler is released and stops sampling. When set, the owner establishes control for the specified period. When read, the remaining time in the interval is returned.A management entity wanting to maintain control of the sampler is responsible for setting a new value before the old one expires.When the interval expires, the agent is responsible for restoring all other entities in this row to their default values. It must also free all other resources associated with this sFlowRcvrTable entry.";
        } // END of receiverTimeout definition.

        leaf maxDatagramSize  {
            if-feature feature_list:HAVE_SFLOW;
            type  cml_data_types:CML_INT32_T {
                 range "200..9000";
            }
            description "The maximum number of data bytes that can be sent in a single sample datagram. The manager should set this value to avoid fragmentation of the sFlow datagrams.";
        } // END of maxDatagramSize definition.

        leaf sflowDatagramVersion  {
            type  cml_data_types:CML_INT32_T;
            config false;
            description "The version of sFlow datagrams that should be sent.When set to a value not support by the agent, the agent should adjust the value to the highest supported value less than the requested value, or return an SNMP bad value error if no such value exists.";
        } // END of sflowDatagramVersion definition.

        leaf rate  {
            if-feature feature_list:HAVE_SFLOW;
            if-feature feature_list:HAVE_BROADCOM;
            type  cml_data_types:CML_INT32_T {
                 range "2000..100000";
            }
            description "Rate in packets per second";
        } // END of rate definition.

    } // END of sflow-container definition.
    } // END of sflow-container definition.

    grouping  sflowInterfaceConfigs-grouping {
    description
        "sampling and polling-interval configs of an interface";
    container sflowInterfaceConfigs {
        description
            "sampling and polling-interval configs of an interface";
        leaf pollingInterval  {
            type  cml_data_types:CML_INT32_T {
                 range "5..60";
            }
            description "The maximum number of seconds between successive samples of the counters associated with this data source. A sampling interval of 0 disables counter sampling.The agent is permitted to have minimum and maximum allowable values for the counter polling interval. A minimum interval lets the agent designer set an upper bound on the overhead associated with polling, anda maximum interval may be the result of implementation restrictions (such as counter size).In addition notall values between the maximum and minimum may be realizable as the sampling interval (again because of implementation considerations).When the sampling rate is set the agent is free to adjust the value so that it lies between the maximum and minimum values and has the closest achievable value.When read, the agent must return the actual sampling interval it will be using (after the adjustments previously described).The sampling algorithm must converge so that over time the number of packets sampledapproaches 1/Nth of the total number of packets in the monitored flows.";
        } // END of pollingInterval definition.

        leaf pollingCount  {
            type  cml_data_types:CML_UINT32_T;
            config false;
            description "Retrieved from SFLOWPoller";
        } // END of pollingCount definition.

        leaf IngressSamplingStatus  {
            type  cml_data_types:SFLOW_EGRESS_INGRESS_T;
            config false;
            description "Ingress status";
        } // END of IngressSamplingStatus definition.

        leaf IngressSampledPktCount  {
            type  cml_data_types:CML_UINT32_T;
            config false;
            description "Retrieved from SFLOWSampler";
        } // END of IngressSampledPktCount definition.

        leaf EgressSampledPktCount  {
            type  cml_data_types:CML_UINT32_T;
            config false;
            description "Retrieved from SFLOWSampler";
        } // END of EgressSampledPktCount definition.

        leaf EgressSamplingStatus  {
            type  cml_data_types:SFLOW_EGRESS_INGRESS_T;
            config false;
            description "Egress status";
        } // END of EgressSamplingStatus definition.

        leaf limit  {
            if-feature feature_list:HAVE_SFLOW;
            if-feature feature_list:HAVE_UT;
            if-feature feature_list:HAVE_MARVELL;
            type  cml_data_types:CML_UINT32_T;
            config false;
            description "hw configured sampling rate";
        } // END of limit definition.

        leaf sampledPktCnt  {
            if-feature feature_list:HAVE_SFLOW;
            if-feature feature_list:HAVE_UT;
            if-feature feature_list:HAVE_MARVELL;
            type  cml_data_types:CML_UINT32_T;
            config false;
            description "packet sampled count in the hw";
        } // END of sampledPktCnt definition.

        leaf countdownCnt  {
            if-feature feature_list:HAVE_SFLOW;
            if-feature feature_list:HAVE_UT;
            if-feature feature_list:HAVE_MARVELL;
            type  cml_data_types:CML_UINT32_T;
            config false;
            description "packet count down information";
        } // END of countdownCnt definition.

        container samplingIngress {
            description
                "samplingIngress";
            leaf samplingRateIngress  {
                type  cml_data_types:CML_INT32_T {
                     range "1024..16777215";
                }
                description "The statistical sampling rate for packet sampling from this source. Set to N to sample 1/Nth of the packets in the monitored flows.An agent should choose its own algorithm to introduce variance into the sampling so that exactly every Nth packet is not counted. A sampling rateof 1 counts all packets. A sampling rate of 0 disables sampling.The agent is permitted to have minimum and maximum allowable values for the sampling rate. A minimum rate lets the agent designer set an upper bound on the overhead associated with sampling, and a maximum rate may be the result of hardware restrictions (such as counter size). In addition not all values between the maximum and minimum may be realizable as the sampling rate (again because of implementation considerations).When the sampling rate is set the agent is free to adjust the value so that it lies between the maximum and minimum values and has the closest achievable value.When read, the agent must return the actual sampling rate it will be using (after the adjustments previously described). The sampling algorithm must converge so that over time the number of packets sampled approaches 1/Nth of the total number of packets in the monitored flows.";
            } // END of samplingRateIngress definition.

            leaf maxHeaderSizeIngress  {
                type  cml_data_types:CML_INT32_T {
                     range "16..256";
                }
                description "The maximum number of bytes that should be copied from a sampled packet. The agent may have an internal maximum and minimum permissible sizes. If an attempt is made to set this value outside the permissible range then the agent should adjust the value to the closest permissible value.";
            } // END of maxHeaderSizeIngress definition.

        } // END of samplingIngress-container definition.
        container samplingEgress {
            description
                "samplingEgress";
            leaf samplingRateEgress  {
                type  cml_data_types:CML_INT32_T {
                     range "1024..16777215";
                }
                description "The statistical sampling rate for packet sampling from this source Set to N to sample 1/Nth of the packets in the monitored flows.An agent should choose its own algorithm to introduce variance into the sampling so that exactly every Nth packet is not counted. A sampling rateof 1 counts all packets. A sampling rate of 0 disables sampling.The agent is permitted to have minimum and maximum allowable values for the sampling rate. A minimum rate lets the agent designer set an upper bound on the overhead associated with sampling, and a maximum rate may be the result of hardware restrictions (such as counter size). In addition not all values between the maximum and minimum may be realizable as the sampling rate (again because of implementation considerations).When the sampling rate is set the agent is free to adjust the value so that it lies between the maximum and minimum values and has the closest achievable value.When read, the agent must return the actual sampling rate it will be using (after the adjustments previously described). The sampling algorithm must converge so that over time the number of packets sampled approaches 1/Nth of the total number of packets in the monitored flows.";
            } // END of samplingRateEgress definition.

            leaf maxHeaderSizeEgress  {
                type  cml_data_types:CML_INT32_T {
                     range "16..256";
                }
                description "The maximum number of bytes that should be copied from a sampled packet. The agent may have an internal maximum and minimum permissible sizes. If an attempt is made to set this value outside the permissible range then the agent should adjust the value to the closest permissible value.";
            } // END of maxHeaderSizeEgress definition.

        } // END of samplingEgress-container definition.
        container samplingEnable {
            description
                "samplingEnable";
            leaf samplingEnable  {
                type  cml_data_types:CML_BOOL_T;
                description "To enable or disable sampling on an interface after giving the sflow sampling-rate command on the same interface";
            } // END of samplingEnable definition.

        } // END of samplingEnable-container definition.
    } // END of sflowInterfaceConfigs-container definition.
    } // END of sflowInterfaceConfigs-container definition.

    grouping  debugsflow-grouping {
    description
        "debugsflow";
    container debugsflow {
        description
            "debugsflow";
        leaf debugsflow  {
            if-feature feature_list:HAVE_SFLOW;
            type  cml_data_types:CML_SFLOW_DEBUG_TYPE_T;
            description "";
        } // END of debugsflow definition.

        leaf debugtermsflow  {
            if-feature feature_list:HAVE_SFLOW;
            type  cml_data_types:CML_SFLOW_DEBUG_TYPE_T;
            description "";
        } // END of debugtermsflow definition.

    } // END of debugsflow-container definition.
    } // END of debugsflow-container definition.

    grouping  ACLsFlow-grouping {
    description
        "ACLsFlow";
    container ACLsFlow {
        description
            "ACLsFlow";
        leaf cacheSize  {
            if-feature feature_list:HAVE_SFLOW;
            if-feature feature_list:HAVE_ACL;
            type  cml_data_types:CML_INT32_T {
                 range "1000..10000";
            }
            description "Specifies the maximum number of log entries that are cached, default is 1000 entries";
        } // END of cacheSize definition.

        leaf accessRate  {
            if-feature feature_list:HAVE_SFLOW;
            if-feature feature_list:HAVE_ACL;
            if-feature feature_list:HAVE_BROADCOM;
            type  cml_data_types:CML_INT16_T {
                 range "0..1000";
            }
            description "Configures rate limits in packets per second, Default is 200 packets/sec";
        } // END of accessRate definition.

    } // END of ACLsFlow-container definition.
    } // END of ACLsFlow-container definition.


}
