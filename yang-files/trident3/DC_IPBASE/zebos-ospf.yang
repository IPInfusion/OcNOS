/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-ospf.yang
*
*/

submodule zebos-ospf {

    belongs-to  zebos { prefix zebos; }

    import cml_data_types {
        prefix cml_data_types;
    }

    import feature_list {
        prefix feature_list;
    }

    include zebos-vrf;
    include zebos-vrf;
    organization
        "IP Infusion Inc.";

    contact
        "Address: 3965 Freedom Circle, Suite 200, Santa Clara, CA 95054
        Phone: +1 408-400-1900
        E-mail: support@ipinfusion.com
        Web: http://www.ipinfusion.com/";

    description
        "Layer-3 ospf configurations";


    revision "2018-06-21" {
        description " Initial Version.";
        reference "";
    }



    grouping ospf-grouping {
    description
        "OSPF attributes for each ospf process id";
        list ospf {
            key "ospfProcessId";
            description
                "OSPF attributes for each ospf process id";
            leaf ospfUpTime  {
                type  cml_data_types:CML_STRING_T;
                config false;
                description "";
            } // END of ospfUpTime definition.

            leaf ddCountIn  {
                type  cml_data_types:CML_UINT16_T;
                config false;
                description "";
            } // END of ddCountIn definition.

            leaf ddCountOut  {
                type  cml_data_types:CML_UINT16_T;
                config false;
                description "";
            } // END of ddCountOut definition.

            leaf externalLsaCount  {
                type  cml_data_types:CML_INT32_T;
                config false;
                description "";
            } // END of externalLsaCount definition.

            leaf externalLsaChecksum  {
                type  cml_data_types:CML_STRING_T;
                config false;
                description "";
            } // END of externalLsaChecksum definition.

            leaf opaqueLsaCount  {
                type  cml_data_types:CML_INT32_T;
                config false;
                description "";
            } // END of opaqueLsaCount definition.

            leaf opaqueLsaChecksum  {
                type  cml_data_types:CML_STRING_T;
                config false;
                description "";
            } // END of opaqueLsaChecksum definition.

            leaf nonDefaulExternalLsaCount  {
                type  cml_data_types:CML_INT32_T;
                config false;
                description "";
            } // END of nonDefaulExternalLsaCount definition.

            leaf lsdbExceedOverflowInterval  {
                type  cml_data_types:CML_UINT32_T;
                config false;
                description "";
            } // END of lsdbExceedOverflowInterval definition.

            leaf lsaOriginateCount  {
                type  cml_data_types:CML_UINT32_T;
                config false;
                description "";
            } // END of lsaOriginateCount definition.

            leaf lsaRecievedCount  {
                type  cml_data_types:CML_UINT32_T;
                config false;
                description "";
            } // END of lsaRecievedCount definition.

            leaf areaCount  {
                type  cml_data_types:CML_INT32_T;
                config false;
                description "";
            } // END of areaCount definition.

            leaf dsteStatus  {
                if-feature feature_list:HAVE_DSTE;
                type  cml_data_types:CML_STRING_T;
                config false;
                description "";
            } // END of dsteStatus definition.

            leaf ospfPacketSendBuffer  {
                type  cml_data_types:CML_UINT32_T;
                config false;
                description "";
            } // END of ospfPacketSendBuffer definition.

            leaf ospfLsaBuffer  {
                type  cml_data_types:CML_UINT32_T;
                config false;
                description "";
            } // END of ospfLsaBuffer definition.

            leaf ospfPacketUnusedCount  {
                type  cml_data_types:CML_UINT32_T;
                config false;
                description "";
            } // END of ospfPacketUnusedCount definition.

            leaf ospfTotalPacketUnusedCount  {
                type  cml_data_types:CML_UINT32_T;
                config false;
                description "";
            } // END of ospfTotalPacketUnusedCount definition.

            leaf ospfStatsUpTime  {
                type  cml_data_types:CML_STRING_T;
                config false;
                description "";
            } // END of ospfStatsUpTime definition.

            leaf ospfRouterIdChanges  {
                type  cml_data_types:CML_UINT32_T;
                config false;
                description "";
            } // END of ospfRouterIdChanges definition.

            leaf ospfDRElectionCounter  {
                type  cml_data_types:CML_UINT32_T;
                config false;
                description "";
            } // END of ospfDRElectionCounter definition.

            leaf ospfOlderLsaReceived  {
                type  cml_data_types:CML_UINT32_T;
                config false;
                description "";
            } // END of ospfOlderLsaReceived definition.

            leaf ospfNbrStateChangeCount  {
                type  cml_data_types:CML_UINT32_T;
                config false;
                description "";
            } // END of ospfNbrStateChangeCount definition.

            leaf ospfNbrExpirationCount  {
                type  cml_data_types:CML_UINT32_T;
                config false;
                description "";
            } // END of ospfNbrExpirationCount definition.

            leaf ospfNbrBadLsReqsCount  {
                type  cml_data_types:CML_UINT32_T;
                config false;
                description "";
            } // END of ospfNbrBadLsReqsCount definition.

            leaf ospfNbrSeqNumMismatchCount  {
                type  cml_data_types:CML_UINT32_T;
                config false;
                description "";
            } // END of ospfNbrSeqNumMismatchCount definition.

            leaf ospfSpfFull  {
                type  cml_data_types:CML_UINT32_T;
                config false;
                description "";
            } // END of ospfSpfFull definition.

            leaf ospfSpfSummary  {
                type  cml_data_types:CML_UINT32_T;
                config false;
                description "";
            } // END of ospfSpfSummary definition.

            leaf ospfSpfExternal  {
                type  cml_data_types:CML_UINT32_T;
                config false;
                description "";
            } // END of ospfSpfExternal definition.

            leaf defaultRouterId  {
                type  cml_data_types:CML_STRING_T;
                config false;
                description "";
            } // END of defaultRouterId definition.

            leaf ospfProcessId  {
                type  cml_data_types:CML_UINT16_T {
                     range "0..65535";
                }
                description "OSPF process ID";
            } // END of ospfProcessId definition.

            leaf vrfName  {
                type  cml_data_types:CML_STRING_T;
                description "";
            } // END of vrfName definition.

            leaf routerId  {
                type  cml_data_types:CML_IPV4_ADDR_T;
                description "The router identifier";
            } // END of routerId definition.

            leaf floodReduction  {
                type  cml_data_types:CML_BOOL_T;
                description "floodReduction";
            } // END of floodReduction definition.

            leaf isCompitableRfc1583  {
                type  cml_data_types:CML_BOOL_T;
                description "TRUE will set and FALSE will unset";
            } // END of isCompitableRfc1583 definition.

            leaf isdbSummary  {
                type  cml_data_types:CML_BOOL_T;
                description "isdbSummary";
            } // END of isdbSummary definition.

            leaf bfdEnabled  {
                if-feature feature_list:HAVE_BFD;
                type  cml_data_types:CML_BOOL_T;
                description "";
            } // END of bfdEnabled definition.

            leaf cspfEnabled  {
                if-feature feature_list:HAVE_OSPF_CSPF;
                type  cml_data_types:CML_BOOL_T;
                description "cspfEnabled";
            } // END of cspfEnabled definition.

            leaf cspfTieBreak  {
                if-feature feature_list:HAVE_OSPF_CSPF;
                type  cml_data_types:CML_OSPF6_CSPF_TYPE_T;
                description "";
            } // END of cspfTieBreak definition.

            leaf cspfDefRetryInterval  {
                if-feature feature_list:HAVE_OSPF_CSPF;
                type  cml_data_types:CML_UINT16_T {
                     range "1..3600";
                }
                description "Interval";
            } // END of cspfDefRetryInterval definition.

            leaf cspfBetterProtection  {
                if-feature feature_list:HAVE_GMPLS;
                if-feature feature_list:HAVE_OSPF_CSPF;
                type  cml_data_types:CML_BOOL_T;
                description "cspfBetterProtection";
            } // END of cspfBetterProtection definition.

            leaf vrfLiteEnable  {
                if-feature feature_list:HAVE_VRF_OSPF;
                type  cml_data_types:CML_BOOL_T;
                description "vrfLiteEnable";
            } // END of vrfLiteEnable definition.

            leaf logAdjacencyDebugType  {
                type  cml_data_types:CML_STRING_T;
                description "";
            } // END of logAdjacencyDebugType definition.

            leaf shutDown  {
                type  cml_data_types:CML_BOOL_T;
                description "shutDown";
            } // END of shutDown definition.

            leaf areaBorderType  {
                type  cml_data_types:CML_OSPF_ABR_TYPE_T;
                description "";
            } // END of areaBorderType definition.

            leaf spfMinDelay  {
                type  cml_data_types:CML_UINT32_T {
                     range "0..2147483647";
                }
                default "500";
                description "The minimum SPF hold delay time in milliseconds: 500 milliseconds.";
            } // END of spfMinDelay definition.

            leaf spfMaxDelay  {
                type  cml_data_types:CML_UINT32_T {
                     range "0..2147483647";
                }
                default "5000";
                description "The maximum SPF hold delay time in milliseconds: 50000 milliseconds (50 seconds)";
            } // END of spfMaxDelay definition.

            leaf throttleTimersStartDelay  {
                type  cml_data_types:CML_UINT32_T {
                     range "0..600000";
                }
                default "0";
                description "";
            } // END of throttleTimersStartDelay definition.

            leaf throttleMinInterval  {
                type  cml_data_types:CML_UINT32_T {
                     range "1..600000";
                }
                default "5000";
                description "The maximum SPF hold delay time in milliseconds: 50000 milliseconds (50 seconds)";
            } // END of throttleMinInterval definition.

            leaf throttleTimersMaxDelay  {
                type  cml_data_types:CML_UINT32_T {
                     range "1..600000";
                }
                default "5000";
                description "";
            } // END of throttleTimersMaxDelay definition.

            leaf lsaMinArrival  {
                type  cml_data_types:CML_UINT32_T {
                     range "0..600000";
                }
                default "1";
                description "";
            } // END of lsaMinArrival definition.

            leaf referenceBandwidth  {
                type  cml_data_types:CML_INT32_T {
                     range "1..4294967";
                }
                default "100000";
                description "";
            } // END of referenceBandwidth definition.

            leaf maxDBDescriptor  {
                type  cml_data_types:CML_UINT16_T {
                     range "1..65535";
                }
                default "5000";
                description "";
            } // END of maxDBDescriptor definition.

            leaf restartMethod  {
                if-feature feature_list:HAVE_RESTART;
                type  cml_data_types:CML_BOOL_T;
                description "";
            } // END of restartMethod definition.

            leaf restartMethodlls  {
                if-feature feature_list:HAVE_RESTART;
                type  cml_data_types:CML_BOOL_T;
                description "";
            } // END of restartMethodlls definition.

            leaf isCapabilityOpaque  {
                if-feature feature_list:HAVE_OPAQUE_LSA;
                type  cml_data_types:CML_BOOL_T;
                description "";
            } // END of isCapabilityOpaque definition.

            leaf isCapabilityTe  {
                if-feature feature_list:HAVE_OSPF_TE;
                type  cml_data_types:CML_OSPF_CAPABILITY_TE_T;
                description "";
            } // END of isCapabilityTe definition.

            leaf metricValue  {
                type  cml_data_types:CML_UINT32_T {
                     range "1..16777214";
                }
                default "2";
                description "";
            } // END of metricValue definition.

            leaf lsdbExternalLimit  {
                if-feature feature_list:HAVE_OSPF_DB_OVERFLOW;
                type  cml_data_types:CML_UINT32_T {
                     range "0..2147483647";
                }
                description "";
            } // END of lsdbExternalLimit definition.

            leaf exitOverflowInterval  {
                if-feature feature_list:HAVE_OSPF_DB_OVERFLOW;
                type  cml_data_types:CML_UINT32_T {
                     range "0..65535";
                }
                default "0";
                description "";
            } // END of exitOverflowInterval definition.

            leaf lsdbLimit  {
                type  cml_data_types:CML_UINT32_T {
                     range "0..4294967294";
                }
                default "0";
                description "";
            } // END of lsdbLimit definition.

            leaf lsdbLimitType  {
                type  cml_data_types:CML_OSPF_ACTION_TYPE_T;
                description "";
            } // END of lsdbLimitType definition.

            leaf maxAreaLimit  {
                type  cml_data_types:CML_UINT32_T {
                     range "1..4294967294";
                }
                description "";
            } // END of maxAreaLimit definition.

            leaf ospfmaxUnusePackets  {
                type  cml_data_types:CML_UINT32_T {
                     range "0..65535";
                }
                default "200";
                description "";
            } // END of ospfmaxUnusePackets definition.

            leaf lsaunuseMax  {
                type  cml_data_types:CML_UINT16_T {
                     range "0..65535";
                }
                description "";
            } // END of lsaunuseMax definition.

            leaf refreshTimer  {
                type  cml_data_types:CML_UINT32_T {
                     range "10..1800";
                }
                default "10";
                description "";
            } // END of refreshTimer definition.

            leaf isP2pRfcIncompatible  {
                type  cml_data_types:CML_BOOL_T;
                description "";
            } // END of isP2pRfcIncompatible definition.

            leaf isFrrSet  {
                if-feature feature_list:HAVE_OSPF_LFA;
                type  cml_data_types:CML_BOOL_T;
                description "";
            } // END of isFrrSet definition.

            leaf srMpls  {
                if-feature feature_list:HAVE_SR_MPLS;
                type  cml_data_types:CML_BOOL_T;
                description "";
            } // END of srMpls definition.

            leaf ospfsrgbBase  {
                type  cml_data_types:CML_INT32_T {
                     range "16000..23999";
                }
                description "";
            } // END of ospfsrgbBase definition.

            leaf ospfsrgbRangeSize  {
                if-feature feature_list:HAVE_SR_MPLS;
                type  cml_data_types:CML_INT32_T {
                     range "16000..23999";
                }
                description "";
            } // END of ospfsrgbRangeSize definition.

            leaf adminDistance  {
                type  cml_data_types:CML_INT32_T {
                     range "1..255";
                }
                description "";
            } // END of adminDistance definition.


            list ospfInterfaceNeighbor {
                key "ospfNbrIfname";
                config false;
                description
                    "ospfInterfaceNeighbor";
                leaf ospfNbrIfname  {
                    type  cml_data_types:CML_STRING_T;
                    description "";
                } // END of ospfNbrIfname definition.

                leaf ospfAreaId  {
                    type  cml_data_types:CML_STRING_T;
                    description "";
                } // END of ospfAreaId definition.


                list ospfNeighborRuntime {
                    key "ospfNbrRouterId";
                    config false;
                    description
                        "ospfNeighborRuntime";
                    leaf ospfNbrRouterId  {
                        type  cml_data_types:CML_STRING_T;
                        description "";
                    } // END of ospfNbrRouterId definition.

                    leaf ospfNbrOptions  {
                        type  cml_data_types:CML_STRING_T;
                        description "";
                    } // END of ospfNbrOptions definition.

                    leaf ospfNeighborState  {
                        type  cml_data_types:CML_STRING_T;
                        description "";
                    } // END of ospfNeighborState definition.

                    leaf ospfNbrEvents  {
                        type  cml_data_types:CML_UINT32_T;
                        description "";
                    } // END of ospfNbrEvents definition.

                    leaf ospfNbrAddressLessIndex  {
                        type  cml_data_types:CML_UINT32_T;
                        description "";
                    } // END of ospfNbrAddressLessIndex definition.

                    leaf ospfNbrLsRetransQLen  {
                        type  cml_data_types:CML_UINT32_T;
                        description "";
                    } // END of ospfNbrLsRetransQLen definition.

                    leaf ospfNbmaNbrPermanence  {
                        type  cml_data_types:CML_UINT32_T;
                        description "";
                    } // END of ospfNbmaNbrPermanence definition.

                    leaf ospfNbrHelloSuppressed  {
                        type  cml_data_types:CML_UINT32_T;
                        description "";
                    } // END of ospfNbrHelloSuppressed definition.

                    leaf ospfNbrRestartHelperStatus  {
                        if-feature feature_list:HAVE_RESTART;
                        type  cml_data_types:CML_UINT32_T;
                        description "";
                    } // END of ospfNbrRestartHelperStatus definition.

                    leaf ospfNbrRestartHelperAge  {
                        if-feature feature_list:HAVE_RESTART;
                        type  cml_data_types:CML_UINT32_T;
                        description "";
                    } // END of ospfNbrRestartHelperAge definition.

                    leaf ospfNbrRestartHelperExitReason  {
                        if-feature feature_list:HAVE_RESTART;
                        type  cml_data_types:CML_UINT32_T;
                        description "";
                    } // END of ospfNbrRestartHelperExitReason definition.

                    leaf ospfLsDbCount  {
                        type  cml_data_types:CML_UINT32_T;
                        description "";
                    } // END of ospfLsDbCount definition.

                    leaf ospfLsRequestCount  {
                        type  cml_data_types:CML_UINT32_T;
                        description "";
                    } // END of ospfLsRequestCount definition.

                    leaf ospfLsRetransmitCount  {
                        type  cml_data_types:CML_UINT32_T;
                        description "";
                    } // END of ospfLsRetransmitCount definition.

                    leaf llsOptions  {
                        if-feature feature_list:HAVE_RESTART;
                        type  cml_data_types:CML_STRING_T;
                        description "";
                    } // END of llsOptions definition.

                    leaf llsExtendedOption  {
                        if-feature feature_list:HAVE_RESTART;
                        type  cml_data_types:CML_STRING_T;
                        description "";
                    } // END of llsExtendedOption definition.

                    leaf lastOobResyncTime  {
                        if-feature feature_list:HAVE_RESTART;
                        type  cml_data_types:CML_STRING_T;
                        description "";
                    } // END of lastOobResyncTime definition.

                    leaf oobResyncTimeout  {
                        if-feature feature_list:HAVE_RESTART;
                        type  cml_data_types:CML_STRING_T;
                        description "";
                    } // END of oobResyncTimeout definition.

                    leaf deadTimerDueTime  {
                        type  cml_data_types:CML_STRING_T;
                        description "";
                    } // END of deadTimerDueTime definition.

                    leaf ospfPollTimerDueIn  {
                        type  cml_data_types:CML_STRING_T;
                        description "";
                    } // END of ospfPollTimerDueIn definition.

                    leaf ospfNeighborUpTime  {
                        type  cml_data_types:CML_STRING_T;
                        description "";
                    } // END of ospfNeighborUpTime definition.

                    leaf ospfCryptSeqNum  {
                        if-feature feature_list:HAVE_MD5;
                        type  cml_data_types:CML_UINT32_T;
                        description "";
                    } // END of ospfCryptSeqNum definition.

                    leaf ospfDesignatedRouter  {
                        type  cml_data_types:CML_STRING_T;
                        description "";
                    } // END of ospfDesignatedRouter definition.

                    leaf ospfBackDesignatedRouter  {
                        type  cml_data_types:CML_STRING_T;
                        description "";
                    } // END of ospfBackDesignatedRouter definition.

                    leaf threadInactivityTimer  {
                        type  cml_data_types:CML_ON_OFF_T;
                        description "";
                    } // END of threadInactivityTimer definition.

                    leaf threadDBdescRetransmission  {
                        type  cml_data_types:CML_ON_OFF_T;
                        description "";
                    } // END of threadDBdescRetransmission definition.

                    leaf threadLinkStateRqstRetransmission  {
                        type  cml_data_types:CML_ON_OFF_T;
                        description "";
                    } // END of threadLinkStateRqstRetransmission definition.

                    leaf threadLinkStateUpdateRetransmission  {
                        type  cml_data_types:CML_ON_OFF_T;
                        description "";
                    } // END of threadLinkStateUpdateRetransmission definition.

                    leaf ospfNeighborPriority  {
                        type  cml_data_types:CML_UINT32_T;
                        description "";
                    } // END of ospfNeighborPriority definition.

                } // End of ospfNeighborRuntime-list
            } // End of ospfInterfaceNeighbor-list

            list passiveInterface {
                key "passiveIfName";
                description
                    "OSPF Passive Interface list";
                leaf passiveIfName  {
                    type  cml_data_types:CML_STRING_T;
                    description "";
                } // END of passiveIfName definition.

                leaf-list passiveIfAddr  {
                    type  cml_data_types:CML_IPV4_ADDR_T;
                    description "";
                } // END of passiveIfAddr definition.

            } // End of passiveInterface-list

            list frr_pref {
                if-feature feature_list:HAVE_OSPF_LFA;
                key "frrPrefIndex";
                description
                    "Keeps user preferences, lower index in the array is higher priority";
                leaf frrPrefIndex  {
                    type  cml_data_types:CML_UINT32_T {
                         range "1..10";
                    }
                    description "Index";
                } // END of frrPrefIndex definition.

                leaf frrPrefVal  {
                    if-feature feature_list:HAVE_OSPF_LFA;
                    type  cml_data_types:CML_OSPF_FRR_TIE_BREAK_VAL_T;
                    mandatory true;
                    description "";
                } // END of frrPrefVal definition.

            } // End of frr_pref-list

            list srcDistance {
                key "distprefix";
                description
                    "srcDistance";
                leaf distprefix  {
                    type  cml_data_types:CML_IPV4_ADDR_PREFIX_T;
                    description "";
                } // END of distprefix definition.

                leaf aclDistance  {
                    type  cml_data_types:CML_UINT8_T {
                         range "1..255";
                    }
                    description "";
                } // END of aclDistance definition.

                leaf accessListName  {
                    type  cml_data_types:CML_STRING_T;
                    mandatory true;
                    description "";
                } // END of accessListName definition.

            } // End of srcDistance-list

            list topsrTrunk {
                if-feature feature_list:HAVE_SR_MPLS;
                key "topsrTrunkName";
                description
                    "List of all Segment Routing trunks enabled for this OSPF Instance";
                leaf topsrTrunkName  {
                    type  cml_data_types:CML_STRING_T;
                    description "";
                } // END of topsrTrunkName definition.

            } // End of topsrTrunk-list

            list distributeList {
                if-feature feature_list:HAVE_ACL;
                key "distAccessListName";
                description
                    "Distribute list for OSPF Protocol";
                leaf distAccessListName  {
                    type  cml_data_types:CML_STRING_T;
                    description "";
                } // END of distAccessListName definition.

                leaf ospfDistIn  {
                    type  cml_data_types:CML_BOOL_T;
                    description "";
                } // END of ospfDistIn definition.


                list distributeListProtocol {
                    key "ospfdistProtocol";
                    description
                        "Distribute list for OSPF Protocol";
                    leaf ospfdistProtocol  {
                        type  cml_data_types:CML_OSPF_DIST_ROUTE_SOURCE_TYPE_T;
                        description "";
                    } // END of ospfdistProtocol definition.

                } // End of distributeListProtocol-list

                list distributeListOspf {
                    key "ospfdistOspfProtocol";
                    description
                        "Distribute list for OSPF Protocol";
                    leaf ospfdistOspfProtocol  {
                        type  cml_data_types:CML_INT32_T {
                             range "1..65535";
                        }
                        description "";
                    } // END of ospfdistOspfProtocol definition.

                } // End of distributeListOspf-list
            } // End of distributeList-list

            list redistributeisis {
                key "isisProcessId";
                description
                    "reditribute isis routes to ospf process id";
                leaf isisProcessId  {
                    type  cml_data_types:CML_STRING_T;
                    description "";
                } // END of isisProcessId definition.

                leaf redistOspfMetricType  {
                    type  cml_data_types:CML_OSPF_METRIC_TYPE_T;
                    default "2";
                    description "";
                } // END of redistOspfMetricType definition.

                leaf redistOspfMetricValue  {
                    type  cml_data_types:CML_INT32_T {
                         range "0..16777214";
                    }
                    default "0";
                    description "";
                } // END of redistOspfMetricValue definition.

                leaf redistOspfTag  {
                    type  cml_data_types:CML_UINT32_T {
                         range "0..4294967295";
                    }
                    default "0";
                    description "";
                } // END of redistOspfTag definition.

                leaf ospfrouteMapName  {
                    type  cml_data_types:CML_STRING_T;
                    description "";
                } // END of ospfrouteMapName definition.

            } // End of redistributeisis-list

            list redistributeProc {
                key "secondaryOspfProcessId";
                description
                    "reditribute routes internally to other ospf process id";
                leaf secondaryOspfProcessId  {
                    type  cml_data_types:CML_INT32_T {
                         range "1..65535";
                    }
                    description "";
                } // END of secondaryOspfProcessId definition.

                leaf redistOspfMetricType  {
                    type  cml_data_types:CML_OSPF_METRIC_TYPE_T;
                    default "2";
                    description "";
                } // END of redistOspfMetricType definition.

                leaf redistOspfMetricValue  {
                    type  cml_data_types:CML_INT32_T {
                         range "0..16777214";
                    }
                    default "0";
                    description "";
                } // END of redistOspfMetricValue definition.

                leaf redistOspfTag  {
                    type  cml_data_types:CML_UINT32_T {
                         range "0..4294967295";
                    }
                    default "0";
                    description "";
                } // END of redistOspfTag definition.

                leaf ospfrouteMapName  {
                    type  cml_data_types:CML_STRING_T;
                    description "";
                } // END of ospfrouteMapName definition.

            } // End of redistributeProc-list

            list redistribute {
                key "routeSourceType";
                description
                    "redistribute routes to external process (bgp/static etc.)";
                leaf routeSourceType  {
                    type  cml_data_types:CML_OSPF_ROUTE_SOURCE_TYPE_T;
                    description "";
                } // END of routeSourceType definition.

                leaf redistMetricType  {
                    type  cml_data_types:CML_OSPF_METRIC_TYPE_T;
                    description "";
                } // END of redistMetricType definition.

                leaf redistMetricValue  {
                    type  cml_data_types:CML_INT32_T {
                         range "0..16777214";
                    }
                    description "";
                } // END of redistMetricValue definition.

                leaf redistTag  {
                    type  cml_data_types:CML_UINT32_T {
                         range "0..4294967295";
                    }
                    description "";
                } // END of redistTag definition.

                leaf routeMapName  {
                    type  cml_data_types:CML_STRING_T;
                    description "";
                } // END of routeMapName definition.

            } // End of redistribute-list

            list neighbor {
                key "neighborIpAddr";
                description
                    "ospf neighbour";
                leaf neighborIpAddr  {
                    type  cml_data_types:CML_IPV4_ADDR_T;
                    description "";
                } // END of neighborIpAddr definition.

                leaf neighborCost  {
                    type  cml_data_types:CML_UINT16_T {
                         range "1..65535";
                    }
                    default "10";
                    description "";
                } // END of neighborCost definition.

                leaf ospfNbmaNbrStatus  {
                    type  cml_data_types:CML_OSPF_NBMA_ROW_STATUS;
                    description "";
                } // END of ospfNbmaNbrStatus definition.

                container nbrOptions {
                    description
                        "nbrOptions";
                    leaf neighborStaticPriority  {
                        type  cml_data_types:CML_UINT8_T {
                             range "0..255";
                        }
                        default "0";
                        description "";
                    } // END of neighborStaticPriority definition.

                    leaf neighborPollInterval  {
                        type  cml_data_types:CML_INT32_T {
                             range "1..2147483647";
                        }
                        default "120";
                        description "";
                    } // END of neighborPollInterval definition.

                } // END of nbrOptions-container definition.
            } // End of neighbor-list

            list summary {
                key "summaryAddr";
                description
                    "ospf summary";
                leaf summaryAddr  {
                    type  cml_data_types:CML_IPV4_PREFIX_T;
                    description "";
                } // END of summaryAddr definition.

                leaf summaryAddressNotAdvertise  {
                    type  cml_data_types:CML_BOOL_T;
                    description "";
                } // END of summaryAddressNotAdvertise definition.

                leaf addressTag  {
                    type  cml_data_types:CML_UINT32_T {
                         range "0..4294967295";
                    }
                    description "";
                } // END of addressTag definition.

            } // End of summary-list

            list area {
                key "areaId";
                description
                    "ospf area";
                leaf AreaInterfaceCount  {
                    type  cml_data_types:CML_INT32_T;
                    config false;
                    description "";
                } // END of AreaInterfaceCount definition.

                leaf AreaNeighborCount  {
                    type  cml_data_types:CML_INT32_T;
                    config false;
                    description "";
                } // END of AreaNeighborCount definition.

                leaf spfLastExexTime  {
                    type  cml_data_types:CML_STRING_T;
                    config false;
                    description "";
                } // END of spfLastExexTime definition.

                leaf spfExecCount  {
                    type  cml_data_types:CML_UINT32_T;
                    config false;
                    description "";
                } // END of spfExecCount definition.

                leaf areaLsaCount  {
                    type  cml_data_types:CML_INT32_T;
                    config false;
                    description "";
                } // END of areaLsaCount definition.

                leaf areaLsaChecksum  {
                    type  cml_data_types:CML_STRING_T;
                    config false;
                    description "";
                } // END of areaLsaChecksum definition.

                leaf nssaTranslatorCount  {
                    if-feature feature_list:HAVE_NSSA;
                    type  cml_data_types:CML_INT32_T;
                    config false;
                    description "";
                } // END of nssaTranslatorCount definition.

                leaf nssaTranslatorState  {
                    if-feature feature_list:HAVE_NSSA;
                    type  cml_data_types:CML_STRING_T;
                    config false;
                    description "";
                } // END of nssaTranslatorState definition.

                leaf areaId  {
                    type  cml_data_types:CML_OSPF_AREA_T;
                    description "";
                } // END of areaId definition.

                leaf areaAuthType  {
                    type  cml_data_types:CML_OSPF_AREA_AUTHENTICATION_TYPE_T;
                    description "";
                } // END of areaAuthType definition.

                leaf areaShortcutType  {
                    type  cml_data_types:CML_OSPF_AREA_SHORTCUT_TYPE_T;
                    default "default";
                    description "";
                } // END of areaShortcutType definition.

                leaf areaCost  {
                    type  cml_data_types:CML_UINT32_T {
                         range "0..16777215";
                    }
                    default "1";
                    description "";
                } // END of areaCost definition.

                leaf exportListName  {
                    if-feature feature_list:HAVE_ACL;
                    type  cml_data_types:CML_STRING_T;
                    default "NULL";
                    description "";
                } // END of exportListName definition.

                leaf importListName  {
                    if-feature feature_list:HAVE_ACL;
                    type  cml_data_types:CML_STRING_T;
                    default "NULL";
                    description "";
                } // END of importListName definition.


                list Stub {
                    key "isStubArea";
                    description
                        "ospf area stub configuration";
                    leaf isStubArea  {
                        type  cml_data_types:CML_OSPF_STUB_T;
                        description "";
                    } // END of isStubArea definition.

                    leaf stubAreaNoSummary  {
                        type  cml_data_types:CML_BOOL_T;
                        description "";
                    } // END of stubAreaNoSummary definition.

                } // End of Stub-list

                list Nssa {
                    if-feature feature_list:HAVE_NSSA;
                    key "isNssaArea";
                    description
                        "ospf area stub configuration";
                    leaf isNssaArea  {
                        type  cml_data_types:CML_OSPF_NSSA_T;
                        description "";
                    } // END of isNssaArea definition.

                    leaf nssaStabilityInterval  {
                        type  cml_data_types:CML_INT32_T {
                             range "0..2147483647";
                        }
                        default "40";
                        description "";
                    } // END of nssaStabilityInterval definition.

                    leaf nssaTranslatorRole  {
                        type  cml_data_types:CML_OSPF_TRANSLATOR_ROLE_T;
                        default "candidate";
                        description "";
                    } // END of nssaTranslatorRole definition.

                    leaf nssaDefaultOriginMetric  {
                        type  cml_data_types:CML_INT32_T {
                             range "0..16777214";
                        }
                        default "0";
                        description "";
                    } // END of nssaDefaultOriginMetric definition.

                    leaf nssaDefaultOriginMetricType  {
                        type  cml_data_types:CML_INT32_T {
                             range "1..2";
                        }
                        default "2";
                        description "";
                    } // END of nssaDefaultOriginMetricType definition.

                    leaf isNssaNoDist  {
                        type  cml_data_types:CML_BOOL_T;
                        description "";
                    } // END of isNssaNoDist definition.

                    leaf isNssaDefaultOriginate  {
                        type  cml_data_types:CML_BOOL_T;
                        description "";
                    } // END of isNssaDefaultOriginate definition.

                    leaf nssaAreaNoSummary  {
                        type  cml_data_types:CML_BOOL_T;
                        description "";
                    } // END of nssaAreaNoSummary definition.

                    leaf nssarouteMap  {
                        type  cml_data_types:CML_STRING_T;
                        description "";
                    } // END of nssarouteMap definition.

                } // End of Nssa-list

                list filterPrefixList {
                    if-feature feature_list:HAVE_ACL;
                    key "prefixType";
                    description
                        "filterPrefixList";
                    leaf prefixName  {
                        type  cml_data_types:CML_NONEMPTY_STRING_T;
                        mandatory true;
                        description "";
                    } // END of prefixName definition.

                    leaf prefixType  {
                        type  cml_data_types:CML_OSPF_AREA_FILTER_LIST_PREFIX_T;
                        description "";
                    } // END of prefixType definition.

                } // End of filterPrefixList-list

                list filterAccessList {
                    if-feature feature_list:HAVE_ACL;
                    key "accessType";
                    description
                        "filterAccessList";
                    leaf accessName  {
                        type  cml_data_types:CML_NONEMPTY_STRING_T;
                        mandatory true;
                        description "";
                    } // END of accessName definition.

                    leaf accessType  {
                        type  cml_data_types:CML_OSPF_AREA_FILTER_LIST_PREFIX_T;
                        description "";
                    } // END of accessType definition.

                } // End of filterAccessList-list

                list hostAddr {
                    key "hostIpAddr";
                    description
                        "ospf host entries";
                    leaf hostIpAddr  {
                        type  cml_data_types:CML_IPV4_ADDR_T;
                        description "";
                    } // END of hostIpAddr definition.

                    leaf hostEntryCost  {
                        type  cml_data_types:CML_INT32_T {
                             range "0..65535";
                        }
                        default "0";
                        description "";
                    } // END of hostEntryCost definition.

                } // End of hostAddr-list

                list network {
                    key "networkPrefix";
                    description
                        "ospf network";
                    leaf networkPrefix  {
                        type  cml_data_types:CML_IPV4_PREFIX_T;
                        description "";
                    } // END of networkPrefix definition.

                    leaf InstanceId  {
                        if-feature feature_list:HAVE_OSPF_MULTI_INST;
                        type  cml_data_types:CML_INT16_T {
                             range "0..255";
                        }
                        description "";
                    } // END of InstanceId definition.

                } // End of network-list

                list virtLink {
                    key "peerId";
                    description
                        "ospf virtual link";
                    leaf peerId  {
                        type  cml_data_types:CML_IPV4_ADDR_T;
                        description "";
                    } // END of peerId definition.

                    leaf vlinkAuthType  {
                        type  cml_data_types:CML_OSPF_VLINK_AUTH_TYPE_T;
                        default "authentication-null";
                        description "";
                    } // END of vlinkAuthType definition.

                    leaf vlinkMsgDigestKeyId  {
                        type  cml_data_types:CML_UINT8_T {
                             range "1..255";
                        }
                        description "";
                    } // END of vlinkMsgDigestKeyId definition.

                    leaf vlinkMsgDigestKey  {
                        type  cml_data_types:CML_STRING_T;
                        description "";
                    } // END of vlinkMsgDigestKey definition.

                    leaf vlinkAuthKey  {
                        type  cml_data_types:CML_STRING_T;
                        description "";
                    } // END of vlinkAuthKey definition.

                    leaf vlinkRetransIntvl  {
                        type  cml_data_types:CML_INT32_T {
                             range "1..3600";
                        }
                        default "5";
                        description "";
                    } // END of vlinkRetransIntvl definition.

                    leaf vlinkTransmitDelay  {
                        type  cml_data_types:CML_INT32_T {
                             range "1..3600";
                        }
                        default "1";
                        description "";
                    } // END of vlinkTransmitDelay definition.

                    leaf vlinkHelloInterval  {
                        type  cml_data_types:CML_INT32_T {
                             range "1..65535";
                        }
                        default "10";
                        description "";
                    } // END of vlinkHelloInterval definition.

                    leaf vlinkDeadInterval  {
                        type  cml_data_types:CML_INT32_T {
                             range "1..65535";
                        }
                        default "40";
                        description "";
                    } // END of vlinkDeadInterval definition.

                    leaf vlinkWaitInterval  {
                        type  cml_data_types:CML_INT32_T;
                        config false;
                        description "wait timer interval";
                    } // END of vlinkWaitInterval definition.

                    leaf vlinkName  {
                        type  cml_data_types:CML_STRING_T;
                        config false;
                        description "Virtual Link Name";
                    } // END of vlinkName definition.

                    leaf vlinkStatus  {
                        type  cml_data_types:CML_OSPF_VLINK_STATUS_T;
                        config false;
                        description "Virtual Link Status";
                    } // END of vlinkStatus definition.

                    leaf vlinkInterface  {
                        type  cml_data_types:CML_STRING_T;
                        config false;
                        description "Virtual Link Interface";
                    } // END of vlinkInterface definition.

                    leaf vlinkLocalAddress  {
                        type  cml_data_types:CML_STRING_T;
                        config false;
                        description "Virtual Link Local address";
                    } // END of vlinkLocalAddress definition.

                    leaf vlinkRemoteAddress  {
                        type  cml_data_types:CML_STRING_T;
                        config false;
                        description "Virtual Link Remote address";
                    } // END of vlinkRemoteAddress definition.

                    leaf vlinkHelloDue  {
                        type  cml_data_types:CML_STRING_T;
                        config false;
                        description "Virtual Link Hello due";
                    } // END of vlinkHelloDue definition.

                    leaf vlinkInterfaceState  {
                        type  cml_data_types:CML_OSPF_VLINK_INTERFACE_STATE_T;
                        config false;
                        description "Virtual Link Interface State";
                    } // END of vlinkInterfaceState definition.

                    leaf vlinkAdjState  {
                        type  cml_data_types:CML_OSPF_VLINK_ADJ_STATE_T;
                        config false;
                        description "Virtual Link Adjacency state";
                    } // END of vlinkAdjState definition.

                    container vlinkbfd {
                        description
                            "Bidirectional Forwarding Detection";
                        leaf vlinkFallOverBfd  {
                            if-feature feature_list:HAVE_BFD;
                            type  cml_data_types:CML_BOOL_T;
                            description "";
                        } // END of vlinkFallOverBfd definition.

                    } // END of vlinkbfd-container definition.
                } // End of virtLink-list

                list areaRange {
                    key "rangeId";
                    description
                        "ospf range";
                    leaf rangeId  {
                        type  cml_data_types:CML_IPV4_PREFIX_T;
                        description "";
                    } // END of rangeId definition.

                    leaf rangeAdvertise  {
                        type  cml_data_types:CML_OSPF_AREA_RANGE_ADVERTISE_T;
                        description "";
                    } // END of rangeAdvertise definition.

                    leaf substituteAddr  {
                        type  cml_data_types:CML_IPV4_ADDR_PREFIX_T;
                        description "";
                    } // END of substituteAddr definition.

                } // End of areaRange-list
            } // End of area-list
            container defaultInformation {
                presence "yes";
                description
                    "Default external route Information";
                leaf defaultInformationOriginate  {
                    type  cml_data_types:CML_OSPF_DEFAULT_INFO_T;
                    mandatory true;
                    description "";
                } // END of defaultInformationOriginate definition.

                leaf metric  {
                    type  cml_data_types:CML_UINT32_T {
                         range "0..16777214";
                    }
                    description "";
                } // END of metric definition.

                leaf metricType  {
                    type  cml_data_types:CML_OSPF_METRIC_TYPE_T;
                    description "";
                } // END of metricType definition.

                leaf routeMap  {
                    type  cml_data_types:CML_STRING_T;
                    description "";
                } // END of routeMap definition.

                leaf alwaysSet  {
                    type  cml_data_types:CML_BOOL_T;
                    description "";
                } // END of alwaysSet definition.

            } // END of defaultInformation-container definition.
            container distance {
                description
                    "Define an administrative distance";
                leaf distanceIntra  {
                    type  cml_data_types:CML_UINT32_T {
                         range "1..255";
                    }
                    description "";
                } // END of distanceIntra definition.

                leaf distanceInter  {
                    type  cml_data_types:CML_UINT32_T {
                         range "1..255";
                    }
                    description "";
                } // END of distanceInter definition.

                leaf distanceExternal  {
                    type  cml_data_types:CML_UINT32_T {
                         range "1..255";
                    }
                    description "";
                } // END of distanceExternal definition.

            } // END of distance-container definition.
            container domain-id {
                description
                    "domainCMLSEPid";
                leaf domainPrimaryAddr  {
                    if-feature feature_list:HAVE_VRF_OSPF;
                    type  cml_data_types:CML_IPV4_ADDR_T;
                    description "";
                } // END of domainPrimaryAddr definition.

                leaf domainNull  {
                    if-feature feature_list:HAVE_VRF_OSPF;
                    type  cml_data_types:CML_STRING_T;
                    description "";
                } // END of domainNull definition.

                leaf domainType  {
                    if-feature feature_list:HAVE_VRF_OSPF;
                    type  cml_data_types:CML_OSPF_DOMAIN_TYPE_T;
                    description "";
                } // END of domainType definition.

                leaf domainHexValue  {
                    if-feature feature_list:HAVE_VRF_OSPF;
                    type  cml_data_types:CML_STRING_T;
                    description "";
                } // END of domainHexValue definition.

                leaf domainTypeSecondary  {
                    if-feature feature_list:HAVE_VRF_OSPF;
                    type  cml_data_types:CML_BOOL_T;
                    description "";
                } // END of domainTypeSecondary definition.


                list domainIdSecondary {
                    if-feature feature_list:HAVE_VRF_OSPF;
                    key "domainSecondaryAddr";
                    description
                        "domainIdSecondary";
                    leaf domainSecondaryAddr  {
                        type  cml_data_types:CML_IPV4_ADDR_T;
                        description "";
                    } // END of domainSecondaryAddr definition.

                } // End of domainIdSecondary-list
            } // END of domain-id-container definition.
            uses TrafficStats;
        } // End of ospf-list
    } // END of ospf-grouping definition.


    grouping teLinkOspf-grouping {
    description
        "teLinkOspf";
        list teLinkOspf {
            if-feature feature_list:HAVE_GMPLS;
            if-feature feature_list:HAVE_OSPF_TE;
            key "teName";
            description
                "teLinkOspf";
            leaf teName  {
                type  cml_data_types:CML_STRING_T;
                description "";
            } // END of teName definition.

            leaf teLinkOspfInstance  {
                type  cml_data_types:CML_UINT16_T {
                     range "0..65535";
                }
                description "";
            } // END of teLinkOspfInstance definition.

            leaf teLinkAreaId  {
                type  cml_data_types:CML_OSPF_AREA_T;
                description "";
            } // END of teLinkAreaId definition.

            leaf teLinkTEMetric  {
                if-feature feature_list:HAVE_OSPF_TE;
                if-feature feature_list:HAVE_GMPLS;
                type  cml_data_types:CML_UINT32_T {
                     range "1..65535";
                }
                default "1";
                description "The limit";
            } // END of teLinkTEMetric definition.

            leaf telinkLocalEnable  {
                if-feature feature_list:HAVE_GMPLS;
                if-feature feature_list:HAVE_OSPF_TE;
                type  cml_data_types:CML_BOOL_T;
                description "";
            } // END of telinkLocalEnable definition.

        } // End of teLinkOspf-list
    } // END of teLinkOspf-grouping definition.
    grouping ipOspfCmds {
        description
            "ip ospf command attributes";
        leaf ifAuthTypeAddr  {
            type  cml_data_types:CML_OSPF_AUTH_TYPE_T;
            description "";
        } // END of ifAuthTypeAddr definition.

        leaf ospfIfAdminStat  {
            type  cml_data_types:CML_OSPF_IF_STATE;
            description "";
        } // END of ospfIfAdminStat definition.

        leaf ospfIfAreaId  {
            if-feature feature_list:HAVE_OSPF_MULTI_INST;
            type  cml_data_types:CML_STRING_T;
            description "";
        } // END of ospfIfAreaId definition.

        leaf ifStatus  {
            if-feature feature_list:HAVE_OSPF_MULTI_INST;
            type  cml_data_types:CML_OSPF_ROW_STATUS;
            description "";
        } // END of ifStatus definition.

        leaf ospfIfMulticastForwarding  {
            if-feature feature_list:HAVE_OSPF_MULTI_INST;
            type  cml_data_types:CML_UINT32_T;
            description "the Interval";
        } // END of ospfIfMulticastForwarding definition.

        leaf ospfIfDemand  {
            if-feature feature_list:HAVE_OSPF_MULTI_INST;
            type  cml_data_types:CML_UINT32_T;
            description "no of packets unused";
        } // END of ospfIfDemand definition.

        leaf ospfAddressLessIf  {
            type  cml_data_types:CML_UINT32_T;
            config false;
            description "";
        } // END of ospfAddressLessIf definition.

        leaf ospfIfState  {
            type  cml_data_types:CML_UINT32_T;
            config false;
            description "";
        } // END of ospfIfState definition.

        leaf ospfIfEvents  {
            type  cml_data_types:CML_UINT32_T;
            config false;
            description "";
        } // END of ospfIfEvents definition.

        leaf ospfIfLsaCount  {
            type  cml_data_types:CML_UINT32_T;
            config false;
            description "";
        } // END of ospfIfLsaCount definition.

        leaf ospfIfLsaCksumSum  {
            type  cml_data_types:CML_UINT32_T;
            config false;
            description "";
        } // END of ospfIfLsaCksumSum definition.

        leaf ospfIfDesignatedRouter  {
            type  cml_data_types:CML_STRING_T;
            config false;
            description "";
        } // END of ospfIfDesignatedRouter definition.

        leaf ospfIfBackupDesignatedRouter  {
            type  cml_data_types:CML_STRING_T;
            config false;
            description "";
        } // END of ospfIfBackupDesignatedRouter definition.

        leaf ospfIfDesignatedRouterId  {
            type  cml_data_types:CML_STRING_T;
            config false;
            description "";
        } // END of ospfIfDesignatedRouterId definition.

        leaf ospfIfBackupDesignatedRouterId  {
            type  cml_data_types:CML_STRING_T;
            config false;
            description "";
        } // END of ospfIfBackupDesignatedRouterId definition.

        leaf ifPriorityAddr  {
            type  cml_data_types:CML_UINT8_T {
                 range "0..255";
            }
            default "1";
            description "";
        } // END of ifPriorityAddr definition.

        leaf ifCostAddr  {
            type  cml_data_types:CML_UINT32_T {
                 range "1..65535";
            }
            default "10";
            description "";
        } // END of ifCostAddr definition.

        leaf ifDeadIntervalAddr  {
            type  cml_data_types:CML_UINT32_T {
                 range "1..65535";
            }
            default "40";
            description "";
        } // END of ifDeadIntervalAddr definition.

        leaf ifHelloIntervalAddr  {
            type  cml_data_types:CML_UINT32_T {
                 range "1..65535";
            }
            default "10";
            description "";
        } // END of ifHelloIntervalAddr definition.

        leaf ifRetransmitIntervalAddr  {
            type  cml_data_types:CML_UINT32_T {
                 range "1..65535";
            }
            default "5";
            description "";
        } // END of ifRetransmitIntervalAddr definition.

        leaf ifTransmitDelayAddr  {
            type  cml_data_types:CML_UINT32_T {
                 range "1..3600";
            }
            default "1";
            description "";
        } // END of ifTransmitDelayAddr definition.

        leaf ifDatabaseFilterAddr  {
            type  cml_data_types:CML_BOOL_T;
            description "";
        } // END of ifDatabaseFilterAddr definition.

        leaf isMtuIgnoreAddr  {
            type  cml_data_types:CML_BOOL_T;
            description "";
        } // END of isMtuIgnoreAddr definition.

        leaf ifResyncTimeoutAddr  {
            type  cml_data_types:CML_UINT32_T {
                 range "1..65535";
            }
            default "40";
            description "";
        } // END of ifResyncTimeoutAddr definition.

    } // END of ipOspfCmds definition.
    grouping TrafficStats {
        description
            "Runtime attrs of TrafficStats";
        leaf trafficTimeStamp  {
            type  cml_data_types:CML_STRING_T;
            config false;
            description "";
        } // END of trafficTimeStamp definition.

        leaf totalStatsIn  {
            type  cml_data_types:CML_INT32_T;
            config false;
            description "";
        } // END of totalStatsIn definition.

        leaf totalStatsOut  {
            type  cml_data_types:CML_INT32_T;
            config false;
            description "";
        } // END of totalStatsOut definition.

        leaf errorsDropIn  {
            type  cml_data_types:CML_INT32_T;
            config false;
            description "";
        } // END of errorsDropIn definition.

        leaf errorsDropOut  {
            type  cml_data_types:CML_INT32_T;
            config false;
            description "";
        } // END of errorsDropOut definition.

        leaf errorsHellosIn  {
            type  cml_data_types:CML_INT32_T;
            config false;
            description "";
        } // END of errorsHellosIn definition.

        leaf dbdsIn  {
            type  cml_data_types:CML_INT32_T;
            config false;
            description "";
        } // END of dbdsIn definition.

        leaf lsreqIn  {
            type  cml_data_types:CML_INT32_T;
            config false;
            description "";
        } // END of lsreqIn definition.

        leaf lsuIn  {
            type  cml_data_types:CML_INT32_T;
            config false;
            description "";
        } // END of lsuIn definition.

        leaf lsacksIn  {
            type  cml_data_types:CML_INT32_T;
            config false;
            description "";
        } // END of lsacksIn definition.

        leaf unknownIn  {
            type  cml_data_types:CML_INT32_T;
            config false;
            description "";
        } // END of unknownIn definition.

        leaf unknownOut  {
            type  cml_data_types:CML_INT32_T;
            config false;
            description "";
        } // END of unknownOut definition.

        leaf badVersion  {
            type  cml_data_types:CML_INT32_T;
            config false;
            description "";
        } // END of badVersion definition.

        leaf badCrc  {
            type  cml_data_types:CML_INT32_T;
            config false;
            description "";
        } // END of badCrc definition.

        leaf invalidSrc  {
            type  cml_data_types:CML_INT32_T;
            config false;
            description "";
        } // END of invalidSrc definition.

        leaf invalidDSt  {
            type  cml_data_types:CML_INT32_T;
            config false;
            description "";
        } // END of invalidDSt definition.

        leaf noNbr  {
            type  cml_data_types:CML_INT32_T;
            config false;
            description "";
        } // END of noNbr definition.

        leaf passive  {
            type  cml_data_types:CML_INT32_T;
            config false;
            description "";
        } // END of passive definition.

        leaf wrongArea  {
            type  cml_data_types:CML_INT32_T;
            config false;
            description "";
        } // END of wrongArea definition.

        leaf pktLength  {
            type  cml_data_types:CML_INT32_T;
            config false;
            description "";
        } // END of pktLength definition.

        leaf badAuth  {
            type  cml_data_types:CML_INT32_T;
            config false;
            description "";
        } // END of badAuth definition.

        leaf statsHelloIn  {
            type  cml_data_types:CML_INT32_T;
            config false;
            description "";
        } // END of statsHelloIn definition.

        leaf statsDbDescIn  {
            type  cml_data_types:CML_INT32_T;
            config false;
            description "";
        } // END of statsDbDescIn definition.

        leaf statsLsReqIn  {
            type  cml_data_types:CML_INT32_T;
            config false;
            description "";
        } // END of statsLsReqIn definition.

        leaf statsLsUpdIn  {
            type  cml_data_types:CML_INT32_T;
            config false;
            description "";
        } // END of statsLsUpdIn definition.

        leaf statsLsAckIn  {
            type  cml_data_types:CML_INT32_T;
            config false;
            description "";
        } // END of statsLsAckIn definition.

        leaf statsHelloOut  {
            type  cml_data_types:CML_INT32_T;
            config false;
            description "";
        } // END of statsHelloOut definition.

        leaf statsDbDescOut  {
            type  cml_data_types:CML_INT32_T;
            config false;
            description "";
        } // END of statsDbDescOut definition.

        leaf statsLsReqOut  {
            type  cml_data_types:CML_INT32_T;
            config false;
            description "";
        } // END of statsLsReqOut definition.

        leaf statsLsUpdOut  {
            type  cml_data_types:CML_INT32_T;
            config false;
            description "";
        } // END of statsLsUpdOut definition.

        leaf statsLsAckOut  {
            type  cml_data_types:CML_INT32_T;
            config false;
            description "";
        } // END of statsLsAckOut definition.

    } // END of TrafficStats definition.

    grouping  ospfMaster-grouping {
    description
        "OSPF Master commands";
    container ospfMaster {
        description
            "OSPF Master commands";
        leaf multiInstanceSet  {
            if-feature feature_list:HAVE_OSPF_MULTI_INST;
            type  cml_data_types:CML_BOOL_T;
            description "OSPF instance";
        } // END of multiInstanceSet definition.

        leaf graceperiod  {
            if-feature feature_list:HAVE_RESTART;
            type  cml_data_types:CML_UINT16_T {
                 range "2..1800";
            }
            description "Grace period in seconds";
        } // END of graceperiod definition.

        leaf plannedOnly  {
            if-feature feature_list:HAVE_RESTART;
            type  cml_data_types:CML_BOOL_T;
            description "Pointer to structure ospf_master";
        } // END of plannedOnly definition.

        leaf-list helperId  {
            type  cml_data_types:CML_IPV4_ADDR_T;
            description "Helper policy (Never, Only reload, Only Upgrade)";
        } // END of helperId definition.


        list srPath {
            if-feature feature_list:HAVE_SR_MPLS;
            key "ospfsrPathName";
            description
                "List for paths for Segment Routing";
            leaf ospfsrPathName  {
                type  cml_data_types:CML_STRING_T;
                description "";
            } // END of ospfsrPathName definition.


            list srPathEro {
                if-feature feature_list:HAVE_SR_MPLS;
                key "hopAddr";
                description
                    "List of hops";
                leaf hopAddr  {
                    type  cml_data_types:CML_IPV4_ADDR_T;
                    description "";
                } // END of hopAddr definition.


                list srPathEronext {
                    if-feature feature_list:HAVE_SR_MPLS;
                    key "hopnbrAddr";
                    description
                        "List of hops";
                    leaf hopnbrAddr  {
                        type  cml_data_types:CML_IPV4_ADDR_T;
                        description "";
                    } // END of hopnbrAddr definition.

                } // End of srPathEronext-list
            } // End of srPathEro-list
        } // End of srPath-list

        list srTrunk {
            if-feature feature_list:HAVE_SR_MPLS;
            key "ospfsrTrunkName";
            description
                "Hash table to store ingress trunks only";
            leaf ospfsrTrunkName  {
                type  cml_data_types:CML_STRING_T;
                description "";
            } // END of ospfsrTrunkName definition.

            leaf Tegress  {
                if-feature feature_list:HAVE_SR_MPLS;
                type  cml_data_types:CML_IPV4_ADDR_T;
                description "";
            } // END of Tegress definition.

            leaf TrunkPathName  {
                if-feature feature_list:HAVE_SR_MPLS;
                type  cml_data_types:CML_STRING_T;
                description "";
            } // END of TrunkPathName definition.

        } // End of srTrunk-list
        container ospfDebugConf {
            description
                "OSPF global debug flags";
            leaf ospfDebugConfAllType  {
                type  cml_data_types:CML_BOOL_T;
                description "";
            } // END of ospfDebugConfAllType definition.

            leaf ospfPacketDebugConfType  {
                type  cml_data_types:CML_OSPF_PACKET_TYPE_T;
                description "";
            } // END of ospfPacketDebugConfType definition.

            leaf ospfEventFlagsConf  {
                type  cml_data_types:CML_OSPF_DEBUG_EVENT_TYPE_T;
                description "";
            } // END of ospfEventFlagsConf definition.

            leaf ospfIfsmFlagsConf  {
                type  cml_data_types:CML_OSPF_DEBUG_IFSM_T;
                description "";
            } // END of ospfIfsmFlagsConf definition.

            leaf ospfNfsmFlagsConf  {
                type  cml_data_types:CML_OSPF_DEBUG_NFSM_T;
                description "";
            } // END of ospfNfsmFlagsConf definition.

            leaf ospfLsaFlagsConf  {
                type  cml_data_types:CML_OSPF_DEBUG_LSA_T;
                description "";
            } // END of ospfLsaFlagsConf definition.

            leaf ospfNsmFlagsConf  {
                type  cml_data_types:CML_OSPF_DEBUG_NSM_T;
                description "";
            } // END of ospfNsmFlagsConf definition.

            leaf ospfRibFlagsConf  {
                if-feature feature_list:HAVE_RIBD;
                type  cml_data_types:CML_OSPF_DEBUG_RIB_T;
                description "";
            } // END of ospfRibFlagsConf definition.

            leaf ospfBfdFlagsConf  {
                if-feature feature_list:HAVE_BFD;
                type  cml_data_types:CML_BOOL_T;
                description "";
            } // END of ospfBfdFlagsConf definition.

            leaf ospfRtCalcflagsConf  {
                type  cml_data_types:CML_OSPF_DEBUG_ROUTE_T;
                description "";
            } // END of ospfRtCalcflagsConf definition.

            leaf ospfDatabaseTimerflagsConf  {
                type  cml_data_types:CML_BOOL_T;
                description "";
            } // END of ospfDatabaseTimerflagsConf definition.

            leaf ospfRedistributeFlagsConf  {
                type  cml_data_types:CML_OSPF_DEBUG_REDIST_T;
                description "";
            } // END of ospfRedistributeFlagsConf definition.

            leaf ospfGracefulRestartFlagsConf  {
                type  cml_data_types:CML_OSPF_DEBUG_GRACEFUL_T;
                description "";
            } // END of ospfGracefulRestartFlagsConf definition.

            leaf ospfPolicyFlagsConf  {
                type  cml_data_types:CML_BOOL_T;
                description "";
            } // END of ospfPolicyFlagsConf definition.

            leaf ospfRetransmissionFlagsConf  {
                type  cml_data_types:CML_BOOL_T;
                description "";
            } // END of ospfRetransmissionFlagsConf definition.

            leaf ospfLfaRouteFlagsConf  {
                if-feature feature_list:HAVE_OSPF_LFA;
                type  cml_data_types:CML_BOOL_T;
                description "";
            } // END of ospfLfaRouteFlagsConf definition.

            leaf ospfHaFlagsConf  {
                if-feature feature_list:HAVE_OSPF_SSO;
                type  cml_data_types:CML_BOOL_T;
                description "";
            } // END of ospfHaFlagsConf definition.

            leaf debugospfSrFlagsConf  {
                if-feature feature_list:HAVE_SR_MPLS;
                type  cml_data_types:CML_BOOL_T;
                description "";
            } // END of debugospfSrFlagsConf definition.

            leaf ospfCspfDebugEventsConf  {
                if-feature feature_list:HAVE_OSPF_CSPF;
                type  cml_data_types:CML_BOOL_T;
                description "";
            } // END of ospfCspfDebugEventsConf definition.

            leaf ospfCspfDebugHexdumpConf  {
                if-feature feature_list:HAVE_OSPF_CSPF;
                type  cml_data_types:CML_BOOL_T;
                description "";
            } // END of ospfCspfDebugHexdumpConf definition.

        } // END of ospfDebugConf-container definition.
        container ospfDebug {
            description
                "OSPF global debug flags";
            leaf ospfDebugAllType  {
                type  cml_data_types:CML_BOOL_T;
                description "";
            } // END of ospfDebugAllType definition.

            leaf ospfPacketDebugType  {
                type  cml_data_types:CML_OSPF_PACKET_TYPE_T;
                description "";
            } // END of ospfPacketDebugType definition.

            leaf ospfEventFlags  {
                type  cml_data_types:CML_OSPF_DEBUG_EVENT_TYPE_T;
                description "";
            } // END of ospfEventFlags definition.

            leaf ospfIfsmFlags  {
                type  cml_data_types:CML_OSPF_DEBUG_IFSM_T;
                description "";
            } // END of ospfIfsmFlags definition.

            leaf ospfNfsmFlags  {
                type  cml_data_types:CML_OSPF_DEBUG_NFSM_T;
                description "";
            } // END of ospfNfsmFlags definition.

            leaf ospfLsaFlags  {
                type  cml_data_types:CML_OSPF_DEBUG_LSA_T;
                description "";
            } // END of ospfLsaFlags definition.

            leaf ospfNsmFlags  {
                type  cml_data_types:CML_OSPF_DEBUG_NSM_T;
                description "";
            } // END of ospfNsmFlags definition.

            leaf ospfRibFlags  {
                if-feature feature_list:HAVE_RIBD;
                type  cml_data_types:CML_OSPF_DEBUG_RIB_T;
                description "";
            } // END of ospfRibFlags definition.

            leaf ospfBfdFlags  {
                if-feature feature_list:HAVE_BFD;
                type  cml_data_types:CML_BOOL_T;
                description "";
            } // END of ospfBfdFlags definition.

            leaf ospfRtCalcflags  {
                type  cml_data_types:CML_OSPF_DEBUG_ROUTE_T;
                description "";
            } // END of ospfRtCalcflags definition.

            leaf ospfDatabaseTimerflags  {
                type  cml_data_types:CML_BOOL_T;
                description "";
            } // END of ospfDatabaseTimerflags definition.

            leaf ospfRedistributeFlags  {
                type  cml_data_types:CML_OSPF_DEBUG_REDIST_T;
                description "";
            } // END of ospfRedistributeFlags definition.

            leaf ospfGracefulRestartFlags  {
                type  cml_data_types:CML_OSPF_DEBUG_GRACEFUL_T;
                description "";
            } // END of ospfGracefulRestartFlags definition.

            leaf ospfPolicyFlags  {
                type  cml_data_types:CML_BOOL_T;
                description "";
            } // END of ospfPolicyFlags definition.

            leaf ospfRetransmissionFlags  {
                type  cml_data_types:CML_BOOL_T;
                description "";
            } // END of ospfRetransmissionFlags definition.

            leaf ospfLfaRouteFlags  {
                if-feature feature_list:HAVE_OSPF_LFA;
                type  cml_data_types:CML_BOOL_T;
                description "";
            } // END of ospfLfaRouteFlags definition.

            leaf ospfHaFlags  {
                if-feature feature_list:HAVE_OSPF_SSO;
                type  cml_data_types:CML_BOOL_T;
                description "";
            } // END of ospfHaFlags definition.

            leaf ospfSrFlags  {
                if-feature feature_list:HAVE_SR_MPLS;
                type  cml_data_types:CML_BOOL_T;
                description "";
            } // END of ospfSrFlags definition.

            leaf ospfCspfDebugEvents  {
                if-feature feature_list:HAVE_OSPF_CSPF;
                type  cml_data_types:CML_BOOL_T;
                description "";
            } // END of ospfCspfDebugEvents definition.

            leaf ospfCspfDebugHexdump  {
                if-feature feature_list:HAVE_OSPF_CSPF;
                type  cml_data_types:CML_BOOL_T;
                description "";
            } // END of ospfCspfDebugHexdump definition.

        } // END of ospfDebug-container definition.
        container helperPolicy {
            description
                "Helper policy for Graceful Restart";
            leaf MaxGracePeriod  {
                type  cml_data_types:CML_UINT16_T {
                     range "2..1800";
                }
                description "Maximum grace period in seconds";
            } // END of MaxGracePeriod definition.

        } // END of helperPolicy-container definition.
    } // END of ospfMaster-container definition.
    } // END of ospfMaster-container definition.

    grouping  ospfInterface-grouping {
    description
        "OSPF interface related operations";
    container ospfInterface {
        description
            "OSPF interface related operations";
        leaf ifTEMetric  {
            if-feature feature_list:HAVE_OSPF_TE;
            type  cml_data_types:CML_UINT32_T {
                 range "1..65535";
            }
            default "1";
            description "The minimum delay in milliseconds between accepting the same LSA from neighbors";
        } // END of ifTEMetric definition.

        leaf ospfholddown  {
            if-feature feature_list:HAVE_LDPD;
            type  cml_data_types:CML_UINT32_T {
                 range "1..2147483";
            }
            default "70000";
            description "";
        } // END of ospfholddown definition.

        leaf ifBfdEnable  {
            if-feature feature_list:HAVE_BFD;
            type  cml_data_types:CML_OSPF_BFD_STATE;
            description "";
        } // END of ifBfdEnable definition.

        leaf ifNetworkType  {
            type  cml_data_types:CML_OSPF_NETWORK_T;
            description "";
        } // END of ifNetworkType definition.

        leaf ifMtu  {
            type  cml_data_types:CML_UINT16_T {
                 range "576..65535";
            }
            default "576";
            description "";
        } // END of ifMtu definition.

        leaf ifDisableAll  {
            type  cml_data_types:CML_BOOL_T;
            description "";
        } // END of ifDisableAll definition.

        leaf fastRerouteIfSet  {
            if-feature feature_list:HAVE_OSPF_LFA;
            type  cml_data_types:CML_BOOL_T;
            description "";
        } // END of fastRerouteIfSet definition.

        leaf ifFloodReduction  {
            type  cml_data_types:CML_BOOL_T;
            description "";
        } // END of ifFloodReduction definition.

        leaf ifDemandCircuit  {
            if-feature feature_list:HAVE_OSPF_OD;
            if-feature feature_list:HAVE_OSPF_MULTI_INST;
            type  cml_data_types:CML_BOOL_T;
            description "";
        } // END of ifDemandCircuit definition.


        list ospfMultiAreaProcess {
            if-feature feature_list:HAVE_OSPF_MULTI_AREA;
            key "ospfProcess";
            description
                "OSPF multi-area configs";
            leaf ospfProcess  {
                type  cml_data_types:CML_UINT16_T {
                     range "0..65535";
                }
                description "";
            } // END of ospfProcess definition.


            list ospfMultiArea {
                if-feature feature_list:HAVE_OSPF_MULTI_AREA;
                key "multiAreaId";
                description
                    "OSPF multi-area configs";
                leaf multiAreaId  {
                    type  cml_data_types:CML_OSPF_AREA_T;
                    description "";
                } // END of multiAreaId definition.

                leaf neighborAddr  {
                    type  cml_data_types:CML_IPV4_ADDR_T;
                    description "";
                } // END of neighborAddr definition.

            } // End of ospfMultiArea-list
        } // End of ospfMultiAreaProcess-list

        list ospfInterfaceAddr {
            key "ipOspfAddr";
            description
                "OSPF interface addr related operations";
            leaf ipOspfAddr  {
                type  cml_data_types:CML_IPV4_ADDR_T;
                description "";
            } // END of ipOspfAddr definition.


            list ospfInterfaceMessageDigestKey {
                key "msgDigestKeyIdAddr";
                description
                    "OSPF message-digest-key related operations";
                leaf msgDigestKeyIdAddr  {
                    type  cml_data_types:CML_UINT32_T {
                         range "1..255";
                    }
                    description "";
                } // END of msgDigestKeyIdAddr definition.

                leaf msgDigestKeyEncryptionAddr  {
                    type  cml_data_types:CML_OSPF_MD5_T;
                    description "";
                } // END of msgDigestKeyEncryptionAddr definition.

                leaf msgifAuthKeyAddr  {
                    type  cml_data_types:CML_STRING_T;
                    description "";
                } // END of msgifAuthKeyAddr definition.

            } // End of ospfInterfaceMessageDigestKey-list
            container Authkey {
                description
                    "Enable authentication-key on this interface";
                leaf ifAuthKeyAddr  {
                    type  cml_data_types:CML_STRING_T;
                    description "";
                } // END of ifAuthKeyAddr definition.

                leaf authKeyEncryptionAddr  {
                    type  cml_data_types:CML_OSPF_MD5_T;
                    description "";
                } // END of authKeyEncryptionAddr definition.

            } // END of Authkey-container definition.
            uses ipOspfCmds;
        } // End of ospfInterfaceAddr-list
        container ipOspfInterface {
            description
                "ip OSPF interface addr related operations";

            list ospfInterfaceMessageDigestKey {
                key "msgDigestKeyIdAddr";
                description
                    "OSPF message-digest-key related operations";
                leaf msgDigestKeyIdAddr  {
                    type  cml_data_types:CML_UINT32_T {
                         range "1..255";
                    }
                    description "";
                } // END of msgDigestKeyIdAddr definition.

                leaf msgDigestKeyEncryptionAddr  {
                    type  cml_data_types:CML_OSPF_MD5_T;
                    description "";
                } // END of msgDigestKeyEncryptionAddr definition.

                leaf msgifAuthKeyAddr  {
                    type  cml_data_types:CML_STRING_T;
                    description "";
                } // END of msgifAuthKeyAddr definition.

            } // End of ospfInterfaceMessageDigestKey-list
            container Authkey {
                description
                    "Enable authentication-key on this interface";
                leaf ifAuthKeyAddr  {
                    type  cml_data_types:CML_STRING_T;
                    description "";
                } // END of ifAuthKeyAddr definition.

                leaf authKeyEncryptionAddr  {
                    type  cml_data_types:CML_OSPF_MD5_T;
                    description "";
                } // END of authKeyEncryptionAddr definition.

            } // END of Authkey-container definition.
            uses ipOspfCmds;
        } // END of ipOspfInterface-container definition.
        uses TrafficStats;
    } // END of ospfInterface-container definition.
    } // END of ospfInterface-container definition.


}
