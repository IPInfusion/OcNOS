/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-plist.yang
*
*/

submodule zebos-plist {

    belongs-to  zebos { prefix zebos; }

    import cml_data_types {
        prefix cml_data_types;
    }

    organization
        "IP Infusion Inc.";

    contact
        "Address: 3965 Freedom Circle, Suite 200, Santa Clara, CA 95054
        Phone: +1 408-400-1900
        E-mail: support@ipinfusion.com
        Web: http://www.ipinfusion.com/";

    description
        "";


    revision "2018-06-21" {
        description " Initial Version.";
        reference "";
    }


    grouping  prefixMaster-grouping {
    description
        "Master structure";
    container prefixMaster {
        description
            "Master structure";
        leaf seqnum  {
            type  cml_data_types:CML_BOOL_T;
            description "";
        } // END of seqnum definition.


        list ipPrefix {
            key "plistname";
            description
                "List of struct prefix_list";
            leaf plistname  {
                type  cml_data_types:CML_STRING_T;
                description "";
            } // END of plistname definition.

            leaf description  {
                type  cml_data_types:CML_LINE_T;
                description "";
            } // END of description definition.

            leaf count  {
                type  cml_data_types:CML_INT32_T;
                config false;
                description "";
            } // END of count definition.

            leaf rangeCount  {
                type  cml_data_types:CML_INT32_T;
                config false;
                description "";
            } // END of rangeCount definition.


            list ipPrefixEntry {
                key "seq";
                description
                    "Each prefix-list's entry";
                leaf seq  {
                    type  cml_data_types:CML_UINT32_T {
                         range "1..4294967295";
                    }
                    description "";
                } // END of seq definition.

                leaf type  {
                    type  cml_data_types:CML_PREFIX_LIST_TYPE;
                    description "";
                } // END of type definition.

                leaf network  {
                    type  cml_data_types:CML_IPV4_ADDR_PREFIX_T;
                    description "";
                } // END of network definition.

                leaf minPrefixLength  {
                    type  cml_data_types:CML_UINT8_T {
                         range "0..32";
                    }
                    description "";
                } // END of minPrefixLength definition.

                leaf maxPrefixLength  {
                    type  cml_data_types:CML_UINT8_T {
                         range "0..32";
                    }
                    description "";
                } // END of maxPrefixLength definition.

                leaf eqPrefixLength  {
                    type  cml_data_types:CML_UINT8_T {
                         range "0..32";
                    }
                    default "0";
                    description "";
                } // END of eqPrefixLength definition.

                leaf any  {
                    type  cml_data_types:CML_PREFIX_LIST_ANY_T;
                    description "";
                } // END of any definition.

                leaf refCount  {
                    type  cml_data_types:CML_UINT32_T;
                    config false;
                    description "";
                } // END of refCount definition.

                leaf hitCount  {
                    type  cml_data_types:CML_UINT32_T;
                    config false;
                    description "";
                } // END of hitCount definition.

            } // End of ipPrefixEntry-list
        } // End of ipPrefix-list
    } // END of prefixMaster-container definition.
    } // END of prefixMaster-container definition.

    grouping  prefixMaster6-grouping {
    description
        "Master structure of prefix_list";
    container prefixMaster6 {
        description
            "Master structure of prefix_list";
        leaf ipv6Seqnum  {
            type  cml_data_types:CML_BOOL_T;
            description "";
        } // END of ipv6Seqnum definition.


        list ipv6Prefix {
            key "plistname6";
            description
                "List of struct prefix_list";
            leaf plistname6  {
                type  cml_data_types:CML_STRING_T;
                description "";
            } // END of plistname6 definition.

            leaf description6  {
                type  cml_data_types:CML_LINE_T;
                default "NULL";
                description "";
            } // END of description6 definition.

            leaf count6  {
                type  cml_data_types:CML_INT32_T;
                config false;
                description "";
            } // END of count6 definition.

            leaf rangeCount6  {
                type  cml_data_types:CML_INT32_T;
                config false;
                description "";
            } // END of rangeCount6 definition.


            list ipv6PrefixEntry {
                key "seq6";
                description
                    "Each prefix-list's entry";
                leaf seq6  {
                    type  cml_data_types:CML_UINT32_T {
                         range "1..4294967295";
                    }
                    description "";
                } // END of seq6 definition.

                leaf type6  {
                    type  cml_data_types:CML_PREFIX_LIST_TYPE;
                    description "";
                } // END of type6 definition.

                leaf network6  {
                    type  cml_data_types:CML_IPV6_PREFIX_T;
                    description "";
                } // END of network6 definition.

                leaf minPrefixLength6  {
                    type  cml_data_types:CML_UINT8_T {
                         range "0..128";
                    }
                    default "0";
                    description "";
                } // END of minPrefixLength6 definition.

                leaf maxPrefixLength6  {
                    type  cml_data_types:CML_UINT8_T {
                         range "0..128";
                    }
                    default "0";
                    description "";
                } // END of maxPrefixLength6 definition.

                leaf any6  {
                    type  cml_data_types:CML_PREFIX_LIST_ANY_T;
                    description "";
                } // END of any6 definition.

                leaf refCount6  {
                    type  cml_data_types:CML_UINT32_T;
                    config false;
                    description "";
                } // END of refCount6 definition.

                leaf hitCount6  {
                    type  cml_data_types:CML_UINT32_T;
                    config false;
                    description "";
                } // END of hitCount6 definition.

            } // End of ipv6PrefixEntry-list
        } // End of ipv6Prefix-list
    } // END of prefixMaster6-container definition.
    } // END of prefixMaster6-container definition.


}
