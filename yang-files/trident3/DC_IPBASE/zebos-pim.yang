/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-pim.yang
*
*/

submodule zebos-pim {

    belongs-to  zebos { prefix zebos; }

    import cml_data_types {
        prefix cml_data_types;
    }

    include zebos-vrf;
    organization
        "IP Infusion Inc.";

    contact
        "Address: 3965 Freedom Circle, Suite 200, Santa Clara, CA 95054
        Phone: +1 408-400-1900
        E-mail: support@ipinfusion.com
        Web: http://www.ipinfusion.com/";

    description
        "";


    revision "2018-06-21" {
        description " Initial Version.";
        reference "";
    }



    grouping pimDebug-grouping {
    description
        "pimDebug";
        list pimDebug {
            key "vrfName";
            description
                "pimDebug";
            leaf vrfName  {
                type  cml_data_types:CML_STRING_T;
                description "";
            } // END of vrfName definition.

            leaf debugall  {
                type  cml_data_types:CML_BOOL_T;
                description "";
            } // END of debugall definition.

        } // End of pimDebug-list
    } // END of pimDebug-grouping definition.


    grouping pimTermDebug-grouping {
    description
        "pimTermDebug";
        list pimTermDebug {
            key "vrfName";
            description
                "pimTermDebug";
            leaf vrfName  {
                type  cml_data_types:CML_STRING_T;
                description "";
            } // END of vrfName definition.

            leaf debugtermall  {
                type  cml_data_types:CML_BOOL_T;
                description "";
            } // END of debugtermall definition.

        } // End of pimTermDebug-list
    } // END of pimTermDebug-grouping definition.


}
