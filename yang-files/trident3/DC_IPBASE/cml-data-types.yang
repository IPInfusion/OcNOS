/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : cml-data-types.yang
*
*/

module cml-data-types {

    namespace   "http://www.ipinfusion.com/CMLSchema/cml-data-types";

    prefix "cml-data-types";

    import ietf-inet-types {
        prefix inet;
    }

    import ietf-yang-types {
        prefix yang;
    }

    organization
        "IP Infusion Inc.";

    contact
        "Address: 3965 Freedom Circle, Suite 200, Santa Clara, CA 95054
        Phone: +1 408-400-1900
        E-mail: support@ipinfusion.com
        Web: http://www.ipinfusion.com/";

    description
        "YANG version of the cml-data-types";


    revision "2018-06-21" {
        description " Initial Version.";
        reference "";
    }



    typedef  CML_INT32_T {

        type int32{
         range -2147483648..2147483647;
        }
        description "";
        reference "";
    }

    typedef  CML_UINT32_T {

        type uint32{
         range 0..4294967295;
        }
        description "";
        reference "";
    }

    typedef  CML_STRING_T {

        type string{
        pattern "[^?' =,>|]*";
        }
        description "";
        reference "";
    }

    typedef  CML_IPV4_ADDR_PREFIX_T {

        type inet:ipv4-prefix;
        description "";
        reference "";
    }

    typedef  CML_NONEMPTY_STRING_T {

        type string{
        pattern "[^?' =,>|]+";
        }
        description "";
        reference "";
    }

    typedef  CML_LINE_T {

        type string{
        pattern "[^?'=,>|]*";
        }
        description "";
        reference "";
    }

    typedef  CML_SSH_PUBKEY_T {

        type string;
        description "";
        reference "";
    }

    typedef  CML_HOST_STRING_T {

        type string;
        description "";
        reference "";
    }

    typedef  CML_RANGE_T {

        type string{
        pattern "[^?'=>|]*";
        }
        description "";
        reference "";
    }

    typedef  CML_UINT8_T {

        type uint8{
         range 0..255;
        }
        description "";
        reference "";
    }

    typedef  CML_INT8_T {

        type int8{
         range -128..127;
        }
        description "";
        reference "";
    }

    typedef  CML_UINT16_T {

        type uint16{
         range 0..65535;
        }
        description "";
        reference "";
    }

    typedef  CML_BITMAP_T {

        type uint32{
         range 0..4294967295;
        }
        description "";
        reference "";
    }

    typedef  CML_INT16_T {

        type int16{
         range -32768..32767;
        }
        description "";
        reference "";
    }

    typedef  CML_UINT64_T {

        type uint64;
        description "";
        reference "";
    }

    typedef  CML_INT64_T {

        type int64;
        description "";
        reference "";
    }

    typedef  CML_BOOL_T {

        type boolean;
        description "";
        reference "";
    }

    typedef  CML_FLOAT_T {

        type decimal64{
         fraction-digits 2;
        }
        description "";
        reference "";
    }

    typedef  CML_FLOAT_PRECISION_3_T {

        type decimal64{
         fraction-digits 3;
        }
        description "";
        reference "";
    }

    typedef  CML_VM_AFFINITY_T {

        type string{
        pattern "[^?' =>|]*";
        }
        description "";
        reference "";
    }

    typedef  CML_IPV4_ADDR_T {

        type inet:ipv4-address{
        length 0..15;
        }
        description "";
        reference "";
    }

    typedef  CML_IPV6_ADDR_T {

        type inet:ipv6-address{
        length 0..45;
        }
        description "";
        reference "";
    }

    typedef  CML_SNMP_IPV6_ADDR_T {

        type inet:ipv6-address{
        length 0..45;
        }
        description "";
        reference "";
    }

    typedef  CML_IPV4_PREFIX_T {

        type inet:ipv4-prefix{
        length 0..32;
        }
        description "";
        reference "";
    }

    typedef  CML_IPV6_PREFIX_T {

        type inet:ipv6-prefix{
        length 0..50;
        }
        description "";
        reference "";
    }

    typedef  CML_MAC_ADDR_T {

        type string;
        description "";
        reference "";
    }

    typedef  CML_EMPTY_T {

        type empty;
        description "";
        reference "";
    }

    typedef  CML_QOS_NAME_T {

        type string;
        description "";
        reference "";
    }

    typedef  CML_CMAP_MATCH_ANY_CRITERIA_T {
        type enumeration {
            enum match-any {
                value 2;
                description "Logical-OR of all match statements under this class-map";
            }
        }
        description "";
        reference "";
    }

    typedef  CML_CMAP_MATCH_CRITERIA_T {
        type enumeration {
            enum default-match-type {
                value 0;
                description "Match type is default which is match-al";
            }
            enum match-all {
                value 1;
                description "Logical-AND of all match statements under this class-map";
            }
            enum match-any {
                value 2;
                description "Logical-OR of all match statements under this class-map";
            }
        }
        description "";
        reference "";
    }

    typedef  CML_CLEAR_STAT_QOS_T {
        type enumeration {
            enum input {
                value 0;
                description "Input";
            }
            enum input-type-qos {
                value 1;
                description "input,Type,QoS is ingress/egress policy-map";
            }
            enum output {
                value 2;
                description "egress";
            }
            enum output-type-qos {
                value 3;
                description "egressType,QoS is ingress/egress policy-map";
            }
            enum output-type-queuing {
                value 4;
                description "egress,Type,Queuing is egress policy-map";
            }
        }
        description "";
        reference "";
    }

    typedef  CML_PMAP_TYPE_T {
        type enumeration {
            enum type-qos {
                value 1;
                description "Type,QoS is ingress/egress policy-map";
            }
            enum type-queuing {
                value 2;
                description "Type,Queuing is egress policy-map";
            }
            enum type-queuing-default {
                value 3;
                description "Type,Queuing is egress policy-map,Default queue of port";
            }
        }
        description "";
        reference "";
    }

    typedef  CML_QOS_FILTER_TYPE_T {
        type enumeration {
            enum ingress-ipv4 {
                value 4;
                description "ingress ipv4";
            }
            enum ingress-ipv6 {
                value 16;
                description "ingress ipv6";
            }
            enum egress-ipv6 {
                value 32;
                description "egress ipv6";
            }
            enum ingress-arp {
                value 128;
                description "ingress arp";
            }
        }
        description "";
        reference "";
    }

    typedef  CML_QOS_OPERATION_T {
        type enumeration {
            enum qos-noop {
                value 0;
                description "qos noop";
            }
            enum qos-equal {
                value 1;
                description "qos equal";
            }
            enum qos-not-equal {
                value 2;
                description "qos not equal";
            }
            enum qos-less-than {
                value 3;
                description "qos less than";
            }
            enum qos-greater-than {
                value 4;
                description "qos greater than";
            }
            enum qos-operation-max {
                value 5;
                description "qos operation max";
            }
        }
        description "";
        reference "";
    }

    typedef  CML_FILTER_TYPE_T {
        type enumeration {
            enum qos-filter-deny {
                value 0;
                description "qos filter deny";
            }
            enum qos-filter-permit {
                value 1;
                description "qos filter permit";
            }
            enum qos-filter-mirror {
                value 2;
                description "qos filter mirror";
            }
            enum qos-filter-dynamic {
                value 3;
                description "qos filter dynamic";
            }
            enum qos-filter-source {
                value 4;
                description "qos filter source";
            }
            enum qos-filter-destination {
                value 5;
                description "qos filter destination";
            }
            enum qos-filter-no-match {
                value 6;
                description "qos filter no match";
            }
        }
        description "";
        reference "";
    }

    typedef  CML_CONFORM_ACTION_T {
        type enumeration {
            enum none {
                value 0;
                description "Sets the action to take when the data rate is within bounds";
            }
            enum transmit {
                value 1;
                description "Specifies the action of transmitting packets";
            }
            enum set-dscp-transmit {
                value 2;
                description "Specify the IP DSCP value 0 to 63";
            }
            enum set-prec-transmit {
                value 3;
                description "Specify the IP Precedence value 0 to 7";
            }
            enum set-cos-transmit {
                value 4;
                description "Specify the cos value 0 to 7";
            }
            enum set-mpls-class {
                value 5;
                description "Set the mpls class filed to the give value and tx the packet";
            }
            enum set-qos-transmit {
                value 6;
                description "Specify the qos value";
            }
        }
        description "";
        reference "";
    }

    typedef  CML_EXCEED_ACTION_T {
        type enumeration {
            enum none {
                value 0;
                description "default value";
            }
            enum drop {
                value 1;
                description "Sets the action to take when the data rate is exceeded.default is drop";
            }
            enum set-dscp-transmit {
                value 2;
                description "Specify the IP DSCP value 0 to 63";
            }
            enum set-prec-transmit {
                value 3;
                description "Specify the IP Precedence value 0 to 7";
            }
            enum set-cos-transmit {
                value 4;
                description "Specify the cos value 0 to 7";
            }
            enum set-mpls-class {
                value 5;
                description "Set the mpls class filed to the give value and tx the packet";
            }
            enum set-flow-control {
                value 6;
                description "Send a pause frame on the ingress port and pass the packet";
            }
            enum set-axe-ret {
                value 7;
                description " Send a pause frame on the ingress port and pass the packet";
            }
            enum transmit {
                value 8;
                description "Pass the packet by setting DEI";
            }
        }
        description "";
        reference "";
    }

    typedef  CML_VIOLATE_ACTION_T {
        type enumeration {
            enum none {
                value 0;
                description "default value";
            }
            enum drop {
                value 1;
                description "Sets the action to take when the data rate is exceeded.default is drop";
            }
            enum set-dscp-transmit {
                value 2;
                description "Specify the IP DSCP value 0 to 63";
            }
            enum set-cos-transmit {
                value 3;
                description "Specify the cos value 0 to 7";
            }
            enum set-mpls-class {
                value 4;
                description "Set the mpls class filed to the give value and tx the packet";
            }
            enum transmit {
                value 5;
                description "Pass the packet by setting DEI";
            }
        }
        description "";
        reference "";
    }

    typedef  CML_BURST_TYPE_T {
        type enumeration {
            enum none {
                value 0;
                description "default value";
            }
            enum kbytes {
                value 2;
                description "Specifies the units of kilobytes per second";
            }
            enum mbytes {
                value 3;
                description "Specifies the units of megabytes per second";
            }
            enum ms {
                value 4;
                description "Specifies the units of milliseconds";
            }
            enum us {
                value 5;
                description "Specifies the units of microseconds";
            }
        }
        description "";
        reference "";
    }

    typedef  CML_QOS_RATE_T {
        type enumeration {
            enum none {
                value 0;
                description "default value";
            }
            enum kbps {
                value 2;
                description "Specifies the units of kilobits per second";
            }
            enum mbps {
                value 3;
                description "Specifies the units of megabits per second";
            }
            enum gbps {
                value 4;
                description "Specifies the units of gigabits per second";
            }
        }
        description "";
        reference "";
    }

    typedef  CML_FLOW_CONTROL_MODE_T {
        type enumeration {
            enum nsm-qos-flow-control {
                value 0;
                description "nsm qos flow control mode none";
            }
            enum nsm-full-bucket-size {
                value 1;
                description "nsm resume on full bucket size";
            }
            enum nsm-cbs-bucket-size {
                value 2;
                description "nsm resume on cbs bucket size";
            }
        }
        description "";
        reference "";
    }

    typedef  CML_QOS_DSCP_VAL_T {
        type union {
            type CML_RANGE_T {

            }
            type CML_DSCP_TYPE_T {

            }
        }
        description "";
        reference "";
    }

    typedef  CML_MSTP_INSTANCE_TYPE_T {
        type union {
            type int32 {
                range "1..63";

            }
            type CML_MSTP_INSTANCE_SPBM_T {

            }
        }
        description "";
        reference "";
    }

    typedef  CML_MSTP_INSTANCE_SPBM_T {
        type enumeration {
            enum spbm {
                value 4092;
                description "spbm instance";
            }
        }
        description "";
        reference "";
    }

    typedef  CML_QOS_SET_VAL_T {
        type union {
            type int32 {
                range "0..63";

            }
            type CML_DSCP_TYPE_T {

            }
        }
        description "";
        reference "";
    }

    typedef  CML_DSCP_TYPE_T {
        type enumeration {
            enum default {
                value 0;
                description "Default dscp (000000)";
            }
            enum cs1 {
                value 8;
                description "CS1(precedence 1) dscp (001000)";
            }
            enum af11 {
                value 10;
                description "AF11 dscp (001010)";
            }
            enum af12 {
                value 12;
                description "AF12 dscp (001100)";
            }
            enum af13 {
                value 14;
                description "AF13 dscp (001110)";
            }
            enum cs2 {
                value 16;
                description "CS2(precedence 2) dscp (010000)";
            }
            enum af21 {
                value 18;
                description "AF21 dscp (010010)";
            }
            enum af22 {
                value 20;
                description "AF22 dscp (010100)";
            }
            enum af23 {
                value 22;
                description "AF23 dscp (010110)";
            }
            enum cs3 {
                value 24;
                description "CS3(precedence 3) dscp (011000)";
            }
            enum af31 {
                value 26;
                description "AF31 dscp (011010)";
            }
            enum af32 {
                value 28;
                description "AF32 dscp (011100)";
            }
            enum af33 {
                value 30;
                description "AF33 dscp (011110)";
            }
            enum cs4 {
                value 32;
                description "CS4(precedence 4) dscp (100000)";
            }
            enum af41 {
                value 34;
                description "AF41 dscp (100010)";
            }
            enum af42 {
                value 36;
                description "AF42 dscp (100100)";
            }
            enum af43 {
                value 38;
                description "AF43 dscp (100110)";
            }
            enum cs5 {
                value 40;
                description "CS5(precedence 5) dscp (101000)";
            }
            enum ef {
                value 46;
                description "EF dscp (101110)";
            }
            enum cs6 {
                value 48;
                description "CS6(precedence 6) dscp (110000)";
            }
            enum cs7 {
                value 56;
                description "CS7(precedence 7) dscp (111000)";
            }
        }
        description "";
        reference "";
    }

    typedef  CML_QOS_PREC_VAL_T {
        type union {
            type CML_RANGE_T {

            }
            type CML_PREC_TYPE_T {

            }
        }
        description "";
        reference "";
    }

    typedef  CML_PREC_TYPE_T {
        type enumeration {
            enum routine {
                value 0;
                description "Routine precedence(0)";
            }
            enum priority {
                value 1;
                description "Priority precedence(1)";
            }
            enum immediate {
                value 2;
                description "Immediate precedence(2)";
            }
            enum flash {
                value 3;
                description "Flash precedence(3)";
            }
            enum flashoverride {
                value 4;
                description "Flash override precedence(4)";
            }
            enum critical {
                value 5;
                description "Critical precedence(5)";
            }
            enum internet {
                value 6;
                description "Internetwork control precedence(6)";
            }
            enum network {
                value 7;
                description "Network control precedence(7)";
            }
        }
        description "";
        reference "";
    }

    typedef  CML_PROTO_TYPE_T {
        type enumeration {
            enum arp {
                value 0;
                description "Address Resolution protocol";
            }
            enum bridging {
                value 1;
                description "Bridging";
            }
            enum cdp {
                value 2;
                description "CISCO Discovery Protocol";
            }
            enum clns {
                value 3;
                description "connectionless network service";
            }
            enum clns-es {
                value 4;
                description "CLNS END systems";
            }
            enum clns-is {
                value 5;
                description "CLNS Intermediate systems";
            }
            enum dhcp {
                value 6;
                description "Dynamic host configuration";
            }
            enum isis {
                value 7;
                description "Intermediate system to Intermedaite system";
            }
            enum ldp {
                value 8;
                description "Label Distrubution protocol";
            }
            enum netbios {
                value 9;
                description "NetBIOS Extended User Interface";
            }
        }
        description "";
        reference "";
    }

    typedef  CML_QOS_CLASS_DEFAULT_T {
        type enumeration {
            enum class-default {
                value 0;
                description "Default class map";
            }
        }
        description "";
        reference "";
    }

    typedef  CML_QUEUING_CLASS_DEFAULT_T {
        type enumeration {
            enum queuing-class-default {
                value 0;
                description "Default class map";
            }
        }
        description "";
        reference "";
    }

    typedef  CML_HQOS_ENABLE_DISABLE_T {
        type enumeration {
            enum disable {
                value 0;
                description "Disable QoS globally";
            }
            enum enable {
                value 1;
                description "Enable QoS globally";
            }
        }
        description "";
        reference "";
    }

    typedef  CML_HQOS_CLASS_TYPE_T {
        type enumeration {
            enum q0 {
                value 0;
                description "Queue 0 and priority 0 lowest";
            }
            enum q1 {
                value 1;
                description "Queue 1 and priority 1";
            }
            enum q2 {
                value 2;
                description "Queue 2 and priority 2";
            }
            enum q3 {
                value 3;
                description "Queue 3 and priority 3";
            }
            enum q4 {
                value 4;
                description "Queue 4 and priority 4";
            }
            enum q5 {
                value 5;
                description "Queue 5 and priority 5";
            }
            enum q6 {
                value 6;
                description "Queue 6 and priority 6";
            }
            enum q7 {
                value 7;
                description "Queue 7 and priority 7";
            }
        }
        description "";
        reference "";
    }

    typedef  CML_QOS_PMAPC_CLASS_NAME_T {
        type union {
            type CML_QOS_NAME_T {

            }
            type CML_QUEUING_CLASS_DEFAULT_T {

            }
        }
        description "";
        reference "";
    }

    typedef  CML_QOS_PMAP_CLASS_NAME_T {
        type union {
            type CML_QOS_NAME_T {

            }
            type CML_QOS_CLASS_DEFAULT_T {

            }
        }
        description "";
        reference "";
    }

    typedef  CML_HQOS_MAC_DIR_T {
        type enumeration {
            enum src {
                value 0;
                description "Source address";
            }
            enum dest {
                value 1;
                description "Destination address";
            }
        }
        description "";
        reference "";
    }

    typedef  CML_HQOS_TRAFFIC_TYPE_NOT_T {
        type enumeration {
            enum traffic-type {
                value 0;
                description "Traffic Type";
            }
            enum not-traffic-type {
                value 1;
                description "match all except this,Traffic Type";
            }
        }
        description "";
        reference "";
    }

    typedef  CML_HQOS_TRAFFIC_TYPE_T {
        type enumeration {
            enum l2-uc {
                value 1;
                description "L2 Unicast";
            }
            enum l2-uc-unknown {
                value 2;
                description "Unknown L2 Unicast";
            }
            enum default {
                value 6;
                description "L2 traffic-type all";
            }
        }
        description "";
        reference "";
    }

    typedef  CML_HQOS_MATCH_NOT_T {
        type enumeration {
            enum cos {
                value 0;
                description "List COS Values";
            }
            enum not-cos {
                value 1;
                description "match all except this,List COS Values";
            }
        }
        description "";
        reference "";
    }

    typedef  CML_HQOS_SHAPE_TYPE_T {
        type enumeration {
            enum bps {
                value 1;
                description "";
            }
            enum kbps {
                value 2;
                description "";
            }
            enum mbps {
                value 3;
                description "";
            }
            enum gbps {
                value 4;
                description "";
            }
            enum percent {
                value 6;
                description "";
            }
        }
        description "";
        reference "";
    }

    typedef  CML_HQOS_SHAPE_RATE_TYPE_T {
        type enumeration {
            enum kbps {
                value 2;
                description "Specifies the units of kilobits per second";
            }
            enum mbps {
                value 3;
                description "Specifies the units of megabits per second";
            }
            enum gbps {
                value 4;
                description "Specifies the units of gigabits per second";
            }
        }
        description "";
        reference "";
    }

    typedef  CML_HQOS_SET_BRIDGE_T {
        type enumeration {
            enum set-bridge {
                value 0;
                description "Setting a new value in the packet,Remark only Bridged packets";
            }
            enum set {
                value 1;
                description "Setting a new value in the packet";
            }
        }
        description "";
        reference "";
    }

    typedef  CML_HQOS_SET_TYPE_T {
        type enumeration {
            enum cos {
                value 1;
                description "Specify a CoS";
            }
            enum dscp {
                value 2;
                description "Match packets with given dscp value";
            }
            enum precedence {
                value 3;
                description "IP Precedence value";
            }
            enum mpls-class {
                value 4;
                description "MPLS Class(or Queue) which mapped to exp,Specify Class value";
            }
            enum qos-group {
                value 14;
                description "Specify a QoS Group";
            }
        }
        description "";
        reference "";
    }

    typedef  CML_HQOS_MATCH_NOT_DSCP_T {
        type enumeration {
            enum not-dscp {
                value 0;
                description "match all except this,List DSCP Values";
            }
            enum dscp {
                value 1;
                description "List DSCP Values";
            }
        }
        description "";
        reference "";
    }

    typedef  CML_HQOS_MATCH_NOT_PRECEDENCE_T {
        type enumeration {
            enum not-precedence {
                value 0;
                description "match all except this,List precedence Values";
            }
            enum precedence {
                value 1;
                description "List precedence Values";
            }
        }
        description "";
        reference "";
    }

    typedef  CML_HQOS_MATCH_NOT_RTP_T {
        type enumeration {
            enum not-ip {
                value 0;
                description "match all except this,Internet Protocol (IP)";
            }
            enum ip {
                value 1;
                description "Internet Protocol (IP)";
            }
        }
        description "";
        reference "";
    }

    typedef  CML_QOS_SERVICE_TYPE_T {
        type enumeration {
            enum qos {
                value 1;
                description "Qos";
            }
            enum queuing {
                value 2;
                description "Queuing";
            }
        }
        description "";
        reference "";
    }

    typedef  CML_QOS_CMAPDEF_TYPE_T {
        type enumeration {
            enum type-queuing-default {
                value 3;
                description "type,queuing,default";
            }
        }
        description "";
        reference "";
    }

    typedef  CML_QOS_CMAPANY_TYPE_T {
        type enumeration {
            enum type-qos {
                value 1;
                description "type,qos is ingress/egress class-map";
            }
        }
        description "";
        reference "";
    }

    typedef  CML_QOS_CMAP_TYPE_T {
        type enumeration {
            enum type-qos {
                value 1;
                description "type,qos is ingress/egress class-map";
            }
            enum type-queuing {
                value 2;
                description "Specify type of this class-map,Match on Egress Queuing class";
            }
        }
        description "";
        reference "";
    }

    typedef  CML_VXLAN_QOS_GLOBAL_MODE_T {
        type enumeration {
            enum cos-dscp {
                value 1;
                description "COS vs DSCP mapping";
            }
            enum dscp-dscp {
                value 2;
                description "DSCP vs DSCP mapping";
            }
        }
        description "";
        reference "";
    }

    typedef  CML_VXLAN_QOS_DIR_T {
        type enumeration {
            enum ingress {
                value 0;
                description "Apply ingress direction";
            }
            enum egress {
                value 1;
                description "Apply Egress direction";
            }
        }
        description "";
        reference "";
    }

    typedef  CML_VXLAN_QOS_EGRESS_DIR_T {
        type enumeration {
            enum egress {
                value 1;
                description "Apply Egress direction";
            }
        }
        description "";
        reference "";
    }

    typedef  CML_VXLAN_QOS_INGRESS_DIR_T {
        type enumeration {
            enum ingress {
                value 0;
                description "Apply ingress direction";
            }
        }
        description "";
        reference "";
    }

    typedef  CML_QOS_MATCH_TYPE_T {
        type enumeration {
            enum match-any {
                value 1;
                description "match any";
            }
            enum match-all {
                value 2;
                description "match all";
            }
        }
        description "";
        reference "";
    }

    typedef  CML_HQOS_MATCH_NOT_PROTOCOL_T {
        type enumeration {
            enum not-protocol {
                value 0;
                description "match all except this,Protocol classification";
            }
            enum protocol {
                value 1;
                description "Protocol classification";
            }
        }
        description "";
        reference "";
    }

    typedef  CML_HQOS_MATCH_NOT_VLAN_T {
        type enumeration {
            enum not-vlan {
                value 0;
                description "match all except this,List VLAN ID";
            }
            enum vlan {
                value 1;
                description "List VLAN ID";
            }
        }
        description "";
        reference "";
    }

    typedef  CML_HQOS_MATCH_NOT_MPLS_EXP_T {
        type enumeration {
            enum not-mpls {
                value 0;
                description "match all except this,Multi Protocol Label Switch list values";
            }
            enum mpls {
                value 1;
                description "Multi Protocol Label Switch list values";
            }
        }
        description "";
        reference "";
    }

    typedef  CML_HQOS_SHAPE_AVG_T {
        type enumeration {
            enum shape-average {
                value 0;
                description "Configure Traffic Shaping,Specifies an optional keyword";
            }
            enum shape {
                value 1;
                description "Configure Traffic Shaping";
            }
        }
        description "";
        reference "";
    }

    typedef  CML_HQOS_SHAPE_AVG_UNITS_T {
        type enumeration {
            enum bps {
                value 0;
                description "Specifies the units of bits per second";
            }
            enum kbps {
                value 1;
                description "Specifies the units of kilobits per second";
            }
            enum mbps {
                value 2;
                description "Specifies the units of megabits per second";
            }
            enum gbps {
                value 3;
                description "Specifies the units of gigabits per second";
            }
        }
        description "";
        reference "";
    }

    typedef  CML_HQOS_THRESHOLD_TYPE_T {
        type enumeration {
            enum packets {
                value 1;
                description "Number of Packets (max 600)";
            }
            enum bytes {
                value 2;
                description "bytes (max 524288)";
            }
            enum kbytes {
                value 3;
                description "kilo-bytes (max 512)";
            }
        }
        description "";
        reference "";
    }

    typedef  CML_HOSTNAME_T {
        type union {
            type CML_IP_ADDR_T {

            }
            type CML_STRING_T {

            }
        }
        description "";
        reference "";
    }

    typedef  CML_HOSTPNAME_T {
        type union {
            type CML_IP_ADDR_T {

            }
            type CML_HOST_STRING_T {

            }
        }
        description "";
        reference "";
    }

    typedef  CML_IPV4HOSTNAME_T {
        type union {
            type CML_IPV4_ADDR_T {

            }
            type CML_HOST_STRING_T {

            }
        }
        description "";
        reference "";
    }

    typedef  CML_HOST_T {
        type enumeration {
            enum hostname {
                value 1;
                description "Hostname";
            }
        }
        description "";
        reference "";
    }

    typedef  CML_IPV4_ADDR_OR_PREFIX_T {
        type union {
            type CML_IPV4_ADDR_T {

            }
            type CML_IPV4_ADDR_PREFIX_T {

            }
        }
        description "";
        reference "";
    }

    typedef  CML_IP_ADDR_T {
        type union {
            type CML_IPV4_ADDR_T {

            }
            type CML_IPV6_ADDR_T {

            }
        }
        description "";
        reference "";
    }

    typedef  CML_IPV4_ADDR_DESC_T {

        type inet:ipv4-address{
        length 0..15;
        }
        description "";
        reference "";
    }

    typedef  CML_IPV6_ADDR_DESC_T {

        type inet:ipv6-address{
        length 0..45;
        }
        description "";
        reference "";
    }

    typedef  CML_IP_PREFIX_ADDR_T {
        type union {
            type CML_IPV4_PREFIX_T {

            }
            type CML_IPV6_PREFIX_T {

            }
        }
        description "";
        reference "";
    }

    typedef  CML_MAC_ETH_TYPE_T {
        type union {
            type CML_ETH_TYPE_T {

            }
            type CML_STRING_T {

            }
        }
        description "";
        reference "";
    }

    typedef  CML_ETH_TYPE_T {
        type enumeration {
            enum ip4 {
                value 0;
                description "IPv4 Ethertype - 0x0800";
            }
            enum ip6 {
                value 1;
                description "IPv6 Ethertype - 0x86dd";
            }
            enum mpls {
                value 2;
                description "MPLS Ethertype - 0x8847";
            }
        }
        description "";
        reference "";
    }

    typedef  CML_VLAN_OPERSTATUS_T {
        type enumeration {
            enum vlan_oper_up {
                value 1;
                description "VLAN operstatus is up";
            }
            enum vlan_oper_down {
                value 2;
                description "VLAN operstatus is down";
            }
        }
        description "";
        reference "";
    }

    typedef  CML_VLAN_TYPE_CUSTOMER_T {
        type enumeration {
            enum customer {
                value 1;
                description "Customer Vlan";
            }
        }
        description "";
        reference "";
    }

    typedef  CML_VLAN_TYPE_SERVICE_T {
        type enumeration {
            enum service-point-point {
                value 16;
                description "VLAN Type,Service VLAN,Service Point to Point Service VLAN";
            }
            enum service-multipoint-multipoint {
                value 32;
                description "VLAN Type,Service VLAN,Service Multi Point to Multi Point Service VLAN";
            }
            enum service-rooted-multipoint {
                value 2048;
                description "VLAN Type,Service VLAN,Service Rooted Multipoint Service VLAN";
            }
        }
        description "";
        reference "";
    }

    typedef  CML_FACILITY_T {
        type enumeration {
            enum local0 {
                value 0;
                description "Use local0 facility";
            }
            enum local1 {
                value 1;
                description "Use local1 facility";
            }
            enum local2 {
                value 2;
                description "Use local2 facility";
            }
            enum local3 {
                value 3;
                description "Use local3 facility";
            }
            enum local4 {
                value 4;
                description "Use local4 facility";
            }
            enum local5 {
                value 5;
                description "Use local5 facility";
            }
            enum local6 {
                value 6;
                description "Use local6 facility";
            }
            enum local7 {
                value 7;
                description "Use local7 facility";
            }
            enum user {
                value 8;
                description "Use user facility";
            }
        }
        description "";
        reference "";
    }

    typedef  CML_HOSTT_T {
        type enumeration {
            enum emergencies {
                value 0;
                description "Use local0 facility";
            }
            enum alerts {
                value 1;
                description "Use local1 facility";
            }
            enum critical {
                value 2;
                description "Use local2 facility";
            }
            enum errors {
                value 3;
                description "Use local3 facility";
            }
            enum warnings {
                value 4;
                description "Use local4 facility";
            }
            enum notifications {
                value 5;
                description "Use local5 facility";
            }
            enum informational {
                value 6;
                description "Use local6 facility";
            }
            enum debugging {
                value 7;
                description "Use local7 facility";
            }
        }
        description "";
        reference "";
    }

    typedef  CML_DISCARDFORWARD_T {
        type enumeration {
            enum discard {
                value 0;
                description "discard";
            }
            enum forward {
                value 1;
                description "forward";
            }
        }
        description "";
        reference "";
    }

    typedef  CML_SWITCH_PORT_MODE_T {
        type enumeration {
            enum access {
                value 1;
                description "Set the Layer2 interface as Access";
            }
            enum hybrid {
                value 2;
                description "Set the Layer2 interface as hybrid";
            }
            enum trunk {
                value 3;
                description "Set the Layer2 interface as trunk";
            }
            enum customer-network {
                value 5;
                description "Set the Layer2 interface as Customer Network";
            }
            enum provider-network {
                value 6;
                description "Set the Layer2 interface as provider network";
            }
            enum sbp {
                value 20;
                description "Station-facing bridge-port";
            }
            enum uap {
                value 21;
                description "Uplink Access Port";
            }
            enum customer-edge-access {
                value 41;
                description "Set the Layer2 interface as customer edge,Set the Layer2 interface as Access";
            }
            enum customer-edge-hybrid {
                value 42;
                description "Set the Layer2 interface as customer edge,Set the Layer2 interface as hybrid";
            }
            enum customer-edge-trunk {
                value 43;
                description "Set the Layer2 interface as customer edge,Set the Layer2 interface as trunk";
            }
        }
        description "";
        reference "";
    }

    typedef  CML_VLAN_FRAME_TYPE_T {
        type enumeration {
            enum vlan-tagged {
                value 1;
                description "Set vlan-tagged frames can only be received";
            }
            enum all {
                value 2;
                description "Set vlan-tagged frames can only be received";
            }
        }
        description "";
        reference "";
    }

    typedef  CML_OSPFV3_LINK_STATUS_T {
        type enumeration {
            enum up {
                value 1;
                description "Vlink Status is up";
            }
            enum down {
                value 2;
                description "Vlink Status is down";
            }
        }
        description "";
        reference "";
    }

    typedef  CML_OSPF6_CSPF_TYPE_T {
        type enumeration {
            enum random {
                value 0;
                description "Random";
            }
            enum most-fill {
                value 1;
                description "Most fill";
            }
            enum least-fill {
                value 2;
                description "Least fill";
            }
        }
        description "";
        reference "";
    }

    typedef  CML_OSPF6_ABR_TYPE_T {
        type enumeration {
            enum standard {
                value 1;
                description "Standard behavior (RFC2328)";
            }
            enum cisco {
                value 2;
                description "Alternative ABR, Cisco implementation (RFC3509)";
            }
            enum ibm {
                value 3;
                description "Alternative ABR, IBM implementation (RFC3509)";
            }
        }
        description "";
        reference "";
    }

    typedef  CML_OSPF6_TRANSLATOR_ROLE_T {
        type enumeration {
            enum always {
                value 1;
                description "Translate always";
            }
            enum candidate {
                value 2;
                description "Candidate for translator (default)";
            }
        }
        description "";
        reference "";
    }

    typedef  CML_OSPF6_NETWORK_T {
        type enumeration {
            enum point-to-point {
                value 1;
                description "OSPF point-to-point network";
            }
            enum broadcast {
                value 2;
                description "OSPF broadcast multi-access network";
            }
            enum non-broadcast {
                value 3;
                description "OSPF NBMA network";
            }
            enum point-to-multipoint {
                value 4;
                description "OSPF point-to-multipoint network";
            }
            enum point-to-multipoint-non-broadcast {
                value 5;
                description "OSPF point-to-multipoint NBMA network,non-broadcast point-to-multipoint network";
            }
        }
        description "";
        reference "";
    }

    typedef  CML_OSPF6_LSA_SUPRESSION_STATE_T {
        type enumeration {
            enum disable {
                value 0;
                description "Disable";
            }
            enum enable {
                value 1;
                description "Enable";
            }
        }
        description "";
        reference "";
    }

    typedef  CML_OSPF6_RESTART_HELPER_T {
        type enumeration {
            enum only-reload {
                value 4;
                description "Only help on software reloads";
            }
            enum only-upgrade {
                value 8;
                description "Only help on software upgrades";
            }
        }
        description "";
        reference "";
    }

    typedef  CML_OSPF6_ROUTE_SOURCE_TYPE_T {
        type enumeration {
            enum kernel {
                value 1;
                description "Kernel routes";
            }
            enum connected {
                value 2;
                description "Connected";
            }
            enum static {
                value 3;
                description " Static routes";
            }
            enum rip {
                value 4;
                description " Routing Information Protocol (RIP/RIPNG)";
            }
            enum bgp {
                value 8;
                description " Border Gateway Protocol (BGP)";
            }
            enum isis {
                value 9;
                description "ISO IS-IS";
            }
        }
        description "";
        reference "";
    }

    typedef  CML_OSPF6_DIST_ROUTE_SOURCE_TYPE_T {
        type enumeration {
            enum kernel {
                value 1;
                description "Kernel routes";
            }
            enum connected {
                value 2;
                description "Connected";
            }
            enum static {
                value 3;
                description " Static routes";
            }
            enum rip {
                value 4;
                description " Routing Information Protocol (RIP/RIPNG)";
            }
            enum bgp {
                value 8;
                description " Border Gateway Protocol (BGP)";
            }
            enum isis {
                value 9;
                description "ISO IS-IS";
            }
        }
        description "";
        reference "";
    }

    typedef  CML_OSPF6_AF_ROUTE_SOURCE_TYPE_T {
        type enumeration {
            enum kernel {
                value 1;
                description "Kernel routes";
            }
            enum connected {
                value 2;
                description "Connected";
            }
            enum static {
                value 3;
                description " Static routes";
            }
            enum rip {
                value 4;
                description " Routing Information Protocol (RIP/RIPNG)";
            }
            enum ospf {
                value 6;
                description "Open Shortest Path First (OSPF/OSPF6)";
            }
            enum bgp {
                value 8;
                description " Border Gateway Protocol (BGP)";
            }
            enum isis {
                value 9;
                description "ISO IS-IS";
            }
        }
        description "";
        reference "";
    }

    typedef  CML_OSPF6_AREA_RANGE_T {
        type enumeration {
            enum not-advertise {
                value 0;
                description "DoNotAdvertise this range";
            }
            enum advertise {
                value 1;
                description "Advertise this range (default)";
            }
        }
        description "";
        reference "";
    }

    typedef  CML_OSPF_INTERFACE_STATE_MSG_T {
        type enumeration {
            enum DependUpon {
                value 0;
                description "DependUpon";
            }
            enum Down {
                value 1;
                description "Down";
            }
            enum Loopback {
                value 2;
                description "Loopback";
            }
            enum Waiting {
                value 3;
                description "Waiting";
            }
            enum Point-To-Point {
                value 4;
                description "Point-To-Point";
            }
            enum DROther {
                value 5;
                description "DROther";
            }
            enum Backup {
                value 6;
                description "Backup";
            }
            enum DR {
                value 7;
                description "DR";
            }
        }
        description "";
        reference "";
    }

    typedef  CML_TUNNEL_IPV6_MODE_T {
        type enumeration {
            enum ipv6ip {
                value 3;
                description "IPv6 over IP encapsulation";
            }
            enum 6to4 {
                value 4;
                description "IPv6 automatic tunnelling using 6to4";
            }
            enum isatap {
                value 5;
                description "IPv6 automatic tunnelling using ISATAP";
            }
        }
        description "";
        reference "";
    }

    typedef  CML_TUNNEL_MODE_T {
        type enumeration {
            enum vxlan {
                value 7;
                description "Vxlan encapsulation";
            }
        }
        description "";
        reference "";
    }

    typedef  CML_OSPF_AREA_T {
        type union {
            type CML_IPV4_ADDR_T {

            }
            type uint32 {
                range "0..4294967295";

            }
        }
        description "";
        reference "";
    }

    typedef  CML_OSPF6_PATH_TYPE_T {
        type enumeration {
            enum Connected {
                value 0;
                description "Connected";
            }
            enum IntraArea {
                value 1;
                description "IntraArea";
            }
            enum InterArea {
                value 2;
                description "InterArea";
            }
            enum External {
                value 3;
                description "External";
            }
            enum Discard {
                value 4;
                description "Discard";
            }
        }
        description "";
        reference "";
    }

    typedef  CML_OSPF6_PATH_FLAGS_T {
        type enumeration {
            enum Type2 {
                value 1;
                description "Type2";
            }
            enum ABR {
                value 2;
                description "ABR";
            }
            enum ASBR {
                value 3;
                description "ASBR";
            }
            enum RangeMatched {
                value 4;
                description "RangeMatched";
            }
        }
        description "";
        reference "";
    }

    typedef  CML_OSPF_ACTION_TYPE_T {
        type enumeration {
            enum soft {
                value 1;
                description "Soft limit";
            }
            enum hard {
                value 2;
                description "Hard limit";
            }
        }
        description "";
        reference "";
    }

    typedef  CML_OSPF_TELINK_LOCAL_T {
        type enumeration {
            enum disable-te-link-local {
                value 0;
                description "Disable TE Link local exchange";
            }
            enum enable-te-link-local {
                value 1;
                description "Enable TE Link local exchange";
            }
        }
        description "";
        reference "";
    }

    typedef  CML_OSPF_ROUTE_SOURCE_TYPE_T {
        type enumeration {
            enum kernel {
                value 1;
                description "Kernel routes";
            }
            enum connected {
                value 2;
                description "Connected";
            }
            enum static {
                value 3;
                description " Static routes";
            }
            enum rip {
                value 4;
                description " Routing Information Protocol (RIP)";
            }
            enum ospf {
                value 6;
                description "ISO OSPF";
            }
            enum bgp {
                value 8;
                description " Border Gateway Protocol (BGP)";
            }
            enum isis {
                value 9;
                description "ISO IS-IS";
            }
        }
        description "";
        reference "";
    }

    typedef  CML_OSPF_DIST_ROUTE_SOURCE_TYPE_T {
        type enumeration {
            enum kernel {
                value 1;
                description "Kernel routes";
            }
            enum connected {
                value 2;
                description "Connected";
            }
            enum static {
                value 3;
                description " Static routes";
            }
            enum rip {
                value 4;
                description " Routing Information Protocol (RIP)";
            }
            enum bgp {
                value 8;
                description " Border Gateway Protocol (BGP)";
            }
            enum isis {
                value 9;
                description "ISO IS-IS";
            }
        }
        description "";
        reference "";
    }

    typedef  CML_PORT_SEC_MODE_T {
        type enumeration {
            enum static {
                value 1;
                description "static mode";
            }
            enum default {
                value 2;
                description "dynamic mode";
            }
        }
        description "";
        reference "";
    }

    typedef  CML_PROVIDER_EDGE_T {
        type enumeration {
            enum edge {
                value 1;
                description "Configure as Edge bridge";
            }
        }
        description "";
        reference "";
    }

    typedef  CML_BRIDGE_PROTOCOL_T {
        type enumeration {
            enum ieee {
                value 1;
                description "IEEE 801.1Q spanning-tree protocol";
            }
            enum ieee-vlan-bridge {
                value 2;
                description "IEEE 801.1Q spanning-tree protocol";
            }
            enum rstp {
                value 3;
                description "IEEE 801.1w rapid spanning-tree protocol";
            }
            enum rstp-vlan-bridge {
                value 4;
                description "IEEE 801.1w rapid spanning-tree protocol";
            }
            enum mstp {
                value 5;
                description "IEEE 802.1s multiple spanning-tree protocol";
            }
            enum provider-rstp {
                value 6;
                description "IEEE 802.1s multiple spanning-tree protocol";
            }
            enum provider-mstp {
                value 7;
                description "IEEE 802.1s rapid spanning-tree protocol";
            }
            enum rpvst+ {
                value 8;
                description "IEEE 801.1w rapid per vlan spanning-tree protocol";
            }
            enum provider-rpvst+ {
                value 9;
                description "IEEE 801.1w rapid per vlan spanning-tree protocol";
            }
            enum trill {
                value 20;
                description "Transparent Interconnection of Lots of Link";
            }
            enum evb {
                value 97;
                description "evb";
            }
            enum svlan-evb {
                value 98;
                description "Svlan aware evb";
            }
        }
        description "";
        reference "";
    }

    typedef  CML_BRIDGE_TYPE_T {
        type enumeration {
            enum spanning-tree {
                value 1;
                description "IEEE 801.1Q spanning-tree protocol";
            }
            enum rapid-spanning-tree {
                value 3;
                description "IEEE 801.1w rapid spanning-tree protocol";
            }
            enum multiple-spanning-tree {
                value 5;
                description "IEEE 802.1s multiple spanning-tree protocol";
            }
            enum provider-rstp {
                value 6;
                description "Provider Rapid spanning-tree protocol";
            }
            enum rapid-pervlan-spanning-tree {
                value 12;
                description "Rapid pervlan spanning-tree protocol";
            }
        }
        description "";
        reference "";
    }

    typedef  CML_OVERMACTYPE_T {
        type enumeration {
            enum static {
                value 1;
                description "The MAC is a static entry";
            }
            enum static-priority-override {
                value 2;
                description "The MAC is a Static Management";
            }
            enum static-mgmt {
                value 3;
                description "The MAC is a Static Management with priority override";
            }
            enum static-mgmt-priority-overide {
                value 4;
                description "The MAC is a static with priority override";
            }
        }
        description "";
        reference "";
    }

    typedef  CML_ENABLE_DISABLE_T {
        type enumeration {
            enum disable {
                value 0;
                description "Disable";
            }
            enum enable {
                value 1;
                description "Enable";
            }
        }
        description "";
        reference "";
    }

    typedef  CML_VLANSTATE_T {
        type enumeration {
            enum disable {
                value 1;
                description "Disable";
            }
            enum enable {
                value 2;
                description "Enable";
            }
        }
        description "";
        reference "";
    }

    typedef  CML_PBRINTERFACE_T {
        type enumeration {
            enum null0 {
                value 0;
                description "Forward to no interface";
            }
            enum tunnel-te {
                value 1;
                description "Forward to MPLS-TE tunnel";
            }
        }
        description "";
        reference "";
    }

    typedef  CML_SPANNINGTREE_ENABLE_DISABLE_T {
        type enumeration {
            enum enable {
                value 0;
                description "Enable";
            }
            enum disable {
                value 1;
                description "Disable";
            }
        }
        description "";
        reference "";
    }

    typedef  CML_PATHCOST_METHOD_T {
        type enumeration {
            enum short {
                value 0;
                description "short - Use 16 bit based values for default port path cost";
            }
            enum long {
                value 1;
                description "long  - Use 32 bit based values for default port path costs";
            }
            enum default {
                value 2;
                description "Default";
            }
        }
        description "";
        reference "";
    }

    typedef  CML_LINK_TYPE_T {
        type enumeration {
            enum shared {
                value 0;
                description "shared - disable rapid transition";
            }
            enum point-to-point {
                value 1;
                description "point-to-point - enable rapid transition";
            }
            enum auto {
                value 2;
                description "auto - will be set to either p2p or shared based on duplex state";
            }
        }
        description "";
        reference "";
    }

    typedef  CML_PORTEDGE_T {
        type enumeration {
            enum edgeport {
                value 0;
                description "edgeport - enable it as edgeport";
            }
            enum portfast {
                value 1;
                description "portfast - enable fast transitions";
            }
        }
        description "";
        reference "";
    }

    typedef  CML_BPDU_T {
        type enumeration {
            enum enable {
                value 0;
                description "Enable";
            }
            enum disable {
                value 1;
                description "Disable";
            }
            enum default {
                value 2;
                description "Default";
            }
        }
        description "";
        reference "";
    }

    typedef  CML_BRIDGE_TOPOLOGY_T {
        type enumeration {
            enum topology-none {
                value 0;
                description "Topology none";
            }
            enum ring {
                value 1;
                description "RING Topology";
            }
        }
        description "";
        reference "";
    }

    typedef  CML_BRIDGE_FORWARDING_SET_T {
        type enumeration {
            enum disable {
                value 0;
                description "disable bridge forwarding";
            }
            enum enable {
                value 1;
                description "enable bridge forwarding";
            }
        }
        description "";
        reference "";
    }

    typedef  CML_BRIDGE_MSTPENABLE_T {
        type enumeration {
            enum enable {
                value 1;
                description "enable spanning tree protocol";
            }
        }
        description "";
        reference "";
    }

    typedef  CML_BRIDGE_AGEING_STATE {
        type enumeration {
            enum disable {
                value 0;
                description "disable bridge ageing";
            }
        }
        description "";
        reference "";
    }

    typedef  CML_OSPF_DOMAIN_TYPE_T {
        type enumeration {
            enum type-as {
                value 1;
                description "Type 0x0005";
            }
            enum type-as4 {
                value 2;
                description "Type 0x0205";
            }
            enum type-back-comp {
                value 3;
                description "Type 0x8005";
            }
            enum type-ip {
                value 4;
                description "Type 0x0105";
            }
        }
        description "";
        reference "";
    }

    typedef  CML_OSPF_ABR_TYPE_T {
        type enumeration {
            enum standard {
                value 1;
                description "Standard behavior (RFC2328)";
            }
            enum cisco {
                value 2;
                description " Cisco implementation (RFC3509)";
            }
            enum ibm {
                value 3;
                description "IBM implementation (RFC3509)";
            }
            enum shortcut {
                value 4;
                description "Shortcut ABR";
            }
        }
        description "";
        reference "";
    }

    typedef  CML_OSPF_AREA_AUTH_TYPE_T {
        type enumeration {
            enum simple {
                value 1;
                description "Use simple authentication";
            }
            enum message-digest {
                value 2;
                description "Use message-digest authentication";
            }
        }
        description "";
        reference "";
    }

    typedef  CML_OSPF_AREA_SHORTCUT_TYPE_T {
        type enumeration {
            enum default {
                value 0;
                description "Set default shortcutting behavior";
            }
            enum enable {
                value 1;
                description "Enable shortcutting through the area";
            }
            enum disable {
                value 2;
                description "Disable shortcutting through the area";
            }
        }
        description "";
        reference "";
    }

    typedef  CML_OSPF_TRANSLATOR_ROLE_T {
        type enumeration {
            enum never {
                value 0;
                description "Do not translate";
            }
            enum always {
                value 1;
                description "Translate always";
            }
            enum candidate {
                value 2;
                description "Candidate for translator (default)";
            }
        }
        description "";
        reference "";
    }

    typedef  CML_OSPF_NSSA_TRANSLATOR_ROLE_T {
        type enumeration {
            enum translate-never {
                value 0;
                description "Do not translate";
            }
            enum translate-always {
                value 1;
                description "Translate always";
            }
            enum translate-candidate {
                value 2;
                description "Candidate for translator (default)";
            }
        }
        description "";
        reference "";
    }

    typedef  CML_OSPF_STUB_T {
        type enumeration {
            enum stub {
                value 1;
                description "Configure OSPF area as stub";
            }
        }
        description "";
        reference "";
    }

    typedef  CML_OSPF_NSSA_T {
        type enumeration {
            enum nssa {
                value 1;
                description "Configure OSPF area as nssa";
            }
        }
        description "";
        reference "";
    }

    typedef  CML_OSPF_AREA_FILTER_TYPE_T {
        type enumeration {
            enum access {
                value 0;
                description "Filter networks by access-list";
            }
            enum prefix {
                value 1;
                description "Filter networks by prefix-list";
            }
        }
        description "";
        reference "";
    }

    typedef  CML_OSPF_AREA_FILTER_LIST_PREFIX_T {
        type enumeration {
            enum in {
                value 0;
                description "Filter networks sent to this area";
            }
            enum out {
                value 1;
                description "Filter networks sent from this area";
            }
        }
        description "";
        reference "";
    }

    typedef  CML_OSPF_VIRT_AUTH_KEY_T {
        type enumeration {
            enum null {
                value 0;
                description "unencrypted authentication key";
            }
            enum PASSWORD {
                value 1;
                description "Authentication key (8 chars)";
            }
        }
        description "";
        reference "";
    }

    typedef  CML_OSPF_VIRT_AUTH_TYPE_T {
        type enumeration {
            enum null {
                value 0;
                description "Use no authentication";
            }
            enum simple {
                value 1;
                description "Use simple authentication";
            }
            enum message-digest {
                value 2;
                description "Use message-digest authentication";
            }
        }
        description "";
        reference "";
    }

    typedef  CML_OSPF_RESTART_METHOD_T {
        type enumeration {
            enum graceful {
                value 1;
                description "Graceful OSPF Restart (default)";
            }
            enum signaling {
                value 2;
                description "OSPF Restart Signaling";
            }
        }
        description "";
        reference "";
    }

    typedef  CML_CSPF_TIE_BREAK_T {
        type enumeration {
            enum least-fill {
                value 1;
                description "least fill";
            }
            enum most-fill {
                value 2;
                description "Most fill";
            }
            enum random {
                value 3;
                description "Random";
            }
        }
        description "";
        reference "";
    }

    typedef  CML_OSPF_METRIC_TYPE_T {
        type enumeration {
            enum 1 {
                value 1;
                description "Set OSPF External Type 1 metrics";
            }
            enum 2 {
                value 2;
                description "Set OSPF External Type 2 metrics";
            }
        }
        description "";
        reference "";
    }

    typedef  CML_OSPF_NETWORK_T {
        type enumeration {
            enum point-to-point {
                value 1;
                description "OSPF point-to-point network";
            }
            enum broadcast {
                value 2;
                description "OSPF broadcast multi-access network";
            }
            enum non-broadcast {
                value 3;
                description "OSPF NBMA network";
            }
            enum point-to-multipoint {
                value 4;
                description "OSPF point-to-multipoint network";
            }
            enum point-to-multipoint-non-broadcast {
                value 5;
                description "OSPF point-to-multipoint network,non-broadcast point-to-multipoint network";
            }
        }
        description "";
        reference "";
    }

    typedef  CML_OSPF_AUTH_TYPE_T {
        type enumeration {
            enum null {
                value 0;
                description "Use no authentication";
            }
            enum simple {
                value 1;
                description "Use simple authentication";
            }
            enum message-digest {
                value 2;
                description "Use message-digest authentication";
            }
        }
        description "";
        reference "";
    }

    typedef  CML_LDP_HELPER_MODE_T {
        type enumeration {
            enum disable {
                value 0;
                description "Disable graceful restart";
            }
            enum enable {
                value 1;
                description "Enable graceful restart";
            }
        }
        description "";
        reference "";
    }

    typedef  CML_OSPF_FRR_TIE_BREAK_VAL_T {
        type enumeration {
            enum primary-path {
                value 1;
                description "Primary Path";
            }
            enum interface-disjoint {
                value 2;
                description "Link Protecting";
            }
            enum node-protecting {
                value 3;
                description "broadcast-interface-disjoint";
            }
            enum broadcast-interface-disjoint {
                value 4;
                description "Broadcast Link Protecting";
            }
        }
        description "";
        reference "";
    }

    typedef  CML_LDP_ADVERTISE_MODE_T {
        type enumeration {
            enum downstream-unsolicited {
                value 0;
                description "DU advertisement mode";
            }
            enum downstream-on-demand {
                value 1;
                description "DOD advertisement mode";
            }
        }
        description "";
        reference "";
    }

    typedef  CML_LDP_CONTROLMODE_T {
        type enumeration {
            enum independent {
                value 0;
                description "DU advertisement mode";
            }
            enum ordered {
                value 1;
                description "DOD advertisement mode";
            }
        }
        description "";
        reference "";
    }

    typedef  CML_LDP_LABEL_T {
        type enumeration {
            enum liberal {
                value 0;
                description "Set liberal label retention mode";
            }
            enum conservative {
                value 1;
                description "Set conservative label retention mode";
            }
        }
        description "";
        reference "";
    }

    typedef  CML_LDP_MERGE_CAPABLE_T {
        type enumeration {
            enum merge-capable {
                value 0;
                description "Set merge capable";
            }
            enum non-merge-capable {
                value 1;
                description "Set non merge capable";
            }
        }
        description "";
        reference "";
    }

    typedef  CML_PIM_MODE_TYPE_T {
        type enumeration {
            enum dense-mode {
                value 1;
                description "Enable PIM dense-mode operation";
            }
            enum sparse-mode {
                value 2;
                description "Enable PIM sparse-mode operation";
            }
            enum sparse-dense-mode {
                value 3;
                description "Enable PIM sparse-mode and dense-mode operations";
            }
        }
        description "";
        reference "";
    }

    typedef  CML_PIM_EXTENDED_ACCESS_LIST_T {
        type union {
            type CML_STRING_T {

            }
            type uint8 {
                range "1..99";

            }
            type uint16 {
                range "1300..1999";

            }
        }
        description "";
        reference "";
    }

    typedef  CML_IFNAME_T {

        type string;
        description "";
        reference "";
    }

    typedef  CML_IPV4_IFNAME_T {
        type union {
            type CML_IPV4_ADDR_T {

            }
            type CML_IFNAME_T {

            }
        }
        description "";
        reference "";
    }

    typedef  CML_IPV6_IFNAME_T {
        type union {
            type CML_IPV6_ADDR_T {

            }
            type CML_IFNAME_T {

            }
        }
        description "";
        reference "";
    }

    typedef  CML_PIM_SSM_TYPE_T {
        type union {
            type CML_STRING_T {

            }
            type uint8 {
                range "1..99";

            }
        }
        description "";
        reference "";
    }

    typedef  CML_SSM_DEFAULT_T {
        type enumeration {
            enum default {
                value 0;
                description "Use 232/8 group range for SSM";
            }
        }
        description "";
        reference "";
    }

    typedef  CML_SSM_RANGE_T {

        type string;
        description "";
        reference "";
    }

    typedef  CML_PIM_SSM_ACL_TYPE_T {
        type union {
            type CML_SSM_RANGE_T {

            }
            type CML_SSM_DEFAULT_T {

            }
        }
        description "";
        reference "";
    }

    typedef  CML_PIM_DEBUG_TYPE_T {
        type bits {
            bit events {
                position 0;
                description "PIM events";
            }
            bit packet-in {
                position 1;
                description "PIM packet,Incoming PIM packet";
            }
            bit packet-out {
                position 2;
                description "PIM packet,Outgoing PIM packet";
            }
            bit state {
                position 3;
                description "PIM state";
            }
            bit mfc {
                position 4;
                description "PIM MFC updates";
            }
            bit timer-hello-ht {
                position 5;
                description "PIM timers,Hello Timers,Hello timer";
            }
            bit timer-hello-nlt {
                position 6;
                description "PIM timers,Hello Timers,Neighbor Liveliness timer";
            }
            bit timer-hello-tht {
                position 7;
                description "PIM timers,Hello Timers,Triggered Hello timer";
            }
            bit timer-joinprune-jt {
                position 8;
                description "PIM timers,JoinPrune Timers,JoinPrune timer";
            }
            bit timer-joinprune-et {
                position 9;
                description "PIM timers,JoinPrune Timers,Expiry timer";
            }
            bit timer-joinprune-ppt {
                position 10;
                description "PIM timers,JoinPrune Timers,Prune Pending timer";
            }
            bit timer-joinprune-kat {
                position 11;
                description "PIM timers,JoinPrune Timers,Keep Alive timer";
            }
            bit timer-joinprune-ot {
                position 12;
                description "PIM timers,JoinPrune Timers,Override timer";
            }
            bit timer-assert {
                position 13;
                description "PIM timers,Assert Timers";
            }
            bit timer-register {
                position 14;
                description "PIM timers,Register Timers";
            }
            bit timer-bsr-bst {
                position 15;
                description "PIM timers,BSR Timers,Bootstrap timer";
            }
            bit timer-bsr-crp {
                position 16;
                description "PIM timers,BSR Timers,Candidate-RP timer";
            }
            bit mib {
                position 17;
                description "PIM mib";
            }
            bit nsm {
                position 18;
                description "NSM message";
            }
            bit nexthop {
                position 19;
                description "PIM nexthop";
            }
            bit mtrace {
                position 20;
                description "Mtrace messages";
            }
        }
        description "";
        reference "";
    }

    typedef  CML_MRIB_IP_TYPE_T {
        type enumeration {
            enum ip {
                value 1;
                description "Internet Protocol(IP)";
            }
        }
        description "";
        reference "";
    }

    typedef  CML_MRIB_IPV6_TYPE_T {
        type enumeration {
            enum ipv6 {
                value 0;
                description "Internet Protocol(IPv6)";
            }
        }
        description "";
        reference "";
    }

    typedef  CML_MRIB4_DEBUG_T {
        type bits {
            bit event {
                position 0;
                description "None";
            }
            bit vif {
                position 1;
                description "None";
            }
            bit mrt {
                position 2;
                description "None";
            }
            bit stats {
                position 3;
                description "None";
            }
            bit fib-msg {
                position 4;
                description "None";
            }
            bit register-msg {
                position 5;
                description "None";
            }
            bit nsm-msg {
                position 6;
                description "None";
            }
            bit mrib-msg {
                position 7;
                description "None";
            }
            bit mtrace {
                position 8;
                description "None";
            }
            bit mtrace-detail {
                position 9;
                description "None";
            }
        }
        description "";
        reference "";
    }

    typedef  CML_MRIB6_DEBUG_T {
        type bits {
            bit event {
                position 0;
                description "None";
            }
            bit vif {
                position 1;
                description "None";
            }
            bit mrt {
                position 2;
                description "None";
            }
            bit stats {
                position 3;
                description "None";
            }
            bit fib-msg {
                position 4;
                description "None";
            }
            bit register-msg {
                position 5;
                description "None";
            }
            bit nsm-msg {
                position 6;
                description "None";
            }
            bit mrib-msg {
                position 7;
                description "None";
            }
            bit mtrace {
                position 8;
                description "None";
            }
            bit mtrace-detail {
                position 9;
                description "None";
            }
        }
        description "";
        reference "";
    }

    typedef  CML_IGMP_DEBUG_T {
        type bits {
            bit encode {
                position 0;
                description "None";
            }
            bit decode {
                position 1;
                description "None";
            }
            bit events {
                position 2;
                description "None";
            }
            bit fsm {
                position 3;
                description "None";
            }
            bit tib {
                position 4;
                description "None";
            }
        }
        description "";
        reference "";
    }

    typedef  CML_MLD_DEBUG_T {
        type bits {
            bit encode {
                position 0;
                description "None";
            }
            bit decode {
                position 1;
                description "None";
            }
            bit events {
                position 2;
                description "None";
            }
            bit fsm {
                position 3;
                description "None";
            }
            bit tib {
                position 4;
                description "None";
            }
        }
        description "";
        reference "";
    }

    typedef  CML_MAUTYPE_T {
        type enumeration {
            enum dot3MauType10BaseTHD {
                value 10;
                description "UTP MAU half duplex mode";
            }
            enum dot3MauType10BaseTFD {
                value 11;
                description "UTP MAU full duplex mode";
            }
            enum dot3MauType100BaseTXHD {
                value 15;
                description "2 pair category 5 UTP half duplex mode";
            }
            enum dot3MauType100BaseTXFD {
                value 16;
                description "2 pair category 5 UTP full duplex mode";
            }
            enum dot3MauType1000BaseXHD {
                value 21;
                description "PCS/PMA unknown PMD half duplex mode";
            }
            enum dot3MauType1000BaseXFD {
                value 22;
                description "PCS/PMA unknown PMD full duplex mode";
            }
            enum dot3MauType10GigBaseCX4 {
                value 41;
                description "X copper over 8 pair 100-Ohm balanced cable";
            }
            enum dot3MauType10GbaseKX4 {
                value 57;
                description "4 lane X backplane full duplex mode only";
            }
            enum dot3MauType10GbaseKR {
                value 58;
                description "R backplane full duplex mode only";
            }
            enum dot3MauType40GbaseCR4 {
                value 71;
                description "40GBASE-R PCS/PMA over 4 lane shielded copper balanced cable";
            }
        }
        description "";
        reference "";
    }

    typedef  CML_DUPLEX_T {
        type enumeration {
            enum half {
                value 0;
                description "set half duplex";
            }
            enum full {
                value 1;
                description "set full duplex";
            }
        }
        description "";
        reference "";
    }

    typedef  CML_INTF_FEC_T {
        type enumeration {
            enum off {
                value 0;
                description "disable fec";
            }
            enum on {
                value 1;
                description "enable fec";
            }
            enum auto {
                value 2;
                description "enable fec auto";
            }
        }
        description "";
        reference "";
    }

    typedef  CML_INTERFACE_TYPE_T {
        type enumeration {
            enum Router {
                value 0;
                description "L3 interface";
            }
            enum Switch {
                value 1;
                description "L2 interface";
            }
            enum TDM {
                value 2;
                description "TDM interface";
            }
        }
        description "";
        reference "";
    }

    typedef  CML_BANDWIDTHCONSTRAINTMODE_T {
        type enumeration {
            enum MAM {
                value 0;
                description "MAM";
            }
            enum RSDL {
                value 1;
                description "RSDL";
            }
            enum MAR {
                value 2;
                description "MAR";
            }
        }
        description "";
        reference "";
    }

    typedef  CML_AFI_TYPE_T {
        type enumeration {
            enum ipv4 {
                value 1;
                description "Address family";
            }
            enum ipv6 {
                value 2;
                description "Address family";
            }
            enum vpnv4 {
                value 3;
                description "Address family";
            }
            enum vpnv6 {
                value 4;
                description "Address family";
            }
            enum rtfilter {
                value 5;
                description "Address family";
            }
            enum l2vpn {
                value 25;
                description "Address family";
            }
        }
        description "";
        reference "";
    }

    typedef  CML_VRF_AFI_TYPE_T {
        type enumeration {
            enum ipv4 {
                value 1;
                description "Address family";
            }
            enum ipv6 {
                value 2;
                description "Address family";
            }
        }
        description "";
        reference "";
    }

    typedef  CML_VRF_SAFI_TYPE_T {
        type enumeration {
            enum unicast {
                value 1;
                description "Address family modifier";
            }
        }
        description "";
        reference "";
    }

    typedef  CML_SAFI_TYPE_T {
        type enumeration {
            enum unicast {
                value 1;
                description "Address family modifier";
            }
            enum multicast {
                value 2;
                description "Address family modifier";
            }
            enum labeled-unicast {
                value 4;
                description "Address family modifier";
            }
            enum l2vpn-vpls {
                value 65;
                description "Address family modifier";
            }
            enum evpn {
                value 70;
                description "Address family modifier";
            }
            enum vpn-unicast {
                value 128;
                description "Address family modifier";
            }
            enum rtfilter-unicast {
                value 132;
                description "Address family modifier";
            }
        }
        description "";
        reference "";
    }

    typedef  CML_BGP_NETWORK_T {
        type union {
            type CML_IPV4_ADDR_T {

            }
            type CML_IPV4_PREFIX_T {

            }
        }
        description "";
        reference "";
    }

    typedef  CML_BGP_IP_NETWORK_T {
        type union {
            type CML_IPV4_ADDR_T {

            }
            type CML_IPV4_PREFIX_T {

            }
            type CML_IPV6_PREFIX_T {

            }
        }
        description "";
        reference "";
    }

    typedef  CML_BGP_ROUTE_TARGET_T {
        type enumeration {
            enum rt {
                value 0;
                description "Specify route target";
            }
            enum soo {
                value 1;
                description "specify site of origin";
            }
        }
        description "";
        reference "";
    }

    typedef  CML_BGP_CONFIG_T {
        type enumeration {
            enum standard {
                value 0;
                description "standard";
            }
            enum zebos {
                value 1;
                description "ZebOS";
            }
        }
        description "";
        reference "";
    }

    typedef  CML_BGP_MED_TYPE_T {
        type bits {
            bit confed {
                position 0;
                description "Compare MED among confederation paths";
            }
            bit missing-as-worst {
                position 1;
                description "Treat missing MED as the least preferred one";
            }
            bit remove-recv-med {
                position 2;
                description "To remove rcvd MED attribute";
            }
            bit remove-send-med {
                position 3;
                description "To remove send MED attribute";
            }
        }
        description "";
        reference "";
    }

    typedef  CML_CLEAR_TYPE_T {
        type enumeration {
            enum clear_all {
                value 0;
                description "clear all";
            }
            enum clear_peer {
                value 1;
                description "clear peer";
            }
            enum clear_group {
                value 2;
                description "clear group";
            }
            enum clear_external {
                value 3;
                description "clear external";
            }
            enum clear_as {
                value 4;
                description "clear as";
            }
            enum clear_rfd {
                value 5;
                description "clear rfd";
            }
            enum clear_prefix {
                value 6;
                description "clear prefix";
            }
        }
        description "";
        reference "";
    }

    typedef  CML_CLEAR_SOFT_T {
        type enumeration {
            enum soft_none {
                value 1;
                description "clear peer";
            }
            enum soft_out {
                value 2;
                description "clear group";
            }
            enum soft_in {
                value 3;
                description "clear external";
            }
            enum soft_both {
                value 4;
                description "clear as";
            }
            enum soft_in_orf_prefix {
                value 5;
                description "clear rfd";
            }
            enum table_map {
                value 6;
                description "clear prefix";
            }
            enum rfd_damp {
                value 7;
                description "clear prefix";
            }
            enum rfd_flap_stat {
                value 8;
                description "clear prefix";
            }
        }
        description "";
        reference "";
    }

    typedef  CML_BGP_ORF_PREFIX_TYPE_T {
        type bits {
            bit receive {
                position 1;
                description "Capability to RECEIVE the ORF from this neighbor";
            }
            bit send {
                position 2;
                description "Capability to SEND the ORF to this neighbor";
            }
        }
        description "";
        reference "";
    }

    typedef  CML_BGP_COMMUNITY_LIST_ACTION_T {
        type enumeration {
            enum deny {
                value 1;
                description "Specify community to reject";
            }
            enum permit {
                value 2;
                description "Specify community to accept";
            }
        }
        description "";
        reference "";
    }

    typedef  CML_RMAP_PERMIT_T {
        type enumeration {
            enum permit {
                value 0;
                description "Route map permits set operations";
            }
            enum deny {
                value 1;
                description "Route map denies set operations";
            }
        }
        description "";
        reference "";
    }

    typedef  BGP_ADDITIONAL_PATH_TYPE_T {
        type enumeration {
            enum receive {
                value 1;
                description "Receive additional paths from neighbors";
            }
            enum send {
                value 2;
                description "Send additional paths to neighbors";
            }
            enum send-receive {
                value 3;
                description "Send and Receive additional paths from neighbors";
            }
        }
        description "";
        reference "";
    }

    typedef  BGP_PEER_ADDITIONAL_PATH_TYPE_T {
        type enumeration {
            enum receive {
                value 1;
                description "Receive additional paths from neighbors";
            }
            enum send {
                value 2;
                description "Send additional paths to neighbors";
            }
            enum send-receive {
                value 3;
                description "Send and Receive additional paths from neighbors";
            }
            enum disable {
                value 4;
                description "disable additional-paths";
            }
        }
        description "";
        reference "";
    }

    typedef  BGP_ADV_RCV_TYPE_T {
        type enumeration {
            enum advertise {
                value 1;
                description "advertised";
            }
            enum receive {
                value 2;
                description "received";
            }
            enum advertise-receive {
                value 3;
                description "advertised and received both";
            }
            enum advertise-receive-old-and-new {
                value 4;
                description "advertised and received both (old and new)";
            }
            enum advertise-receive-old {
                value 5;
                description "advertised and received both (old)";
            }
            enum advertise-receive-new {
                value 6;
                description "advertised and received both (new)";
            }
            enum receive-old-and-new {
                value 7;
                description "received (old and new)";
            }
            enum receive-old {
                value 8;
                description "received (old)";
            }
            enum receive-new {
                value 9;
                description "received (new)";
            }
        }
        description "";
        reference "";
    }

    typedef  CML_BGP_SEND_COMMU_TYPE_T {
        type bits {
            bit standard {
                position 1;
                description "Send Standard Community attributes";
            }
            bit extended {
                position 2;
                description "Send Extended Community attributes";
            }
        }
        description "";
        reference "";
    }

    typedef  CML_BGP_UPDATE_DEBUG_TYPE_T {
        type bits {
            bit in {
                position 8;
                description "Inbound updates";
            }
            bit out {
                position 9;
                description "Outbound updates";
            }
        }
        description "";
        reference "";
    }

    typedef  CML_ATTRIBUTE_UNCHANGED_TYPE_T {
        type bits {
            bit as-path {
                position 1;
                description "As-path attribute";
            }
            bit next-hop {
                position 2;
                description "Next-hop attribute";
            }
            bit med {
                position 3;
                description "Med attribute";
            }
        }
        description "";
        reference "";
    }

    typedef  CML_BGP_DEBUG_TYPE_T {
        type bits {
            bit nht {
                position 1;
                description "NHT message";
            }
            bit nsm {
                position 2;
                description "NSM message";
            }
            bit fsm {
                position 3;
                description "Finite state machine";
            }
            bit events {
                position 4;
                description "BGP events";
            }
            bit filters {
                position 5;
                description "BGP filter";
            }
            bit keepalives {
                position 6;
                description "BGP keepalives";
            }
            bit updates {
                position 7;
                description "BGP updates";
            }
            bit dampening {
                position 10;
                description "BGP Dampening";
            }
            bit bfd {
                position 11;
                description "Bidirectional Forwarding Detection (BFD)";
            }
        }
        description "";
        reference "";
    }

    typedef  CML_BGP_DISTRIBUTE_LIST_ACTION_T {
        type enumeration {
            enum in {
                value 0;
                description "Filter incoming updates";
            }
            enum out {
                value 1;
                description "Filter outgoing updates";
            }
        }
        description "";
        reference "";
    }

    typedef  CML_BGP_REDISTRIBUTE_TYPE_T {
        type enumeration {
            enum kernel {
                value 1;
                description "Kernel routes";
            }
            enum connected {
                value 2;
                description "Connected";
            }
            enum static {
                value 3;
                description "Static routes";
            }
            enum rip {
                value 4;
                description "Routing Information Protocol(RIP)";
            }
            enum ospf {
                value 5;
                description "Kernel routes";
            }
            enum isis {
                value 6;
                description "ISO IS-IS";
            }
        }
        description "";
        reference "";
    }

    typedef  CML_BGP_COMMUNITY_LIST_ENTRY_T {
        type enumeration {
            enum standard {
                value 0;
                description "Add a standard community-list entry";
            }
            enum expanded {
                value 1;
                description "Add an expanded community-list entry";
            }
            enum default {
                value 2;
                description "default community-list entry";
            }
        }
        description "";
        reference "";
    }

    typedef  CML_BGP_AGGREGATE_ADDR_TYPE_T {
        type enumeration {
            enum summary-only {
                value 1;
                description "Add a standard community-list entry";
            }
            enum as-set {
                value 2;
                description "Add an expanded community-list entry";
            }
        }
        description "";
        reference "";
    }

    typedef  CML_BGP_PEER_STATUS_T {
        type enumeration {
            enum idle {
                value 1;
                description "Idle";
            }
            enum connect {
                value 2;
                description "Connect";
            }
            enum active {
                value 3;
                description "Active";
            }
            enum opensent {
                value 4;
                description "Opensent";
            }
            enum openconfirm {
                value 5;
                description "Openconfirm";
            }
            enum established {
                value 6;
                description "Established";
            }
        }
        description "";
        reference "";
    }

    typedef  CML_PEERFLAG_SHUTDOWN_T {
        type enumeration {
            enum idle {
                value 1;
                description "Idle";
            }
            enum connect {
                value 2;
                description "Connect";
            }
            enum active {
                value 3;
                description "Active";
            }
            enum opensent {
                value 4;
                description "Opensent";
            }
            enum openconfirm {
                value 5;
                description "Openconfirm";
            }
            enum established {
                value 6;
                description "Established";
            }
            enum idle-dmin {
                value 7;
                description "Idle Admin";
            }
            enum idle-pfxct {
                value 8;
                description "Idle PfxCt";
            }
            enum idle-g-shut {
                value 9;
                description "Idle G-shut";
            }
        }
        description "";
        reference "";
    }

    typedef  CML_BGP_PREFIX_ENTRY_TYPE_T {
        type enumeration {
            enum no_match {
                value 1;
                description "No match";
            }
            enum deny {
                value 2;
                description "Deny";
            }
            enum permit {
                value 3;
                description "Permit";
            }
        }
        description "";
        reference "";
    }

    typedef  CML_BGP_RI_TYPE_T {
        type enumeration {
            enum internal {
                value 1;
                description "internal";
            }
            enum confed-external {
                value 2;
                description "confed-external";
            }
            enum external {
                value 3;
                description "external";
            }
            enum aggregated-and-local {
                value 4;
                description "aggregated and local";
            }
            enum sourced {
                value 5;
                description "sourced";
            }
            enum sourced-and-local {
                value 6;
                description "sourced and local";
            }
        }
        description "";
        reference "";
    }

    typedef  CML_BGP_ORIGIN_T {
        type enumeration {
            enum igp {
                value 0;
                description "IGP";
            }
            enum egp {
                value 1;
                description "EGP";
            }
            enum incomplete {
                value 2;
                description "incomplete";
            }
        }
        description "";
        reference "";
    }

    typedef  CML_BGP_LINK_TYPE_T {
        type enumeration {
            enum internal {
                value 0;
                description "internal";
            }
            enum external {
                value 1;
                description "external";
            }
        }
        description "";
        reference "";
    }

    typedef  CML_BGP_CONNECTION_TYPE_T {
        type enumeration {
            enum shared {
                value 0;
                description "shared network";
            }
            enum non_shared {
                value 1;
                description "non shared network";
            }
        }
        description "";
        reference "";
    }

    typedef  CML_BGP_AS_TYPE_T {
        type enumeration {
            enum internal {
                value -2;
                description "internal for iBGP peer";
            }
            enum external {
                value -1;
                description "external for eBGP peer";
            }
        }
        description "";
        reference "";
    }

    typedef  CML_BGP_AS_T {
        type union {
            type CML_BGP_AS_TYPE_T {

            }
            type int64 {
                range "1..4294967295";

            }
        }
        description "";
        reference "";
    }

    typedef  CML_CLUSTER_ID_T {
        type union {
            type CML_IPV4_ADDR_T {

            }
            type uint32 {
                range "1..4294967295";

            }
        }
        description "";
        reference "";
    }

    typedef  CML_MPLS_VLAN_ACTIONTYPE_T {
        type enumeration {
            enum pop {
                value 0;
                description "Pop the outer vid";
            }
        }
        description "";
        reference "";
    }

    typedef  CML_MPLS_MODULE_T {
        type enumeration {
            enum rsvp {
                value 0;
                description "Specify label range value for rsvp";
            }
            enum ldp {
                value 1;
                description "Specify label range value for ldp";
            }
            enum bgp {
                value 4;
                description "Specify label range value for bgp";
            }
        }
        description "";
        reference "";
    }

    typedef  CML_MPLS_ADMN_STATUS_T {
        type enumeration {
            enum up {
                value 1;
                description "None";
            }
            enum down {
                value 2;
                description "None";
            }
            enum testing {
                value 3;
                description "None";
            }
        }
        description "";
        reference "";
    }

    typedef  CML_MPLS_OPR_STATUS_T {
        type enumeration {
            enum up {
                value 1;
                description "None";
            }
            enum down {
                value 2;
                description "None";
            }
            enum testing {
                value 3;
                description "None";
            }
            enum dormant {
                value 4;
                description "None";
            }
            enum not-persent {
                value 5;
                description "None";
            }
            enum ll-down {
                value 6;
                description "None";
            }
        }
        description "";
        reference "";
    }

    typedef  CML_MPLS_ROW_STATUS_T {
        type enumeration {
            enum active {
                value 1;
                description "None";
            }
            enum not-in-severice {
                value 2;
                description "None";
            }
            enum not-ready {
                value 3;
                description "None";
            }
            enum create-go {
                value 4;
                description "None";
            }
            enum create-wait {
                value 5;
                description "None";
            }
            enum destroy {
                value 6;
                description "None";
            }
        }
        description "";
        reference "";
    }

    typedef  CML_MPLS_BFD_FLAG_T {
        type enumeration {
            enum configured {
                value 0;
                description "None";
            }
            enum enabled {
                value 1;
                description "None";
            }
            enum disable {
                value 2;
                description "None";
            }
        }
        description "";
        reference "";
    }

    typedef  CML_NSM_MPLS_TPID_T {
        type enumeration {
            enum 88a8 {
                value 34984;
                description "Set tpid value as 88a8";
            }
            enum 9100 {
                value 37120;
                description "Set tpid value as 9100";
            }
        }
        description "";
        reference "";
    }

    typedef  CML_NSM_SVC_TPID_T {
        type enumeration {
            enum dot1.q {
                value 33024;
                description "Set tpid value as 0x8100";
            }
            enum dot1.ad {
                value 34984;
                description "Set tpid value as 0x88a8";
            }
            enum 0x9100 {
                value 37120;
                description "Set tpid value as 0x9100";
            }
        }
        description "";
        reference "";
    }

    typedef  CML_NSM_MPLS_ADMIN_STATUS_T {
        type enumeration {
            enum down {
                value 0;
                description "Set the admin role as Down";
            }
            enum up {
                value 1;
                description "Set the admin role as UP";
            }
        }
        description "";
        reference "";
    }

    typedef  CML_NSM_MPLS_VPLS_LEARNING_T {
        type enumeration {
            enum reset {
                value 0;
                description "reset learning to global config";
            }
            enum enable {
                value 1;
                description "Enable MAC learning";
            }
            enum disable {
                value 2;
                description "Disable MAC learning";
            }
        }
        description "";
        reference "";
    }

    typedef  CML_NSM_MPLS_VCMODE_T {
        type enumeration {
            enum standby {
                value 2;
                description "VC runtime Standby mode";
            }
            enum revertive {
                value 4;
                description "VC redundancy revertive mode";
            }
        }
        description "";
        reference "";
    }

    typedef  CML_NSM_MPLS_VCLINKMODE_T {
        type enumeration {
            enum primary {
                value 0;
                description "Primary Link";
            }
            enum secondary {
                value 16;
                description "Secondary Link - Will not be activated unless primary fails";
            }
        }
        description "";
        reference "";
    }

    typedef  CML_NSM_MPLS_IF_VCTYPE_T {
        type enumeration {
            enum hdlc {
                value 6;
                description "Hdlc";
            }
            enum ppp {
                value 7;
                description "Point-to-Point";
            }
            enum tdm-E1 {
                value 17;
                description "TDM - E1 line";
            }
            enum tdm-T1 {
                value 18;
                description "TDM - T1 line";
            }
            enum tdm-E3 {
                value 19;
                description "TDM - E3 line";
            }
            enum tdm-T3 {
                value 20;
                description "TDM - T3 line";
            }
        }
        description "";
        reference "";
    }

    typedef  CML_NSM_MPLS_IF_ETHER_VCTYPE_T {
        type enumeration {
            enum ethernet {
                value 5;
                description "Ethernet";
            }
        }
        description "";
        reference "";
    }

    typedef  CML_NSM_MPLS_IF_VLAN_VCTYPE_T {
        type enumeration {
            enum vlan {
                value 4;
                description "VLAN";
            }
        }
        description "";
        reference "";
    }

    typedef  CML_NSM_MPLS_BFD_T {
        type enumeration {
            enum ldp {
                value 0;
                description "LDP type LSP";
            }
            enum static {
                value 2;
                description "Static type LSP";
            }
        }
        description "";
        reference "";
    }

    typedef  CML_BFD_RSVP_LSP_T {
        type enumeration {
            enum rsvp {
                value 1;
                description "RSVP type LSP";
            }
        }
        description "";
        reference "";
    }

    typedef  CML_NSM_MPLS_BFD_TYPE_T {
        type enumeration {
            enum ldp {
                value 0;
                description "LDP type LSP";
            }
            enum rsvp {
                value 1;
                description "RSVP type LSP";
            }
            enum static {
                value 2;
                description "Static type LSP";
            }
        }
        description "";
        reference "";
    }

    typedef  CML_NSM_MPLS_VCCP_STATE_T {
        type enumeration {
            enum start {
                value 1;
                description "start bfd-vccv";
            }
            enum stop {
                value 2;
                description "stop bfd-vccv";
            }
        }
        description "";
        reference "";
    }

    typedef  CML_OSPF_ROW_STATUS {
        type enumeration {
            enum row-status-active {
                value 1;
                description "Active Row status";
            }
            enum row-status-notinservice {
                value 2;
                description "Row status Not in Service";
            }
            enum row-status-notready {
                value 3;
                description "Row status Not Ready";
            }
            enum row-status-createandgo {
                value 4;
                description "Row status Create and Go";
            }
            enum row-status-createandwait {
                value 5;
                description "Row status Create and Wait";
            }
        }
        description "";
        reference "";
    }

    typedef  CML_NSM_VPLS_TYPE_T {
        type enumeration {
            enum vlan {
                value 4;
                description "VLAN";
            }
            enum ethernet {
                value 5;
                description "Ethernet";
            }
        }
        description "";
        reference "";
    }

    typedef  NSM_VPLS_ETHER_ACTION_T {
        type enumeration {
            enum no-op {
                value 1;
                description "Set action as add";
            }
            enum add {
                value 2;
                description "Set action as no operation";
            }
        }
        description "";
        reference "";
    }

    typedef  NSM_VPLS_VLAN_ACTION_T {
        type enumeration {
            enum no-op {
                value 1;
                description "Set action as add";
            }
            enum remove {
                value 3;
                description "Set action as remove";
            }
            enum replace {
                value 4;
                description "Set action as replace";
            }
        }
        description "";
        reference "";
    }

    typedef  CML_NSM_VPLS_VC_SPOKE_TYPE_T {
        type enumeration {
            enum vlan {
                value 4;
                description "VC Spoke type:VLAN";
            }
            enum ethernet {
                value 5;
                description "VC Spoke type:Ethernet";
            }
        }
        description "";
        reference "";
    }

    typedef  CML_NSM_VPLS_PEER_TUNNEL_DIR_T {
        type enumeration {
            enum forward {
                value 0;
                description "Tunnel Direction - Forward tunnel identifier - Default Value";
            }
            enum reverse {
                value 1;
                description "Tunnel Direction - Reverse tunnel identifier";
            }
        }
        description "";
        reference "";
    }

    typedef  CML_NSM_VPLS_PEER_TYPE_T {
        type enumeration {
            enum manual {
                value 1;
                description "No signaling is used to set-up the Virtual Circuit";
            }
        }
        description "";
        reference "";
    }

    typedef  CML_NSM_VPLS_FTN_ENTRY_T {
        type enumeration {
            enum secondary {
                value 0;
                description "Secondary LSP";
            }
            enum primary {
                value 1;
                description "Primary LSP (default)";
            }
        }
        description "";
        reference "";
    }

    typedef  CML_VPLS_REDUNDANCY_ROLE_T {
        type enumeration {
            enum primary {
                value 0;
                description "Set role as primary";
            }
            enum secondary {
                value 1;
                description "Set role as secondary";
            }
        }
        description "";
        reference "";
    }

    typedef  CML_NSM_VPLS_OPCODE_T {
        type enumeration {
            enum swap {
                value 3;
                description "Swap incoming label";
            }
        }
        description "";
        reference "";
    }

    typedef  CML_NSM_MPLS_IPV6OPCODE_T {
        type enumeration {
            enum swap {
                value 3;
                description "Swap incoming label";
            }
        }
        description "";
        reference "";
    }

    typedef  CML_NSM_VPLS_POPOPCODE_T {
        type enumeration {
            enum pop {
                value 2;
                description "pop incoming label";
            }
        }
        description "";
        reference "";
    }

    typedef  CML_VPLS_VC_STYLE1_T {
        type enumeration {
            enum peer {
                value 2;
                description "Mesh Peer";
            }
        }
        description "";
        reference "";
    }

    typedef  CML_VPLS_VC_STYLE2_T {
        type enumeration {
            enum spoke-vc {
                value 3;
                description "Spoke Virtual Circuit";
            }
        }
        description "";
        reference "";
    }

    typedef  CML_L2VPN_PROTOCOL_T {
        type enumeration {
            enum ldp-autodiscovery-bgp {
                value 8;
                description "Specify the protocol as LDP for MPLS Layer-2 Virtual Circuit,Specify the protocol with autodiscovery-bgp for MPLS Layer-2 Virtual Circuit";
            }
        }
        description "";
        reference "";
    }

    typedef  CML_L2VPN_VC_TYPE_T {
        type enumeration {
            enum ethernet {
                value 5;
                description "Ethernet";
            }
            enum hdlc {
                value 6;
                description "Hdlc";
            }
            enum ppp {
                value 7;
                description "Point-to-Point";
            }
            enum tdm-E1 {
                value 17;
                description "TDM - E1 line";
            }
            enum tdm-T1 {
                value 18;
                description "TDM - T1 line";
            }
            enum tdm-E3 {
                value 19;
                description "TDM - E3 line";
            }
            enum tdm-T3 {
                value 20;
                description "TDM - T3 line";
            }
        }
        description "";
        reference "";
    }

    typedef  CML_RSVP_PATH_STATUS_T {
        type enumeration {
            enum loose {
                value 0;
                description "Make this node loose";
            }
            enum strict {
                value 1;
                description "Make this node strict";
            }
        }
        description "";
        reference "";
    }

    typedef  CML_RSVP_PROT_STATUS_T {
        type enumeration {
            enum one-to-one {
                value 1;
                description "One-to-One protection";
            }
            enum facility {
                value 2;
                description "Facility Backup (Bypass) protection";
            }
        }
        description "";
        reference "";
    }

    typedef  CML_RSVP_IP_ADDR_T {
        type union {
            type CML_IPV4_ADDR_T {

            }
            type CML_IPV6_ADDR_T {

            }
        }
        description "";
        reference "";
    }

    typedef  CML_RSVP_FRR_ADMIN_TYPE_T {
        type enumeration {
            enum exclude-any {
                value 0;
                description "Exclude-any attribute";
            }
            enum include-any {
                value 1;
                description "Include-any attribute";
            }
        }
        description "";
        reference "";
    }

    typedef  CML_RSVP_TRAFFIC_TYPE_T {
        type enumeration {
            enum controlled-load {
                value 1;
                description "Controlled load traffic";
            }
            enum guaranteed {
                value 2;
                description "Guaranteed traffic";
            }
        }
        description "";
        reference "";
    }

    typedef  CML_RSVP_UPDATE_TYPE_T {
        type enumeration {
            enum break-before-make {
                value 1;
                description "Break Before Make";
            }
            enum make-before-break {
                value 2;
                description "Make Before Break";
            }
        }
        description "";
        reference "";
    }

    typedef  CML_RSVP_CAPABILITY_TYPE_T {
        type enumeration {
            enum psc-1 {
                value 1;
                description "Packet Switch Capable-1";
            }
            enum psc-2 {
                value 2;
                description "Packet Switch Capable-2";
            }
            enum psc-3 {
                value 4;
                description "Packet Switch Capable-3";
            }
            enum psc-4 {
                value 8;
                description "Packet Switch Capable-4";
            }
        }
        description "";
        reference "";
    }

    typedef  CML_RSVP_DIRECTION_TYPE_T {
        type enumeration {
            enum unidirectional {
                value 0;
                description "Unidirectional";
            }
            enum bidirectional {
                value 1;
                description "Bidirectional";
            }
        }
        description "";
        reference "";
    }

    typedef  CML_RSVP_GPID_TYPE_T {
        type enumeration {
            enum ethernet {
                value 33;
                description "Ethernet gpid type";
            }
            enum ipv4 {
                value 2048;
                description "IPv4 gpid type";
            }
        }
        description "";
        reference "";
    }

    typedef  CML_RSVP_EXPLICIT_FWD_DIR_T {
        type enumeration {
            enum forward {
                value 1;
                description "Forward LSP Direction - Ingress to Egress (Downstream)";
            }
            enum packet-forward {
                value 3;
                description "Default label-type is packet, Forward LSP Direction - Ingress to Egress (Downstream)";
            }
        }
        description "";
        reference "";
    }

    typedef  CML_RSVP_EXPLICIT_REV_DIR_T {
        type enumeration {
            enum reverse {
                value 2;
                description "Reverse LSP Direction - Egress to Ingress (Upstream)";
            }
            enum packet-reverse {
                value 4;
                description "Default label-type is packet,Reverse LSP Direction - Egress to Ingress (Upstream)";
            }
        }
        description "";
        reference "";
    }

    typedef  CML_RSVP_FILTER_TYPE_T {
        type enumeration {
            enum default {
                value 0;
                description "default";
            }
            enum fixed {
                value 1;
                description "Use a Fixed Filter for this LSP";
            }
            enum shared-explicit {
                value 2;
                description "Use a Shared Explicit Filter for this LSP";
            }
        }
        description "";
        reference "";
    }

    typedef  CML_RSVP_PROTECTION_TYPE_T {
        type enumeration {
            enum extra-traffic {
                value 1;
                description "Extra-traffic";
            }
            enum unprotected {
                value 2;
                description "Unprotected";
            }
            enum shared {
                value 4;
                description "Shared";
            }
            enum dedicated-one-to-one {
                value 8;
                description "Dedicated 1:1";
            }
            enum dedicated-one-plus-one {
                value 16;
                description "Dedicated 1+1";
            }
            enum enhanced {
                value 32;
                description "Enhanced";
            }
        }
        description "";
        reference "";
    }

    typedef  CML_RSVP_EXCLUDE_ADDR_TYPE_T {
        type enumeration {
            enum link {
                value 1;
                description "Enables a Link Protection - NHOP";
            }
            enum node {
                value 2;
                description "Enables a Node Protection - NNHOP";
            }
        }
        description "";
        reference "";
    }

    typedef  CML_IS_TYPE_T {
        type enumeration {
            enum level-1 {
                value 1;
                description "Act as a station router only";
            }
            enum level-2-only {
                value 2;
                description "Act as an area router only";
            }
            enum level-1-2 {
                value 3;
                description "Act as both a station router and an area router";
            }
        }
        description "";
        reference "";
    }

    typedef  CML_IS_TYPE2_T {
        type enumeration {
            enum level-1 {
                value 1;
                description "Act as a station router only";
            }
            enum level-2 {
                value 2;
                description "Act as an area router only";
            }
            enum level-1-2 {
                value 3;
                description "Act as both a station router and an area router";
            }
        }
        description "";
        reference "";
    }

    typedef  CML_ISIS_SYSTEMID_T {

        type string{
        pattern "[0-9a-fA-F]{4}\\.[0-9a-f]{4}\\.[0-9a-f]{4}";
        }
        description "";
        reference "";
    }

    typedef  CML_ISIS_LEVEL_T {
        type enumeration {
            enum level-1 {
                value 1;
                description "Set interval for level 1 only";
            }
            enum level-2 {
                value 2;
                description "Set interval for level 2 only";
            }
            enum level-1-2 {
                value 3;
                description "Set interval for both level 1 and level 2";
            }
        }
        description "";
        reference "";
    }

    typedef  CML_ISIS_LEVEL2_T {
        type enumeration {
            enum level-1 {
                value 1;
                description "Level-1";
            }
            enum level-2 {
                value 2;
                description "Level-2";
            }
        }
        description "";
        reference "";
    }

    typedef  CML_ISIS_LEVEL_PROTO_T {
        type enumeration {
            enum ipv4 {
                value 1;
                description "IPv4 address family";
            }
            enum ipv6 {
                value 2;
                description "IPv6 address family";
            }
        }
        description "";
        reference "";
    }

    typedef  CML_ISIS_FRR_ENUM_T {
        type enumeration {
            enum all {
                value 1;
                description "On all prefixes";
            }
        }
        description "";
        reference "";
    }

    typedef  CML_ISIS_FRR_TIE_BREAK_VAL_T {
        type enumeration {
            enum primary-path {
                value 1;
                description "Primary Path";
            }
            enum interface-disjoint {
                value 2;
                description "Link Protecting";
            }
            enum node-protecting {
                value 3;
                description "broadcast-interface-disjoint";
            }
            enum broadcast-interface-disjoint {
                value 4;
                description "Broadcast Link Protecting";
            }
            enum secondary-path {
                value 5;
                description "Secondary path";
            }
            enum downstream-path {
                value 6;
                description "Downstream path";
            }
        }
        description "";
        reference "";
    }

    typedef  CML_ISIS_IFLEVEL_T {
        type enumeration {
            enum level-1 {
                value 1;
                description "Act as a station router only";
            }
            enum level-2 {
                value 2;
                description "Act as an area router only";
            }
            enum p2p {
                value 3;
                description "P2p index";
            }
        }
        description "";
        reference "";
    }

    typedef  CML_ISIS_NBR_ADJ_T {
        type enumeration {
            enum Suppress {
                value 1;
                description "show Adjacency Suppress";
            }
            enum Advertise {
                value 2;
                description "show Adjacency Advertisement";
            }
        }
        description "";
        reference "";
    }

    typedef  CML_ISIS_ORIGIN_TYPE_T {
        type enumeration {
            enum originate {
                value 4;
                description "Distribute a default route";
            }
            enum originate-always {
                value 32;
                description "Distribute a default route,Always advertise default route";
            }
        }
        description "";
        reference "";
    }

    typedef  CML_ISIS_NETWORK_T {
        type enumeration {
            enum broadcast {
                value 1;
                description "Specify IS-IS broadcast multi-access network";
            }
            enum point-to-point {
                value 2;
                description "Specify IS-IS point-to-point network";
            }
        }
        description "";
        reference "";
    }

    typedef  CML_ISIS_DYNAMIC_HOSTANME_T {
        type enumeration {
            enum dynamic-hostname {
                value 0;
                description "Enable dynamic hostname";
            }
            enum area-tag {
                value 1;
                description "Use area-tag as hostname";
            }
        }
        description "";
        reference "";
    }

    typedef  CML_ISIS_STATE_T {
        type enumeration {
            enum Down {
                value 0;
                description "LAN Neighbor Down";
            }
            enum Init {
                value 1;
                description "LAN Neighbor Init";
            }
            enum Up {
                value 2;
                description "LAN Neighbor Up";
            }
        }
        description "";
        reference "";
    }

    typedef  CML_METRIC_STYLE_T {
        type enumeration {
            enum narrow {
                value 1;
                description "Use old style of TLVs with narrow metric";
            }
            enum wide {
                value 2;
                description "Use new style of TLVs to carry wider metric";
            }
            enum transition {
                value 3;
                description "Send and accept both styles of TLVs during transition";
            }
            enum narrow-transition {
                value 4;
                description "Use old style of TLVs with narrow metric,Send and accept both styles of TLVs during transition";
            }
            enum wide-transition {
                value 5;
                description "Use old style of TLVs with wide metric, Send and accept both styles of TLVs during transition";
            }
        }
        description "";
        reference "";
    }

    typedef  CML_TRANSITION_METRIC_STYLE_T {
        type enumeration {
            enum narrow {
                value 1;
                description "Use old style of TLVs with narrow metric";
            }
            enum wide {
                value 2;
                description "Use new style of TLVs to carry wider metric";
            }
        }
        description "";
        reference "";
    }

    typedef  CML_ISIS_AUTH_MODE_T {
        type enumeration {
            enum md5 {
                value 1;
                description "Keyed message digest";
            }
            enum text {
                value 2;
                description "Text mode";
            }
        }
        description "";
        reference "";
    }

    typedef  CML_ISIS_ROUTE_T {
        type enumeration {
            enum redistribution {
                value 0;
                description "Clear ISIS IP local redistribution routes";
            }
            enum all {
                value 1;
                description "all of the IS-IS routing table";
            }
        }
        description "";
        reference "";
    }

    typedef  CML_ISIS_SNP_T {
        type enumeration {
            enum send-only {
                value 1;
                description "Keyed message digest";
            }
            enum validate {
                value 2;
                description "Text mode";
            }
        }
        description "";
        reference "";
    }

    typedef  CML_ISIS_LIFETIME_T {
        type enumeration {
            enum accept-lifetime {
                value 1;
                description "Set accept lifetime of the key";
            }
            enum send-lifetime {
                value 2;
                description "Set send lifetime of the key";
            }
        }
        description "";
        reference "";
    }

    typedef  CML_ISIS_REDISTRIBUTE_T {
        type enumeration {
            enum kernel {
                value 1;
                description "Kernel routes";
            }
            enum connected {
                value 2;
                description "Connected";
            }
            enum static {
                value 3;
                description "Static routes";
            }
            enum rip {
                value 4;
                description "Routing Information Protocol(RIP)";
            }
            enum ospf {
                value 5;
                description "Open Shortest Path First (OSPF)";
            }
            enum bgp {
                value 6;
                description "Border Gateway Protocol (BGP)";
            }
        }
        description "";
        reference "";
    }

    typedef  CML_ISIS_DEBUG_T {
        type bits {
            bit ifsm {
                position 0;
                description "IS-IS Interface Finite State Machine";
            }
            bit nfsm {
                position 1;
                description "IS-IS Neighbor Finite State Machine";
            }
            bit pdu {
                position 2;
                description "IS-IS Protocol Data Unit";
            }
            bit lsp {
                position 3;
                description "IS-IS Link State PDU";
            }
            bit spf {
                position 4;
                description "IS-IS SPF Calculation";
            }
            bit events {
                position 5;
                description "IS-IS Events";
            }
            bit nsm {
                position 6;
                description "IS-IS NSM information";
            }
            bit checksum {
                position 7;
                description "IS-IS Check-Sum";
            }
            bit authentication {
                position 8;
                description "IS-IS Authentication";
            }
            bit local-updates {
                position 9;
                description "IS-IS Local Updates";
            }
            bit protocol-errors {
                position 10;
                description "IS-IS Protocol Errors";
            }
            bit bfd {
                position 12;
                description "Bidirectional Forwarding Detection (BFD)";
            }
            bit rib {
                position 14;
                description "IS-IS RIB information";
            }
        }
        description "";
        reference "";
    }

    typedef  CML_ISIS_DEBUG_HELLO_T {
        type enumeration {
            enum hello {
                value 1;
                description "IS-IS Hello Debug";
            }
        }
        description "";
        reference "";
    }

    typedef  CML_ISIS_CSPF_DEBUG_T {
        type bits {
            bit events {
                position 0;
                description "None";
            }
            bit hexdump {
                position 1;
                description "None";
            }
        }
        description "";
        reference "";
    }

    typedef  CML_PASSWORD_T {

        type string{
        length 1..8;
        pattern "[a-zA-Z0-9].*";
        }
        description "";
        reference "";
    }

    typedef  CML_SYSTEM_HOSTNAME_T {

        type string{
        length 1..64;
        pattern "[a-zA-Z0-9\\-].*";
        }
        description "";
        reference "";
    }

    typedef  CML_USERNAME_T {

        type string{
        length 1..255;
        pattern "[\\-a-zA-Z0-9].*";
        }
        description "";
        reference "";
    }

    typedef  CML_WRAP_T {
        type enumeration {
            enum off {
                value 0;
                description "Disable autowrap";
            }
            enum on {
                value 1;
                description "Enable autowrap";
            }
        }
        description "";
        reference "";
    }

    typedef  CML_LDP_TDP_PROTOCOL_T {
        type enumeration {
            enum both {
                value 0;
                description "Use LDP or TDP (Adapt to peer on multiaccess interface)";
            }
            enum ldp {
                value 1;
                description "Use LDP (default)";
            }
            enum tdp {
                value 2;
                description "Use TDP";
            }
        }
        description "";
        reference "";
    }

    typedef  CML_INTERFACE_T {
        type enumeration {
            enum interface {
                value 0;
                description "Use LDP or TDP (Adapt to peer on multiaccess interface)";
            }
        }
        description "";
        reference "";
    }

    typedef  CML_LDP_DISCOVERY_ADDRESS_T {
        type union {
            type CML_INTERFACE_T {

            }
            type CML_IPV4_ADDR_T {

            }
        }
        description "";
        reference "";
    }

    typedef  CML_MTU_T {
        type union {
            type CML_UINT16_T {

            }
            type CML_UINT16_T {

            }
            type CML_UINT16_T {

            }
        }
        description "";
        reference "";
    }

    typedef  CML_AREA_T {
        type union {
            type uint32 {
                range "0..4294967295";

            }
            type CML_IPV4_ADDR_T {

            }
        }
        description "";
        reference "";
    }

    typedef  CML_SELF_TEST_T {
        type enumeration {
            enum extended {
                value 0;
                description "Extended self test";
            }
            enum fast {
                value 1;
                description "Fast self test";
            }
            enum none {
                value 2;
                description "Turn off self test";
            }
        }
        description "";
        reference "";
    }

    typedef  CML_BAUD_RATE_T {
        type enumeration {
            enum 9600 {
                value 9600;
                description "9600";
            }
            enum 19200 {
                value 19200;
                description "19200";
            }
            enum 38400 {
                value 38400;
                description "38400";
            }
            enum 115200 {
                value 115200;
                description "115200";
            }
        }
        description "";
        reference "";
    }

    typedef  CML_OSPF6_INSTANCE_T {
        type union {
            type CML_UINT8_T {

            }
            type CML_UINT8_T {

            }
        }
        description "";
        reference "";
    }

    typedef  CML_ACCESS_GROUP_DIRECTION_T {
        type enumeration {
            enum in {
                value 0;
                description "inbound packets";
            }
            enum out {
                value 1;
                description "outbound packets";
            }
        }
        description "";
        reference "";
    }

    typedef  CML_VLAN_ID_T {

        type uint16{
         range 0..65535;
        }
        description "";
        reference "";
    }

    typedef  CML_ADDR_OR_SCRIPT_T {
        type union {
            type CML_IPV4_ADDR_T {

            }
            type CML_STRING_T {

            }
        }
        description "";
        reference "";
    }

    typedef  CML_GI_MEDIA_T {
        type enumeration {
            enum 10-full {
                value 0;
                description "10BaseT full duplex";
            }
            enum 10-half {
                value 1;
                description "10BaseT half duplex";
            }
            enum 100-auto {
                value 2;
                description "100BaseTX duplex auto-negotiation and speed up to 100Mbps";
            }
            enum 100-full {
                value 3;
                description "100BaseTX full duplex";
            }
            enum 100-half {
                value 4;
                description "100BaseTX half duplex";
            }
            enum 1000-full {
                value 5;
                description "1000BaseT full duplex";
            }
            enum 1000-half {
                value 6;
                description "1000BaseT half duplex";
            }
            enum auto {
                value 7;
                description "Automatically negotiate speed";
            }
        }
        description "";
        reference "";
    }

    typedef  CML_TE_MEDIA_T {
        type enumeration {
            enum 1000-full {
                value 0;
                description "1000BaseX full duplex";
            }
            enum 10000-full {
                value 1;
                description "10GBase(SR/LR/.../T) full duplex";
            }
            enum auto {
                value 2;
                description "Automatically negotiate speed";
            }
        }
        description "";
        reference "";
    }

    typedef  CML_PORT_TYPE_T {
        type enumeration {
            enum nni {
                value 0;
                description "nni";
            }
        }
        description "";
        reference "";
    }

    typedef  CML_MODE_T {
        type enumeration {
            enum active {
                value 0;
                description "Enable LACP unconditionally";
            }
            enum auto {
                value 1;
                description "Enable PAgP only if a PAgP device is detected";
            }
            enum desirable {
                value 2;
                description "Enable PAgP unconditionally";
            }
            enum on {
                value 3;
                description "Enable Etherchannel only";
            }
            enum passive {
                value 4;
                description "Enable LACP only if a LACP device is detected";
            }
        }
        description "";
        reference "";
    }

    typedef  CML_CHANNEL_PROTOCOL_T {
        type enumeration {
            enum lacp {
                value 0;
                description "Prepare interface for LACP protocol";
            }
            enum pagp {
                value 1;
                description "Prepare interface for PAgP protocol";
            }
        }
        description "";
        reference "";
    }

    typedef  CML_ENCAPSULATION_T {
        type enumeration {
            enum mpls {
                value 0;
                description "Use MPLS encapsulation";
            }
            enum l2tpv3 {
                value 1;
                description "Use L2TPv3 encapsulation";
            }
        }
        description "";
        reference "";
    }

    typedef  CML_SEQUENCE_T {
        type enumeration {
            enum both {
                value 0;
                description "Transmit and receive sequence numbers";
            }
            enum receive {
                value 1;
                description "Receive sequence numbers";
            }
            enum transmit {
                value 2;
                description "Transmit sequence numbers";
            }
        }
        description "";
        reference "";
    }

    typedef  CML_GROUP_ENUM_T {
        type enumeration {
            enum global {
                value 0;
                description "Attach global PPPoE group";
            }
        }
        description "";
        reference "";
    }

    typedef  CML_GROUP_T {
        type union {
            type CML_GROUP_ENUM_T {

            }
            type CML_STRING_T {

            }
        }
        description "";
        reference "";
    }

    typedef  CML_RATE_TYPE_T {

        type uint32{
         range 0..4294967295;
        }
        description "";
        reference "";
    }

    typedef  CML_IP_RATE_T {
        type union {
            type CML_RATE_TYPE_T {

            }
            type CML_STRING_T {

            }
        }
        description "";
        reference "";
    }

    typedef  CML_SPT_NAME_T {
        type enumeration {
            enum mst {
                value 0;
                description "Global Spanning-Tree configuration";
            }
        }
        description "";
        reference "";
    }

    typedef  CML_OSPF_ROUTE_T {
        type enumeration {
            enum connected {
                value 0;
                description "Connected";
            }
            enum kernel {
                value 1;
                description "Kernel routes";
            }
            enum static {
                value 2;
                description "Static routes";
            }
        }
        description "";
        reference "";
    }

    typedef  CML_POLICY_MAP_T {
        type enumeration {
            enum ether-type {
                value 0;
                description "Ethertype";
            }
            enum port {
                value 1;
                description "Entire port";
            }
            enum snpa {
                value 2;
                description "Match a specific MAC address";
            }
            enum vid {
                value 3;
                description "Vlan tag";
            }
        }
        description "";
        reference "";
    }

    typedef  CML_POLICY_MAP_ID_T {
        type union {
            type CML_IP_PREFIX_ADDR_T {

            }
            type CML_POLICY_MAP_T {

            }
        }
        description "";
        reference "";
    }

    typedef  CML_ETHER_VALS_T {
        type enumeration {
            enum ipv4 {
                value 0;
                description "ipv4";
            }
            enum ipv6 {
                value 1;
                description "ipv6";
            }
            enum mpls-unicast {
                value 2;
                description "mpls-unicast";
            }
            enum mpls-multicast {
                value 3;
                description "mpls-multicast";
            }
            enum arp {
                value 4;
                description "arp";
            }
            enum ppoe-discover {
                value 5;
                description "ppoe-discover";
            }
            enum ppoe-session {
                value 6;
                description "ppoe-session";
            }
        }
        description "";
        reference "";
    }

    typedef  CML_ENDIS_T {
        type enumeration {
            enum disable {
                value 0;
                description "disable";
            }
            enum enable {
                value 1;
                description "enable";
            }
        }
        description "";
        reference "";
    }

    typedef  CML_ROUTE_MAP_TYPE_T {
        type enumeration {
            enum client {
                value 0;
                description "Match dynamic clients";
            }
            enum ip {
                value 1;
                description "IP information";
            }
            enum tag {
                value 2;
                description "Tag value for destination routing protocol";
            }
        }
        description "";
        reference "";
    }

    typedef  CML_MIRROR_DIRECTION_T {
        type enumeration {
            enum bidir {
                value 0;
                description "Input and output mirroring";
            }
            enum in {
                value 1;
                description "Input mirroring";
            }
            enum out {
                value 2;
                description "Output mirroring";
            }
        }
        description "";
        reference "";
    }

    typedef  CML_ROUTE_MAP_ACTION_T {
        type enumeration {
            enum deny {
                value 0;
                description "Route map denies set operations";
            }
            enum permit {
                value 1;
                description "Route map permits set operations";
            }
        }
        description "";
        reference "";
    }

    typedef  CML_QUEUES_COUNT_T {
        type enumeration {
            enum 256 {
                value 256;
                description "None";
            }
            enum 512 {
                value 512;
                description "None";
            }
            enum 1024 {
                value 1024;
                description "None";
            }
            enum 2048 {
                value 2048;
                description "None";
            }
        }
        description "";
        reference "";
    }

    typedef  CML_RT_T {
        type bits {
            bit import {
                position 0;
                description "import";
            }
            bit export {
                position 1;
                description "export";
            }
        }
        description "";
        reference "";
    }

    typedef  CML_RSVP_ADDR_T {
        type enumeration {
            enum p2mp {
                value 1;
                description "IPV4 address family trunk";
            }
        }
        description "";
        reference "";
    }

    typedef  CML_HOSTP_TACACS_T {
        type enumeration {
            enum tacacs+ {
                value 1;
                description "Command to enable/disable features";
            }
        }
        description "";
        reference "";
    }

    typedef  CML_HOSTP_KEY_TYPE_T {
        type enumeration {
            enum 0 {
                value 0;
                description "To specify shared key in clear-text form";
            }
            enum 7 {
                value 1;
                description "To specify shared key in encrypted form";
            }
        }
        description "";
        reference "";
    }

    typedef  CML_HOSTP_LOCAL_TYPE_T {
        type enumeration {
            enum local {
                value 1;
                description "Group list can be followed by local";
            }
        }
        description "";
        reference "";
    }

    typedef  CML_HOSTP_LOCAL_NONE_TYPE_T {
        type enumeration {
            enum local {
                value 0;
                description "Group list can be followed by local";
            }
            enum none {
                value 1;
                description "Group list can be followed by none";
            }
        }
        description "";
        reference "";
    }

    typedef  CML_HOSTP_NONE_TYPE_T {
        type enumeration {
            enum none {
                value 1;
                description "Group list can be followed by none";
            }
        }
        description "";
        reference "";
    }

    typedef  CML_SNMP_OID_TREE_T {
        type enumeration {
            enum included {
                value 1;
                description "Specify to include";
            }
            enum excluded {
                value 2;
                description "Specify to exclude";
            }
        }
        description "";
        reference "";
    }

    typedef  CML_SNMP_LINK_TYPE_T {
        type enumeration {
            enum linkUp {
                value 1;
                description "IETF Link state up notification";
            }
            enum linkDown {
                value 2;
                description "IETF Link state down notification";
            }
        }
        description "";
        reference "";
    }

    typedef  CML_SNMP_USER_T {
        type enumeration {
            enum network-operator {
                value 1;
                description "System configured role for read-only";
            }
            enum network-admin {
                value 2;
                description "System configured role for read-write";
            }
        }
        description "";
        reference "";
    }

    typedef  CML_SNMP_GROUP_T {
        type enumeration {
            enum network-operator {
                value 1;
                description "System configured group for read-only(default)";
            }
            enum network-admin {
                value 2;
                description "System configured group for read-write";
            }
        }
        description "";
        reference "";
    }

    typedef  CML_REMOTEID_ENUM_T {
        type enumeration {
            enum hostname {
                value 0;
                description "Use hostname as remote-id";
            }
        }
        description "";
        reference "";
    }

    typedef  CML_REMOTEID_T {
        type union {
            type CML_REMOTEID_ENUM_T {

            }
            type CML_STRING_T {

            }
        }
        description "";
        reference "";
    }

    typedef  CML_OSPF6_METRIC_TYPE_T {
        type enumeration {
            enum 1 {
                value 1;
                description "Set OSPF External Type 1 metrics";
            }
            enum 2 {
                value 2;
                description "Set OSPF External Type 2 metrics";
            }
        }
        description "";
        reference "";
    }

    typedef  CML_UDLD_MODE_TYPE_T {
        type enumeration {
            enum normal {
                value 0;
                description "UDLD Normal Mode";
            }
            enum aggressive {
                value 1;
                description "UDLD Aggressive";
            }
        }
        description "";
        reference "";
    }

    typedef  CML_UDLD_STATE_TYPE_T {
        type enumeration {
            enum enable {
                value 0;
                description "Enable UDLD on an interface";
            }
            enum disable {
                value 1;
                description "Disable UDLD on an interface";
            }
        }
        description "";
        reference "";
    }

    typedef  CML_UDLD_T {
        type enumeration {
            enum disable {
                value 0;
                description "Disable UDLD";
            }
            enum enable {
                value 1;
                description "Enable UDLD";
            }
        }
        description "";
        reference "";
    }

    typedef  CML_SNMP_AUTH_T {
        type enumeration {
            enum md5 {
                value 1;
                description "Specify md5 authentication";
            }
            enum sha {
                value 2;
                description "Specify sha authentication";
            }
        }
        description "";
        reference "";
    }

    typedef  CML_SNMP_PRIV_T {
        type enumeration {
            enum des {
                value 1;
                description "Specify des privilege";
            }
            enum aes {
                value 2;
                description "Specify aes privilege";
            }
        }
        description "";
        reference "";
    }

    typedef  CML_SNMP_VERSION_T {
        type enumeration {
            enum 1 {
                value 1;
                description "Use SNMPv1";
            }
            enum 2c {
                value 2;
                description "Use SNMPv2c";
            }
        }
        description "";
        reference "";
    }

    typedef  CML_SNMP_INFORMS_VERSION_T {
        type enumeration {
            enum 2c {
                value 2;
                description "Use SNMPv2c";
            }
        }
        description "";
        reference "";
    }

    typedef  CML_SNMP_VIEW_VERSION_T {
        type enumeration {
            enum v1 {
                value 1;
                description "Specify v1 for SNMPv1";
            }
            enum v2c {
                value 2;
                description "Specify v2c for SNMPv2c";
            }
        }
        description "";
        reference "";
    }

    typedef  CML_SNMP_INFORMS_T {
        type enumeration {
            enum informs {
                value 2;
                description "Send Inform messages to this host";
            }
        }
        description "";
        reference "";
    }

    typedef  CML_SNMP_TRAP_T {
        type enumeration {
            enum traps {
                value 1;
                description "Send Traps messages to this host";
            }
        }
        description "";
        reference "";
    }

    typedef  CML_VERSION3_T {
        type enumeration {
            enum noauth {
                value 1;
                description "Use the SNMPv3 noAuthNoPriv Security Level";
            }
            enum auth {
                value 2;
                description "Use the SNMPv3 authNoPriv Security Level";
            }
            enum priv {
                value 3;
                description "Use the SNMPv3 authPriv Security Level";
            }
        }
        description "";
        reference "";
    }

    typedef  CML_SNMP_ACCESS_T {
        type enumeration {
            enum ro {
                value 1;
                description "Read-only access with this community string";
            }
        }
        description "";
        reference "";
    }

    typedef  CML_BFD_GTSM_STATE_T {
        type enumeration {
            enum enable {
                value 1;
                description "Enable gtsm protection";
            }
            enum disable {
                value 2;
                description "Disable gtsm protection";
            }
        }
        description "";
        reference "";
    }

    typedef  CML_BFD_MULTIHOP_AUTH_TYPE_T {
        type enumeration {
            enum simple {
                value 1;
                description "Simple Password";
            }
            enum keyed-sha1 {
                value 4;
                description "Keyed Secure hashing algorithm";
            }
            enum meticulous-keyed-sha1 {
                value 5;
                description "Meticulous Keyed Secure hashing algorithm";
            }
        }
        description "";
        reference "";
    }

    typedef  CML_HW_BFD_MULTIHOP_AUTH_TYPE_T {
        type enumeration {
            enum simple {
                value 1;
                description "Simple Password";
            }
            enum keyed-sha1 {
                value 4;
                description "Keyed Secure hashing algorithm";
            }
            enum meticulous-keyed-sha1 {
                value 5;
                description "Meticulous Keyed Secure hashing algorithm";
            }
        }
        description "";
        reference "";
    }

    typedef  CML_BFD_SESSION_STATE_T {
        type enumeration {
            enum disable {
                value 0;
                description "Disable all the bfd sessions on this interface";
            }
            enum enable {
                value 1;
                description "Enable all the bfd sessions on this interface";
            }
        }
        description "";
        reference "";
    }

    typedef  CML_OAMBFD_SESSION_FLAGS_T {
        type bits {
            bit rem-heard-up {
                position 0;
                description "BFD_SESSION_FLAG_REM_HEARD";
            }
            bit admin-down {
                position 1;
                description "BFD_SESSION_FLAG_ADMIN_DOWN";
            }
            bit Fate-Shared {
                position 2;
                description "BFD_SESSION_FLAG_FATE_SHARE";
            }
            bit remote-admin-down {
                position 3;
                description "BFD_SESSION_FLAG_REM_ADMIN_DOWN";
            }
            bit Echo-Enabled {
                position 4;
                description "BFD_SESSION_FLAG_ECHO_ENABLED";
            }
            bit Demand-Enabled {
                position 5;
                description "BFD_SESSION_FLAG_DEMAND";
            }
            bit Remote-Demand-Enabled {
                position 6;
                description "BFD_SESSION_FLAG_REM_DEMAND";
            }
            bit Poll-seq-Init {
                position 8;
                description "BFD_SESSION_FLAG_POLL_INIT";
            }
        }
        description "";
        reference "";
    }

    typedef  CML_OAMBFD_PERFORM_DIAG_T {
        type enumeration {
            enum Diagnostics--None {
                value 0;
                description "bfd_diag_no_diag";
            }
            enum Diagnostics-Control-Detected-Expiry {
                value 1;
                description "bfd_diag_ctrl_detect_exp";
            }
            enum Diagnostics-Echo-Failed {
                value 2;
                description "bfd_diag_echo_failed";
            }
            enum Diagnostics-Neighbor-Session-Down {
                value 3;
                description "bfd_diag_nbr_session_down";
            }
            enum Diagnostics-Forwarding-Plane-Reset {
                value 4;
                description "bfd_diag_fwd_reset";
            }
            enum Diagnostics-Path-Down {
                value 5;
                description "bfd_diag_path_down";
            }
            enum Diagnostics-Concatenated-Path-Down {
                value 6;
                description "bfd_diag_concat_path_down";
            }
            enum Diagnostics-Admin-Down {
                value 7;
                description "bfd_diag_admin_down";
            }
            enum Diagnostics-Reverse-Concatenated-Path-Down {
                value 8;
                description "bfd_diag_rev_concat_path_down";
            }
            enum Diagnostics-Configuration-Error {
                value 9;
                description "bfd_diag_config_error";
            }
            enum Diagnostics--Not-forwarding {
                value 10;
                description "bfd_diag_not_forwarding";
            }
        }
        description "";
        reference "";
    }

    typedef  CML_OAMBFD_SESSION_STATE_T {
        type enumeration {
            enum Admin-Down {
                value 0;
                description "BFD_SESSION_STATE_ADMIN_DOWN";
            }
            enum Down {
                value 1;
                description "BFD_SESSION_STATE_DOWN";
            }
            enum Init {
                value 2;
                description "BFD_SESSION_STATE_INIT";
            }
            enum Up {
                value 3;
                description "BFD_SESSION_STATE_UP";
            }
        }
        description "";
        reference "";
    }

    typedef  CML_OAMBFD_IMAGE_TYPE_T {
        type enumeration {
            enum MONOLITHIC {
                value 1;
                description "BFD_IMAGE_MONOLITHIC";
            }
            enum DISTRIBUTED {
                value 2;
                description "BFD_IMAGE_DIST_MAIN";
            }
            enum DISTRIBUTE {
                value 3;
                description "BFD_IMAGE_DIST_LINE";
            }
        }
        description "";
        reference "";
    }

    typedef  CML_OAMBFD_ADMIN_STATE_T {
        type enumeration {
            enum Up {
                value 1;
                description "BFD_ADMINSTATE_ENABLED";
            }
            enum Down {
                value 2;
                description "BFD_ADMINSTATE_DISABLED";
            }
        }
        description "";
        reference "";
    }

    typedef  CML_OAMBFD_SESSION_TYPE_T {
        type enumeration {
            enum Single-Hop {
                value 1;
                description "BFD_SESSION_TYPE_SINGLE_HOP";
            }
            enum Multihop-Arbit-Path {
                value 2;
                description "BFD_SESSION_TYPE_ARBIT_MHOP";
            }
            enum Multihop-OOB-Signalled {
                value 3;
                description "BFD_SESSION_TYPE_OOB_MHOP";
            }
            enum Multihop-Unidirectional {
                value 4;
                description "BFD_SESSION_TYPE_UDLR_MHOP";
            }
        }
        description "";
        reference "";
    }

    typedef  CML_OAMBFD_SESS_LOWER_LAYER_T {
        type enumeration {
            enum UNKNOWN {
                value 0;
                description "";
            }
            enum IPv4 {
                value 1;
                description "";
            }
            enum IPv6 {
                value 2;
                description "";
            }
            enum MPLS-LSP {
                value 3;
                description "";
            }
            enum MPLS-VCCV {
                value 4;
                description "";
            }
            enum MPLS-TP {
                value 5;
                description "";
            }
        }
        description "";
        reference "";
    }

    typedef  CML_OAMBFD_HW_MULTIHOP_VAL_T {
        type enumeration {
            enum multi-hop {
                value 4784;
                description "Enable multihop session";
            }
            enum micro-bfd {
                value 6784;
                description "Enable micro-bfd session";
            }
        }
        description "";
        reference "";
    }

    typedef  CML_VRRP_VMAC_T {
        type enumeration {
            enum enable {
                value 1;
                description "Enabled";
            }
            enum disable {
                value 2;
                description "Disabled";
            }
        }
        description "";
        reference "";
    }

    typedef  CML_VRRP_ACCEPT_MODE_T {
        type enumeration {
            enum true {
                value 1;
                description "Accept mode enabled";
            }
            enum false {
                value 2;
                description "Accept mode disabled";
            }
        }
        description "";
        reference "";
    }

    typedef  CML_VRRP_PREEMPT_MODE_T {
        type enumeration {
            enum true {
                value 1;
                description "Preemption enabled";
            }
            enum false {
                value 2;
                description "Preemption disabled";
            }
        }
        description "";
        reference "";
    }

    typedef  CML_LLDP_ADMIN_STATUS_T {
        type enumeration {
            enum rxonly {
                value 2;
                description "default";
            }
            enum txonly {
                value 4;
                description "Group list can be followed by 'local'";
            }
            enum txrx {
                value 8;
                description "default";
            }
        }
        description "";
        reference "";
    }

    typedef  CML_LLDP_MEDDEV_T {
        type enumeration {
            enum ep-class1 {
                value 1;
                description "ep-class1";
            }
            enum ep-class2 {
                value 2;
                description "ep-class2";
            }
            enum ep-class3 {
                value 3;
                description "ep-class3";
            }
            enum net-connect {
                value 4;
                description "net-connect";
            }
        }
        description "";
        reference "";
    }

    typedef  CML_LLDP_CHASSIS_ID_T {
        type enumeration {
            enum chassis-component {
                value 0;
                description "default";
            }
            enum if-alias {
                value 1;
                description "default";
            }
            enum port-component {
                value 2;
                description "Group list can be followed by 'local'";
            }
            enum mac-address {
                value 3;
                description "Group list can be followed by 'local'";
            }
            enum ip-address {
                value 4;
                description "Group list can be followed by 'local'";
            }
            enum if-name {
                value 5;
                description "Group list can be followed by 'local'";
            }
            enum local {
                value 6;
                description "Group list can be followed by 'local'";
            }
        }
        description "";
        reference "";
    }

    typedef  CML_LLDP_PORT_ID_T {
        type enumeration {
            enum if-alias {
                value 0;
                description "default";
            }
            enum port-component {
                value 1;
                description "Group list can be followed by 'local'";
            }
            enum mac-address {
                value 2;
                description "Group list can be followed by 'local'";
            }
            enum ip-address {
                value 3;
                description "Group list can be followed by 'local'";
            }
            enum if-name {
                value 4;
                description "Group list can be followed by 'local'";
            }
            enum agent-circuit-id {
                value 5;
                description "Group list can be followed by 'local'";
            }
            enum local {
                value 6;
                description "Group list can be followed by 'local'";
            }
        }
        description "";
        reference "";
    }

    typedef  CML_LLDP_PORT_ADDR_T {
        type enumeration {
            enum mac-address {
                value 1;
                description "default";
            }
            enum ip-address {
                value 2;
                description "Group list can be followed by 'local'";
            }
        }
        description "";
        reference "";
    }

    typedef  CML_LLDP_SET_STATE_T {
        type enumeration {
            enum disable {
                value 0;
                description "Disable";
            }
            enum enable {
                value 1;
                description "Enable";
            }
        }
        description "";
        reference "";
    }

    typedef  CML_LLDP_TLV_MODE_T {
        type enumeration {
            enum manual {
                value 1;
                description "Disable";
            }
            enum auto {
                value 2;
                description "Enable";
            }
        }
        description "";
        reference "";
    }

    typedef  CML_LLDP_IEEE_8023_T {
        type bits {
            bit mac-phy {
                position 0;
                description "mac-phy TLV";
            }
            bit max-mtu-size {
                position 1;
                description "max-mtu-size TLV";
            }
        }
        description "";
        reference "";
    }

    typedef  CML_LLDP_IEEE_8021_T {
        type bits {
            bit port-vlanid {
                position 0;
                description "port-vlanid TLV";
            }
            bit port-ptcl-vlanid {
                position 1;
                description "port-ptcl-vlanid TLV";
            }
            bit vlan-name {
                position 2;
                description "vlan-name TLV";
            }
            bit ptcl-identity {
                position 3;
                description "ptcl-identity TLV";
            }
            bit vid-digest {
                position 4;
                description "vid-digest TLV";
            }
            bit mgmt-vid {
                position 5;
                description "mgmt-vid TLV";
            }
            bit link-agg {
                position 6;
                description "link-agg TLV";
            }
            bit data-center-bridging {
                position 7;
                description "data-center-bridging TLV";
            }
        }
        description "";
        reference "";
    }

    typedef  CML_LLDP_BASIC_T {
        type bits {
            bit port-description {
                position 0;
                description "port-description TLV";
            }
            bit system-name {
                position 1;
                description "system-name TLV";
            }
            bit system-description {
                position 2;
                description "system-description TLV";
            }
            bit system-capabilities {
                position 3;
                description "system-capabilities TLV";
            }
            bit management-address {
                position 4;
                description "management-address TLV";
            }
        }
        description "";
        reference "";
    }

    typedef  CML_LLDP_AGENT_T {
        type enumeration {
            enum non-tpmr-bridge {
                value 0;
                description "Non-TPMR-bridge";
            }
            enum customer-bridge {
                value 1;
                description "Customer-bridge";
            }
            enum default {
                value 2;
                description "default-bridge";
            }
        }
        description "";
        reference "";
    }

    typedef  CML_VXLAN_MODE_T {
        type enumeration {
            enum vxlan {
                value 1;
                description "vxlan mode or nvrge mode ";
            }
        }
        description "";
        reference "";
    }

    typedef  CML_LLDP_MED_T {
        type enumeration {
            enum network-policy {
                value 0;
                description "network-policy";
            }
            enum location {
                value 1;
                description "location";
            }
            enum inventory {
                value 3;
                description "inventory";
            }
            enum media-capabilities {
                value 4;
                description "extended-power-via-mdi";
            }
        }
        description "";
        reference "";
    }

    typedef  CML_LLDP_ENABLE_T {
        type enumeration {
            enum rxonly {
                value 2;
                description "LLDP Recieve Only Mode";
            }
            enum txonly {
                value 4;
                description "LLDP Transmit Only Mode";
            }
            enum txrx {
                value 8;
                description "LLDP Transmit and Recieve Mode";
            }
        }
        description "";
        reference "";
    }

    typedef  CML_LLDP_MGMT_ADDR_T {
        type enumeration {
            enum mac-address {
                value 1;
                description "Use the MAC address as the Management Address";
            }
            enum ip-address {
                value 2;
                description "Use the ip address as the Management Address";
            }
        }
        description "";
        reference "";
    }

    typedef  CML_LLDP_CHASSIS_T {
        type enumeration {
            enum if-alias {
                value 0;
                description "Use the Interface Alias as the chassis-id";
            }
            enum ip-address {
                value 1;
                description "Use the ip-address as the chassis-id";
            }
            enum mac-address {
                value 2;
                description "Use the mac-address as the chassis-id";
            }
            enum if-name {
                value 3;
                description "Use the if-name as the chassis-id";
            }
            enum locally-assigned {
                value 4;
                description "Use the locally-assigned as the chassis-id";
            }
        }
        description "";
        reference "";
    }

    typedef  CML_LLDP_PORT_T {
        type enumeration {
            enum if-alias {
                value 1;
                description "Use the Interface Alias as the port-id-TLV";
            }
            enum mac-address {
                value 2;
                description "Use the mac-address as the port-id-TLV";
            }
            enum ip-address {
                value 3;
                description "Use the ip-address as the port-id-TLV";
            }
            enum if-name {
                value 4;
                description "Use the if-name as the port-id-TLV";
            }
            enum agt-circuit-id {
                value 5;
                description "Use the agt-circuit-id as the port-id-TLV";
            }
            enum locally-assigned {
                value 6;
                description "Use the locally-assigned as the port-id-TLV";
            }
        }
        description "";
        reference "";
    }

    typedef  CML_LACP_TIMEOUT_T {
        type enumeration {
            enum long {
                value 0;
                description "Set LACP long timeout";
            }
            enum short {
                value 1;
                description "Set LACP short timeout";
            }
        }
        description "";
        reference "";
    }

    typedef  CML_LACP_MODE_T {
        type enumeration {
            enum passive {
                value 0;
                description "Disable initiation of LACP negotiation on a port";
            }
            enum active {
                value 1;
                description "Enable initiation of LACP negotiation on a port";
            }
        }
        description "";
        reference "";
    }

    typedef  CML_LACP_PSC_T {
        type enumeration {
            enum dst-mac {
                value 1;
                description "Destination Mac address based load balancing";
            }
            enum src-mac {
                value 2;
                description "Source Mac address based load balancing";
            }
            enum src-dst-mac {
                value 3;
                description "Source and Destination Mac address based load balancing";
            }
            enum src-ip {
                value 4;
                description "Source IP address based load balancing";
            }
            enum dst-ip {
                value 5;
                description "Destination IP address based load balancing";
            }
            enum src-dst-ip {
                value 6;
                description "Source and Destination IP address based load balancing";
            }
            enum src-port {
                value 7;
                description "Source TCP/UDP port based load balancing";
            }
            enum dst-port {
                value 8;
                description "Destination TCP/UDP port based load balancing";
            }
            enum src-dst-port {
                value 9;
                description "Source and Destination TCP/UDP port based load balancing";
            }
        }
        description "";
        reference "";
    }

    typedef  CML_SSH_KEY_RSA_DSA_T {
        type enumeration {
            enum dsa {
                value 1;
                description "DSA keys";
            }
            enum rsa {
                value 2;
                description "RSA keys";
            }
        }
        description "";
        reference "";
    }

    typedef  CML_NSM_MPLS_LOG_T {
        type bits {
            bit error {
                position 0;
                description "Log Error message in MPLS Forwarder";
            }
            bit warning {
                position 1;
                description "Log Warning message in MPLS Forwarder";
            }
            bit debug {
                position 2;
                description "Log Debug messages in MPLS Forwarder";
            }
            bit notice {
                position 3;
                description "Log Notice messages in MPLS Forwarder";
            }
        }
        description "";
        reference "";
    }

    typedef  CML_LDP_ENABLE_TYPE_T {
        type enumeration {
            enum ipv4 {
                value 1;
                description "Enable/Disable LDP for IPV4";
            }
            enum ipv6 {
                value 2;
                description "Enable/Disable LDP for IPV6";
            }
            enum both {
                value 3;
                description "Enable/Disable LDP for both IPV4 and IPV6";
            }
        }
        description "";
        reference "";
    }

    typedef  CML_NSM_CONTAINER_ETHERNET_TYPE_T {
        type enumeration {
            enum ethernet {
                value 0;
                description "VC type Ethernet - needed when one vc is not signaled";
            }
        }
        description "";
        reference "";
    }

    typedef  CML_INTERFACE_ADMIN_STATE_T {
        type enumeration {
            enum up {
                value 0;
                description "Admin State UP";
            }
            enum down {
                value 1;
                description "Admin State DOWN";
            }
            enum administratively-down {
                value 2;
                description "Admin State ADMINISTRATIVELY DOWN";
            }
        }
        description "";
        reference "";
    }

    typedef  CML_NSM_TUNNEL_DIRECTION_TYPE_T {
        type enumeration {
            enum forward {
                value 0;
                description "Tunnel Direction - Forward tunnel identifier - Default Value";
            }
            enum reverse {
                value 1;
                description "Tunnel Direction - Reverse tunnel identifier";
            }
        }
        description "";
        reference "";
    }

    typedef  CML_LACP_BRIDGETYPE_T {
        type enumeration {
            enum customer-bridge-group-address {
                value 0;
                description "customer bridge group address";
            }
            enum multicast-group-address {
                value 1;
                description "multicast group address";
            }
            enum non-tmpr-group-address {
                value 2;
                description "non TPMR group address";
            }
        }
        description "";
        reference "";
    }

    typedef  CML_LACP_DISCARD_CONV_T {
        type enumeration {
            enum disable {
                value 0;
                description "disable";
            }
            enum enable {
                value 1;
                description "enable";
            }
        }
        description "";
        reference "";
    }

    typedef  CML_VXLAN_INGRESS_T {
        type enumeration {
            enum ingress-replication {
                value 1;
                description "Head End Replication";
            }
        }
        description "";
        reference "";
    }

    typedef  CML_FOG_IFCTYPE_T {
        type enumeration {
            enum mpg {
                value 1;
                description "Monitor Port Group";
            }
            enum cpg {
                value 2;
                description "Control Port Group";
            }
        }
        description "";
        reference "";
    }

    typedef  CML_FOG_LINK_TYPE_T {
        type enumeration {
            enum uplink {
                value 1;
                description "Configure Port as Uplink";
            }
            enum downlink {
                value 2;
                description "Configure Port as Downlink";
            }
        }
        description "";
        reference "";
    }

    typedef  CML_VXLAN_INNER_VID_T {
        type enumeration {
            enum inner-vid-disabled {
                value 1;
                description "Vid not to be carried out of network port";
            }
        }
        description "";
        reference "";
    }

    typedef  CML_MROUTE_ROUTETYPE_T {
        type enumeration {
            enum default {
                value 0;
                description "Default route type";
            }
            enum static {
                value 3;
                description "Static routes";
            }
            enum rip {
                value 4;
                description "Routing Information Protocol (RIP)";
            }
            enum ospf {
                value 6;
                description "Open Shortest Patch First (OSPF)";
            }
            enum bgp {
                value 8;
                description "Border Gateway Protocol (BGP)";
            }
            enum isis {
                value 9;
                description "ISO IS-IS";
            }
        }
        description "";
        reference "";
    }

    typedef  CML_MROUTE_IPV6_ROUTETYPE_T {
        type enumeration {
            enum default {
                value 0;
                description "Default route type";
            }
            enum static {
                value 3;
                description "Static routes";
            }
            enum rip {
                value 5;
                description "Routing Information Protocol (RIP)";
            }
            enum ospf {
                value 7;
                description "Open Shortest Patch First (OSPF)";
            }
            enum bgp {
                value 8;
                description "Border Gateway Protocol (BGP)";
            }
            enum isis {
                value 9;
                description "ISO IS-IS";
            }
        }
        description "";
        reference "";
    }

    typedef  CML_MROUTE_IFNAME_T {

        type string{
        length 0..20;
        }
        description "";
        reference "";
    }

    typedef  CML_MROUTE_GW_ADDR_T {
        type union {
            type CML_IPV6_ADDR_T {

            }
            type CML_MROUTE_IFNAME_T {

            }
        }
        description "";
        reference "";
    }

    typedef  CML_FIB_RETAIN_T {
        type union {
            type CML_FIB_RETAIN_TIME_T {

            }
            type CML_FIB_RETAIN_FOREVER_T {

            }
        }
        description "";
        reference "";
    }

    typedef  CML_FIB_RETAIN_FOREVER_T {
        type enumeration {
            enum forever {
                value 0;
                description "Retain FIB forever";
            }
        }
        description "";
        reference "";
    }

    typedef  CML_FIB_RETAIN_TIME_T {

        type uint32{
         range 0..4294967295;
        }
        description "";
        reference "";
    }

    typedef  CML_RIB_DEBUG_TYPE_T {
        type bits {
            bit events {
                position 1;
                description "RIB events";
            }
            bit packet {
                position 2;
                description "RIB packets";
            }
            bit packet-send {
                position 3;
                description "RIB packets,RIB send packets";
            }
            bit packet-recv {
                position 4;
                description "RIB packets,RIB receive packets";
            }
            bit packet-detail {
                position 5;
                description "RIB packets,Detailed information display";
            }
            bit packet-send-detail {
                position 6;
                description "RIB packets,RIB send packets,Detailed information display";
            }
            bit packet-recv-detail {
                position 7;
                description "RIB packets,RIB receive packets,Detailed information display";
            }
            bit kernel {
                position 8;
                description "RIB kernel";
            }
            bit ha {
                position 9;
                description "RIB High Availability";
            }
            bit ha-all {
                position 10;
                description "RIB High Availability,All RIB High Availability events";
            }
            bit nsm {
                position 11;
                description "NSM messages";
            }
            bit bfd {
                position 12;
                description "BFD messages";
            }
            bit monitor {
                position 13;
                description "Enable Monitor route netlink";
            }
            bit hal-events {
                position 18;
                description "Hardware Abstraction Layer,RIB events";
            }
            bit hal-ipc {
                position 19;
                description "Hardware Abstraction Layer,Async Debugging";
            }
        }
        description "";
        reference "";
    }

    typedef  CML_RIB_BFD_STATE {
        type enumeration {
            enum enable {
                value 0;
                description "enable BFD";
            }
            enum disable {
                value 1;
                description "disable BFD";
            }
        }
        description "";
        reference "";
    }

    typedef  CML_RIB_DEBUG_ROUTING_TYPE_T {
        type bits {
            bit routing {
                position 20;
                description "Enable debugging for routing events";
            }
            bit routing-add-route {
                position 21;
                description "Enable debugging for routing events,Add route events";
            }
            bit routing-delete-route {
                position 22;
                description "Enable debugging for routing events, Delete route events";
            }
            bit routing-mod-route {
                position 23;
                description "Enable debugging for routing events, Modify route events";
            }
        }
        description "";
        reference "";
    }

    typedef  CML_RIB_PACKET_DEBUG_TYPE_T {
        type enumeration {
            enum recv {
                value 1;
                description "RIB receive packets";
            }
            enum send {
                value 2;
                description "RIB send packets";
            }
        }
        description "";
        reference "";
    }

    typedef  CML_VRRP_INIT_MSG_CODE_T {
        type enumeration {
            enum admin-down {
                value 0;
                description "(admin state down)";
            }
            enum if-not-running {
                value 1;
                description "(interface is not running)";
            }
            enum circuit-down {
                value 2;
                description "(monitored circuit is down)";
            }
            enum no-subnet {
                value 3;
                description "(no matching subnet)";
            }
            enum vip-unset {
                value 4;
                description "(virtual IP address not set)";
            }
            enum switch-back-delay {
                value 5;
                description "(In Switch Back Delay)";
            }
        }
        description "";
        reference "";
    }

    typedef  CML_VRRP_DEBUG_T {
        type bits {
            bit events {
                position 1;
                description "VRRP events";
            }
            bit packet-send {
                position 2;
                description "VRRP packets,VRRP send packets";
            }
            bit packet-recv {
                position 3;
                description "VRRP packets,VRRP receive packets";
            }
        }
        description "";
        reference "";
    }

    typedef  CML_VRRP_STATE_T {
        type enumeration {
            enum init {
                value 1;
                description "VRRP_STATE_INIT";
            }
            enum backup {
                value 2;
                description "VRRP_STATE_BACKUP";
            }
            enum master {
                value 3;
                description "VRRP_STATE_MASTER";
            }
        }
        description "";
        reference "";
    }

    typedef  CML_VRRP_MEMEBER_STATE {
        type enumeration {
            enum joined {
                value 1;
                description "VRRP_IPV4_MCAST_JOINED";
            }
            enum left {
                value 2;
                description "VRRP_IPV4_MCAST_LEFT";
            }
        }
        description "";
        reference "";
    }

    typedef  CML_MCEC_HELLO_T {
        type enumeration {
            enum long {
                value 0;
                description "Long Timeout";
            }
            enum short {
                value 1;
                description "Short Timeout";
            }
        }
        description "";
        reference "";
    }

    typedef  MCEC_DEBUG_T {
        type bits {
            bit hello {
                position 0;
                description "Hello";
            }
            bit info {
                position 1;
                description "Info";
            }
            bit timer {
                position 2;
                description "Timer";
            }
            bit event {
                position 3;
                description "Event";
            }
            bit cli {
                position 4;
                description "CLI";
            }
            bit mac-sync {
                position 5;
                description "MAC Sync";
            }
            bit stp {
                position 6;
                description "STP";
            }
        }
        description "";
        reference "";
    }

    typedef  CML_OSPF_AREA_ID_T {
        type union {
            type CML_STRING_T {

            }
            type uint16 {
                range "1..65535";

            }
        }
        description "";
        reference "";
    }

    typedef  CML_COMMON_DEBUG_TYPE_T {
        type bits {
            bit decode {
                position 0;
                description "decode";
            }
            bit encode {
                position 1;
                description "encode";
            }
            bit events {
                position 2;
                description "events";
            }
            bit fsm {
                position 3;
                description "FSM";
            }
            bit tib {
                position 4;
                description "Tree-Info-Base (TIB)";
            }
        }
        description "";
        reference "";
    }

    typedef  CML_UNKNOWN_MCAST_T {
        type enumeration {
            enum flood {
                value 0;
                description "flood mode";
            }
            enum discard {
                value 1;
                description "Discard mode";
            }
        }
        description "";
        reference "";
    }

    typedef  CML_OSPF6_DEBUG_PACKET_TYPE_T {
        type bits {
            bit hello {
                position 1;
                description "OSPFv3 Hello ";
            }
            bit dd {
                position 2;
                description "OSPFv3 Database Description";
            }
            bit ls-request {
                position 3;
                description "OSPFv3 Link State Request ";
            }
            bit ls-update {
                position 4;
                description "OSPFv3 Link State Update ";
            }
            bit ls-ack {
                position 5;
                description "OSPFv3 Link State Acknowledgment";
            }
            bit send {
                position 6;
                description "Packet sent";
            }
            bit recv {
                position 7;
                description "packet received";
            }
            bit detail {
                position 8;
                description "Detail information";
            }
        }
        description "";
        reference "";
    }

    typedef  CML_OSPF6_DEBUG_IFSM_T {
        type bits {
            bit status {
                position 0;
                description "IFSM status Information";
            }
            bit events {
                position 1;
                description "IFSM events Information";
            }
            bit timers {
                position 2;
                description "IFSM Timer Information";
            }
        }
        description "";
        reference "";
    }

    typedef  CML_OSPF6_DEBUG_NFSM_T {
        type bits {
            bit status {
                position 0;
                description "NFSM status Information";
            }
            bit events {
                position 1;
                description "NFSM events Information";
            }
            bit timers {
                position 2;
                description "NFSM Timer Information";
            }
        }
        description "";
        reference "";
    }

    typedef  CML_OSPF6_DEBUG_LSA_T {
        type bits {
            bit generate {
                position 0;
                description "LSA Generation";
            }
            bit flooding {
                position 1;
                description "LSA Flooding";
            }
            bit install {
                position 2;
                description "LSA Installation";
            }
            bit refresh {
                position 3;
                description "LSA Refreshment";
            }
            bit maxage {
                position 4;
                description "LSA MaxAge processing";
            }
        }
        description "";
        reference "";
    }

    typedef  CML_OSPF6_DEBUG_NSM_T {
        type bits {
            bit interface {
                position 0;
                description "NSM interface ";
            }
            bit redistribute {
                position 1;
                description "NSM redistribute ";
            }
        }
        description "";
        reference "";
    }

    typedef  CML_OSPF6_DEBUG_RIB_T {
        type bits {
            bit interface {
                position 0;
                description "OSPF NSM information, NSM interface ";
            }
            bit redistribute {
                position 1;
                description "OSPF NSM information, NSM redistribute ";
            }
        }
        description "";
        reference "";
    }

    typedef  CML_OSPF6_DEBUG_ROUTE_T {
        type bits {
            bit spf {
                position 0;
                description "OSPF route information,SPF calculation information";
            }
            bit ia {
                position 1;
                description "OSPF route information, Inter-Area route calculation information";
            }
            bit ase {
                position 2;
                description "OSPF route information,External route calculation information";
            }
            bit install {
                position 3;
                description "OSPF route information, Route installation information";
            }
        }
        description "";
        reference "";
    }

    typedef  CML_OSPF6_DEBUG_EVENT_T {
        type bits {
            bit abr {
                position 0;
                description "OSPF events information, OSPF ABR events";
            }
            bit asbr {
                position 1;
                description "OSPF events information,OSPF ASBR events ";
            }
            bit vlink {
                position 2;
                description "OSPF events information,OSPF Virtual-Link events";
            }
            bit os {
                position 3;
                description "OSPF events information, OSPF OS interaction events ";
            }
            bit router {
                position 4;
                description "OSPF events information,Other router events ";
            }
            bit nssa {
                position 5;
                description "OSPF events information, OSPF NSSA events ";
            }
        }
        description "";
        reference "";
    }

    typedef  CML_MODULE_NAME_T {
        type enumeration {
            enum auth {
                value 1;
                description "Set logging level for auth messages";
            }
            enum bgp {
                value 2;
                description "Set logging level for bgp messages";
            }
            enum cmm {
                value 3;
                description "Set logging level for cmm messages";
            }
            enum hostp {
                value 5;
                description "Set logging level for hostp messages";
            }
            enum hsl {
                value 6;
                description "Set logging level for hsl messages";
            }
            enum isis {
                value 7;
                description "Set logging level for isis messages";
            }
            enum lag {
                value 9;
                description "Set logging level for lagd messages";
            }
            enum l2mrib {
                value 10;
                description "Set logging level for l2mrib messages";
            }
            enum mstp {
                value 11;
                description "Set logging level for mstp messages";
            }
            enum mrib {
                value 12;
                description "Set logging level for mrib messages";
            }
            enum nsm {
                value 13;
                description "Set logging level for nsm messages";
            }
            enum onm {
                value 14;
                description "Set logging level for onm messages";
            }
            enum oam {
                value 15;
                description "Set logging level for oam messages";
            }
            enum ospf {
                value 16;
                description "Set logging level for ospf messages";
            }
            enum ospf6 {
                value 17;
                description "Set logging level for ospf6 messages";
            }
            enum rip {
                value 19;
                description "Set logging level for rip messages";
            }
            enum pim {
                value 21;
                description "Set logging level for pim messages";
            }
            enum rib {
                value 22;
                description "Set logging level for rib messages";
            }
            enum vrrp {
                value 23;
                description "Set logging level for vrrp messages";
            }
            enum sflow {
                value 24;
                description "Set logging level for sflow messages";
            }
            enum pserv {
                value 27;
                description "Set logging level for pservd messages";
            }
            enum cml {
                value 28;
                description "Set logging level for cml messages";
            }
            enum ndd {
                value 29;
                description "Set logging level for ndd messages";
            }
            enum ripng {
                value 30;
                description "Set logging level for ripng messages";
            }
            enum vlog {
                value 31;
                description "Set logging level for vlog messages";
            }
        }
        description "";
        reference "";
    }

    typedef  CML_TIMESTAMP_UNITS_T {
        type enumeration {
            enum none {
                value 0;
                description "No timestamp in log messages";
            }
            enum microseconds {
                value 1;
                description "Timestamp in micro-seconds";
            }
            enum milliseconds {
                value 2;
                description "Timestamp in milli-seconds (Default)";
            }
            enum seconds {
                value 3;
                description "Timestamp in seconds";
            }
        }
        description "";
        reference "";
    }

    typedef  CML_LEVEL_T {
        type enumeration {
            enum debuglogging {
                value 0;
                description "Logging host";
            }
            enum emergencies {
                value 1;
                description "Logging emergency";
            }
            enum alerts {
                value 2;
                description "Logging alert";
            }
            enum critical {
                value 3;
                description "Logging critical";
            }
            enum errors {
                value 4;
                description "Logging Error";
            }
            enum warnings {
                value 5;
                description "Logging warning";
            }
            enum notifications {
                value 6;
                description "Logging notify";
            }
            enum informational {
                value 7;
                description "Logging Info";
            }
            enum debugging {
                value 8;
                description "Logging Debug";
            }
        }
        description "";
        reference "";
    }

    typedef  CML_CLEAR_NTP_STATISTICS_T {
        type enumeration {
            enum all-peers {
                value 0;
                description "Clear per-peer statistics counter of all peers";
            }
            enum io {
                value 1;
                description "Clear input-output statistics";
            }
            enum local {
                value 2;
                description "Clear counters maintained by the local NTP";
            }
            enum memory {
                value 3;
                description "Clear statistics counters related to memory code";
            }
        }
        description "";
        reference "";
    }

    typedef  CML_NTP_PREFER_T {
        type enumeration {
            enum prefer {
                value 1;
                description "preferred server";
            }
        }
        description "";
        reference "";
    }

    typedef  CML_NTP_FEATURE_T {
        type enumeration {
            enum ntp {
                value 1;
                description "Enable NTP";
            }
        }
        description "";
        reference "";
    }

    typedef  CML_RSYSLOG_FEATURE_T {
        type enumeration {
            enum rsyslog {
                value 1;
                description "Remote Logging feature";
            }
        }
        description "";
        reference "";
    }

    typedef  CML_SNMP_ENABLE_T {
        type enumeration {
            enum snmp {
                value 1;
                description "Enable SNMP feature";
            }
        }
        description "";
        reference "";
    }

    typedef  SFLOW_DEBUG_OPTIONS_T {
        type enumeration {
            enum agent {
                value 1;
                description "debug sflow agent";
            }
            enum sampling {
                value 2;
                description "debug sflow sampling";
            }
            enum polling {
                value 3;
                description "debug sflow polling";
            }
            enum all {
                value 4;
                description "debug all";
            }
        }
        description "";
        reference "";
    }

    typedef  SFLOW_DIRECTION_OPTION_T {
        type enumeration {
            enum ingress {
                value 1;
                description "Ingress";
            }
            enum egress {
                value 2;
                description "Egress";
            }
            enum both {
                value 3;
                description "Both";
            }
        }
        description "";
        reference "";
    }

    typedef  SFLOW_EGRESS_INGRESS_T {
        type enumeration {
            enum disabled {
                value 0;
                description "Disable Egress/Ingress";
            }
            enum enabled {
                value 1;
                description "Enable Egress/Ingress";
            }
        }
        description "";
        reference "";
    }

    typedef  USER_MGMT_ROLE_OPTIONS_T {
        type enumeration {
            enum network-admin {
                value 1;
                description "Enter the rolename - Network Administrat or - Have all permissions";
            }
            enum network-engineer {
                value 2;
                description "Enter the rolename - Network Engineer  - Can save configuration";
            }
            enum network-operator {
                value 3;
                description "Enter the rolename - Network Operator  - Can not save configuration";
            }
            enum network-user {
                value 4;
                description "Enter the rolename - Network User - Can n ot change configuration";
            }
        }
        description "";
        reference "";
    }

    typedef  CML_ACCEPT_LIFETIME_T {
        type enumeration {
            enum accept-lifetime {
                value 1;
                description "Set accept lifetime of the key";
            }
        }
        description "";
        reference "";
    }

    typedef  CML_ISIS_ADDRESS_IPV6_T {
        type enumeration {
            enum ipv6 {
                value 1;
                description "Address family";
            }
        }
        description "";
        reference "";
    }

    typedef  CML_SEND_LIFETIME_T {
        type enumeration {
            enum send-lifetime {
                value 1;
                description "Set send lifetime of the key";
            }
        }
        description "";
        reference "";
    }

    typedef  CML_PREFIX_LIST_TYPE {
        type enumeration {
            enum deny {
                value 1;
                description "Specify packets to reject";
            }
            enum permit {
                value 2;
                description "Specify packets to forward";
            }
        }
        description "";
        reference "";
    }

    typedef  CML_PREFIX_LIST_ANY_T {
        type enumeration {
            enum any {
                value 1;
                description "Any prefix match. Same as 0.0.0.0/0 le 32 ";
            }
        }
        description "";
        reference "";
    }

    typedef  CML_ISIS_METRIC_T {
        type enumeration {
            enum internal {
                value 0;
                description "Set IS-IS Internal metric type";
            }
            enum external {
                value 1;
                description "Set IS-IS External metric type";
            }
        }
        description "";
        reference "";
    }

    typedef  CML_OAM_BFD_FW_T {
        type enumeration {
            enum multi-hop {
                value 1;
                description "Enable multihop session";
            }
            enum micro-bfd {
                value 2;
                description "Enable micro-bfd session (DEFAULT)";
            }
        }
        description "";
        reference "";
    }

    typedef  CML_IS_TYPE3_T {
        type enumeration {
            enum level-1 {
                value 1;
                description "IS-IS level-1 routes only";
            }
            enum level-2 {
                value 2;
                description "IS-IS level-2 routes only";
            }
            enum level-1-2 {
                value 3;
                description "IS-IS level-1 and level-2 routes";
            }
        }
        description "";
        reference "";
    }

    typedef  CML_ISIS_SUMMARY_LEVEL_T {
        type enumeration {
            enum level-1 {
                value 1;
                description "Summarize into level-1 area";
            }
            enum level-2 {
                value 2;
                description "Summarize into level-2 sub-domain";
            }
            enum level-1-2 {
                value 3;
                description "Summarize into both area and sub-domain";
            }
        }
        description "";
        reference "";
    }

    typedef  CML_ISIS_LEVEL3_T {
        type enumeration {
            enum level-1 {
                value 1;
                description "Level-1 only";
            }
            enum level-2 {
                value 2;
                description "Level-2 only";
            }
            enum level-1-2 {
                value 3;
                description "Level-1-2";
            }
        }
        description "";
        reference "";
    }

    typedef  CML_ISIS_SYNC_TYPE_T {
        type enumeration {
            enum level-1 {
                value 1;
                description "Enable LDP ISIS synchronization for level-1 only";
            }
            enum level-2 {
                value 2;
                description "Enable LDP ISIS synchronization for level-2 only";
            }
            enum level-1-2 {
                value 3;
                description "Enable LDP ISIS synchronization for level-1 and level-2";
            }
        }
        description "";
        reference "";
    }

    typedef  CML_ISIS_CIRCUIT_TYPE_T {
        type enumeration {
            enum level-1 {
                value 1;
                description "Level-1 only adjacencies are formed";
            }
            enum level-2-only {
                value 2;
                description "Level-2 only adjacencies are formed";
            }
            enum level-1-2 {
                value 3;
                description "Level-1-2 adjacencies are formed";
            }
        }
        description "";
        reference "";
    }

    typedef  CML_ISIS_SUPPRESS_T {
        type enumeration {
            enum default {
                value 0;
                description "Only for set-overload bit value";
            }
            enum external {
                value 1;
                description "If overload-bit set do not advertise IP prefixes learned from other protocols";
            }
            enum interlevel {
                value 2;
                description "If overload-bit set do not advertise IP prefixes learned from another ISIS level";
            }
            enum external-interlevel {
                value 3;
                description "If overload-bit set donot advertise IP prefixes learned from other protocols,If overload-bit set do not advertise IP prefixes learned from another ISIS level";
            }
            enum interlevel-external {
                value 4;
                description "If overload-bit set donot advertise IP prefixes learned from another ISIS level,If overload-bit set donot advertise IP prefixes learned from other protocols";
            }
        }
        description "";
        reference "";
    }

    typedef  CML_WAITFORBGP_T {
        type enumeration {
            enum default {
                value 0;
                description "Only for set-overload bit value";
            }
            enum wait-for-bgp {
                value 1;
                description "Time in seconds to advertise ourself as overloaded after reboot";
            }
        }
        description "";
        reference "";
    }

    typedef  CML_QOS_ALL_T {
        type enumeration {
            enum all {
                value -1;
                description "Include all cos-queues";
            }
        }
        description "";
        reference "";
    }

    typedef  CML_QOS_DATA_T {
        type union {
            type CML_QOS_ALL_T {

            }
            type uint8 {
                range "0..7";

            }
        }
        description "";
        reference "";
    }

    typedef  CML_ISIS_ONSTARTUP_T {
        type union {
            type CML_WAITFORBGP_T {

            }
            type uint32 {
                range "5..86400";

            }
        }
        description "";
        reference "";
    }

    typedef  CML_MESH_BLOCKED_T {
        type enumeration {
            enum blocked {
                value 0;
                description "Block LSPs on this interface";
            }
        }
        description "";
        reference "";
    }

    typedef  CML_ISIS_MESH_TYPE_T {
        type union {
            type CML_MESH_BLOCKED_T {

            }
            type uint32 {
                range "1..4294967295";

            }
        }
        description "";
        reference "";
    }

    typedef  CML_ISIS_MINIMAL_T {
        type enumeration {
            enum minimal {
                value 0;
                description "Holdtime 1 second interval depends on multiplier";
            }
        }
        description "";
        reference "";
    }

    typedef  CML_ISIS_HELLO_INTERVAL_TYPE_T {
        type union {
            type CML_ISIS_MINIMAL_T {

            }
            type uint16 {
                range "1..65535";

            }
        }
        description "";
        reference "";
    }

    typedef  CML_OSPF_CAPABILITY_TE_T {
        type enumeration {
            enum te {
                value 1;
                description "OSPF Traffic Engineering extension";
            }
            enum traffic-engineering {
                value 2;
                description "OSPF Traffic Engineering extension";
            }
        }
        description "";
        reference "";
    }

    typedef  CML_OSPF_AREA_AUTHENTICATION_TYPE_T {
        type enumeration {
            enum authentication {
                value 1;
                description "Enable authentication";
            }
            enum authentication-message-digest {
                value 2;
                description "Enable authentication, Use message-digest authentication";
            }
        }
        description "";
        reference "";
    }

    typedef  CML_OSPF_VLINK_AUTH_TYPE_T {
        type enumeration {
            enum authentication-null {
                value 0;
                description "Enable authentication,Use no authentication";
            }
            enum authentication {
                value 1;
                description "Enable authentication";
            }
            enum authentication-message-digest {
                value 2;
                description "Enable authentication,Use message-digest authentication";
            }
        }
        description "";
        reference "";
    }

    typedef  CML_OSPF_VLINK_INTERFACE_STATE_T {
        type enumeration {
            enum DependUpon {
                value 0;
                description "IFSM DependUpon";
            }
            enum Down {
                value 1;
                description "IFSM Down";
            }
            enum Loopback {
                value 2;
                description "IFSM Loopback";
            }
            enum Waiting {
                value 3;
                description "IFSM Waiting";
            }
            enum Point-To-Point {
                value 4;
                description "IFSM Point-To-Point";
            }
            enum DROther {
                value 5;
                description "IFSM DROther";
            }
            enum Backup {
                value 6;
                description "IFSM Backup";
            }
            enum DR {
                value 7;
                description "IFSM DR";
            }
        }
        description "";
        reference "";
    }

    typedef  CML_OSPF_VLINK_ADJ_STATE_T {
        type enumeration {
            enum DependUpon {
                value 0;
                description "NFSM DependUpon";
            }
            enum Down {
                value 1;
                description "NFSM Down";
            }
            enum Attempt {
                value 2;
                description "NFSM Attempt";
            }
            enum Init {
                value 3;
                description "NFSM Init";
            }
            enum 2-Way {
                value 4;
                description "NFSM 2-Way";
            }
            enum ExStart {
                value 5;
                description "NFSM ExStart";
            }
            enum Exchange {
                value 6;
                description "NFSM Exchange";
            }
            enum Loading {
                value 7;
                description "NFSM Loading";
            }
            enum Full {
                value 8;
                description "NFSM Full";
            }
        }
        description "";
        reference "";
    }

    typedef  CML_OSPF_VLINK_STATUS_T {
        type enumeration {
            enum Down {
                value 0;
                description "Virtual Link Down";
            }
            enum Up {
                value 1;
                description "Virtual Link Up";
            }
        }
        description "";
        reference "";
    }

    typedef  CML_OSPF_AREA_RANGE_ADVERTISE_T {
        type enumeration {
            enum not-advertise {
                value 0;
                description "DoNotAdvertise this range";
            }
            enum advertise {
                value 1;
                description "Advertise this range (default)";
            }
        }
        description "";
        reference "";
    }

    typedef  CML_OSPF_BFD_STATE {
        type enumeration {
            enum enable {
                value 0;
                description "enable BFD";
            }
            enum disable {
                value 1;
                description "disable BFD";
            }
        }
        description "";
        reference "";
    }

    typedef  CML_OSPF_ALL_DEBUG_T {
        type enumeration {
            enum all {
                value 1;
                description "Enable all debugging";
            }
        }
        description "";
        reference "";
    }

    typedef  CML_OSPF_PACKET_TYPE_T {
        type bits {
            bit hello {
                position 0;
                description "OSPF Hello";
            }
            bit dd {
                position 1;
                description "OSPF Database Description";
            }
            bit ls-request {
                position 2;
                description "OSPF Link State Request";
            }
            bit ls-update {
                position 3;
                description "OSPF Link State Update";
            }
            bit ls-ack {
                position 4;
                description "OSPF Link State Acknowledgment";
            }
            bit send {
                position 5;
                description "Packet sent";
            }
            bit recv {
                position 6;
                description "packet received";
            }
            bit detail {
                position 7;
                description "Detail information";
            }
        }
        description "";
        reference "";
    }

    typedef  CML_OSPF_DEBUG_EVENT_TYPE_T {
        type bits {
            bit abr {
                position 0;
                description "OSPF ABR events";
            }
            bit nssa {
                position 1;
                description "OSPF NSSA events";
            }
            bit asbr {
                position 2;
                description "OSPF ASBR events";
            }
            bit vlink {
                position 3;
                description "OSPF Virtual-Link events";
            }
            bit lsa {
                position 4;
                description "OSPF LSA events";
            }
            bit os {
                position 5;
                description "OSPF OS interaction events";
            }
            bit router {
                position 6;
                description "Other router events";
            }
        }
        description "";
        reference "";
    }

    typedef  CML_OSPF_DEBUG_IFSM_T {
        type bits {
            bit status {
                position 0;
                description "IFSM Status Information";
            }
            bit events {
                position 1;
                description "IFSM Event Information";
            }
            bit timers {
                position 2;
                description "IFSM Timers Information";
            }
        }
        description "";
        reference "";
    }

    typedef  CML_OSPF_DEBUG_NFSM_T {
        type bits {
            bit status {
                position 0;
                description "NFSM Status Information";
            }
            bit events {
                position 1;
                description "NFSM Event Information";
            }
            bit timers {
                position 2;
                description "NFSM Timers Information";
            }
        }
        description "";
        reference "";
    }

    typedef  CML_OSPF_DEBUG_LSA_T {
        type bits {
            bit generate {
                position 0;
                description "LSA Generation";
            }
            bit flooding {
                position 1;
                description "LSA Flooding";
            }
            bit install {
                position 2;
                description "LSA Installation";
            }
            bit refresh {
                position 3;
                description "LSA Refreshment";
            }
            bit maxage {
                position 4;
                description "LSA MaxAge processing";
            }
        }
        description "";
        reference "";
    }

    typedef  CML_OSPF_DEBUG_NSM_T {
        type bits {
            bit interface {
                position 0;
                description "NSM interface";
            }
            bit redistribute {
                position 1;
                description "NSM redistribute";
            }
        }
        description "";
        reference "";
    }

    typedef  CML_OSPF_DEBUG_RIB_T {
        type bits {
            bit interface {
                position 0;
                description "RIB interface";
            }
            bit redistribute {
                position 1;
                description "RIB redistribute";
            }
        }
        description "";
        reference "";
    }

    typedef  CML_OSPF_DEBUG_RIB_CLIENT_T {
        type bits {
            bit redistribute {
                position 1;
                description "RIB redistribute";
            }
            bit client {
                position 2;
                description "RIB Client";
            }
        }
        description "";
        reference "";
    }

    typedef  CML_FLOWCTRL_T {
        type enumeration {
            enum off {
                value 0;
                description "Turn off flowcontrol";
            }
            enum on {
                value 1;
                description "Turn on flowcontrol";
            }
        }
        description "";
        reference "";
    }

    typedef  CML_ERROR_SET_TYPE_T {
        type enumeration {
            enum packet-loss {
                value 0;
                description "Error-Type - Packet-loss";
            }
            enum stray-packets {
                value 1;
                description "Error-Type - Stray-packets";
            }
            enum malformed-packets {
                value 2;
                description "Error-Type - Malformed-packets";
            }
            enum excessive-packet-loss-rate {
                value 3;
                description "Error-Type - Excessive packet loss rate";
            }
            enum buffer-overrun {
                value 4;
                description "Error-Type - Buffer-overrun";
            }
            enum remote-packet-loss {
                value 5;
                description "Error-Type - Remote packet loss";
            }
        }
        description "";
        reference "";
    }

    typedef  CML_ERROR_CLEAR_TYPE_T {
        type enumeration {
            enum packet-loss {
                value 6;
                description "Error-Type - Packet-loss";
            }
            enum stray-packets {
                value 7;
                description "Error-Type - Stray-packets";
            }
            enum malformed-packets {
                value 8;
                description "Error-Type - Malformed-packets";
            }
            enum excessive-packet-loss-rate {
                value 9;
                description "Error-Type - Excessive packet loss rate";
            }
            enum buffer-overrun {
                value 10;
                description "Error-Type - Buffer-overrun";
            }
            enum remote-packet-loss {
                value 11;
                description "Error-Type - Remote packet loss";
            }
        }
        description "";
        reference "";
    }

    typedef  CML_SR_ABSOLUTE_T {

        type uint32{
         range 16000..23999;
        }
        description "";
        reference "";
    }

    typedef  CML_SR_INDEX_T {

        type uint32{
         range 1..7999;
        }
        description "";
        reference "";
    }

    typedef  CML_SR_SID_T {
        type union {
            type CML_SR_ABSOLUTE_T {

            }
            type CML_SR_INDEX_T {

            }
        }
        description "";
        reference "";
    }

    typedef  CML_SR_PREFIX_FLAG_T {
        type enumeration {
            enum explicit-null {
                value 1;
                description "Set explicit-null";
            }
            enum no-php {
                value 2;
                description "Set no-PHP";
            }
        }
        description "";
        reference "";
    }

    typedef  CML_SR_N_FLAG_CLEAR_T {
        type enumeration {
            enum n-flag-clear {
                value 1;
                description "Set explicit-null";
            }
        }
        description "";
        reference "";
    }

    typedef  CML_NSM_ERR_REASON_T {
        type bits {
            bit lag-mismatch {
                position 0;
                description "Enable or Disable Lag-Mismatch";
            }
            bit stp-bpdu-guard {
                position 1;
                description "Enable or Disable Stp-Bpdu-Guard";
            }
            bit link-flap {
                position 2;
                description "Enable or Disable  Link-Flap";
            }
        }
        description "";
        reference "";
    }

    typedef  CML_NSM_ERR_DISABLE_TIMEOUT_T {
        type enumeration {
            enum disable {
                value 0;
                description "disable";
            }
            enum enable {
                value 1;
                description "enable";
            }
        }
        description "";
        reference "";
    }

    typedef  CML_NSM_ERRDISABLE_STATE_T {
        type bits {
            bit lag-mismatch {
                position 0;
                description "Lag-Mismatch";
            }
            bit stp-bpdu-guard {
                position 1;
                description "Stp-Bpdu-Guard";
            }
            bit link-flap {
                position 2;
                description "Link-Flap";
            }
            bit not-applicable {
                position 3;
                description "Not Applicable";
            }
        }
        description "";
        reference "";
    }

    typedef  CML_ON_OFF_T {
        type enumeration {
            enum off {
                value 0;
                description "off";
            }
            enum on {
                value 1;
                description "on";
            }
        }
        description "";
        reference "";
    }

    typedef  CML_OSPF_DEBUG_ROUTE_T {
        type bits {
            bit spf {
                position 0;
                description "SPF calculation information";
            }
            bit ia {
                position 1;
                description "Inter-Area route calculation information";
            }
            bit ase {
                position 2;
                description "External route calculation information";
            }
            bit install {
                position 3;
                description "Route installation information";
            }
            bit spf-terse {
                position 4;
                description "SPF Calculation terse information";
            }
        }
        description "";
        reference "";
    }

    typedef  CML_OSPF_DEBUG_REDIST_T {
        type bits {
            bit detail {
                position 0;
                description "OSPF redistribute Details";
            }
            bit terse {
                position 1;
                description "OSPF redistribute Terse";
            }
        }
        description "";
        reference "";
    }

    typedef  CML_OSPF_DEBUG_GRACEFUL_T {
        type bits {
            bit detail {
                position 0;
                description "OSPF graceful-restart Details";
            }
            bit terse {
                position 1;
                description "OSPF graceful-restart Terse";
            }
        }
        description "";
        reference "";
    }

    typedef  CML_OSPF_MD5_T {
        type enumeration {
            enum 0 {
                value 1;
                description "Unencrypted password (key)";
            }
        }
        description "";
        reference "";
    }

    typedef  CML_OSPF_DEFAULT_INFO_T {
        type enumeration {
            enum originate {
                value 1;
                description "Distribute a default route";
            }
        }
        description "";
        reference "";
    }

    typedef  CML_ROUTEMAP_EXTERNAL_TYPE_LIST {
        type enumeration {
            enum type-1 {
                value 1;
                description "Match OSPF External Type 1 metrics";
            }
            enum type-2 {
                value 2;
                description "Match OSPF External Type 2 metrics";
            }
        }
        description "";
        reference "";
    }

    typedef  CML_ROUTEMAP_OSPF_METRIC_TYPE_LIST {
        type enumeration {
            enum type-1 {
                value 1;
                description "Match OSPF External Type 1 metrics";
            }
            enum type-2 {
                value 2;
                description "Match OSPF External Type 2 metrics";
            }
        }
        description "";
        reference "";
    }

    typedef  CML_ROUTEMAP_ISIS_METRIC_TYPE_LIST {
        type enumeration {
            enum internal {
                value 1;
                description "IS-IS internal metric type";
            }
            enum external {
                value 2;
                description "IS-IS external metric type";
            }
        }
        description "";
        reference "";
    }

    typedef  CML_LEVEL_LIST_T {
        type enumeration {
            enum level-1 {
                value 1;
                description "Export into a level-1 area";
            }
            enum level-2 {
                value 2;
                description "Export into level-2 sub-domain";
            }
            enum level-1-2 {
                value 3;
                description "Export into level-1 and level-2Export into level-1 and level-2";
            }
        }
        description "";
        reference "";
    }

    typedef  CML_ROUTEMAP_ORIGIN_CODE {
        type enumeration {
            enum egp {
                value 1;
                description "remote EGP";
            }
            enum igp {
                value 2;
                description "local IGP";
            }
            enum incomplete {
                value 3;
                description "unknown heritage";
            }
        }
        description "";
        reference "";
    }

    typedef  CML_ROUTEMAP_COST_COMPARISION_T {
        type enumeration {
            enum igp {
                value 1;
                description "Compare following IGP cost comparison";
            }
            enum pre-bestpath {
                value 2;
                description "Compare before all other steps in bestpath calculation";
            }
        }
        description "";
        reference "";
    }

    typedef  CML_FORWARDTYPE_T {
        type enumeration {
            enum null0 {
                value 0;
                description "Forward to no interface";
            }
            enum tunnel-te {
                value 1;
                description "Forward to MPLS-TE tunnel";
            }
        }
        description "";
        reference "";
    }

    typedef  CML_ROUTEMAP_COMMUNITY_LIST_T {
        type union {
            type int32 {
                range "1..99 | 100..500";

            }
            type CML_STRING_T {

            }
        }
        description "";
        reference "";
    }

    typedef  CML_ROUT_MAP_EXACT_MATCH_T {
        type enumeration {
            enum exact-match {
                value 1;
                description "Do exact matching of communities";
            }
        }
        description "";
        reference "";
    }

    typedef  CML_ROUTEMAP_MATCH_T {
        type union {
            type CML_IPV6_ADDR_T {

            }
            type CML_STRING_T {

            }
        }
        description "";
        reference "";
    }

    typedef  CML_COMMUNITY_T {

        type string;
        description "";
        reference "";
    }

    typedef  CML_ROUTEMAP_COMMUNITY_T {
        type union {
            type uint32 {
                range "65536..4294901759";

            }
            type CML_COMMUNITY_T {

            }
        }
        description "";
        reference "";
    }

    typedef  CML_ROUTEMAP_ADDITIVE_LIST_T {
        type enumeration {
            enum default {
                value 0;
                description "BGP community attribute set to default";
            }
            enum additive {
                value 1;
                description "BGP community attribute";
            }
        }
        description "";
        reference "";
    }

    typedef  CML_AP_RMAP_ALL_T {
        type enumeration {
            enum all {
                value 1;
                description "Select all available paths";
            }
        }
        description "";
        reference "";
    }

    typedef  CML_AP_RMAP_BEST_T {

        type uint8{
         range 0..255;
        }
        description "";
        reference "";
    }

    typedef  CML_ADDPATH_RMAP_T {
        type union {
            type CML_AP_RMAP_BEST_T {

            }
            type CML_AP_RMAP_ALL_T {

            }
        }
        description "";
        reference "";
    }

    typedef  CML_BRIDGE_FORWARD_T {
        type enumeration {
            enum bridge-blocked {
                value 0;
                description "put all ports of the bridge into blocked state";
            }
            enum bridge-forward {
                value 1;
                description "put all ports of the bridge into forwarding state";
            }
        }
        description "";
        reference "";
    }

    typedef  CML_BCKBONE_BRIDGE_GRP_T {
        type enumeration {
            enum backbone {
                value 0;
                description "Specifies the backbone bridge group name";
            }
        }
        description "";
        reference "";
    }

    typedef  CML_BRIDGE_GRP_T {

        type uint8{
         range 0..255;
        }
        description "";
        reference "";
    }

    typedef  CML_BRIDGE_GRP_CMD_T {
        type union {
            type CML_BRIDGE_GRP_T {

            }
            type CML_BCKBONE_BRIDGE_GRP_T {

            }
        }
        description "";
        reference "";
    }

    typedef  CML_BRIDGE_SPANMODE_T {
        type enumeration {
            enum stp {
                value 1;
                description "IEEE 801.1Q spanning-tree protocol";
            }
            enum stp-vlan-bridge {
                value 2;
                description "IEEE 801.1Q spanning-tree protocol";
            }
            enum rstp {
                value 3;
                description "IEEE 801.1w rapid spanning-tree protocol";
            }
            enum rstp-vlan-bridge {
                value 4;
                description "IEEE 801.1w rapid spanning-tree protocol";
            }
            enum mstp {
                value 5;
                description "IEEE 802.1s multiple spanning-tree protocol";
            }
            enum provider-rstp {
                value 6;
                description "IEEE 802.1s rapid spanning-tree protocol";
            }
            enum provider-mstp {
                value 7;
                description "IEEE 802.1s rapid spanning-tree protocol";
            }
            enum rpvst+ {
                value 12;
                description "IEEE 801.1w rapid per vlan spanning-tree protocol";
            }
        }
        description "";
        reference "";
    }

    typedef  CML_ALLOWED_FORBIDDEN_T {
        type enumeration {
            enum forbidden {
                value 0;
                description "forbidden list";
            }
            enum allowed {
                value 1;
                description "allowed list";
            }
        }
        description "";
        reference "";
    }

    typedef  CML_ADD_REMOVE_T {
        type enumeration {
            enum remove {
                value 0;
                description "Deletes the interface from the vlan list";
            }
            enum add {
                value 1;
                description "Adds the interface in the vlan list";
            }
        }
        description "";
        reference "";
    }

    typedef  CML_VLANSTACK_T {
        type enumeration {
            enum customer-edge-port {
                value 4;
                description "Set the switching characteristics of the Layer2 interface to Customer-edge port";
            }
            enum provider-port {
                value 6;
                description "Set the switching characteristics of the Layer2 interface to Provider port";
            }
        }
        description "";
        reference "";
    }

    typedef  CML_ENABLEBPDURX_T {
        type enumeration {
            enum disableBPDUrx {
                value 0;
                description "disableBPDUrx";
            }
            enum enableBPDUrx {
                value 1;
                description "enableBPDUrx";
            }
        }
        description "";
        reference "";
    }

    typedef  CML_ACLTYPE_T {
        type enumeration {
            enum mac {
                value 1;
                description "Mac access-list";
            }
            enum ip {
                value 3;
                description "ip access-list";
            }
            enum ipv6 {
                value 4;
                description "ipv6 access-list";
            }
        }
        description "";
        reference "";
    }

    typedef  CML_BRIDGE_T {

        type uint8{
         range 0..255;
        }
        description "";
        reference "";
    }

    typedef  CML_BRIDGE_ID_T {
        type union {
            type CML_BRIDGE_T {

            }
            type CML_SPANNING_TREE_T {

            }
        }
        description "";
        reference "";
    }

    typedef  CML_BRIDGE_BACKBONE_ID_T {
        type union {
            type CML_BRIDGE_BCKBONE_T {

            }
            type CML_BACKBONE_T {

            }
        }
        description "";
        reference "";
    }

    typedef  CML_BACKBONE_T {
        type enumeration {
            enum backbone {
                value 33;
                description "Specifies the backbone bridge group name";
            }
        }
        description "";
        reference "";
    }

    typedef  CML_BRIDGE_BCKBONE_T {

        type uint8{
         range 0..255;
        }
        description "";
        reference "";
    }

    typedef  CML_ACTIONTYPE_T {
        type enumeration {
            enum forward {
                value 101;
                description "Forward";
            }
            enum drop {
                value 102;
                description "Drop";
            }
            enum redirect {
                value 103;
                description "redirect to";
            }
        }
        description "";
        reference "";
    }

    typedef  CML_VLAN_OPT_TYPE_T {
        type enumeration {
            enum add {
                value 1;
                description "adds the specified vlans to te-region";
            }
            enum delete {
                value 2;
                description "deletes the vlans from te-region";
            }
        }
        description "";
        reference "";
    }

    typedef  CML_TESI_MODE_T {
        type enumeration {
            enum passive {
                value 1;
                description "mode from active to passive";
            }
            enum active {
                value 2;
                description "mode from passive to active";
            }
        }
        description "";
        reference "";
    }

    typedef  CML_TESI_TYPE_T {
        type enumeration {
            enum dynamic {
                value 1;
                description "type from static to dynamic";
            }
            enum static {
                value 2;
                description "type from dynamic to static";
            }
        }
        description "";
        reference "";
    }

    typedef  CML_PNPADDDEL_T {
        type enumeration {
            enum add {
                value 1;
                description "deletes the subsequest interface from this tesi";
            }
            enum delete {
                value 2;
                description "interface name";
            }
        }
        description "";
        reference "";
    }

    typedef  CML_NSMVLANPORT_MODE_T {
        type enumeration {
            enum pnp {
                value 6;
                description "Default vlan configured on Provider Network Port";
            }
            enum cnp {
                value 8;
                description "Default vlan configured on Customer Network Port";
            }
            enum pip {
                value 10;
                description "Default vlan configured on Provider Instance Port";
            }
            enum cbp {
                value 11;
                description "";
            }
        }
        description "";
        reference "";
    }

    typedef  CML_CMBCKINSTANCE_T {

        type uint32{
         range 1..16777214;
        }
        description "";
        reference "";
    }

    typedef  CML_SPANNING_TREE_T {
        type enumeration {
            enum spanning-tree {
                value 0;
                description "default bridge commands";
            }
        }
        description "";
        reference "";
    }

    typedef  CML_INSTANCE_NAME_T {

        type string;
        description "";
        reference "";
    }

    typedef  CML_SVLAN_INSTANCE_NAME_T {
        type union {
            type CML_CMBCKINSTANCE_T {

            }
            type CML_INSTANCE_NAME_T {

            }
        }
        description "";
        reference "";
    }

    typedef  CML_CMBCKBONE_INSTANCE_T {
        type union {
            type CML_CMBCKINSTANCE_T {

            }
            type CML_INSTANCE_IFNAME_T {

            }
        }
        description "";
        reference "";
    }

    typedef  CML_INSTANCE_IFNAME_T {

        type string;
        description "";
        reference "";
    }

    typedef  CML_VIP_TRAFFIC_T {
        type enumeration {
            enum all {
                value 0;
                description "Ingress/egress allowed";
            }
            enum ingress {
                value 1;
                description "Configures ingress service flow";
            }
            enum egress {
                value 2;
                description "Configures egress service flow";
            }
        }
        description "";
        reference "";
    }

    typedef  CML_BEB_MODE_T {
        type enumeration {
            enum tx {
                value 0;
                description "Transmit only";
            }
            enum rx {
                value 1;
                description "Receive only";
            }
            enum rxtx {
                value 2;
                description "Transmit and Receive";
            }
            enum none {
                value 3;
                description "Neither tx nor rx";
            }
        }
        description "";
        reference "";
    }

    typedef  CML_BRIDGE_BACKBONE_T {
        type union {
            type CML_BACKBONE_T {

            }
            type uint8 {
                range "1..32";

            }
        }
        description "";
        reference "";
    }

    typedef  CML_ASPTEISID_T {
        type enumeration {
            enum add {
                value 1;
                description "adds a new ISID to this aps group";
            }
            enum delete {
                value 2;
                description "deletes an existing ISID from this aps group";
            }
        }
        description "";
        reference "";
    }

    typedef  CML_CNPINS_T {

        type uint32{
         range 1..16777214;
        }
        description "";
        reference "";
    }

    typedef  CML_OSPF_NBMA_ROW_STATUS {
        type enumeration {
            enum row-status-active {
                value 1;
                description "Row status Active";
            }
            enum row-status-notinservice {
                value 2;
                description "Row status Not in service";
            }
            enum row-status-notready {
                value 3;
                description "Row Status not ready";
            }
            enum row-status-createandgo {
                value 4;
                description "Row status create and go";
            }
            enum row-status-createandwait {
                value 5;
                description "Row status Create and wait";
            }
            enum row-status-destroy {
                value 6;
                description "Row status Destroy";
            }
        }
        description "";
        reference "";
    }

    typedef  CML_OSPF_IF_STATE {
        type enumeration {
            enum enabled {
                value 1;
                description "OSPF_API_STATUS_ENABLED";
            }
            enum disabled {
                value 2;
                description "OSPF_API_STATUS_DISABLED";
            }
        }
        description "";
        reference "";
    }

    typedef  CML_CNP_INSTANCE_T {
        type union {
            type CML_CNPINS_T {

            }
            type CML_CNP_INSTANCE_IFNAME_T {

            }
        }
        description "";
        reference "";
    }

    typedef  CML_CNP_INSTANCE_IFNAME_T {

        type string;
        description "";
        reference "";
    }

    typedef  SNMP_TRAP_OPTIONS_T {
        type enumeration {
            enum link {
                value 1;
                description "Module notifications enable";
            }
            enum link-linkDown {
                value 2;
                description "Module notifications enable,IETF Link state down notification";
            }
            enum link-linkUp {
                value 3;
                description "Module notifications enable,IETF Link state up notification";
            }
            enum snmp {
                value 4;
                description "Module notifications enable";
            }
            enum snmp-authentication {
                value 5;
                description "Module notifications enable,SNMP authentication trap";
            }
            enum mpls {
                value 6;
                description "mpls notification trap";
            }
            enum pw {
                value 7;
                description "pw notification trap";
            }
            enum pwdelete {
                value 8;
                description "pwdelete notification trap";
            }
            enum rsvp {
                value 9;
                description "rsvp notification trap";
            }
            enum ospf {
                value 10;
                description "ospf notification trap";
            }
            enum bgp {
                value 11;
                description "bgp notification trap";
            }
            enum isis {
                value 12;
                description "isis notification trap";
            }
        }
        description "";
        reference "";
    }

    typedef  CML_VR_PROTOCOL_T {
        type bits {
            bit rip {
                position 1;
                description "Routing Information Protocol (RIP)";
            }
            bit ipv6-rip {
                position 2;
                description "Internet Protocol Version 6,Routing Information Protocol (RIP)";
            }
            bit ospf {
                position 3;
                description "Open Shortest Path First (OSPF)";
            }
            bit ipv6-ospf {
                position 4;
                description "Internet Protocol Version 6, Open Shortest Path First (OSPF)";
            }
            bit isis {
                position 5;
                description "Intermediate System - Intermediate System (IS-IS)";
            }
            bit pim {
                position 6;
                description "Protocol Independent Multicast (PIM)";
            }
            bit vrrp {
                position 7;
                description "Virtual Router Redundancy Protocol (VRRP)";
            }
            bit bgp {
                position 9;
                description "Border Gateway Protocol (BGP)";
            }
        }
        description "";
        reference "";
    }

    typedef  CML_LDP_ENABLE_IPV4_TYPE_T {
        type enumeration {
            enum disable-ldp {
                value 0;
                description "Disable LDP on interface";
            }
            enum enable-ldp {
                value 1;
                description "Enable LDP on Interface";
            }
        }
        description "";
        reference "";
    }

    typedef  CML_LDP_ENABLE_IPV6_TYPE_T {
        type enumeration {
            enum disable-ldp {
                value 0;
                description "Disable LDP on interface";
            }
            enum enable-ldp {
                value 1;
                description "Enable LDP on Interface";
            }
        }
        description "";
        reference "";
    }

    typedef  CML_LDP_IGP_SYNC_T {
        type enumeration {
            enum igp-sync {
                value 0;
                description "Enable/Disable LDP for IPV4";
            }
            enum no-igp-sync {
                value 1;
                description "Enable/Disable LDP for IPV6";
            }
        }
        description "";
        reference "";
    }

    typedef  CML_RSVP_INSTANCE_T {
        type enumeration {
            enum rsvp {
                value 1;
                description "Resource Reservation Protocol (RSVP)";
            }
        }
        description "";
        reference "";
    }

    typedef  CML_LDP_INSTANCE_T {
        type enumeration {
            enum ldp {
                value 1;
                description "Label Distribution Protocol (LDP)";
            }
        }
        description "";
        reference "";
    }

    typedef  CML_LDP_DEBUG_T {
        type bits {
            bit events {
                position 0;
                description "LDP events";
            }
            bit fsm {
                position 1;
                description "Enable FSM debugging";
            }
            bit hexdump {
                position 2;
                description "Enable HEXDUMP";
            }
            bit dsm {
                position 3;
                description "Enable Downstream SM";
            }
            bit usm {
                position 4;
                description "LDP Upstream SM";
            }
            bit tsm {
                position 5;
                description "LDP Trunk SM";
            }
            bit qos {
                position 6;
                description "LDP QoS";
            }
            bit nsm {
                position 7;
                description "NSM messages";
            }
            bit advertise-labels {
                position 8;
                description "List IP access lists of advertise-labels";
            }
            bit graceful-restart {
                position 12;
                description "LDP Graceful Restart Debugging";
            }
            bit rib {
                position 13;
                description "RIB messages";
            }
        }
        description "";
        reference "";
    }

    typedef  CML_LDP_DEBUG_PACKET_T {
        type bits {
            bit notification {
                position 0;
                description "LDP notification packet";
            }
            bit hello {
                position 1;
                description "LDP hello packet";
            }
            bit initialization {
                position 2;
                description "LDP initialization packet";
            }
            bit keepalive {
                position 3;
                description "LDP keepalive packet";
            }
            bit address {
                position 4;
                description "LDP address (withdraw) packet";
            }
            bit label {
                position 5;
                description "LDP label mapping/request(abort)/withdraw/release packet";
            }
        }
        description "";
        reference "";
    }

    typedef  CML_LDP_FAILURE_T {
        type enumeration {
            enum restart {
                value 0;
                description "Restart LSP";
            }
        }
        description "";
        reference "";
    }

    typedef  CML_LDP_CSPF_T {
        type enumeration {
            enum no-cspf {
                value 0;
                description "Use Hop-by-Hop Routing";
            }
            enum cspf {
                value 1;
                description "Use CSPF for Path Computation";
            }
        }
        description "";
        reference "";
    }

    typedef  CML_LDP_LOOSE_T {
        type enumeration {
            enum strict {
                value 0;
                description "Make this node strict";
            }
            enum loose {
                value 1;
                description "Make this node loose";
            }
        }
        description "";
        reference "";
    }

    typedef  CML_LDP_TRUNK_ADMIN_GROUP_T {
        type enumeration {
            enum exclude-any {
                value 0;
                description "Exclude any of the administrative groups from the explicit route";
            }
            enum include-any {
                value 1;
                description "Include any of the administrative groups in the explicit route";
            }
        }
        description "";
        reference "";
    }

    typedef  CML_LDP_IP_ADDR_T {
        type union {
            type CML_IPV4_ADDR_DESC_T {

            }
            type CML_IPV6_ADDR_DESC_T {

            }
        }
        description "";
        reference "";
    }

    typedef  CML_LDP_ICCP_DEBUG_T {
        type bits {
            bit events {
                position 0;
                description "Events";
            }
            bit fsm {
                position 1;
                description "FSM";
            }
            bit hexdump {
                position 2;
                description "hexdump of messages";
            }
            bit packet {
                position 3;
                description "Packets";
            }
            bit bfd {
                position 4;
                description "BFD";
            }
        }
        description "";
        reference "";
    }

    typedef  CML_RSVP_PATH_TYPE_T {
        type enumeration {
            enum mpls {
                value 0;
                description "Path type is mpls";
            }
            enum gmpls {
                value 1;
                description "Path type is gmpls";
            }
        }
        description "";
        reference "";
    }

    typedef  CML_RSVP_TRUNK_ADDRFAMILY_T {
        type enumeration {
            enum ipv4 {
                value 0;
                description "IPv4 address family trunk";
            }
            enum ipv6 {
                value 1;
                description "IPv6 address family trunk";
            }
        }
        description "";
        reference "";
    }

    typedef  CML_PATH_SEL_TYPE_T {
        type enumeration {
            enum te {
                value 0;
                description "te-- cspf computated path";
            }
            enum igp {
                value 1;
                description "igp - cspf computated path";
            }
        }
        description "";
        reference "";
    }

    typedef  CML_RSVP_RESTART_STATUS_T {
        type enumeration {
            enum disable {
                value 0;
                description "Disable Graceful Restart";
            }
            enum enable {
                value 1;
                description "Enable Graceful Restart";
            }
        }
        description "";
        reference "";
    }

    typedef  CML_RSVP_DETOUR_IDEN_T {
        type enumeration {
            enum sender-template {
                value 1;
                description "Sender Template specific detour identification method";
            }
            enum path {
                value 2;
                description "Path Secific detour identification method (using detour object)";
            }
        }
        description "";
        reference "";
    }

    typedef  CML_RSVP_P2MP_ADDR_T {
        type enumeration {
            enum ipv4 {
                value 1;
                description "IPV4 address family trunk";
            }
            enum ipv6 {
                value 2;
                description "IPV6 address family trunk";
            }
        }
        description "";
        reference "";
    }

    typedef  CML_RSVP_CSPF_TYPE_T {
        type enumeration {
            enum no-cspf {
                value 0;
                description "Use Hop-by-Hop Routing";
            }
            enum cspf {
                value 1;
                description "Use CSPF for Path Computation";
            }
        }
        description "";
        reference "";
    }

    typedef  CML_RSVP_TRUNK_METRIC_TYPE_T {
        type enumeration {
            enum igp-metric {
                value 1;
                description "(admin state down)";
            }
            enum te-metric {
                value 2;
                description "(interface is not running)";
            }
            enum hop-count {
                value 3;
                description "(monitored circuit is down)";
            }
        }
        description "";
        reference "";
    }

    typedef  CML_RSVP_CSPF_STATUS_T {
        type enumeration {
            enum no-cspf {
                value 0;
                description "Disable CSPF usage for RSVP";
            }
            enum cspf {
                value 1;
                description "Enable CSPF usage for RSVP";
            }
        }
        description "";
        reference "";
    }

    typedef  CML_LOOP_DETECTION_T {
        type enumeration {
            enum no-loop-detection {
                value 0;
                description "Disable loop detection";
            }
            enum loop-detection {
                value 1;
                description "Enable loop detection";
            }
        }
        description "";
        reference "";
    }

    typedef  CML_RSVP_PHP_T {
        type enumeration {
            enum no-php {
                value 0;
                description "Disable Penultimate-Hop-Popping for router";
            }
            enum php {
                value 1;
                description "Enable Penultimate-Hop-Popping for router";
            }
        }
        description "";
        reference "";
    }

    typedef  CML_REFRESH_PATH_PARSING_T {
        type enumeration {
            enum no-refresh-path-parsing {
                value 0;
                description "Disable parsing of refresh PATH messages";
            }
            enum refresh-path-parsing {
                value 1;
                description "Enable parsing of refresh PATH messages";
            }
        }
        description "";
        reference "";
    }

    typedef  CML_REFRESH_RESV_PARSING_T {
        type enumeration {
            enum no-refresh-resv-parsing {
                value 0;
                description "Disable parsing of refresh RESV messages";
            }
            enum refresh-resv-parsing {
                value 1;
                description "Enable parsing of refresh RESV messages";
            }
        }
        description "";
        reference "";
    }

    typedef  CML_RSVP_DEBUG_T {
        type bits {
            bit events {
                position 0;
                description "RSVP events";
            }
            bit packet {
                position 1;
                description "RSVP packet";
            }
            bit packet-in {
                position 2;
                description "RSVP packet,Incoming RSVP packet";
            }
            bit packet-out {
                position 3;
                description "RSVP packet, Outgoing RSVP packet";
            }
            bit hexdump {
                position 4;
                description "RSVP Hexdump";
            }
            bit nsm {
                position 5;
                description "NSM messages";
            }
            bit fsm-egress {
                position 7;
                description "Enable FSM debugging,Enable RSVP Egress FSM debugging";
            }
            bit fsm-transit-downstream {
                position 8;
                description "Enable FSM debugging, Enable RSVP Transit FSM debugging, Enable RSVP Transit Downstream FSM debugging";
            }
            bit fsm-transit-upstream {
                position 9;
                description "Enable FSM debugging,Enable RSVP Transit FSM debugging,Enable RSVP Transit Upstream FSM dugging";
            }
            bit fsm-ingress {
                position 10;
                description "Enable FSM debugging, Enable RSVP Ingress FSM debugging";
            }
            bit rib {
                position 11;
                description "RIB messages";
            }
        }
        description "";
        reference "";
    }

    typedef  CML_L2_PROTOCOL_T {
        type enumeration {
            enum stp {
                value 0;
                description "Spanning Tree Protocols";
            }
            enum gmrp {
                value 3;
                description "GARP Multicast Registration Protocol";
            }
            enum gvrp {
                value 4;
                description "GARP Multicast Registration Protocol";
            }
            enum mmrp {
                value 5;
                description "MRP Multicast Registration Protocol";
            }
            enum mvrp {
                value 6;
                description "MRP Multicast Registration Protocol";
            }
            enum lacp {
                value 7;
                description "Link Aggregation (LACP)";
            }
            enum dot1x {
                value 8;
                description "Port Authentication (802.1 X)";
            }
            enum lldp {
                value 9;
                description "Link layer discovery protocol";
            }
            enum pause {
                value 13;
                description "Pause frames";
            }
            enum efm {
                value 14;
                description "Ethernet first mile (Link OAM)";
            }
            enum elmi {
                value 15;
                description "Ethernet local management interface";
            }
            enum ptp {
                value 16;
                description "Precision Time Protocol";
            }
            enum synce {
                value 17;
                description "Synchronous Ethernet";
            }
        }
        description "";
        reference "";
    }

    typedef  CML_DISCARD_L2_PROTOCOL_T {
        type enumeration {
            enum stp {
                value 0;
                description "Spanning Tree Protocols";
            }
            enum lacp {
                value 7;
                description "Link Aggregation (LACP)";
            }
            enum dot1x {
                value 8;
                description "Port Authentication (802.1 X)";
            }
            enum lldp {
                value 9;
                description "Link layer discovery protocol";
            }
            enum pause {
                value 13;
                description "Pause frames";
            }
            enum efm {
                value 14;
                description "Ethernet first mile (Link OAM)";
            }
            enum elmi {
                value 15;
                description "Ethernet local management interface";
            }
            enum ptp {
                value 16;
                description "Precision Time Protocol";
            }
            enum synce {
                value 17;
                description "Synchronous Ethernet";
            }
        }
        description "";
        reference "";
    }

    typedef  CML_PVLAN_MODE_T {
        type enumeration {
            enum host {
                value 1;
                description "host port";
            }
            enum promiscuous {
                value 2;
                description "promiscuous port";
            }
        }
        description "";
        reference "";
    }

    typedef  CML_PVLAN_TYPE_T {
        type enumeration {
            enum community {
                value 1;
                description "vlan type to community";
            }
            enum isolated {
                value 2;
                description "vlan type to isolated";
            }
            enum primary {
                value 3;
                description "vlan type to primary";
            }
            enum association {
                value 4;
                description "association to secondary vlan";
            }
        }
        description "";
        reference "";
    }

    typedef  CML_PVLAN_ADD_REMOVE_TYPE_T {
        type enumeration {
            enum add {
                value 1;
                description "add secondary vlan";
            }
            enum remove {
                value 2;
                description "remove secondary vlan";
            }
        }
        description "";
        reference "";
    }

    typedef  CML_CVLAN_CONFIG_T {
        type bits {
            bit default {
                position 0;
                description "Default value";
            }
            bit untagged-pep {
                position 1;
                description "Configure PEP as Untagged for this CVLAN";
            }
            bit untagged-cep {
                position 2;
                description "Configure CEP as Untagged for this CVLAN";
            }
        }
        description "";
        reference "";
    }

    typedef  CML_OEP_VLAN_TYPE_T {
        type enumeration {
            enum cvlan {
                value 1;
                description "configure C-VLAN oep-mapping table entry";
            }
            enum svlan {
                value 2;
                description "configure S-VLAN oep-mapping table entry";
            }
        }
        description "";
        reference "";
    }

    typedef  CML_EGERSS_TAGGED_TYPE_T {
        type enumeration {
            enum disable {
                value 0;
                description "Set the egress tagging on the outgoing frames to disabled";
            }
            enum enable {
                value 1;
                description "Set the egress tagging on the outgoing frames to enabled";
            }
        }
        description "";
        reference "";
    }

    typedef  CML_EDGE_VLAN_TYPE_T {
        type enumeration {
            enum allowed {
                value 1;
                description "Set the Layer2 interface as trunk";
            }
            enum default-svlan {
                value 2;
                description "Set the default SVLAN for the interface";
            }
        }
        description "";
        reference "";
    }

    typedef  CML_ACL_PORT_OPERATIONS_T {
        type enumeration {
            enum eq {
                value 1;
                description "port equal to";
            }
            enum neq {
                value 2;
                description "port not equal to";
            }
            enum lt {
                value 3;
                description "port less than";
            }
            enum gt {
                value 4;
                description "port greater than";
            }
            enum range {
                value 5;
                description "range";
            }
        }
        description "";
        reference "";
    }

    typedef  CML_ACL_FILTER_ACTION_T {
        type enumeration {
            enum deny {
                value 0;
                description "Specify packets to reject";
            }
            enum permit {
                value 1;
                description "Specify packets to forward";
            }
            enum dynamic {
                value 2;
                description "dynamic ";
            }
            enum deny-all {
                value 3;
                description "Specify all packets to reject";
            }
            enum permit-all {
                value 4;
                description "Specify all packets to forward";
            }
            enum no-match {
                value 5;
                description "No match found";
            }
        }
        description "";
        reference "";
    }

    typedef  CML_ACL_ARP_TYPE_T {
        type enumeration {
            enum none {
                value 0;
                description "Match any ARP packets";
            }
            enum request {
                value 1;
                description "Match ARP request packets";
            }
            enum response {
                value 2;
                description "Match ARP response packets";
            }
        }
        description "";
        reference "";
    }

    typedef  CML_ACL_ANY_T {
        type enumeration {
            enum any {
                value 0;
                description "Wildcard entry matching all addresses";
            }
        }
        description "";
        reference "";
    }

    typedef  CML_ACL_IPV4_HOST_T {

        type string;
        description "";
        reference "";
    }

    typedef  CML_ACL_IPV4_PREFIX_T {

        type inet:ipv4-prefix{
        length 0..32;
        }
        description "";
        reference "";
    }

    typedef  CML_ACL_ANY_IPV4_ADDR_T {
        type union {
            type CML_ACL_ANY_T {

            }
            type CML_ACL_IPV4_HOST_T {

            }
            type CML_ACL_IPV4_PREFIX_T {

            }
        }
        description "";
        reference "";
    }

    typedef  CML_ACL_IPV6_HOST_T {

        type string;
        description "";
        reference "";
    }

    typedef  CML_ACL_IPV6_PREFIX_T {

        type inet:ipv6-prefix{
        length 0..92;
        }
        description "";
        reference "";
    }

    typedef  CML_ACL_ANY_IPV6_ADDR_T {
        type union {
            type CML_ACL_ANY_T {

            }
            type CML_ACL_IPV6_HOST_T {

            }
            type CML_ACL_IPV6_PREFIX_T {

            }
        }
        description "";
        reference "";
    }

    typedef  CML_ACL_UDP_KEYWORD_ENUM_T {
        type enumeration {
            enum echo {
                value 7;
                description "echo";
            }
            enum discard {
                value 9;
                description "discard";
            }
            enum time {
                value 37;
                description "time";
            }
            enum nameserver {
                value 42;
                description "nameserver";
            }
            enum tacacs {
                value 49;
                description "tacacs";
            }
            enum domain {
                value 53;
                description "domain";
            }
            enum bootps {
                value 67;
                description "bootps";
            }
            enum bootpc {
                value 68;
                description "bootpc";
            }
            enum tftp {
                value 69;
                description "tftp";
            }
            enum sunrpc {
                value 111;
                description "sunrpc";
            }
            enum netbios_ns {
                value 137;
                description "netbios_ns";
            }
            enum netbios_dgm {
                value 138;
                description "netbios_dgm";
            }
            enum netbios_ss {
                value 139;
                description "netbios_ss";
            }
            enum snmp {
                value 161;
                description "snmp";
            }
            enum snmptrap {
                value 162;
                description "snmptrap";
            }
            enum xdmcp {
                value 177;
                description "xdmcp";
            }
            enum dnsix {
                value 195;
                description "dnsix";
            }
            enum mobile_ip {
                value 434;
                description "mobile_ip";
            }
            enum pim_auto_rp {
                value 496;
                description "pim_auto_rp";
            }
            enum isakmp {
                value 500;
                description "isakmp";
            }
            enum biff {
                value 512;
                description "biff";
            }
            enum who {
                value 513;
                description "who";
            }
            enum syslog {
                value 514;
                description "syslog";
            }
            enum talk {
                value 517;
                description "talk";
            }
            enum rip {
                value 520;
                description "rip";
            }
            enum non500_isakmp {
                value 4500;
                description "non500_isakmp";
            }
        }
        description "";
        reference "";
    }

    typedef  CML_ACL_UDP_KEYWORD_T {
        type union {
            type CML_ACL_UDP_KEYWORD_ENUM_T {

            }
            type uint32 {
                range "0..65535";

            }
        }
        description "";
        reference "";
    }

    typedef  CML_ACL_TCP_KEYWORD_ENUM_T {
        type enumeration {
            enum echo {
                value 7;
                description "echo";
            }
            enum discard {
                value 9;
                description "discard";
            }
            enum daytime {
                value 13;
                description "daytime";
            }
            enum chargen {
                value 19;
                description "chargen";
            }
            enum ftp_data {
                value 20;
                description "ftp_data";
            }
            enum ftp {
                value 21;
                description "ftp";
            }
            enum ssh {
                value 22;
                description "ssh";
            }
            enum telnet {
                value 23;
                description "telnet";
            }
            enum smtp {
                value 25;
                description "smtp";
            }
            enum time {
                value 37;
                description "time";
            }
            enum whois {
                value 43;
                description "whois";
            }
            enum tacacs {
                value 49;
                description "tacacs";
            }
            enum domain {
                value 53;
                description "domain";
            }
            enum gopher {
                value 70;
                description "gopher";
            }
            enum finger {
                value 79;
                description "finger";
            }
            enum www {
                value 80;
                description "www";
            }
            enum hostname {
                value 101;
                description "hostname";
            }
            enum pop2 {
                value 109;
                description "pop2";
            }
            enum pop3 {
                value 110;
                description "pop3";
            }
            enum sunrpc {
                value 111;
                description "sunrpc";
            }
            enum ident {
                value 113;
                description "ident";
            }
            enum nntp {
                value 119;
                description "nntp";
            }
            enum bgp {
                value 179;
                description "bgp";
            }
            enum irc {
                value 194;
                description "irc";
            }
            enum pim_auto_rp {
                value 496;
                description "pim_auto_rp";
            }
            enum exec {
                value 512;
                description "exec";
            }
            enum login {
                value 513;
                description "login";
            }
            enum cmd {
                value 514;
                description "cmd";
            }
            enum lpd {
                value 515;
                description "lpd";
            }
            enum talk {
                value 517;
                description "talk";
            }
            enum uucp {
                value 540;
                description "uucp";
            }
            enum klogin {
                value 543;
                description "klogin";
            }
            enum kshell {
                value 544;
                description "kshell";
            }
            enum drip {
                value 3949;
                description "drip";
            }
        }
        description "";
        reference "";
    }

    typedef  CML_ACL_TCP_KEYWORD_T {
        type union {
            type CML_ACL_TCP_KEYWORD_ENUM_T {

            }
            type uint32 {
                range "0..65535";

            }
        }
        description "";
        reference "";
    }

    typedef  CML_ACL_IP_PROTO_ENUM_T {
        type enumeration {
            enum ipv6_hop {
                value 0;
                description "ipv6_hop";
            }
            enum icmp {
                value 1;
                description "icmp";
            }
            enum igmp {
                value 2;
                description "igmp";
            }
            enum ipip {
                value 4;
                description "ipip";
            }
            enum tcp {
                value 6;
                description "tcp";
            }
            enum udp {
                value 17;
                description "udp";
            }
            enum ipv6ip {
                value 41;
                description "ipv6ip";
            }
            enum rsvp {
                value 46;
                description "rsvp";
            }
            enum gre {
                value 47;
                description "gre";
            }
            enum esp {
                value 50;
                description "esp";
            }
            enum ahp {
                value 51;
                description "ahp";
            }
            enum eigrp {
                value 88;
                description "eigrp";
            }
            enum ospf {
                value 89;
                description "ospf";
            }
            enum pim {
                value 103;
                description "pim";
            }
            enum ipcomp {
                value 108;
                description "ipcomp";
            }
            enum vrrp {
                value 112;
                description "vrrp";
            }
            enum sctp {
                value 132;
                description "sctp";
            }
            enum any {
                value 256;
                description "any";
            }
        }
        description "";
        reference "";
    }

    typedef  CML_ACL_IP_PROTO_T {
        type union {
            type CML_ACL_IP_PROTO_ENUM_T {

            }
            type uint16 {
                range "0..255";

            }
        }
        description "";
        reference "";
    }

    typedef  CML_ACL_IPV6_PROTO_ENUM_T {
        type enumeration {
            enum ipv6_hop {
                value 0;
                description "ipv6_hop";
            }
            enum igmp {
                value 2;
                description "igmp";
            }
            enum ipv6ip {
                value 4;
                description "ipv6ip";
            }
            enum tcp {
                value 6;
                description "tcp";
            }
            enum udp {
                value 17;
                description "udp";
            }
            enum ipv6ipv6 {
                value 41;
                description "ipv6ipv6";
            }
            enum rsvp {
                value 46;
                description "rsvp";
            }
            enum gre {
                value 47;
                description "gre";
            }
            enum esp {
                value 50;
                description "esp";
            }
            enum ahp {
                value 51;
                description "ahp";
            }
            enum icmpv6 {
                value 58;
                description "icmpv6";
            }
            enum ospf {
                value 89;
                description "ospf";
            }
            enum pim {
                value 103;
                description "pim";
            }
            enum ipcomp {
                value 108;
                description "ipcomp";
            }
            enum vrrp {
                value 112;
                description "vrrp";
            }
            enum sctp {
                value 132;
                description "sctp";
            }
            enum any {
                value 256;
                description "any";
            }
        }
        description "";
        reference "";
    }

    typedef  CML_ACL_IPV6_PROTO_T {
        type union {
            type CML_ACL_IPV6_PROTO_ENUM_T {

            }
            type uint16 {
                range "0..255";

            }
        }
        description "";
        reference "";
    }

    typedef  CML_ACL_DSCP_ENUM_T {
        type enumeration {
            enum default {
                value 0;
                description "default";
            }
            enum cs1 {
                value 8;
                description "cs1";
            }
            enum af11 {
                value 10;
                description "af11";
            }
            enum af12 {
                value 12;
                description "af12";
            }
            enum af13 {
                value 14;
                description "af13";
            }
            enum cs2 {
                value 16;
                description "cs2";
            }
            enum af21 {
                value 18;
                description "af21";
            }
            enum af22 {
                value 20;
                description "af22";
            }
            enum af23 {
                value 22;
                description "af23";
            }
            enum cs3 {
                value 24;
                description "cs3";
            }
            enum af31 {
                value 26;
                description "af31";
            }
            enum af32 {
                value 28;
                description "af32";
            }
            enum af33 {
                value 30;
                description "af33";
            }
            enum cs4 {
                value 32;
                description "cs4";
            }
            enum af41 {
                value 34;
                description "af41";
            }
            enum af42 {
                value 36;
                description "af42";
            }
            enum af43 {
                value 38;
                description "af43";
            }
            enum cs5 {
                value 40;
                description "cs5";
            }
            enum ef {
                value 46;
                description "ef";
            }
            enum cs6 {
                value 48;
                description "cs6";
            }
            enum cs7 {
                value 56;
                description "cs7";
            }
        }
        description "";
        reference "";
    }

    typedef  CML_ACL_DSCP_T {
        type union {
            type CML_ACL_DSCP_ENUM_T {

            }
            type int8 {
                range "0..63";

            }
        }
        description "";
        reference "";
    }

    typedef  CML_ACL_PRECEDENCE_ENUM_T {
        type enumeration {
            enum routine {
                value 0;
                description "routine";
            }
            enum priority {
                value 1;
                description "priority";
            }
            enum immediate {
                value 2;
                description "immediate";
            }
            enum flash {
                value 3;
                description "flash";
            }
            enum flashoverride {
                value 4;
                description "flashoverride";
            }
            enum critical {
                value 5;
                description "critical";
            }
            enum internet {
                value 6;
                description "internet";
            }
            enum network {
                value 7;
                description "network";
            }
        }
        description "";
        reference "";
    }

    typedef  CML_ACL_PRECEDENCE_T {
        type union {
            type CML_ACL_PRECEDENCE_ENUM_T {

            }
            type int8 {
                range "0..7";

            }
        }
        description "";
        reference "";
    }

    typedef  CML_ACL_ICMP_OPTIONS_T {
        type enumeration {
            enum administratively-prohibited {
                value 1;
                description "administrativelyProhibited";
            }
            enum alternate-address {
                value 2;
                description "alternateAddress";
            }
            enum conversion-error {
                value 3;
                description "conversionError";
            }
            enum dod-host-prohibited {
                value 4;
                description "dodHostProhibited";
            }
            enum dod-net-prohibited {
                value 5;
                description "dodNetProhibited";
            }
            enum echo {
                value 6;
                description "echo";
            }
            enum echo-reply {
                value 7;
                description "echoReply";
            }
            enum general-parameter-problem {
                value 8;
                description "generalParameterProblem";
            }
            enum host-isolated {
                value 9;
                description "hostIsolated";
            }
            enum host-precedence-unreachable {
                value 10;
                description "hostPrecedenceUnreachable";
            }
            enum host-redirect {
                value 11;
                description "hostRedirect";
            }
            enum host-tos-redirect {
                value 12;
                description "hostTosRedirect";
            }
            enum host-tos-unreachable {
                value 13;
                description "hostTosUnreachable";
            }
            enum host-unknown {
                value 14;
                description "hostUnknown";
            }
            enum host-unreachable {
                value 15;
                description "hostUnreachable";
            }
            enum information-reply {
                value 16;
                description "informationReply";
            }
            enum information-request {
                value 17;
                description "informationRequest";
            }
            enum mask-reply {
                value 18;
                description "maskReply";
            }
            enum mask-request {
                value 19;
                description "maskRequest";
            }
            enum mobile-redirect {
                value 20;
                description "mobileRedirect";
            }
            enum net-redirect {
                value 21;
                description "netRedirect";
            }
            enum net-tos-redirect {
                value 22;
                description "netTosRedirect";
            }
            enum net-tos-unreachable {
                value 23;
                description "netTosUnreachable";
            }
            enum net-unreachable {
                value 24;
                description "netUnreachable";
            }
            enum network-unknown {
                value 25;
                description "networkUnknown";
            }
            enum no-room-for-option {
                value 26;
                description "noRoomForOption";
            }
            enum option-missing {
                value 27;
                description "optionMissing";
            }
            enum packet-too-big {
                value 28;
                description "packetTooBig";
            }
            enum parameter-problem {
                value 29;
                description "parameterProblem";
            }
            enum port-unreachable {
                value 30;
                description "portUnreachable";
            }
            enum precedence-unreachable {
                value 31;
                description "precedenceUnreachable";
            }
            enum protocol-unreachable {
                value 32;
                description "protocolUnreachable";
            }
            enum reassembly-timeout {
                value 33;
                description "reassemblyTimeout";
            }
            enum redirect {
                value 34;
                description "redirect";
            }
            enum router-advertisement {
                value 35;
                description "routerAdvertisement";
            }
            enum router-solicitation {
                value 36;
                description "routerSolicitation";
            }
            enum source-quench {
                value 37;
                description "sourceQuench";
            }
            enum source-route-failed {
                value 38;
                description "sourceRouteFailed";
            }
            enum time-exceeded {
                value 39;
                description "timeExceeded";
            }
            enum timestamp-reply {
                value 40;
                description "timestampReply";
            }
            enum timestamp-request {
                value 41;
                description "timestampRequest";
            }
            enum traceroute {
                value 42;
                description "traceroute";
            }
            enum ttl-exceeded {
                value 43;
                description "ttlExceeded";
            }
            enum unreachable {
                value 44;
                description "unreachable";
            }
        }
        description "";
        reference "";
    }

    typedef  CML_ACL_ICMPV6_OPTIONS_T {
        type enumeration {
            enum beyond-scope {
                value 0;
                description "beyond-scope";
            }
            enum destination-unreachable {
                value 1;
                description "destination-unreachable";
            }
            enum echo-reply {
                value 2;
                description "echo-reply";
            }
            enum echo-request {
                value 3;
                description "echo-request";
            }
            enum header {
                value 4;
                description "header";
            }
            enum hop-limit {
                value 5;
                description "hop-limit";
            }
            enum mld-query {
                value 6;
                description "mld-query";
            }
            enum mld-reduction {
                value 7;
                description "mld-reduction";
            }
            enum mld-report {
                value 8;
                description "mld-report";
            }
            enum nd-na {
                value 9;
                description "nd-na";
            }
            enum nd-ns {
                value 10;
                description "nd-ns";
            }
            enum next-header {
                value 11;
                description "next-header";
            }
            enum no-admin {
                value 12;
                description "no-admin";
            }
            enum no-route {
                value 13;
                description "no-route";
            }
            enum packet-too-big {
                value 14;
                description "packet-too-big";
            }
            enum parameter-option {
                value 15;
                description "parameter-option";
            }
            enum parameter-problem {
                value 16;
                description "parameter-problem";
            }
            enum port-unreachable {
                value 17;
                description "port-unreachable";
            }
            enum reassembly-timeout {
                value 18;
                description "reassembly-timeout";
            }
            enum redirect {
                value 19;
                description "redirect";
            }
            enum renum-command {
                value 20;
                description "renum-command";
            }
            enum renum-result {
                value 21;
                description "renum-result";
            }
            enum renum-seq-number {
                value 22;
                description "renum-seq-number";
            }
            enum router-advertisement {
                value 23;
                description "router-advertisement";
            }
            enum router-renumbering {
                value 24;
                description "router-renumbering";
            }
            enum router-solicitation {
                value 25;
                description "router-solicitation";
            }
            enum time-exceeded {
                value 26;
                description "time-exceeded";
            }
            enum unreachable {
                value 27;
                description "unreachable";
            }
        }
        description "";
        reference "";
    }

    typedef  CML_ACL_TCP_FLAGS_T {
        type bits {
            bit fin {
                position 0;
                description "fin";
            }
            bit syn {
                position 1;
                description "syn";
            }
            bit rst {
                position 2;
                description "rst";
            }
            bit psh {
                position 3;
                description "psh";
            }
            bit ack {
                position 4;
                description "ack";
            }
            bit urg {
                position 5;
                description "urg";
            }
            bit established {
                position 6;
                description "established";
            }
        }
        description "";
        reference "";
    }

    typedef  CML_ACL_ANY_MAC_ADDR_T {
        type union {
            type CML_ACL_ANY_T {

            }
            type CML_MAC_ADDR_T {

            }
        }
        description "";
        reference "";
    }

    typedef  CML_ACL_ETHER_TYPE_ENUM_T {
        type enumeration {
            enum ipv4 {
                value 2048;
                description "ipv4";
            }
            enum arp {
                value 2054;
                description "arp";
            }
            enum vines-echo {
                value 2991;
                description "vines-echo";
            }
            enum etype-6000 {
                value 24576;
                description "etype-6000";
            }
            enum mop-dump {
                value 24577;
                description "mop-dump";
            }
            enum mop-console {
                value 24578;
                description "mop-console";
            }
            enum decnet-iv {
                value 24579;
                description "decnet-iv";
            }
            enum lat {
                value 24580;
                description "lat";
            }
            enum diagnostic {
                value 24581;
                description "diagnostic";
            }
            enum lavc-sca {
                value 24583;
                description "lavc-sca";
            }
            enum etype-8042 {
                value 32834;
                description "etype-8042";
            }
            enum appletalk {
                value 32923;
                description "appletalk";
            }
            enum aarp {
                value 33011;
                description "aarp";
            }
            enum ipv6 {
                value 34525;
                description "ipv6";
            }
            enum mpls {
                value 34886;
                description "mpls";
            }
        }
        description "";
        reference "";
    }

    typedef  CML_ACL_ETHER_TYPE_T {
        type union {
            type CML_ACL_ETHER_TYPE_ENUM_T {

            }
            type CML_STRING_T {

            }
        }
        description "";
        reference "";
    }

    typedef  CML_ACL_TYPES_T {
        type enumeration {
            enum mac {
                value 1;
                description "Configure MAC parameters";
            }
            enum ip {
                value 3;
                description "Internet Protocol (IP)";
            }
            enum ipv6 {
                value 4;
                description "Internet Protocol version 6 (IPv6)";
            }
            enum arp {
                value 5;
                description "Configure ARP parameters";
            }
        }
        description "";
        reference "";
    }

    typedef  CML_VTY_ACL_TYPES_T {
        type enumeration {
            enum ip {
                value 0;
                description "Internet Protocol (IP)";
            }
            enum ipv6 {
                value 1;
                description "Internet Protocol version 6 (IPv6)";
            }
        }
        description "";
        reference "";
    }

    typedef  CML_ACL_PACKET_DIR_T {
        type enumeration {
            enum in {
                value 0;
                description "Specify to filter incoming packets";
            }
            enum out {
                value 1;
                description "Specify to filter outgoing packets";
            }
        }
        description "";
        reference "";
    }

    typedef  CML_AUTH_PORT_SEC_MODE {
        type enumeration {
            enum filter {
                value 0;
                description "Set port to filter mode";
            }
            enum shutdown {
                value 1;
                description "Set port to disable mode";
            }
        }
        description "";
        reference "";
    }

    typedef  CML_AUTH_CTRL_DIR_T {
        type enumeration {
            enum in {
                value 0;
                description "Discard receive packets from supplicant";
            }
            enum both {
                value 1;
                description "Discard receive and transmit packets from supplicant";
            }
        }
        description "";
        reference "";
    }

    typedef  CML_AUTH_PORT_CTRL {
        type enumeration {
            enum force-unauthorized {
                value 0;
                description "Force port state to unauthorized";
            }
            enum force-authorized {
                value 1;
                description "Force port state to authorized";
            }
            enum auto {
                value 2;
                description "Allow port client to negotiate authentication";
            }
        }
        description "";
        reference "";
    }

    typedef  CML_DOT1X_DEBUG_T {
        type bits {
            bit event {
                position 0;
                description "802.1X events";
            }
            bit timer {
                position 1;
                description "802.1X timer";
            }
            bit packet {
                position 2;
                description "802.1X packets";
            }
            bit nsm {
                position 3;
                description "802.1X NSM information";
            }
        }
        description "";
        reference "";
    }

    typedef  CML_RIP_DEBUG_T {
        type bits {
            bit events {
                position 1;
                description "RIP events";
            }
            bit packet {
                position 2;
                description "RIP packets";
            }
            bit packet-send {
                position 3;
                description "RIP packets,RIP send packets";
            }
            bit packet-recv {
                position 4;
                description "RIP packets, RIP receive packets";
            }
            bit packet-detail {
                position 5;
                description "RIP packets, Detailed information display";
            }
            bit packet-send-detail {
                position 6;
                description "RIP packets, RIP send packets, Detailed information display";
            }
            bit packet-recv-detail {
                position 7;
                description "RIP packets, RIP receive packets, Detailed information display";
            }
            bit nsm {
                position 8;
                description "RIP NSM information";
            }
            bit rib {
                position 9;
                description "RIP RIB information";
            }
            bit bfd {
                position 10;
                description "RIP BFD information";
            }
        }
        description "";
        reference "";
    }

    typedef  CML_RIP_ROUTE_T {
        type enumeration {
            enum kernel {
                value 1;
                description "Kernel routes";
            }
            enum connected {
                value 2;
                description "Connected";
            }
            enum static {
                value 3;
                description "Static routes";
            }
            enum isis {
                value 4;
                description "ISO IS-IS";
            }
            enum ospf {
                value 5;
                description "Open Shortest Path First (OSPF)";
            }
            enum bgp {
                value 6;
                description "Border Gateway Protocol (BGP)";
            }
            enum rip {
                value 7;
                description "Routing Information Protocol (RIP)";
            }
            enum all {
                value 8;
                description "all of the RIP routing tabl";
            }
        }
        description "";
        reference "";
    }

    typedef  CML_RIP_INSTANCE_T {
        type enumeration {
            enum rip {
                value 1;
                description "Routing Information Protocol (RIP)";
            }
        }
        description "";
        reference "";
    }

    typedef  CML_RIP_DIRECTION_T {
        type enumeration {
            enum in {
                value 0;
                description "For incoming updates";
            }
            enum out {
                value 1;
                description "For outgoing updates";
            }
        }
        description "";
        reference "";
    }

    typedef  CML_RIP_DIST_TYPE_T {
        type enumeration {
            enum in {
                value 0;
                description "Filter incoming routing updates";
            }
            enum out {
                value 1;
                description "Filter incoming routing updates";
            }
        }
        description "";
        reference "";
    }

    typedef  CML_RIP_METRIC_T {
        type enumeration {
            enum disable {
                value 0;
                description "Disables updating metric consistent with Cisco";
            }
            enum enable {
                value 1;
                description "Enables updating metric consistent with Cisco";
            }
        }
        description "";
        reference "";
    }

    typedef  CML_RIP_AUTH_MODE_T {
        type enumeration {
            enum text {
                value 2;
                description "Clear text authentication";
            }
            enum md5 {
                value 3;
                description "Keyed message digest";
            }
        }
        description "";
        reference "";
    }

    typedef  CML_RIP_SPLIT_HORIZON_T {
        type enumeration {
            enum split-horizon {
                value 0;
                description "Perform split horizon";
            }
            enum split-horizon-poisoned {
                value 1;
                description "Perform poisoned reverse";
            }
        }
        description "";
        reference "";
    }

    typedef  CML_RIP_DEFAULT_ORIGINATE_T {
        type enumeration {
            enum originate {
                value 0;
                description "Distribute a default route";
            }
            enum originate-always {
                value 1;
                description "Distribute a default route,Always advertise default route";
            }
        }
        description "";
        reference "";
    }

    typedef  CML_RIP_RECV_VERSION_TYPE_T {
        type enumeration {
            enum 1 {
                value 1;
                description "RIP version 1";
            }
            enum 2 {
                value 2;
                description "RIP version 2";
            }
            enum 1-2 {
                value 3;
                description "RIP version 1, RIP version 2";
            }
            enum 2-1 {
                value 5;
                description "RIP version 2, RIP version 1";
            }
        }
        description "";
        reference "";
    }

    typedef  CML_RIP_SEND_VERSION_TYPE_T {
        type enumeration {
            enum 1 {
                value 1;
                description "RIP version 1";
            }
            enum 2 {
                value 2;
                description "RIP version 2";
            }
            enum 1-2 {
                value 3;
                description "RIP version 1, RIP version 2";
            }
            enum 1-compatible {
                value 4;
                description "RIPv1-compatible";
            }
            enum 2-1 {
                value 5;
                description "RIP version 2, RIP version 1";
            }
        }
        description "";
        reference "";
    }

    typedef  CML_RIP_REDIST_PROTOS_T {
        type enumeration {
            enum kernel {
                value 0;
                description "Kernel routes";
            }
            enum connected {
                value 1;
                description "Connected";
            }
            enum static {
                value 2;
                description "Static routes";
            }
            enum ospf {
                value 3;
                description "Open Shortest Path First (OSPF)";
            }
            enum isis {
                value 4;
                description "ISO IS-IS";
            }
            enum bgp {
                value 5;
                description "Border Gateway Protocol (BGP)";
            }
        }
        description "";
        reference "";
    }

    typedef  CML_RIP_VRF_REDIST_PROTOS_T {
        type enumeration {
            enum connected {
                value 1;
                description "Connected";
            }
            enum static {
                value 2;
                description "Static routes";
            }
            enum ospf {
                value 3;
                description "Open Shortest Path First (OSPF)";
            }
            enum bgp {
                value 5;
                description "Border Gateway Protocol (BGP)";
            }
        }
        description "";
        reference "";
    }

    typedef  CML_NSM_LOAD_TRILL_T {
        type enumeration {
            enum outer-l2 {
                value 1;
                description "TRILL outer l2 header (outer SMAC, outer DMAC, outer VLAN)";
            }
            enum inner-l2 {
                value 2;
                description "TRILL inner l2 header (inner SMAC, inner DMAC, inner VLAN, trill tunnel)";
            }
            enum inner-l3 {
                value 3;
                description "TRILL inner l3 header (inner SIP, inner DIP, L4 srx/dest port)";
            }
        }
        description "";
        reference "";
    }

    typedef  CML_NSM_LOAD_HASH_T {
        type enumeration {
            enum crc16-bisync {
                value 0;
                description "16-bit CRC16 using the BISYNC Polynomial (DEFAULT)";
            }
            enum crc16-ccitt {
                value 1;
                description "16-bit CRC16 using the CCITT Polynomial";
            }
            enum crc32-lo {
                value 2;
                description "16 LSBs of computated CRC32";
            }
            enum crc32-hi {
                value 3;
                description "16 MSBs of computated CRC32";
            }
        }
        description "";
        reference "";
    }

    typedef  CML_NSM_HARDWARE_PORTMODE_T {
        type enumeration {
            enum 4X10g {
                value 1;
                description "split to 4X10g";
            }
        }
        description "";
        reference "";
    }

    typedef  CML_NSM_BREAKOUT_TYPE_T {
        type enumeration {
            enum 4X10g {
                value 1;
                description "split to 4X10g";
            }
            enum 4X25g {
                value 2;
                description "split to 4X25g";
            }
            enum 2X50g {
                value 3;
                description "split to 2X50g";
            }
        }
        description "";
        reference "";
    }

    typedef  CML_NSM_PORT_GROUP_SPEED_T {
        type enumeration {
            enum 10g {
                value 1;
                description "port group speed 10g";
            }
        }
        description "";
        reference "";
    }

    typedef  CML_NSM_HARDWARE_PROFILE_PORTMODE_BUNDLE_T {
        type enumeration {
            enum 4X10g {
                value 6;
                description "unbundle 40g port";
            }
            enum 40g {
                value 7;
                description "bundle four 10g ports into 40g por";
            }
        }
        description "";
        reference "";
    }

    typedef  CML_LACP_DEBUG_TYPE_T {
        type bits {
            bit event {
                position 0;
                description "event - echo events to console";
            }
            bit cli {
                position 1;
                description "cli - echo commands to console";
            }
            bit timer {
                position 2;
                description "timer - echo timer expiry to console";
            }
            bit sync {
                position 3;
                description "sync - echo synchronization to console";
            }
            bit packet {
                position 4;
                description "packet - echo packet contents to console";
            }
            bit tx {
                position 5;
                description "tx - echo transmission of lacpdus to console";
            }
            bit rx {
                position 6;
                description "rx - echo receving of lacpdus to console";
            }
            bit ha {
                position 7;
                description "ha - echo High availability events to console";
            }
        }
        description "";
        reference "";
    }

    typedef  CML_ALLOWEDVLAN_T {
        type enumeration {
            enum none {
                value 1;
                description "Add a VLAN to Xmit/Tx through the Layer2 interface";
            }
            enum all {
                value 2;
                description "Allow no VLANs to Xmit/Rx through the Layer2 interface";
            }
        }
        description "";
        reference "";
    }

    typedef  CML_SWVLANOPER_T {
        type enumeration {
            enum remove {
                value 1;
                description "Remove a VLAN to Xmit/Rx through the Layer2 interface";
            }
            enum except {
                value 2;
                description "Allow all VLANs except VID to Xmit/Rx through the Layer2 interface";
            }
        }
        description "";
        reference "";
    }

    typedef  CML_DHCPSNOOP_DEBUG_T {
        type bits {
            bit event {
                position 0;
                description "enable event debugs";
            }
            bit rx {
                position 1;
                description "enable rx debugs";
            }
            bit tx {
                position 2;
                description "enable tx debugs";
            }
            bit packet {
                position 3;
                description "enable packet debug";
            }
        }
        description "";
        reference "";
    }

    typedef  CML_DHCP_VALIDATION_T {
        type enumeration {
            enum src-mac {
                value 0;
                description "source mac validation";
            }
            enum dst-mac {
                value 1;
                description "destination mac validation";
            }
            enum ip {
                value 2;
                description "arp ip address validation";
            }
        }
        description "";
        reference "";
    }

    typedef  CML_COMMON_ENABLE_DISABLE_T {
        type enumeration {
            enum Disabled {
                value 0;
                description "Disabled";
            }
            enum Enabled {
                value 1;
                description "Enabled";
            }
        }
        description "";
        reference "";
    }

    typedef  CML_COMMON_FLAGS_T {
        type enumeration {
            enum False {
                value 0;
                description "None";
            }
            enum True {
                value 1;
                description "None";
            }
        }
        description "";
        reference "";
    }

    typedef  CML_UNI_ENNI_T {
        type enumeration {
            enum uni {
                value 1;
                description "Configure UNI Parameter";
            }
            enum enni {
                value 2;
                description "Configure ENNI Parameter";
            }
        }
        description "";
        reference "";
    }

    typedef  CML_UNI_ENNI_TYPE_T {
        type enumeration {
            enum leaf {
                value 1;
                description "Leaf";
            }
            enum root {
                value 2;
                description "Root";
            }
            enum trunk {
                value 3;
                description "Trunk";
            }
        }
        description "";
        reference "";
    }

    typedef  CML_UNI_SERVICE_T {
        type enumeration {
            enum bundle {
                value 1;
                description "UNI supports bundling without multiplexing";
            }
            enum all-to-one {
                value 2;
                description "UNI supports all to one bundling";
            }
            enum multiplex {
                value 3;
                description "UNI supports multiplexing without bundling";
            }
        }
        description "";
        reference "";
    }

    typedef  CML_UNI_ENABLE_DISABLE_T {
        type enumeration {
            enum disable {
                value 0;
                description "uni type disable will set the default uni type";
            }
            enum enable {
                value 1;
                description "uni type enable will update the uni type";
            }
        }
        description "";
        reference "";
    }

    typedef  CML_OEP_MAP_TYPE_T {
        type enumeration {
            enum uni-oep {
                value 2;
                description "Configure OVC endpoint map";
            }
            enum enni-oep {
                value 4;
                description "Configure OEP mapping table";
            }
        }
        description "";
        reference "";
    }

    typedef  CML_BIND_T {
        type enumeration {
            enum delete {
                value 0;
                description "Command delete rule from a group";
            }
            enum add {
                value 1;
                description "Command add rule to a group";
            }
        }
        description "";
        reference "";
    }

    typedef  CML_ETHERTYPE_T {
        type enumeration {
            enum ETHERTYPE {
                value 0;
                description "Valid ethernet protocol number (0x600-0xFFFF)";
            }
            enum ip {
                value 2048;
                description "IP (0x0800)";
            }
            enum x25 {
                value 2053;
                description "CCITT X.25 (0x0805)";
            }
            enum arp {
                value 2054;
                description "Address Resolution Protocol (0x0806)";
            }
            enum g8bpqx25 {
                value 2303;
                description "G8BPQ AX.25 (0x08FF)";
            }
            enum ieeepup {
                value 2560;
                description "Xerox IEEE802.3 PUP (0x0a00)";
            }
            enum ieeeaddrtrans {
                value 2561;
                description "Xerox IEEE802.3 PUP Address Translation (0x0a01)";
            }
            enum dec {
                value 24576;
                description "DEC Assigned (0x6000)";
            }
            enum decdnadumpload {
                value 24577;
                description "DEC DNA Dump/Load (0x6001)";
            }
            enum decdnaremoteconsole {
                value 24578;
                description "DEC DNA Remote Console (0x6002)";
            }
            enum decdnarouting {
                value 24579;
                description "DEC DNA Routing (0x6003)";
            }
            enum declat {
                value 24580;
                description "DEC LAT (0x6004)";
            }
            enum decdiagnostics {
                value 24581;
                description "DEC Diagnostics (0x6005)";
            }
            enum rarp {
                value 32821;
                description "Reverse Address Resolution Protocol (0x8035)";
            }
            enum atalkddp {
                value 32923;
                description "Appletalk DDP (0x809B)";
            }
            enum atalkaarp {
                value 33011;
                description "Appletalk AARP (0x80F3)";
            }
            enum ipx {
                value 33079;
                description "IPX (0x8137)";
            }
            enum ipv6 {
                value 34525;
                description "IPv6 (0x86DD)";
            }
            enum atmmulti {
                value 34892;
                description "MultiProtocol Over ATM (0x884c)";
            }
            enum pppdiscovery {
                value 34915;
                description "PPPoE discovery (0x8863)";
            }
            enum pppsession {
                value 34916;
                description "PPPoE session (0x8864)";
            }
            enum atmtransport {
                value 34948;
                description "Frame-based ATM Transport (0x8884)";
            }
        }
        description "";
        reference "";
    }

    typedef  CML_CE_SVLAN_T {
        type enumeration {
            enum ce-vlan {
                value 1;
                description "Preservation for Customer Edge VLAN";
            }
            enum svlan {
                value 2;
                description "Preservation for Service VLAN";
            }
        }
        description "";
        reference "";
    }

    typedef  CML_OVC_TYPE_T {
        type enumeration {
            enum preserve-cos {
                value 1;
                description "Preserve Cos";
            }
            enum preserve-vlanid {
                value 2;
                description "Preserve vlan-id";
            }
        }
        description "";
        reference "";
    }

    typedef  CML_MSTP_ENUM_T {
        type enumeration {
            enum te-msti {
                value 65;
                description "MSTI to be the traffic engineering MSTI instance";
            }
            enum instance-spbm {
                value 4092;
                description "instance,spbm instance";
            }
            enum instance-spbv {
                value 4093;
                description "instance,spbv instance";
            }
        }
        description "";
        reference "";
    }

    typedef  CML_MSTP_RANGE_T {

        type uint16{
         range 1..63;
        }
        description "";
        reference "";
    }

    typedef  CML_MSTP_INSTANCE_T {
        type union {
            type CML_MSTP_ENUM_T {

            }
            type CML_MSTP_RANGE_T {

            }
        }
        description "";
        reference "";
    }

    typedef  CML_VXLAN_PORT_T {
        type enumeration {
            enum port-only {
                value 1;
                description "Configures the port access interface";
            }
        }
        description "";
        reference "";
    }

    typedef  CML_VXLAN_HOST_T {
        type enumeration {
            enum Dynamic {
                value 0;
                description "Host type is Dynamic";
            }
            enum Static-Local {
                value 1;
                description "Host type is Static Local";
            }
            enum Remote-Dynamic {
                value 2;
                description "Host type is Evpn Dynamic";
            }
            enum Remote-Static {
                value 3;
                description "Host type is Evpn Static";
            }
            enum Static-Remote {
                value 4;
                description "Host type is Static Remote";
            }
        }
        description "";
        reference "";
    }

    typedef  CML_VXLAN_DF_STATUS_T {
        type enumeration {
            enum --- {
                value 0;
                description "Default DF status";
            }
            enum DF {
                value 1;
                description "Designated Forwarder";
            }
            enum NON-DF {
                value 2;
                description "Non Designated Forwarder";
            }
        }
        description "";
        reference "";
    }

    typedef  CML_VXLAN_STATIC_HOST_STATE_T {
        type enumeration {
            enum Inactive {
                value 1;
                description "static host state Inactive";
            }
            enum Active {
                value 2;
                description "static host state Active";
            }
            enum Conflict {
                value 4;
                description "static host state Conflict";
            }
            enum Learnt-Conflict {
                value 8;
                description "static host state Learnt Conflict";
            }
            enum Discard-Inactive {
                value 16;
                description "static host state Discard Inactive";
            }
        }
        description "";
        reference "";
    }

    typedef  CML_CMM_CPU_TYPE_T {
        type enumeration {
            enum cpu-usage1 {
                value 1;
                description "Set CPU Usage for past 1 min";
            }
            enum cpu-usage5 {
                value 5;
                description "Set CPU Usage for past 5 min";
            }
            enum cpu-usage15 {
                value 15;
                description "Set CPU Usage for past 15 min";
            }
        }
        description "";
        reference "";
    }

    typedef  CML_CMM_TRANS_TYPE_T {
        type enumeration {
            enum sfp {
                value 1;
                description "trans type sfp";
            }
            enum qsfp {
                value 2;
                description "trans type qsfp";
            }
            enum unknown {
                value 3;
                description "trans type unknown";
            }
        }
        description "";
        reference "";
    }

    typedef  CML_CMM_TRANS_IDENTIFIER_T {
        type enumeration {
            enum unknown {
                value 1;
                description "trans identifier unknown";
            }
            enum gbic {
                value 2;
                description "trans identifier gbic";
            }
            enum soldered-to-motherboard {
                value 3;
                description "trans identifier soldered-to-motherboard";
            }
            enum sfp-or-sfpplus-or-sfp28 {
                value 4;
                description "trans identifier sfp-or-sfpplus-or-sfp28";
            }
            enum xbi-300pin {
                value 5;
                description "trans identifier xbi-300pin";
            }
            enum xenpak {
                value 6;
                description "trans identifier xenpak";
            }
            enum xep {
                value 7;
                description "trans identifier xep";
            }
            enum xff {
                value 8;
                description "trans identifier xff";
            }
            enum xfpe {
                value 9;
                description "trans identifier xfpe";
            }
            enum xpak {
                value 10;
                description "trans identifier xpak";
            }
            enum x2 {
                value 11;
                description "trans identifier x2";
            }
            enum dwdmsfp-or-dwdmsfpplus {
                value 12;
                description "trans identifier dwdmsfp-or-dwdmsfpplus";
            }
            enum qsfp {
                value 13;
                description "trans identifier qsfp";
            }
            enum qsfpplus-or-later {
                value 14;
                description "trans identifier qsfpplus-or-later";
            }
            enum cxp-or-later {
                value 15;
                description "trans identifier cxp-or-later";
            }
            enum shielded-mini-multilane-hd4x {
                value 16;
                description "trans identifier shielded-mini-multilane-hd4x";
            }
            enum shielded-mini-multilane-hd8x {
                value 17;
                description "trans identifier shielded-mini-multilane-hd8x";
            }
            enum qsfp28-or-later {
                value 18;
                description "trans identifier qsfp28-or-later";
            }
            enum cxp2-aka-cxp28-or-later {
                value 19;
                description "trans identifier cxp2-aka-cxp28-or-later";
            }
            enum cdfpstyle1-or-cdfpstyle2 {
                value 20;
                description "trans identifier cdfpstyle1-or-cdfpstyle2";
            }
            enum shielded-mini-multilane-hd4x-fanoutcable {
                value 21;
                description "trans identifier shielded-mini-multilane-hd4x-fanoutcable";
            }
            enum shielded-mini-multilane-hd8x-fanoutcable {
                value 22;
                description "trans identifier shielded-mini-multilane-hd8x-fanoutcable";
            }
            enum cdfpstyle3 {
                value 23;
                description "trans identifier cdfpstyle3";
            }
            enum microqsfp {
                value 24;
                description "trans identifier microqsfp";
            }
            enum qsfp-doubledensity-8x-pluggable-transceiver {
                value 25;
                description "trans identifier qsfp-doubledensity-8x-pluggable-transceiver";
            }
            enum reserved {
                value 26;
                description "trans identifier reserved";
            }
            enum vendor-specific {
                value 27;
                description "trans identifier vendor-specific";
            }
        }
        description "";
        reference "";
    }

    typedef  CML_CMM_TRANS_SFP_EXTENDED_IDENTIFIER_T {
        type enumeration {
            enum gbic-notspecified-or-compliant-with-moddef {
                value 1;
                description "sfp ext-identifier gbic-notspecified-or-compliant-with-moddef ";
            }
            enum gbic-compliant-with-moddef1 {
                value 2;
                description "sfp ext-identifier gbic-compliant-with-moddef1";
            }
            enum gbic-compliant-with-moddef2 {
                value 3;
                description "sfp ext-identifier gbic-compliant-with-moddef2";
            }
            enum gbic-compliant-with-moddef3 {
                value 4;
                description "sfp ext-identifier gbic-compliant-with-moddef3";
            }
            enum gbic-or-sfp-definedby-twowire-interfaceid-only {
                value 5;
                description "sfp ext-identifier gbic-or-sfp-definedby-twowire-interfaceid-only";
            }
            enum gbic-compliant-with-moddef5 {
                value 6;
                description "sfp ext-identifier gbic-compliant-with-moddef5";
            }
            enum gbic-compliant-with-moddef6 {
                value 7;
                description "sfp ext-identifier gbic-compliant-with-moddef6";
            }
            enum gbic-compliant-with-moddef7 {
                value 8;
                description "sfp ext-identifier gbic-compliant-with-moddef7";
            }
            enum unallocated {
                value 9;
                description "sfp ext-identifier unallocated";
            }
            enum unknown {
                value 10;
                description "sfp ext-identifier unknown";
            }
        }
        description "";
        reference "";
    }

    typedef  CML_CMM_QSFP_EXTENDED_IDENTIFIER_T {
        type bits {
            bit powerclass1-1dot5wmax {
                position 0;
                description "qsfp ext-identifier powerclass1-1dot5wmax";
            }
            bit powerclass2-2wmax {
                position 1;
                description "qsfp ext-identifier powerclass2-2wmax";
            }
            bit powerclass3-2dot5wmax {
                position 2;
                description "qsfp ext-identifier powerclass3-2dot5wmax";
            }
            bit powerclass4-3dot5wmax {
                position 3;
                description "qsfp ext-identifier powerclass4-3dot5wmax";
            }
            bit cleicode-present {
                position 4;
                description "qsfp ext-identifier cleicode-present";
            }
            bit cdrpresent-in-tx {
                position 5;
                description "qsfp ext-identifier cdrpresent-in-tx";
            }
            bit cdrpresent-in-rx {
                position 6;
                description "qsfp ext-identifier cdrpresent-in-rx";
            }
            bit powerclass5-4wmax {
                position 7;
                description "qsfp ext-identifier powerclass5-4wmax";
            }
            bit powerclass6-4dot5wmax {
                position 8;
                description "qsfp ext-identifier powerclass6-4dot5wmax";
            }
            bit powerclass7-5wmax {
                position 9;
                description "qsfp ext-identifier powerclass7-5wmax";
            }
        }
        description "";
        reference "";
    }

    typedef  CML_CMM_TRANS_CONNECTOR_TYPE_T {
        type enumeration {
            enum unknown {
                value 1;
                description "trans connector unknown";
            }
            enum subscriber-connector {
                value 2;
                description "trans connector subscriber-connector";
            }
            enum fibrechannel-style1-copperconnector {
                value 3;
                description "trans connector fibrechannel-style1-copperconnector";
            }
            enum fibrechannel-style2-copperconnector {
                value 4;
                description "trans connector fibrechannel-style2-copperconnector";
            }
            enum bayonet-or-threaded-neill-concelman {
                value 5;
                description "trans connector bayonet-or-threaded-neill-concelman";
            }
            enum fibrechannel-coaxheaders {
                value 6;
                description "trans connector fibrechannel-coaxheaders";
            }
            enum fiber-jack {
                value 7;
                description "trans connector fiber-jack";
            }
            enum lucent-connector {
                value 8;
                description "trans connector lucent-connector";
            }
            enum mechanical-transfer-registeredjack {
                value 9;
                description "trans connector mechanical-transfer-registeredjack";
            }
            enum multiple-optical {
                value 10;
                description "trans connector multiple-optical";
            }
            enum sg {
                value 11;
                description "trans connector sg";
            }
            enum optical-pigtail {
                value 12;
                description "trans connector optical-pigtail";
            }
            enum multifiber-paralleloptic-1x12 {
                value 13;
                description "trans connector multifiber-paralleloptic-1x12";
            }
            enum multifiber-paralleloptic-1x16 {
                value 14;
                description "trans connector multifiber-paralleloptic-1x16";
            }
            enum sfp-reserved {
                value 15;
                description "sfp trans connector reserved";
            }
            enum hssdcii {
                value 16;
                description "trans connector hssdcii";
            }
            enum copper-pigtail {
                value 17;
                description "trans connector copper-pigtail";
            }
            enum rj45 {
                value 18;
                description "trans connector rj45";
            }
            enum no-separable-connector {
                value 19;
                description "trans connector no-separable-connector";
            }
            enum mxc2-x16 {
                value 20;
                description "trans connector mxc2-x16";
            }
            enum qsfp-reserved {
                value 21;
                description "qsfp trans connector reserved";
            }
            enum vendor-specific {
                value 22;
                description "trans connector vendor-specific";
            }
        }
        description "";
        reference "";
    }

    typedef  CML_CMM_TRANS_ETH_COMPLIANCE_T {
        type enumeration {
            enum ec-unknown {
                value 1;
                description "trans compliance ec-unknown";
            }
            enum ec-10gbase-sr {
                value 2;
                description "trans compliance ec-10gbase-sr";
            }
            enum ec-10gbase-lr {
                value 3;
                description "trans compliance ec-10gbase-lr";
            }
            enum ec-10gbase-lrm {
                value 4;
                description "trans compliance ec-10gbase-lrm";
            }
            enum ec-10gbase-er {
                value 5;
                description "trans compliance ec-10gbase-er";
            }
            enum ec-1000base-sx {
                value 6;
                description "trans compliance ec-1000base-sx";
            }
            enum ec-1000base-lx {
                value 7;
                description "trans compliance ec-1000base-lx";
            }
            enum ec-1000base-cx {
                value 8;
                description "trans compliance ec-1000base-cx";
            }
            enum ec-1000base-t {
                value 9;
                description "trans compliance ec-1000base-t";
            }
            enum ec-100base-lx-or-lx10 {
                value 10;
                description "trans compliance ec-100base-lx-or-lx10";
            }
            enum ec-100base-fx {
                value 11;
                description "trans compliance ec-100base-fx";
            }
            enum ec-base-bx10 {
                value 12;
                description "trans compliance ec-base-bx10";
            }
            enum ec-base-px {
                value 13;
                description "trans compliance ec-base-px";
            }
            enum ec-40gbase-cr4 {
                value 14;
                description "trans compliance ec-40gbase-cr4";
            }
            enum ec-40gbase-sr4 {
                value 15;
                description "trans compliance ec-40gbase-sr4";
            }
            enum ec-40gbase-lr4 {
                value 16;
                description "trans compliance ec-40gbase-lr4";
            }
            enum ec-40g-activecable {
                value 17;
                description "trans compliance ec-40g-activecable";
            }
        }
        description "";
        reference "";
    }

    typedef  CML_CMM_TRANS_EXT_ETH_COMPLIANCE_T {
        type bits {
            bit eec-unspecified {
                position 0;
                description "trans ext compliance eec-unspecified";
            }
            bit eec-100g-activeopticalcable-or-25g-auic2maoc {
                position 1;
                description "trans ext compliance eec-100g-activeopticalcable-or-25g-auic2maoc";
            }
            bit eec-100gbase-sr4-or-25gbase-sr {
                position 2;
                description "trans ext compliance eec-100gbase-sr4-or-25gbase-sr";
            }
            bit eec-100gbase-lr4-or-25gbase-lr {
                position 3;
                description "trans ext compliance eec-100gbase-lr4-or-25gbase-lr";
            }
            bit eec-100gbase-er4-or-25gbase-er {
                position 4;
                description "trans ext compliance eec-100gbase-er4-or-25gbase-er";
            }
            bit eec-100gbase-sr10 {
                position 5;
                description "trans ext compliance eec-100gbase-sr10";
            }
            bit eec-100g-cwdm4 {
                position 6;
                description "trans ext compliance eec-100g-cwdm4";
            }
            bit eec-100g-psm4-parallelsmf {
                position 7;
                description "trans ext compliance eec-100g-psm4-parallelsmf";
            }
            bit eec-100g-activecoppercable-or-25g-auic2macc {
                position 8;
                description "trans ext compliance eec-100g-activecoppercable-or-25g-auic2macc";
            }
            bit eec-obsolete {
                position 9;
                description "trans ext compliance eec-obsolete";
            }
            bit eec-reserved {
                position 10;
                description "trans ext compliance eec-reserved";
            }
            bit eec-100gbase-cr4-or-25gbase-crca-l {
                position 11;
                description "trans ext compliance eec-100gbase-cr4-or-25gbase-crca-l";
            }
            bit eec-25gbase-crca-s {
                position 12;
                description "trans ext compliance eec-25gbase-crca-s";
            }
            bit eec-25gbase-crca-n {
                position 13;
                description "trans ext compliance eec-25gbase-crca-n";
            }
            bit eec-40gbase-er4 {
                position 14;
                description "trans ext compliance eec-40gbase-er4";
            }
            bit eec-4x10gbase-sr {
                position 15;
                description "trans ext compliance eec-4x10gbase-sr";
            }
            bit eec-40g-psm4-parallelsmf {
                position 16;
                description "trans ext compliance eec-40g-psm4-parallelsmf";
            }
            bit eec-g959-dot1-profilep1-i1-2d1 {
                position 17;
                description "trans ext compliance eec-g959-dot1-profilep1-i1-2d1";
            }
            bit eec-g959-dot1-profilep1-s1-2d2 {
                position 18;
                description "trans ext compliance eec-g959-dot1-profilep1-s1-2d2";
            }
            bit eec-g959-dot1-profilep1-l1-2d2 {
                position 19;
                description "trans ext compliance eec-g959-dot1-profilep1-l1-2d2";
            }
            bit eec-100gbase-t-with-sfi-electricalinterface {
                position 20;
                description "trans ext compliance eec-100gbase-t-with-sfi-electricalinterface";
            }
            bit eec-100g-clr4 {
                position 21;
                description "trans ext compliance eec-100g-clr4";
            }
            bit eec-100g-aoc-or-25g-auic2maoc {
                position 22;
                description "trans ext compliance eec-100g-aoc-or-25g-auic2maoc";
            }
            bit eec-100g-acc-or-25g-auic2macc {
                position 23;
                description "trans ext compliance eec-100g-acc-or-25g-auic2macc";
            }
            bit eec-100ge-dwdm2 {
                position 24;
                description "trans ext compliance eec-100ge-dwdm2";
            }
            bit null {
                position 31;
                description "NULL";
            }
        }
        description "";
        reference "";
    }

    typedef  CML_CMM_TRANS_SONET_COMPLIANCE_T {
        type bits {
            bit oc192-shortreach {
                position 0;
                description "oc192-shortreach";
            }
            bit sonet-reachspecifier-bit1 {
                position 1;
                description "sonet-reachspecifier-bit1";
            }
            bit sonet-reachspecifier-bit2 {
                position 2;
                description "sonet-reachspecifier-bit2";
            }
            bit oc48-longreach {
                position 3;
                description "oc48-longreach";
            }
            bit oc48-intermediatereach {
                position 4;
                description "oc48-intermediatereach";
            }
            bit oc48-shortreach {
                position 5;
                description "oc48-shortreach";
            }
            bit oc12-singlemode-longreach {
                position 6;
                description "oc12-singlemode-longreach";
            }
            bit oc12-singlemode-intermediatereach {
                position 7;
                description "oc12-singlemode-intermediatereach";
            }
            bit oc12-singlemode-shortreach {
                position 8;
                description "oc12-singlemode-shortreach";
            }
            bit oc3-singlemode-longreach {
                position 9;
                description "oc3-singlemode-longreach";
            }
            bit oc3-singlemode-intermediatereach {
                position 10;
                description "oc3-singlemode-intermediatereach";
            }
            bit oc3-singlemode-shortreach {
                position 11;
                description "oc3-singlemode-shortreach";
            }
            bit null {
                position 31;
                description "NULL";
            }
        }
        description "";
        reference "";
    }

    typedef  CML_CMM_TRANS_FIBER_CHANNEL_LINKLEN_T {
        type bits {
            bit short {
                position 0;
                description "short";
            }
            bit medium {
                position 1;
                description "medium";
            }
            bit intermediate {
                position 2;
                description "intermediate";
            }
            bit long {
                position 3;
                description "long";
            }
            bit verylong {
                position 4;
                description "very long";
            }
            bit null {
                position 31;
                description "NULL";
            }
        }
        description "";
        reference "";
    }

    typedef  CML_CMM_TRANS_FIBER_CHANNEL_TRANSMITTECH_T {
        type bits {
            bit shortwaveLaserLinearRx {
                position 0;
                description "shortwaveLaserLinearRx";
            }
            bit longwaveLaserLC {
                position 1;
                description "longwaveLaser LC";
            }
            bit electricalInter-Enclosure {
                position 2;
                description "electricalInter-Enclosure";
            }
            bit electricalIntra-Enclosure {
                position 3;
                description "electricalIntra-Enclosure";
            }
            bit shortwaveLaserWithOutOFC {
                position 4;
                description "shortwaveLaserWithOutOFC";
            }
            bit shortwaveLaserwithOFC {
                position 5;
                description "shortwaveLaserwithOFC";
            }
            bit longwaveLaserLL {
                position 6;
                description "longwaveLaser LL";
            }
            bit null {
                position 31;
                description "NULL";
            }
        }
        description "";
        reference "";
    }

    typedef  CML_CMM_TRANS_FIBER_CHANNEL_TRANSMITMEDIA_T {
        type bits {
            bit twinaxial-pair {
                position 0;
                description "twinaxial-pair";
            }
            bit twisted-pair {
                position 1;
                description "twisted-pair";
            }
            bit miniature-coax {
                position 2;
                description "miniature-coax";
            }
            bit video-coax {
                position 3;
                description "video-coax";
            }
            bit multi-mode62dot5m {
                position 4;
                description "multi-mode62dot5m";
            }
            bit multi-mode50m {
                position 5;
                description "multi-mode50m";
            }
            bit multi-mode50um {
                position 6;
                description "multi-mode50um";
            }
            bit single-mode {
                position 7;
                description "single-mode";
            }
            bit null {
                position 31;
                description "NULL";
            }
        }
        description "";
        reference "";
    }

    typedef  CML_CMM_TRANS_FIBER_CHANNEL_SPEED_T {
        type bits {
            bit fcs-3200mbps {
                position 0;
                description "fcs-3200mbps";
            }
            bit fcs-1600mbps {
                position 1;
                description "fcs-1600mbps";
            }
            bit fcs-1200mbps {
                position 2;
                description "fcs-1200mbps";
            }
            bit fcs-800mbps {
                position 3;
                description "fcs-800mbps";
            }
            bit fcs-400mbps {
                position 4;
                description "fcs-400mbps";
            }
            bit fcs-200mbps {
                position 5;
                description "fcs-200mbps";
            }
            bit fcs-100mbps {
                position 6;
                description "fcs-100mbps";
            }
            bit null {
                position 31;
                description "NULL";
            }
        }
        description "";
        reference "";
    }

    typedef  CML_CMM_TRANS_SFP_INIFINBAND_COMPLIANCE_T {
        type enumeration {
            enum ibc-1xsx {
                value 1;
                description "ibc-1xsx";
            }
            enum ibc-1xlx {
                value 2;
                description "ibc-1xlx";
            }
            enum ibc-1xcopperactive {
                value 3;
                description "ibc-1xcopperactive";
            }
            enum ibc-1xcopperpassive {
                value 4;
                description "ibc-1xcopperpassive";
            }
            enum ibc-unknown {
                value 5;
                description "ibc-unknown";
            }
            enum ibc-notapplicable {
                value 6;
                description "ibc-notapplicable";
            }
        }
        description "";
        reference "";
    }

    typedef  CML_CMM_TRANS_SFP_ESCON_COMPLIANCE_T {
        type enumeration {
            enum escon-mmf-1310nm-led {
                value 1;
                description "escon-mmf-1310nm-led";
            }
            enum escon-smf-1310nm-laser {
                value 2;
                description "escon-smf-1310nm-laser";
            }
            enum unknown {
                value 3;
                description "unknown";
            }
            enum notapplicable {
                value 4;
                description "notapplicable";
            }
        }
        description "";
        reference "";
    }

    typedef  CML_CMM_TRANS_SFP_PLUS_CABLE_TECH_T {
        type enumeration {
            enum active {
                value 1;
                description "active";
            }
            enum passive {
                value 2;
                description "passive";
            }
            enum unknown {
                value 3;
                description "unknown";
            }
            enum notapplicable {
                value 4;
                description "notapplicable";
            }
        }
        description "";
        reference "";
    }

    typedef  CML_CMM_TRANS_ENCODING_T {
        type enumeration {
            enum enc-unspecified {
                value 1;
                description "enc-unspecified";
            }
            enum enc-8b-or-10b {
                value 2;
                description "enc-8b-or-10b";
            }
            enum enc-4b-or-5b {
                value 3;
                description "enc-4b-or-5b";
            }
            enum enc-nrz {
                value 4;
                description "enc-nrz";
            }
            enum enc-manchester {
                value 5;
                description "enc-manchester";
            }
            enum enc-sonet-scrambled {
                value 6;
                description "enc-sonet-scrambled";
            }
            enum enc-64b-or-66b {
                value 7;
                description "enc-64b-or-66b";
            }
            enum enc-256b-or-257b {
                value 8;
                description "enc-256b-or-257b";
            }
            enum enc-pam4 {
                value 9;
                description "enc-pam4";
            }
            enum enc-reserved {
                value 10;
                description "enc-reserved";
            }
        }
        description "";
        reference "";
    }

    typedef  CML_CMM_TRANS_DDM_SUPPORT_T {
        type enumeration {
            enum yes {
                value 1;
                description "DDM is supported";
            }
            enum no {
                value 2;
                description "DDM is not supported";
            }
            enum unknown {
                value 3;
                description "DDM support unknown";
            }
        }
        description "";
        reference "";
    }

    typedef  CML_CMM_TRANS_PRESENCE_T {
        type enumeration {
            enum present {
                value 1;
                description "transceiver present";
            }
            enum notpresent {
                value 2;
                description "transceiver not present";
            }
            enum unknown {
                value 3;
                description "unknown";
            }
        }
        description "";
        reference "";
    }

    typedef  CML_CMM_TRANS_TX_RX_STATE_T {
        type enumeration {
            enum enable {
                value 1;
                description "enabled";
            }
            enum disable {
                value 2;
                description "disabled";
            }
            enum unknown {
                value 3;
                description "state unknown";
            }
        }
        description "";
        reference "";
    }

    typedef  CML_CMM_TRANS_RESET_STATE_T {
        type enumeration {
            enum normal {
                value 1;
                description "normal";
            }
            enum reset {
                value 2;
                description "reset";
            }
            enum unknown {
                value 3;
                description "State unknown";
            }
        }
        description "";
        reference "";
    }

    typedef  CML_CMM_TRANS_POWER_MODE_T {
        type enumeration {
            enum low {
                value 1;
                description "trans power low";
            }
            enum high {
                value 2;
                description "trans power high";
            }
            enum unknown {
                value 3;
                description "trans power state unknown";
            }
        }
        description "";
        reference "";
    }

    typedef  CML_CMM_TRANS_SFP_OPTIONS_IMPLEMENTED_T {
        type bits {
            bit reserved {
                position 0;
                description "reserved";
            }
            bit power-level3 {
                position 1;
                description "power-level3";
            }
            bit paging {
                position 2;
                description "paging";
            }
            bit internal-retimer-or-cdr {
                position 3;
                description "internal-retimer-or-cdr";
            }
            bit cooled-laser-transmitter {
                position 4;
                description "cooled-laser-transmitter";
            }
            bit power-level2 {
                position 5;
                description "power-level2";
            }
            bit power-level1 {
                position 6;
                description "power-level1";
            }
            bit linear-receiver-output {
                position 7;
                description "linear-receiver-output";
            }
            bit receiver-decision-threshold {
                position 8;
                description "receiver-decision-threshold";
            }
            bit transmitter-wavelength-or-tunable-frequency {
                position 9;
                description "transmitter-wavelength-or-tunable-frequency";
            }
            bit rate-select {
                position 10;
                description "rate-select";
            }
            bit tx-disable {
                position 11;
                description "tx-disable";
            }
            bit tx-fault {
                position 12;
                description "tx-fault";
            }
            bit rx-loss-of-signal {
                position 13;
                description "rx-loss-of-signal";
            }
            bit null {
                position 31;
                description "NULL";
            }
        }
        description "";
        reference "";
    }

    typedef  CML_CMM_TRANS_QSFP_OPTIONS_IMPLEMENTED_T {
        type bits {
            bit reserved {
                position 0;
                description "reserved";
            }
            bit tx-inputequalization-auto-adaptive {
                position 1;
                description "tx-inputequalization-auto-adaptive";
            }
            bit tx-inputequalization-fixed-programmable {
                position 2;
                description "tx-inputequalization-fixed-programmable";
            }
            bit tx-outputemphasis-fixed-programmable {
                position 3;
                description "tx-outputemphasis-fixed-programmable";
            }
            bit tx-outputamplitude-fixed-programmable {
                position 4;
                description "tx-outputamplitude-fixed-programmable";
            }
            bit tx-cdr-on-or-off-controllable {
                position 5;
                description "tx-cdr-on-or-off-controllable";
            }
            bit tx-cdr-on-or-off-fixed {
                position 6;
                description "tx-cdr-on-or-off-fixed";
            }
            bit rx-cdr-on-or-off-controllable {
                position 7;
                description "rx-cdr-on-or-off-controllable";
            }
            bit rx-cdr-on-or-off-fixed {
                position 8;
                description "rx-cdr-on-or-off-fixed";
            }
            bit tx-cdr-lossoflock {
                position 9;
                description "tx-cdr-lossoflock";
            }
            bit rx-cdr-lossoflock {
                position 10;
                description "rx-cdr-lossoflock";
            }
            bit rx-squelch-disable {
                position 11;
                description "rx-squelch-disable";
            }
            bit rx-output-disable {
                position 12;
                description "rx-output-disable";
            }
            bit tx-squelch-disable {
                position 13;
                description "tx-squelch-disable";
            }
            bit tx-squelch {
                position 14;
                description "tx-squelch";
            }
            bit page2-provided {
                position 15;
                description "page2-provided";
            }
            bit page1-provided {
                position 16;
                description "page1-provided";
            }
            bit rateselect-controllable {
                position 17;
                description "rateselect-controllable";
            }
            bit rateselect-fixed {
                position 18;
                description "rateselect-fixed";
            }
            bit tx-disable {
                position 19;
                description "tx-disable";
            }
            bit tx-fault {
                position 20;
                description "tx-fault";
            }
            bit tx-squelch-to-reduce-pave {
                position 21;
                description "tx-squelch-to-reduce-pave";
            }
            bit tx-squelch-to-reduce-oma {
                position 22;
                description "tx-squelch-to-reduce-oma";
            }
            bit tx-loss-of-signal {
                position 23;
                description "tx-loss-of-signal";
            }
            bit null {
                position 31;
                description "NULL";
            }
        }
        description "";
        reference "";
    }

    typedef  CML_CMM_TRANS_TX_RX_POWER_SUPPORTED_T {
        type enumeration {
            enum supported {
                value 1;
                description "trans tx/rx power supported";
            }
            enum unsupported {
                value 2;
                description "trans tx/rx power not supported";
            }
            enum notapplicable {
                value 3;
                description "trans tx/rx power support notapplicable";
            }
            enum unknown {
                value 4;
                description "trans tx/rx power support unknown";
            }
        }
        description "";
        reference "";
    }

    typedef  CML_CMM_TRANS_DDM_STATUS_T {
        type enumeration {
            enum active {
                value 1;
                description "ddm status is active";
            }
            enum activeunsupported {
                value 2;
                description "ddm status is active but transceiver is unsupported";
            }
            enum inactive {
                value 3;
                description "ddm status is inactive";
            }
            enum inactiveunsupported {
                value 4;
                description "ddm status is inactive and transceiver is unsupported";
            }
            enum notapplicable {
                value 5;
                description "ddm status is not applicable";
            }
            enum unknown {
                value 6;
                description "ddm status is unknown";
            }
        }
        description "";
        reference "";
    }

    typedef  CML_CMM_POWER_SUPPLY_OPERSTATUS_T {
        type enumeration {
            enum notpresent {
                value 1;
                description "psu not present";
            }
            enum running {
                value 2;
                description "psu running";
            }
            enum faulty {
                value 3;
                description "psu faulty";
            }
            enum unknown {
                value 4;
                description "psu status unknown";
            }
        }
        description "";
        reference "";
    }

    typedef  CML_CMM_POWER_SUPPLY_TYPE_T {
        type enumeration {
            enum ac-normal {
                value 1;
                description "psu type ac-normal";
            }
            enum ac-reverse {
                value 2;
                description "psu type ac-reverse";
            }
            enum dc-normal {
                value 3;
                description "psu type dc-normal";
            }
            enum dc-reverse {
                value 4;
                description "psu type dc-reverse";
            }
            enum unknown {
                value 5;
                description "psu type unknown";
            }
            enum notapplicable {
                value 6;
                description "psu type notapplicable";
            }
        }
        description "";
        reference "";
    }

    typedef  CML_CMM_POWER_RAIL_T {
        type enumeration {
            enum good {
                value 1;
                description "power rail good";
            }
            enum fail {
                value 2;
                description "power rail fail";
            }
            enum unknown {
                value 3;
                description "power rail status unknown";
            }
            enum notapplicable {
                value 4;
                description "power rail notapplicable";
            }
        }
        description "";
        reference "";
    }

    typedef  CML_CMM_PSU_PMBUS_PARAM_SUPPORT_T {
        type bits {
            bit volt-in {
                position 0;
                description "input voltage supported";
            }
            bit volt-out {
                position 1;
                description "output voltage supported";
            }
            bit curr-in {
                position 2;
                description "input current supported";
            }
            bit curr-out {
                position 3;
                description "output current supported";
            }
            bit power-in {
                position 4;
                description "input power supported";
            }
            bit power-out {
                position 5;
                description "output power supported";
            }
            bit temp1 {
                position 6;
                description "PSU Temp senor 1 supported";
            }
            bit temp2 {
                position 7;
                description "PSU Temp sensor 2 supported";
            }
            bit fan1 {
                position 8;
                description "PSU Fan 1 supported";
            }
            bit fan2 {
                position 9;
                description "PSU Fan 2 supported";
            }
            bit null {
                position 31;
                description "NULL";
            }
        }
        description "";
        reference "";
    }

    typedef  CML_CMM_LED_COLOR_CODE_T {
        type enumeration {
            enum none {
                value 1;
                description "ino color";
            }
            enum green {
                value 2;
                description "green color";
            }
            enum blinking-green {
                value 3;
                description "blinking-green color";
            }
            enum solid-green {
                value 4;
                description "solid-green color";
            }
            enum amber {
                value 5;
                description "amber color";
            }
            enum blinking-amber {
                value 6;
                description "blinking-amber color";
            }
            enum solid-amber {
                value 7;
                description "solid-amber color";
            }
            enum red {
                value 8;
                description "red color";
            }
            enum blinking-red {
                value 9;
                description "blinking-red color";
            }
            enum solid-red {
                value 10;
                description "solid-red color";
            }
            enum blue {
                value 11;
                description "blue color";
            }
            enum blinking-blue {
                value 12;
                description "blinking-blue color";
            }
            enum yellow {
                value 13;
                description "yellow color";
            }
            enum blinking-yellow {
                value 14;
                description "blinking-yellow color";
            }
            enum orange {
                value 15;
                description "orange color";
            }
            enum slow-blinking-green {
                value 16;
                description "slow-blinking-green color";
            }
            enum fast-blinking-green {
                value 17;
                description "fast-blinking-green color";
            }
            enum unknown {
                value 30;
                description "color unknown";
            }
        }
        description "";
        reference "";
    }

    typedef  CML_CMM_FAN_TRAY_STATUS_T {
        type enumeration {
            enum notpresent {
                value 1;
                description "fan tray not present";
            }
            enum present {
                value 2;
                description "fan tray present";
            }
            enum unknown {
                value 3;
                description "fan tray status unknown";
            }
        }
        description "";
        reference "";
    }

    typedef  CML_CMM_FAN_STATUS_T {
        type enumeration {
            enum notpresent {
                value 1;
                description "fan not present";
            }
            enum running {
                value 2;
                description "fan running";
            }
            enum faulty {
                value 3;
                description "fan faulty";
            }
            enum stalled {
                value 4;
                description "fan stalled";
            }
            enum unknown {
                value 5;
                description "fan status unknown";
            }
        }
        description "";
        reference "";
    }

    typedef  CML_CMM_FAN_LOCATION_T {
        type enumeration {
            enum front {
                value 1;
                description "fan located in front";
            }
            enum rear {
                value 2;
                description "fan located in rear";
            }
            enum unknown {
                value 3;
                description "fan location unknown";
            }
            enum notapplicable {
                value 4;
                description "fan location notapplicable";
            }
        }
        description "";
        reference "";
    }

    typedef  CML_CMM_FAN_TYPE_T {
        type enumeration {
            enum blow-outfan {
                value 1;
                description "fan type blow-out";
            }
            enum blow-infan {
                value 2;
                description "fan type blow-in";
            }
            enum fan-type-unknown {
                value 3;
                description "fan type unknown";
            }
        }
        description "";
        reference "";
    }

    typedef  CML_CMM_SYS_AND_COMPONENT_STATUS_T {
        type enumeration {
            enum normal {
                value 1;
                description "system/component status normal";
            }
            enum minor-fault {
                value 2;
                description "system/component in minor-fault";
            }
            enum major-fault {
                value 3;
                description "system/component in major-fault";
            }
            enum unknown {
                value 4;
                description "system/component status unknown";
            }
        }
        description "";
        reference "";
    }

    typedef  CML_CMM_MASTER_LOCATOR_STATUS_T {
        type enumeration {
            enum notpresent {
                value 1;
                description "component not present";
            }
            enum on {
                value 2;
                description "component led on";
            }
            enum off {
                value 3;
                description "component led off";
            }
            enum unknown {
                value 4;
                description "component status unknown";
            }
        }
        description "";
        reference "";
    }

    typedef  CML_CMM_SYS_FAULT_STATUS_T {
        type bits {
            bit cpu {
                position 0;
                description "cpu fault";
            }
            bit ram {
                position 1;
                description "ram fault";
            }
            bit disk {
                position 2;
                description "disk fault";
            }
            bit low-temperature {
                position 3;
                description "temperature fault in low";
            }
            bit high-temperature {
                position 4;
                description "temperature fault in high";
            }
            bit fan {
                position 5;
                description "fan fault";
            }
            bit power {
                position 6;
                description "psu fault";
            }
            bit software {
                position 7;
                description "software fault";
            }
            bit null {
                position 31;
                description "NULL";
            }
        }
        description "";
        reference "";
    }

    typedef  CML_RATE_LIMIT_TYPE {
        type enumeration {
            enum kbps {
                value 1;
                description "Specifies the units of kilobits per second";
            }
            enum mbps {
                value 2;
                description "Specifies the units of megabits per second";
            }
            enum gbps {
                value 3;
                description "Specifies the units of gigabits per second";
            }
        }
        description "";
        reference "";
    }

    typedef  CML_RATE_LIMIT_LEVEL_T {

        type string;
        description "";
        reference "";
    }

    typedef  CML_RATE_LIMIT_T {
        type union {
            type uint32 {
                range "0..100000000";

            }
            type CML_RATE_LIMIT_LEVEL_T {

            }
        }
        description "";
        reference "";
    }

    typedef  CML_HOSTP_SNMP_KEY_TYPE_T {
        type enumeration {
            enum plain {
                value 0;
                description "To specify shared key in clear-text form";
            }
            enum encrypt {
                value 1;
                description "To specify shared key in encrypted form";
            }
        }
        description "";
        reference "";
    }

    typedef  CML_FORWARDING_PROFILE_T {
        type enumeration {
            enum l2-profile-one {
                value 0;
                description "Configures the L2 profile One";
            }
            enum l2-profile-two {
                value 1;
                description "Configures the L2 profile Two";
            }
            enum l2-profile-three {
                value 2;
                description "Configures the L2 profile Three (default)";
            }
            enum l3-profile {
                value 3;
                description "Configures the L3 profile";
            }
            enum l3-128bit-profile {
                value 4;
                description "Configures the L3 profile with 128 bit prefix support";
            }
            enum lpm-profile {
                value 5;
                description "Configures the LPM profile profile";
            }
            enum lpm-128bit-profile {
                value 6;
                description "Configures the LPM profile with 128 bit prefix support";
            }
        }
        description "";
        reference "";
    }

    typedef  CML_FORWARDING_PROFILE_MH_T {
        type enumeration {
            enum l3-nvo-mh-profile {
                value 1;
                description "configures the Multihoming ecmp for nvo";
            }
        }
        description "";
        reference "";
    }

    typedef  CML_FORWARDING_CUSTOM_PROFILE_LPM_T {
        type enumeration {
            enum 2 {
                value 2;
                description "Two banks for lpm and Remaining banks can be used by any";
            }
        }
        description "";
        reference "";
    }

    typedef  CML_PROFILE_T {
        type enumeration {
            enum kaps-profile-one {
                value 1;
                description "Configures kaps profile one";
            }
            enum kaps-profile-two {
                value 2;
                description "Configures kaps profile two";
            }
            enum elk-tcam-profile-one {
                value 3;
                description "Configures elk-tcam profile one";
            }
            enum elk-tcam-profile-two {
                value 4;
                description "Configures elk-tcam profile two";
            }
            enum elk-tcam-profile-three {
                value 5;
                description "Configures elk-tcam profile three";
            }
        }
        description "";
        reference "";
    }

    typedef  CML_NSM_HW_PROFILE_T {
        type enumeration {
            enum qos-group {
                value 1;
                description "Configures the qos-group";
            }
            enum ingress-l2-group {
                value 2;
                description "Configures the ingress-l2-group";
            }
            enum ingress-ipv4 {
                value 4;
                description "Configures the ingress-ipv4";
            }
            enum egress-ipv4 {
                value 8;
                description "Configures the egress-ipv4";
            }
            enum egress-ipv6 {
                value 16;
                description "Configures the egress-ipv6";
            }
            enum egress-l2-group {
                value 64;
                description "Configures egress-l2-group";
            }
        }
        description "";
        reference "";
    }

    typedef  CML_NSM_CONFIG_MODE_T {
        type bits {
            bit addressmonitor {
                position 1;
                description "Enable Monitor adddress netlink";
            }
            bit bfd {
                position 2;
                description "Bidirectional Forwarding Detection (BFD)";
            }
            bit events {
                position 3;
                description "NSM events";
            }
            bit hal-events {
                position 4;
                description " Hardware Abstraction Layer,NSM events";
            }
            bit hal-ipc {
                position 5;
                description "Hardware Abstraction Layer,Async Debugging";
            }
            bit linkmonitor {
                position 6;
                description "Enable Monitor link netlink";
            }
            bit packet {
                position 7;
                description "NSM packets";
            }
            bit packet-detail {
                position 8;
                description "NSM packets,Detailed information display";
            }
            bit packet-recv {
                position 9;
                description "NSM packets,NSM receive packets";
            }
            bit packet-recv-detail {
                position 10;
                description "NSM packets,NSM receive packets,Detailed information display";
            }
            bit packet-send {
                position 11;
                description "NSM packets,NSM receive packets";
            }
            bit packet-send-detail {
                position 12;
                description "NSM packets,NSM receive packets,Detailed information display";
            }
            bit vxlan {
                position 15;
                description "VXLAN";
            }
        }
        description "";
        reference "";
    }

    typedef  CML_NSM_EXEC_MODE_T {
        type bits {
            bit addressmonitor {
                position 1;
                description "Enable Monitor adddress netlink";
            }
            bit bfd {
                position 2;
                description "Bidirectional Forwarding Detection (BFD)";
            }
            bit events {
                position 3;
                description "NSM events";
            }
            bit hal-events {
                position 4;
                description " Hardware Abstraction Layer,NSM events";
            }
            bit hal-ipc {
                position 5;
                description "Hardware Abstraction Layer,Async Debugging";
            }
            bit linkmonitor {
                position 6;
                description "Enable Monitor link netlink";
            }
            bit packet {
                position 7;
                description "NSM packets";
            }
            bit packet-detail {
                position 8;
                description "NSM packets,Detailed information display";
            }
            bit packet-recv {
                position 9;
                description "NSM packets,NSM receive packets";
            }
            bit packet-recv-detail {
                position 10;
                description "NSM packets,NSM receive packets,Detailed information display";
            }
            bit packet-send {
                position 11;
                description "NSM packets,NSM receive packets";
            }
            bit packet-send-detail {
                position 12;
                description "NSM packets,NSM receive packets,Detailed information display";
            }
            bit vxlan {
                position 15;
                description "VXLAN";
            }
        }
        description "";
        reference "";
    }

    typedef  CML_NSM_PKT_MGR_T {
        type bits {
            bit l2-protocol-cfm {
                position 2;
                description "debug pktmgr,layer2,protocol,cfm";
            }
            bit l2-protocol-eapol {
                position 3;
                description "debug pktmgr,layer2,protocol,eapol";
            }
            bit l2-protocol-efm {
                position 4;
                description "debug pktmgr,layer2,protocol,efm";
            }
            bit l2-protocol-igmp-snoop {
                position 5;
                description "debug pktmgr,layer2,protocol,igmp snoop";
            }
            bit l2-protocol-lacp {
                position 6;
                description "debug pktmgr,layer2,protocol,lacp";
            }
            bit l2-protocol-lldp {
                position 7;
                description "debug pktmgr,layer2,protocol,lldp";
            }
            bit l2-protocol-mldp-snoop {
                position 8;
                description "debug pktmgr,layer2,protocol,mldp snoop";
            }
            bit l2-protocol-mstp {
                position 9;
                description "debug pktmgr,layer2,protocol,mstp";
            }
            bit l2-protocol-ptp {
                position 10;
                description "debug pktmgr,layer2,protocol,ptp";
            }
        }
        description "";
        reference "";
    }

    typedef  CML_MSTP_DEBUG_T {
        type bits {
            bit mstp-protocol {
                position 1;
                description "debug mstp,mstp protocol";
            }
            bit mstp-protocol-detail {
                position 2;
                description "debug mstp,mstp protocol,display detailed information";
            }
            bit mstp-timer {
                position 3;
                description "debug mstp,mstp timer";
            }
            bit mstp-timer-detail {
                position 4;
                description "debug mstp,mstp timer,display detailed information";
            }
            bit mstp-packet-tx {
                position 5;
                description "debug mstp,mstp packet,tx";
            }
            bit mstp-packet-rx {
                position 6;
                description "debug mstp,mstp packet,rx";
            }
            bit mstp-cli {
                position 7;
                description "debug mstp,mstp cli";
            }
            bit mstp-bpdu {
                position 8;
                description "debug mstp,mstp bpdu";
            }
            bit mstp-mcec {
                position 9;
                description "debug mstp,mstp mcec";
            }
        }
        description "";
        reference "";
    }

    typedef  CML_EXEC_MSTP_T {
        type enumeration {
            enum stats {
                value 1;
                description "STATISTICS";
            }
            enum pkt-errors {
                value 2;
                description "PACKET ERROR STATS";
            }
        }
        description "";
        reference "";
    }

    typedef  CML_SFLOW_DEBUG_TYPE_T {
        type bits {
            bit agent {
                position 0;
                description "debug sflow agent";
            }
            bit sampling {
                position 1;
                description "debug sflow sampling";
            }
            bit polling {
                position 2;
                description "debug sflow polling";
            }
        }
        description "";
        reference "";
    }

    typedef  CML_URPF_MODE_T {
        type enumeration {
            enum any {
                value 1;
                description "Source is reachable via any interface";
            }
            enum rx {
                value 2;
                description "Source is reachable via interface on which packet was received";
            }
            enum any-allow-default {
                value 3;
                description "Source is reachable via any interface, Loose Default Route Unicast Reverse Path Forwarding";
            }
        }
        description "";
        reference "";
    }

    typedef  CML_MACTYPE_T {
        type enumeration {
            enum static {
                value 0;
                description "Clear all entries configured through management";
            }
            enum multicast {
                value 2;
                description "Clear all multicast entries";
            }
        }
        description "";
        reference "";
    }

    typedef  CML_INT_TRACK_MATCH_TYPE_T {
        type enumeration {
            enum all {
                value 1;
                description "Match criteria all";
            }
            enum any {
                value 2;
                description "Match criteria any";
            }
        }
        description "";
        reference "";
    }

    typedef  CML_INT_TRACK_STATE_TYPE_T {
        type enumeration {
            enum down {
                value 1;
                description "Make interface DOWN";
            }
            enum up {
                value 2;
                description "Make interface UP";
            }
        }
        description "";
        reference "";
    }

    typedef  CML_PMIRROR_SESS_TYPE_T {
        type enumeration {
            enum local {
                value 1;
                description "Create a local session";
            }
            enum remote {
                value 2;
                description "Create a remote source node session";
            }
        }
        description "";
        reference "";
    }

    typedef  CML_PMIRROR_STATE_T {
        type enumeration {
            enum shut {
                value 0;
                description "shut";
            }
            enum no-shut {
                value 1;
                description "unser, shut";
            }
        }
        description "";
        reference "";
    }

    typedef  CML_PMIRROR_DIR_T {
        type bits {
            bit rx {
                position 0;
                description "Ingress";
            }
            bit tx {
                position 1;
                description "Engress";
            }
        }
        description "";
        reference "";
    }

    typedef  CML_PMIRROR_ALT_DIR_T {
        type bits {
            bit receive {
                position 0;
                description "Mirror received traffic";
            }
            bit transmit {
                position 1;
                description "Mirror transmit traffic";
            }
        }
        description "";
        reference "";
    }

    typedef  CML_PMIRROR_ALL_SESS_T {
        type enumeration {
            enum all {
                value 0;
                description "All sessions";
            }
        }
        description "";
        reference "";
    }

    typedef  CML_PMIRROR_SESS_T {
        type union {
            type CML_PMIRROR_ALL_SESS_T {

            }
            type uint32 {
                range "1..18";

            }
        }
        description "";
        reference "";
    }

    typedef  CML_TUNNEL_STATUS_T {
        type enumeration {
            enum Deleted {
                value 0;
                description "Tunnel is deleted";
            }
            enum Un-Resolved {
                value 1;
                description "Tunnel not established";
            }
            enum Resolved {
                value 2;
                description "Tunnel established but not in hardware";
            }
            enum Installed {
                value 3;
                description "Tunnel established succesfully in hardware";
            }
        }
        description "";
        reference "";
    }

    typedef  CML_RSVP_TRUNK_FAMILY_T {
        type enumeration {
            enum ipv4 {
                value 2;
                description "IPv4 address family trunk";
            }
            enum ipv6 {
                value 10;
                description "IPv6 address family trunk";
            }
        }
        description "";
        reference "";
    }

    typedef  CML_RSVP_FRR_PROTECTION_T {
        type enumeration {
            enum one-to-one {
                value 1;
                description "One-to-One protection mechanism";
            }
        }
        description "";
        reference "";
    }

    typedef  CML_RSVP_ADMIN_TYPE_T {
        type enumeration {
            enum exclude-any {
                value 0;
                description "Exclude-any attribute";
            }
            enum include-any {
                value 1;
                description "Include-any attribute";
            }
            enum include-all {
                value 2;
                description "Include-all attribute";
            }
        }
        description "";
        reference "";
    }

    typedef  CML_RSVP_IGP_T {
        type enumeration {
            enum disable-igp-shortcut {
                value 0;
                description "Disable RSVP LSP for IGP Shortcut use";
            }
            enum enable-igp-shortcut {
                value 1;
                description "Enable RSVP LSP for IGP Shortcut use";
            }
        }
        description "";
        reference "";
    }

    typedef  CML_RSVP_EXCLUDE_PATH_TYPE_T {
        type enumeration {
            enum link {
                value 1;
                description "Enables a Link Protection - NHOP";
            }
            enum node {
                value 2;
                description "Enables a Node Protection - NNHOP";
            }
        }
        description "";
        reference "";
    }

    typedef  CML_RSVP_SESS_TYEP_T {
        type enumeration {
            enum secondary {
                value 0;
                description "Configure secondary LSP option";
            }
            enum primary {
                value 1;
                description "Configure primary LSP option";
            }
        }
        description "";
        reference "";
    }

    typedef  CML_RSVP_AFFINITY_T {
        type enumeration {
            enum no-affinity {
                value 0;
                description "Dont pack affinity info into session attribute object";
            }
            enum affinity {
                value 1;
                description "Pack affinity info into session attribute object";
            }
        }
        description "";
        reference "";
    }

    typedef  CML_RSVP_RECORD_T {
        type enumeration {
            enum no-record {
                value 0;
                description "Disable record of route taken by PATH message";
            }
            enum record {
                value 1;
                description "Record route taken by PATH message in order to reach tunnel egress";
            }
        }
        description "";
        reference "";
    }

    typedef  CML_BFD_MULTI_HOP_TYPE_T {
        type enumeration {
            enum multihop {
                value 1;
                description "Multihop Session";
            }
        }
        description "";
        reference "";
    }

    typedef  CML_RIPNG_DEBUG_T {
        type bits {
            bit events {
                position 1;
                description "RIP events";
            }
            bit packet-send {
                position 2;
                description "RIP packets,RIP send packets";
            }
            bit packet-recv {
                position 3;
                description "RIP packets, RIP receive packets";
            }
            bit nsm {
                position 5;
                description "RIP NSM information";
            }
            bit rib {
                position 6;
                description "RIP RIB information";
            }
        }
        description "";
        reference "";
    }

    typedef  CML_RIPNG_SPLIT_HORIZON_T {
        type enumeration {
            enum split-horizon {
                value 0;
                description "Perform split horizon";
            }
            enum split-horizon-poisoned {
                value 1;
                description "Perform poisoned reverse";
            }
        }
        description "";
        reference "";
    }

    typedef  CML_RIPNG_INSTANCE_T {
        type enumeration {
            enum rip {
                value 1;
                description "Routing Information Protocol (RIP)";
            }
        }
        description "";
        reference "";
    }

    typedef  CML_RIPNG_REDIST_PROTOS_T {
        type enumeration {
            enum kernel {
                value 0;
                description "Kernel routes";
            }
            enum connected {
                value 1;
                description "Connected";
            }
            enum static {
                value 2;
                description "Static routes";
            }
            enum ospf6 {
                value 3;
                description "Open Shortest Path First (OSPF)";
            }
            enum isis {
                value 4;
                description "ISO IS-IS";
            }
            enum bgp {
                value 5;
                description "Border Gateway Protocol (BGP)";
            }
        }
        description "";
        reference "";
    }

    typedef  CML_RIPNG_VRF_REDIST_PROTOS_T {
        type enumeration {
            enum connected {
                value 1;
                description "Connected";
            }
            enum static {
                value 2;
                description "Static routes";
            }
            enum ospf6 {
                value 3;
                description "Open Shortest Path First (OSPF)";
            }
            enum bgp {
                value 5;
                description "Border Gateway Protocol (BGP)";
            }
        }
        description "";
        reference "";
    }

    typedef  CML_RIPNG_FILTERING_T {
        type enumeration {
            enum in {
                value 0;
                description "For incoming updates";
            }
            enum out {
                value 1;
                description "For outgoing updates";
            }
        }
        description "";
        reference "";
    }

    typedef  CML_RIPNG_ROUTE_T {
        type enumeration {
            enum kernel {
                value 1;
                description "Kernel routes";
            }
            enum connected {
                value 2;
                description "Connected";
            }
            enum static {
                value 3;
                description "Static routes";
            }
            enum isis {
                value 4;
                description "ISO IS-IS";
            }
            enum ospf6 {
                value 5;
                description "Open Shortest Path First (OSPF)";
            }
            enum bgp {
                value 6;
                description "Border Gateway Protocol (BGP)";
            }
            enum rip {
                value 7;
                description "Routing Information Protocol (RIP)";
            }
            enum all {
                value 8;
                description "all of the RIP routing tabl";
            }
        }
        description "";
        reference "";
    }

    typedef  CML_CONFIDENCETYPE_T {
        type enumeration {
            enum native {
                value 1;
                description "Confidence level associated with MAC learned after decapsulation of frames";
            }
            enum decap {
                value 2;
                description "Confidence level associated with MAC learned from native frames";
            }
            enum static {
                value 3;
                description "Confidence level associated with MAC that are statically configured";
            }
        }
        description "";
        reference "";
    }

    typedef  CML_ESADI_T {
        type enumeration {
            enum enable {
                value 1;
                description "Enable ESADI";
            }
            enum disable {
                value 2;
                description "Disable ESADI";
            }
        }
        description "";
        reference "";
    }

    typedef  CML_TRILL_T {
        type enumeration {
            enum disable {
                value 0;
                description "Disable vlan pruningI";
            }
            enum enable {
                value 1;
                description "Enable vlan pruning";
            }
        }
        description "";
        reference "";
    }

    typedef  CML_ISUNICAST_T {
        type enumeration {
            enum multicast {
                value 0;
                description "Enable Multipath for multicast";
            }
            enum unicast {
                value 1;
                description "Enable Multipath for unicast";
            }
        }
        description "";
        reference "";
    }

    typedef  CML_CONFIGTYPE_T {
        type enumeration {
            enum broadcast {
                value 1;
                description "Link is broadcast multi-access";
            }
            enum point-to-point {
                value 2;
                description "Link is point-to-point";
            }
        }
        description "";
        reference "";
    }

    typedef  CML_VLAN_ENUM_T {
        type enumeration {
            enum all {
                value 4095;
                description "All the vlan";
            }
        }
        description "";
        reference "";
    }

    typedef  CML_VLAN_RANGE_T {

        type uint16{
         range 1..4094;
        }
        description "";
        reference "";
    }

    typedef  CML_STARTVIDESADI_T {
        type union {
            type CML_VLAN_ENUM_T {

            }
            type CML_VLAN_RANGE_T {

            }
        }
        description "";
        reference "";
    }

    typedef  CML_NSM_DCB_QCN_MODE_T {
        type enumeration {
            enum admin {
                value 1;
                description "Admin-Mode";
            }
            enum auto {
                value 2;
                description "Automatic mode - LLDP should be enabled";
            }
            enum component {
                value 3;
                description "Defense mode same as the bridge level defense mode";
            }
        }
        description "";
        reference "";
    }

    typedef  CML_MAPPING_TYPE_T {
        type enumeration {
            enum admin {
                value 1;
                description "Admin-Mode";
            }
            enum auto {
                value 2;
                description "Automatic mode - LLDP should be enabled";
            }
            enum component {
                value 3;
                description "Defense mode same as the bridge level defense mode";
            }
        }
        description "";
        reference "";
    }

    typedef  CML_ETS_MODE_T {
        type enumeration {
            enum on {
                value 1;
                description "ON to force enable Enhanced-trasnsmission-selection";
            }
            enum auto {
                value 2;
                description "AUTO to negotiate Enhanced-transmission-selection capabilities)";
            }
        }
        description "";
        reference "";
    }

    typedef  CML_DCBSTATE_T {
        type enumeration {
            enum off {
                value 0;
                description "disable";
            }
            enum on {
                value 1;
                description "enable";
            }
        }
        description "";
        reference "";
    }

    typedef  CML_PRIOFLAG_T {
        type enumeration {
            enum remove {
                value 0;
                description "remove";
            }
            enum add {
                value 1;
                description "add";
            }
        }
        description "";
        reference "";
    }

    typedef  CML_PROTOID_T {
        type enumeration {
            enum tcp {
                value 2;
                description "Protocol Type tcp";
            }
            enum udp {
                value 3;
                description "Protocol Type udp";
            }
            enum both-tcp-udp {
                value 4;
                description "Protocol Type both-tcp-udp";
            }
            enum neither-tcp-udp {
                value 5;
                description "Protocol Type neither-tcp-udp";
            }
        }
        description "";
        reference "";
    }

    typedef  CML_DEFENSEMODE_T {
        type enumeration {
            enum disabled {
                value 1;
                description "Disabled Mode";
            }
            enum interior {
                value 2;
                description "Interior Mode";
            }
            enum interior-ready {
                value 3;
                description "Interior Ready Mode";
            }
            enum edge {
                value 4;
                description "Edge Mode";
            }
        }
        description "";
        reference "";
    }

    typedef  CML_LOADSHARE_T {

        type string;
        description "";
        reference "";
    }

    typedef  CML_PBR_LOADSHARE_T {
        type union {
            type CML_IPV4_ADDR_T {

            }
            type CML_LOADSHARE_T {

            }
        }
        description "";
        reference "";
    }

    typedef  CML_PBR_V6_LOADSHARE_T {
        type union {
            type CML_IPV6_ADDR_T {

            }
            type CML_LOADSHARE_T {

            }
        }
        description "";
        reference "";
    }

    typedef  CML_DEBUG_EVENT_T {
        type bits {
            bit event {
                position 0;
                description "ARP related events";
            }
            bit packet {
                position 1;
                description "ARP packet debugging";
            }
        }
        description "";
        reference "";
    }

    typedef  CML_VRF_ENUM_T {
        type enumeration {
            enum all {
                value 1;
                description "All VRFs";
            }
            enum default {
                value 2;
                description "Default VRF";
            }
        }
        description "";
        reference "";
    }

    typedef  CML_VRF_STRING_T {

        type string;
        description "";
        reference "";
    }

    typedef  CML_VRF_NAME_T {
        type union {
            type CML_VRF_ENUM_T {

            }
            type CML_VRF_STRING_T {

            }
        }
        description "";
        reference "";
    }

    typedef  CML_ADJNBR_T {
        type enumeration {
            enum adjacency {
                value 1;
                description "Clear adjacency";
            }
            enum neighbor {
                value 2;
                description "Clear neighbors";
            }
        }
        description "";
        reference "";
    }

    typedef  CML_MPLS_VCLINKMODE_T {
        type enumeration {
            enum primary {
                value 0;
                description "Primary Link";
            }
            enum secondary {
                value 16;
                description "Secondary Link - Will not be activated unless primary fails";
            }
        }
        description "";
        reference "";
    }

    typedef  CML_VR_CONFIG_T {
        type enumeration {
            enum read {
                value 0;
                description "Read file";
            }
            enum write {
                value 1;
                description "Write file";
            }
        }
        description "";
        reference "";
    }

    typedef  CML_STATIC_BFD_ENABLE_DISABLE_T {
        type enumeration {
            enum fall-over-bfd-disable {
                value 0;
                description "static fall-over, BFD, disable bfd";
            }
            enum fall-over-bfd {
                value 1;
                description "Enable static fall-over bfd,BFD";
            }
        }
        description "";
        reference "";
    }

    typedef  CML_CMM_TRANSCEIVER_T {
        type enumeration {
            enum 1000base-sx {
                value 1;
                description "sfp 1000base-sx";
            }
            enum 1000base-lx {
                value 2;
                description "sfp 1000base-lx";
            }
            enum 1000base-ex {
                value 3;
                description "sfp 1000base-ex";
            }
            enum 1000base-cx {
                value 4;
                description "sfp 1000base-cx";
            }
            enum 10gbase-sr {
                value 5;
                description "sfp+ 10gbase-sr";
            }
            enum 10gbase-lr {
                value 6;
                description "sfp+ 10gbase-lr";
            }
            enum 10gbase-er {
                value 7;
                description "sfp+ 10gbase-er";
            }
            enum 10gbase-cr {
                value 8;
                description "sfp+ 10gbase-cr";
            }
            enum 40gbase-sr4 {
                value 9;
                description "qsfp 40gbase-sr4";
            }
            enum 40gbase-lr4 {
                value 10;
                description "qsfp 40gbase-lr4";
            }
            enum 40gbase-er4 {
                value 11;
                description "qsfp 40gbase-er4";
            }
            enum 40gbase-cr4 {
                value 12;
                description "qsfp 40gbase-cr4";
            }
            enum 100gbase-sr4 {
                value 13;
                description "qsfp28 100gbase-sr4";
            }
            enum 100gbase-lr4 {
                value 14;
                description "qsfp28 100gbase-lr4";
            }
            enum 100gbase-er4 {
                value 15;
                description "qsfp28 100gbase-er4";
            }
            enum 100gbase-cr4 {
                value 16;
                description "qsfp28 100gbase-cr4";
            }
        }
        description "";
        reference "";
    }

    typedef  CML_LLDP_DEBUG_T {
        type bits {
            bit event {
                position 0;
                description "enable event debugs";
            }
            bit rx {
                position 1;
                description "enable rx debugs";
            }
            bit tx {
                position 2;
                description "enable tx debugs";
            }
            bit message {
                position 3;
                description "enable nsm-message debugs";
            }
            bit ha {
                position 4;
                description "enable ha debugs";
            }
        }
        description "";
        reference "";
    }

    typedef  CML_L2PROCESS_T {
        type enumeration {
            enum discard {
                value 1;
                description "Discard the protocol data unit";
            }
            enum peer {
                value 2;
                description "Act as peer to the customer Device instance of the protocol";
            }
        }
        description "";
        reference "";
    }

    typedef  CML_TUNNEL_KEY_T {
        type union {
            type uint32 {
                range "0..4294967295";

            }
            type CML_IPV4_ADDR_T {

            }
        }
        description "";
        reference "";
    }

    typedef  CML_NAT_PORT_TYPE_T {
        type enumeration {
            enum tcp {
                value 0;
                description "TCP";
            }
            enum udp {
                value 1;
                description "UDP";
            }
        }
        description "";
        reference "";
    }

    typedef  CML_NAT_DIR_T {
        type enumeration {
            enum inside {
                value 0;
                description "Inside";
            }
            enum outside {
                value 1;
                description "Outside";
            }
        }
        description "";
        reference "";
    }

    typedef  CML_NAT_ADDR_TYPE_T {
        type enumeration {
            enum source {
                value 0;
                description "Source Address";
            }
            enum destination {
                value 1;
                description "Destination Address";
            }
        }
        description "";
        reference "";
    }

    typedef  CML_NAT_DIR_OUT_T {
        type enumeration {
            enum outside {
                value 1;
                description "Outside";
            }
        }
        description "";
        reference "";
    }

    typedef  CML_NAT_ADDR_TYPE_DEST_T {
        type enumeration {
            enum destination {
                value 1;
                description "Destination Address";
            }
        }
        description "";
        reference "";
    }

    typedef  CML_NAT_TRANS_DIR_T {
        type enumeration {
            enum src {
                value 0;
                description "Source address";
            }
            enum dest {
                value 1;
                description "Destination address";
            }
        }
        description "";
        reference "";
    }

    typedef  CML_AGENTX_DEBUG_TYPE_T {
        type bits {
            bit snmp-send {
                position 0;
                description "SNMP  (AgentX or SMUX),Packet send";
            }
            bit snmp-receive {
                position 1;
                description "SNMP  (AgentX or SMUX),Packet receive";
            }
            bit snmp-process {
                position 2;
                description "SNMP  (AgentX or SMUX),Packet process";
            }
            bit snmp-xdump {
                position 3;
                description "SNMP  (AgentX or SMUX),Packet hexa dump";
            }
            bit snmp-error-string {
                position 4;
                description "SNMP  (AgentX or SMUX),Error string display";
            }
            bit snmp-detail {
                position 5;
                description "SNMP  (AgentX or SMUX),Detail debugging";
            }
        }
        description "";
        reference "";
    }

    typedef  CML_PERMASTATE_T {
        type enumeration {
            enum permanent {
                value 1;
                description "permanent state";
            }
        }
        description "";
        reference "";
    }

    typedef  CML_IFSTATE_T {
        type enumeration {
            enum down {
                value 0;
                description "interface state down";
            }
            enum up {
                value 1;
                description "interface state up";
            }
        }
        description "";
        reference "";
    }

    typedef  CML_GMPLS_LMPTYPE_T {
        type enumeration {
            enum static {
                value 0;
                description "static";
            }
            enum using-lmp {
                value 1;
                description "lmp";
            }
        }
        description "";
        reference "";
    }

    typedef  CML_GMPLS_TYPE_T {
        type enumeration {
            enum data-control {
                value 1;
                description "Data and Conrol";
            }
            enum data {
                value 2;
                description "Data";
            }
            enum control {
                value 3;
                description "Control";
            }
            enum data-numbered {
                value 4;
                description "Data, Numbered";
            }
        }
        description "";
        reference "";
    }

    typedef  CML_MPLS_VPLS_OPCODE_T {
        type enumeration {
            enum swap {
                value 3;
                description "Swap incoming label";
            }
            enum vpnpop {
                value 4;
                description "Pop incoming label and forward VPN packet";
            }
        }
        description "";
        reference "";
    }

    typedef  CML_MPLS_VPLS_POPOPCODE_T {
        type enumeration {
            enum pop {
                value 2;
                description "pop incoming label";
            }
        }
        description "";
        reference "";
    }

    typedef  CML_MPLS_IPV6OPCODE_T {
        type enumeration {
            enum swap {
                value 3;
                description "Swap incoming label";
            }
        }
        description "";
        reference "";
    }

    typedef  CML_GMPLS_BIDIRECTIONAL_FLAG_T {
        type enumeration {
            enum False {
                value 0;
                description "Bidirectional flag is not set";
            }
            enum True {
                value 1;
                description "Bidirectional flag is set";
            }
        }
        description "";
        reference "";
    }

    typedef  CML_GMPLS_CAPABILITY_TYPE_T {
        type enumeration {
            enum psc1 {
                value 1;
                description "Packet Switch Capable-1 (PSC1)";
            }
            enum psc2 {
                value 2;
                description "Packet Switch Capable-2 (PSC2)";
            }
            enum psc3 {
                value 4;
                description "Packet Switch Capable-3 (PSC3)";
            }
            enum psc4 {
                value 8;
                description "Packet Switch Capable-4 (PSC4)";
            }
            enum pbb-te {
                value 256;
                description "Provider Backbone Bridging-Traffic Engineering (PBB-TE)";
            }
        }
        description "";
        reference "";
    }

    typedef  CML_DATE_TIME_T {

        type yang:date-and-time{
        pattern "\\d{4}-\\d{2}-\\d{2}T\\d{2}:\\d{2}:\\d{2}(\\.\\d+)?(Z|[\\+\\-]\\d{2}:\\d{2})";
        }
        description "The date-and-time type is a profile of the ISO 8601 standard for representation of dates and times using the Gregorian calendar.  The profile is defined by the date-time production in Section 5.6 of RFC 3339.";
        reference "RFC 6991: Common YANG data types";
    }

    typedef  CML_COUNTER32_T {

        type yang:counter32{
         range 0..4294967295;
        }
        description "The counter32 type represents a non-negative integer that monotonically increases until it reaches a maximum value of 2^32-1 (4294967295 decimal), when it wraps around and starts increasing again from zero.";
        reference "RFC 6991: Common YANG data types";
    }

    typedef  CML_ZERO_BASED_COUNTER32_T {

        type yang:zero-based-counter32{
         range 0..4294967295;
        }
        description "The zero-based-counter32 type represents a counter32 that has the defined 'initial' value zero. A schema node of this type will be set to zero (0) on creation and will thereafter increase monotonically until it reaches a maximum value of 2^32-1 (4294967295 decimal), when it wraps around and starts increasing again from zero.";
        reference "RFC 6991: Common YANG data types";
    }

    typedef  CML_COUNTER64_T {

        type yang:counter64;
        description "The counter64 type represents a non-negative integer that monotonically increases until it reaches a maximum value of 2^64-1 (18446744073709551615 decimal), when it wraps around and starts increasing again from zero.";
        reference "RFC 6991: Common YANG data types";
    }

    typedef  CML_ZERO_BASED_COUNTER64_T {

        type yang:zero-based-counter64;
        description "The zero-based-counter32 type represents a counter32 that has the defined 'initial' value zero. A schema node of this type will be set to zero (0) on creation and will thereafter increase monotonically until it reaches a maximum value of 2^32-1 (4294967295 decimal), when it wraps around and starts increasing again from zero.";
        reference "RFC 6991: Common YANG data types";
    }

    typedef  CML_GAUGE32_T {

        type yang:gauge32{
         range 0..4294967295;
        }
        description "The gauge32 type represents a non-negative integer, which may increase or decrease, but shall never exceed a maximum value, nor fall below a minimum value.  The maximum value cannot be greater than 2^32-1 (4294967295 decimal), and the minimum value cannot be smaller than 0.  The value of a gauge32 has its maximum value whenever the information being modeled is greater than or equal to its maximum value, and has its minimum value whenever the information being modeled is smaller than or equal to its minimum value. If the information being modeled subsequently decreases below (increases above) the maximum (minimum) value, the gauge32 also decreases (increases).";
        reference "RFC 6991: Common YANG data types";
    }

    typedef  CML_GAUGE64_T {

        type yang:gauge64;
        description "The gauge64 type represents a non-negative integer, which may increase or decrease, but shall never exceed a maximum value, nor fall below a minimum value.  The maximum value cannot be greater than 2^64-1 (18446744073709551615), and the minimum value cannot be smaller than 0.  The value of a gauge64 has its maximum value whenever the information being modeled is greater than or equal to its maximum value, and has its minimum value whenever the information being modeled is smaller than or equal to its minimum value. If the information being modeled subsequently decreases below (increases above) the maximum (minimum) value, the gauge64 also decreases (increases).";
        reference "RFC 6991: Common YANG data types";
    }

    typedef  CML_TIMETICKS_T {

        type yang:timeticks{
         range 0..4294967295;
        }
        description "The timeticks type represents a non-negative integer that represents the time, modulo 2^32 (4294967296 decimal), in hundredths of a second between two epochs.  When a schema node is defined that uses this type, the description of the schema node identifies both of the reference epochs.";
        reference "RFC 6991: Common YANG data types";
    }

    typedef  CML_TIMESTAMP_T {

        type yang:timestamp{
         range 0..4294967295;
        }
        description "The timestamp type represents the value of an associated timeticks schema node at which a specific occurrence happened.  The specific occurrence must be defined in the description of any schema node defined using this type.  When the specific occurrence occurred prior to the last time the associated timeticks attribute was zero, then the timestamp value is zero.  Note that this requires all timestamp values to be reset to zero when the value of the associated timeticks attribute reaches 497+ days and wraps around to zero.";
        reference "RFC 6991: Common YANG data types";
    }

    typedef  CML_PHYSICAL_ADDRESS_T {

        type yang:phys-address{
        pattern "([0-9a-fA-F]{2}(:[0-9a-fA-F]{2})*)?";
        }
        description "Represents media- or physical-level addresses represented as a sequence octets, each octet represented by two hexadecimal numbers.  Octets are separated by colons. The canonical representation uses lowercase characters.";
        reference "RFC 6991: Common YANG data types";
    }

    typedef  CML_MAC_ADDRESS_T {

        type yang:mac-address{
        pattern "[0-9a-fA-F]{2}(:[0-9a-fA-F]{2}){5}";
        }
        description "The mac-address type represents an IEEE 802 MAC address. The canonical representation uses lowercase characters.";
        reference "RFC 6991: Common YANG data types";
    }

    typedef  CML_IP_VERSION_T {
        type enumeration {
            enum unknown {
                value 0;
                description "An unknown or unspecified version of the Internet protocol";
            }
            enum ipv4 {
                value 1;
                description "The IPv4 protocol as defined in RFC 2460.";
            }
            enum ipv6 {
                value 2;
                description "The IPv6 protocol as defined in RFC 2460.";
            }
        }
        description "This value represents the version of the IP protocol.";
        reference "RFC 6991: Common YANG data types";
    }

    typedef  CML_DSCP_T {

        type inet:dscp{
         range 0..63;
        }
        description "The dscp type represents a Differentiated Services Code Point that may be used for marking packets in a traffic stream. In the value set and its semantics, this type is equivalent to the Dscp textual convention of the SMIv2.";
        reference "RFC 6991: Common YANG data types";
    }

    typedef  CML_IPV6_FLOW_LABEL_T {

        type inet:ipv6-flow-label{
         range 0..1048575;
        }
        description "The ipv6-flow-label type represents the flow identifier or Flow Label in an IPv6 packet header that may be used to discriminate traffic flows.";
        reference "RFC 6991: Common YANG data types";
    }

    typedef  CML_PORT_NUMBER_T {

        type inet:port-number{
         range 0..65535;
        }
        description "The port-number type represents a 16-bit port number of an Internet transport-layer protocol such as UDP, TCP, DCCP, or SCTP.";
        reference "RFC 6991: Common YANG data types";
    }

    typedef  CML_AS_NUMBER_T {

        type inet:as-number{
         range 0..65535;
        }
        description "The as-number type represents autonomous system numbers which identify an Autonomous System (AS).";
        reference "RFC 6991: Common YANG data types";
    }

    typedef  CML_DOMAIN_NAME_T {

        type inet:domain-name{
        length 1..253;
        pattern "((([a-zA-Z0-9_]([a-zA-Z0-9\\-_]){0,61})?[a-zA-Z0-9]\\.)*([a-zA-Z0-9_]([a-zA-Z0-9\\-_]){0,61})?[a-zA-Z0-9]\\.?)|\\.";
        }
        description "The domain-name type represents a DNS domain name.  The name SHOULD be fully qualified whenever possible.";
        reference "RFC 6991: Common YANG data types";
    }

    typedef  CML_URI_T {

        type inet:uri;
        description "The uri type represents a Uniform Resource Identifier (URI) as defined by STD 66.";
        reference "RFC 6991: Common YANG data types";
    }

    typedef  CML_VRX_FLAG_T {
        type enumeration {
            enum normal {
                value 0;
                description "Normal Interface";
            }
            enum EVR-wrpj {
                value 1;
                description "EVR wrpj Interface";
            }
            enum VS-wrp {
                value 2;
                description "VS wrp Interface";
            }
        }
        description "";
        reference "";
    }

    typedef  CML_BIND_INFO_T {
        type bits {
            bit vrf {
                position 0;
                description "Bind Information vrf";
            }
            bit mpls_vc {
                position 1;
                description "Bind Information mpls_vc";
            }
            bit mpls_vc_vlan {
                position 2;
                description "Bind Information mpls_vc_vlan";
            }
            bit vpls {
                position 3;
                description "Bind Information vpls";
            }
            bit vpls_vlan {
                position 4;
                description "Bind Information vpls_vlan";
            }
            bit vxlan {
                position 5;
                description "Bind Information vxlan";
            }
            bit nvgre {
                position 6;
                description "Bind Information nvgre";
            }
        }
        description "";
        reference "";
    }

    typedef  CML_LOCAL_FLAG_T {
        type enumeration {
            enum localsrc {
                value 1;
                description "localsrc of VS";
            }
        }
        description "";
        reference "";
    }

    typedef  CML_TRUST_STATE_T {
        type enumeration {
            enum none {
                value 0;
                description "mls qos trust none";
            }
            enum cos {
                value 1;
                description "mls qos trust cos";
            }
            enum dscp {
                value 2;
                description "mls qos trust dscp";
            }
            enum ip-precedence {
                value 3;
                description "mls qos trust ip-precedence";
            }
            enum dscp-cos {
                value 6;
                description "mls qos trust cos and dscp both";
            }
        }
        description "";
        reference "";
    }

    typedef  CML_TFO_LINK_TYPE_T {
        type enumeration {
            enum default {
                value 0;
                description "default link type";
            }
            enum uplink {
                value 1;
                description "link-type uplink";
            }
            enum downlink {
                value 2;
                description "link-type downlink";
            }
        }
        description "";
        reference "";
    }

    typedef  CML_HW_TYPE_T {
        type enumeration {
            enum UNK {
                value 0;
                description "UNK-Interface type unknown";
            }
            enum LB {
                value 1;
                description "LB-loopback";
            }
            enum ETH {
                value 2;
                description "ETH-Ethernet";
            }
            enum HDLC {
                value 3;
                description "HDLC";
            }
            enum PPP {
                value 4;
                description "PPP";
            }
            enum ATM {
                value 5;
                description "ATM";
            }
            enum FR {
                value 6;
                description "FR-Frame Relay";
            }
            enum SVI {
                value 7;
                description "VLAN";
            }
            enum AGG {
                value 9;
                description "AGG-aggregate";
            }
            enum PBB {
                value 11;
                description "PBB- PBB logical Port";
            }
            enum VP {
                value 12;
                description "VPORT- Virtual port";
            }
            enum CVP {
                value 13;
                description "CVP-Channelised Virtual port";
            }
            enum METH {
                value 14;
                description "Management Ethernet";
            }
            enum MLAG {
                value 16;
                description "MLAG-Mlag Aggregate";
            }
            enum TUN {
                value 101;
                description "TUN-Tunnel";
            }
        }
        description "";
        reference "";
    }

    typedef  CML_IFACE_PROP_T {
        type bits {
            bit interface_active {
                position 0;
                description "active interface";
            }
            bit dhcp_addr {
                position 15;
                description "IPV4 DHCP client is enabled";
            }
            bit dhcp6_addr {
                position 16;
                description "IPV6 DHCP IA-NA client is enabled";
            }
            bit Breakout_control_port {
                position 20;
                description "Breakout Control Port (Active)";
            }
            bit Bundle_control_port {
                position 21;
                description "Bundle Control Port (Active)";
            }
            bit Breakout_enable {
                position 22;
                description "port breakout enable";
            }
            bit Bundle_enable {
                position 23;
                description "port bundle enable";
            }
            bit Sbuport_inactive {
                position 24;
                description "Non Control Port (InActive)";
            }
        }
        description "";
        reference "";
    }

    typedef  CML_LACP_RCV_STATE_T {
        type enumeration {
            enum Invalid {
                value 0;
                description "";
            }
            enum Initialize {
                value 1;
                description "";
            }
            enum Port-disabled {
                value 2;
                description "";
            }
            enum LACP-disabled {
                value 3;
                description "";
            }
            enum Expired {
                value 4;
                description "";
            }
            enum Defaulted {
                value 5;
                description "";
            }
            enum Current {
                value 6;
                description "";
            }
        }
        description "";
        reference "";
    }

    typedef  CML_LACP_PERIODIC_TX_STATE_T {
        type enumeration {
            enum Invalid {
                value 0;
                description "";
            }
            enum No-periodic {
                value 1;
                description "";
            }
            enum Fast-periodic {
                value 2;
                description "";
            }
            enum Slow-periodic {
                value 3;
                description "";
            }
            enum Periodic {
                value 4;
                description "";
            }
        }
        description "";
        reference "";
    }

    typedef  CML_LACP_MUX_STATE_T {
        type enumeration {
            enum Detached {
                value 0;
                description "";
            }
            enum Waiting {
                value 1;
                description "";
            }
            enum Attached {
                value 2;
                description "";
            }
            enum Collecting {
                value 3;
                description "";
            }
            enum Distributing {
                value 4;
                description "";
            }
            enum Collecting-Distributing {
                value 5;
                description "";
            }
        }
        description "";
        reference "";
    }

    typedef  CML_PSSTATE_T {
        type enumeration {
            enum Not-Running {
                value 0;
                description "Stop the process";
            }
            enum Running {
                value 1;
                description "Start the process";
            }
        }
        description "";
        reference "";
    }

    typedef  CML_GLOBAL_PSSTATE_T {
        type enumeration {
            enum False {
                value 0;
                description "one of the process not running";
            }
            enum True {
                value 1;
                description "All process are running";
            }
        }
        description "";
        reference "";
    }

    typedef  CML_WATCHDOGSTATUS_T {
        type enumeration {
            enum Disabled {
                value 0;
                description "Watchdog status is disabled globally";
            }
            enum Enabled {
                value 1;
                description "Watchdog status is enabled globally";
            }
        }
        description "";
        reference "";
    }

    typedef  CML_MPLS_PORT_TYPE_T {
        type enumeration {
            enum access-port {
                value 1;
                description "Access interface statistics counters";
            }
            enum network-port {
                value 2;
                description "Network interface statistics counters";
            }
        }
        description "";
        reference "";
    }

    typedef  CML_HW_TCAM_FILTER_T {
        type enumeration {
            enum ingress-l2-acl {
                value 1;
                description "Ingress ACL L2 filter profile";
            }
            enum ingress-qos {
                value 2;
                description "Ingress ACL QOS filter profile";
            }
            enum ingress-ipv4-acl {
                value 3;
                description "Ingress ACL IPV4 filter profile";
            }
            enum ingress-ipv6-acl {
                value 4;
                description "Ingress ACL IPV6 filter profile";
            }
            enum egress-l2-l3 {
                value 5;
                description "Egress ACL L2-L3 filter profile";
            }
            enum egress-ipv6-acl {
                value 6;
                description "Egress ACL IPV6 filter profile";
            }
        }
        description "";
        reference "";
    }

    typedef  CML_KAPS_FORWADING_PROFILE_T {
        type enumeration {
            enum kaps-profile-one {
                value 9;
                description "kaps profile one";
            }
            enum kaps-profile-two {
                value 10;
                description "kaps profile two";
            }
        }
        description "";
        reference "";
    }

    typedef  CML_ELK_TCAM_FORWADING_PROFILE_T {
        type enumeration {
            enum elk-tcam-profile-one {
                value 11;
                description "elk-tcam profile one";
            }
            enum elk-tcam-profile-two {
                value 12;
                description "elk-tcam profile two";
            }
            enum elk-tcam-profile-three {
                value 13;
                description "elk-tcam profile three";
            }
        }
        description "";
        reference "";
    }

    typedef  CML_FRWD_PROFILE_T {
        type enumeration {
            enum l2-profile-one {
                value 0;
                description "L2 profile One";
            }
            enum l2-profile-two {
                value 1;
                description "L2 profile Two";
            }
            enum l2-profile-three {
                value 2;
                description "L2 profile Three (default)";
            }
            enum l3-profile {
                value 3;
                description "L3 profile";
            }
            enum l3-128bit-profile {
                value 4;
                description "L3 profile with 128 bit prefix support";
            }
            enum lpm-profile {
                value 5;
                description "LPM profile";
            }
            enum lpm-128bit-profile {
                value 6;
                description "LPM profile with 128 bit prefix support";
            }
            enum acl-profile {
                value 7;
                description "ACL profile";
            }
            enum custom-profile {
                value 8;
                description "custom profile";
            }
        }
        description "";
        reference "";
    }

    typedef  CML_WATCHDOG_T {
        type enumeration {
            enum software-watchdog {
                value 1;
                description "Software Watchdog";
            }
        }
        description "";
        reference "";
    }

    typedef  CML_WATCHDOG_MODULE_NAME_T {
        type enumeration {
            enum nsm {
                value 1;
                description "Software watchdog for NSM module";
            }
            enum ripd {
                value 2;
                description "Software watchdog for RIP module";
            }
            enum ripngd {
                value 3;
                description "Software watchdog for RIPNG module";
            }
            enum ospfd {
                value 4;
                description "Software watchdog for OSPF module";
            }
            enum ospf6d {
                value 5;
                description "Software watchdog for OSPF6 module";
            }
            enum isisd {
                value 6;
                description "Software watchdog for ISIS module";
            }
            enum hostpd {
                value 7;
                description "Software watchdog for HOSTP module";
            }
            enum mribd {
                value 10;
                description "Software watchdog for MRIB module";
            }
            enum pimd {
                value 11;
                description "Software watchdog for PIM module";
            }
            enum authd {
                value 13;
                description "Software watchdog for AUTH module";
            }
            enum mstpd {
                value 17;
                description "Software watchdog for MSTP module";
            }
            enum imi {
                value 18;
                description "Software watchdog for IMI module";
            }
            enum onmd {
                value 24;
                description "Software watchdog for ONM module";
            }
            enum hsl {
                value 26;
                description "Software watchdog for HSL module";
            }
            enum oamd {
                value 28;
                description "Software watchdog for OAM module";
            }
            enum vlogd {
                value 30;
                description "Software watchdog for VLOG module";
            }
            enum vrrpd {
                value 39;
                description "Software watchdog for VRRP module";
            }
            enum ndd {
                value 40;
                description "Software watchdog for NDD module";
            }
            enum ribd {
                value 42;
                description "Software watchdog for RIB module";
            }
            enum bgpd {
                value 44;
                description "Software watchdog for BGP module";
            }
            enum l2mribd {
                value 46;
                description "Software watchdog for L2MRIB module";
            }
            enum lagd {
                value 49;
                description "Software watchdog for LAG module";
            }
            enum sflow {
                value 50;
                description "Software watchdog for SFLOW module";
            }
            enum cmld {
                value 52;
                description "Software watchdog for CML module";
            }
            enum cmmd {
                value 69;
                description "Software watchdog for CMM module";
            }
        }
        description "";
        reference "";
    }

    typedef  CML_WATCHDOG_MODULE_STATUS_T {
        type enumeration {
            enum disabled {
                value 0;
                description "Disable software watchdog";
            }
            enum enabled {
                value 1;
                description "Enable software watchdog";
            }
        }
        description "";
        reference "";
    }

    typedef  CML_AGGREGATOR_TYPE_T {
        type enumeration {
            enum Layer3 {
                value 0;
                description "Layer3 aggregator";
            }
            enum Layer2 {
                value 1;
                description "Layer2 aggregator";
            }
        }
        description "";
        reference "";
    }

    typedef  CML_PROTOCOL_DEST_ADDR_TYPE_T {
        type enumeration {
            enum 01-80-c2-00-00-00 {
                value 0;
                description "LACP_NR_CUST_BR_ADDR";
            }
            enum 01-80-c2-00-00-02 {
                value 1;
                description "LACP_MCAST_GRP_ADDR";
            }
            enum 01-80-c2-00-00-03 {
                value 2;
                description "LACP_NR_NON_TPMR_BR_ADDR";
            }
        }
        description "";
        reference "";
    }

    typedef  CML_INTERFACE_SPEED_T {
        type enumeration {
            enum 10m {
                value 0;
                description "10 mega bits";
            }
            enum 100m {
                value 1;
                description "100 mega bits";
            }
            enum 1g {
                value 2;
                description "1 giga bits";
            }
            enum 2.5g {
                value 3;
                description "2.5 giga bits";
            }
            enum 10g {
                value 4;
                description "10 giga bits";
            }
            enum 20g {
                value 5;
                description "20 giga bits";
            }
            enum 25g {
                value 6;
                description "25 giga bits";
            }
            enum 40g {
                value 7;
                description "40 giga bits";
            }
            enum 50g {
                value 8;
                description "50 giga bits";
            }
            enum 100g {
                value 9;
                description "100 giga bits";
            }
            enum auto {
                value 10;
                description "Auto Negotiation";
            }
            enum auto-10m {
                value 11;
                description "Auto Negotiation, 10 mega bits";
            }
            enum auto-100m {
                value 12;
                description "Auto Negotiation, 100 mega bits";
            }
            enum auto-1g {
                value 13;
                description "Auto Negotiation, 1 giga bits";
            }
            enum auto-2.5g {
                value 14;
                description "Auto Negotiation, 2.5 giga bits";
            }
            enum auto-10g {
                value 15;
                description "Auto Negotiation, 10 giga bits";
            }
            enum auto-20g {
                value 16;
                description "Auto Negotiation, 20 giga bits";
            }
            enum auto-25g {
                value 17;
                description "Auto Negotiation, 25 giga bits";
            }
            enum auto-40g {
                value 18;
                description "Auto Negotiation, 40 giga bits";
            }
            enum auto-50g {
                value 19;
                description "Auto Negotiation, 50 giga bits";
            }
            enum auto-100g {
                value 20;
                description "Auto Negotiation, 100 giga bits";
            }
        }
        description "";
        reference "";
    }

    typedef  CML_RAW_STRING_T {

        type string;
        description "";
        reference "";
    }

    typedef  CML_SWITCHPORT_ETHERTYPE_T {
        type enumeration {
            enum dropped {
                value 0;
                description "dropped (0x0000)";
            }
            enum ipv4 {
                value 2048;
                description "IP (0x0800)";
            }
            enum arp {
                value 2054;
                description "Address Resolution Protocol (0x0806)";
            }
            enum ipv6 {
                value 34525;
                description "IPv6 (0x86DD)";
            }
            enum mpls {
                value 34887;
                description "mpls (0x8847)";
            }
        }
        description "";
        reference "";
    }

    typedef  CML_HOSTP_RBAC_RULE_TYPE_T {
        type enumeration {
            enum deny {
                value 0;
                description "Remove rule from policy";
            }
            enum permit {
                value 1;
                description "Add rule to policy";
            }
        }
        description "";
        reference "";
    }

    typedef  CML_HOSTP_RBAC_DEFAULT_RULE_TYPE_T {
        type enumeration {
            enum deny-all {
                value 0;
                description "Set default rule as deny-all";
            }
            enum permit-all {
                value 1;
                description "Set default rule as permit-all";
            }
        }
        description "";
        reference "";
    }

    typedef  CML_PORT_SECURITY_LOGGING_T {
        type enumeration {
            enum disable {
                value 0;
                description "Logging Disable";
            }
            enum enable {
                value 1;
                description "Logging Enable";
            }
        }
        description "";
        reference "";
    }

    typedef  CML_LIBHWCONF_LOADBALANCE {
        type enumeration {
            enum rtag7 {
                value 1;
                description "Load Balancing";
            }
        }
        description "";
        reference "";
    }

    typedef  CML_LIBHWCONF_CPU_QUEUE_LOSSY {
        type enumeration {
            enum lossless {
                value 0;
                description "Configure cpu queue as lossless";
            }
            enum lossy {
                value 1;
                description "Configure cpu queue as lossy";
            }
        }
        description "";
        reference "";
    }

    typedef  CML_LIBHWCONF_CPU_QUEUE_MONITOR {
        type enumeration {
            enum no-monitor {
                value 0;
                description "do not monitor cpu queue usage";
            }
            enum monitor {
                value 1;
                description "monitor cpu queue usage";
            }
        }
        description "";
        reference "";
    }

    typedef  CML_LIBHWCONF_CPU_QUEUE_NAME {
        type enumeration {
            enum best-effort {
                value 0;
                description "Best-effort queue parameters";
            }
            enum ipmc-miss {
                value 4;
                description "IPMC-Miss  queue parameters";
            }
            enum l3-miss {
                value 5;
                description "L3-Miss queue parameters";
            }
            enum sflow {
                value 9;
                description "SFLOW queue parameters";
            }
            enum bgp {
                value 10;
                description "BGP queue parameters";
            }
            enum vrrp {
                value 11;
                description "VRRP queue parameters";
            }
            enum rip {
                value 13;
                description "RIP queue parameters";
            }
            enum ospf {
                value 14;
                description "OSPF queue parameters";
            }
            enum dhcp {
                value 15;
                description "DHCP queue parameters";
            }
            enum nd {
                value 16;
                description "ND queue parameters";
            }
            enum pim {
                value 18;
                description "PIM queue parameters";
            }
            enum arp {
                value 19;
                description "ARP queue parameters";
            }
            enum igmp {
                value 20;
                description "IGMP queue parameters";
            }
            enum bpdu {
                value 21;
                description "BPDU queue parameters";
            }
            enum sw-bfd {
                value 23;
                description "BFD queue parameters";
            }
            enum isis {
                value 25;
                description "ISIS queue parameters";
            }
            enum acl {
                value 30;
                description "ACL queue parameters (for acl logging)";
            }
            enum vxlan {
                value 31;
                description "VXLAN queue parameters";
            }
        }
        description "";
        reference "";
    }

    typedef  CML_ACL_FILTER_TYPE_T {
        type enumeration {
            enum deny {
                value 0;
                description "Specify packets to reject";
            }
            enum permit {
                value 1;
                description "Specify packets to forward";
            }
        }
        description "";
        reference "";
    }

    typedef  CML_SUPPRESSRA_T {
        type enumeration {
            enum disable {
                value 0;
                description "Disable IPv6 Router Advertisements";
            }
            enum enable {
                value 1;
                description "Enable IPv6 Router Advertisements";
            }
        }
        description "";
        reference "";
    }

    typedef  CML_SUPPRESSRA_MTU_T {
        type enumeration {
            enum disable {
                value 0;
                description "Disable sending MTU in Router Advertisement messages";
            }
            enum enable {
                value 1;
                description "Enable sending MTU in Router Advertisement messages";
            }
        }
        description "";
        reference "";
    }

    typedef  CML_VM_STATUS_T {
        type enumeration {
            enum DOWN {
                value 0;
                description "DOWN";
            }
            enum UP {
                value 1;
                description "UP";
            }
        }
        description "";
        reference "";
    }

    typedef  CML_EVPN_SERVICE_TYPE_T {
        type enumeration {
            enum vlan-based {
                value 1;
                description "vlan-based EVPN-Service type";
            }
        }
        description "";
        reference "";
    }

}
