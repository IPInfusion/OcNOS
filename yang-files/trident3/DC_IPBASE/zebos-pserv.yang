/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-pserv.yang
*
*/

submodule zebos-pserv {

    belongs-to  zebos { prefix zebos; }

    import cml_data_types {
        prefix cml_data_types;
    }

    import feature_list {
        prefix feature_list;
    }

    organization
        "IP Infusion Inc.";

    contact
        "Address: 3965 Freedom Circle, Suite 200, Santa Clara, CA 95054
        Phone: +1 408-400-1900
        E-mail: support@ipinfusion.com
        Web: http://www.ipinfusion.com/";

    description
        "System Software status";


    revision "2018-04-05" {
        description " Initial Version.";
        reference "";
    }



    grouping cmmSoftwareProcessObjects-grouping {
    description
        "monitoring information for protocol Module running on the host";
        list cmmSoftwareProcessObjects {
            key "cmmSoftwareProcessID";
            config false;
            description
                "monitoring information for protocol Module running on the host";
            leaf cmmSoftwareProcessID  {
                type  cml_data_types:CML_UINT32_T;
                description "Each protocol module is uniquely identified with a number, also called as protocol module id";
            } // END of cmmSoftwareProcessID definition.

            leaf cmmSoftwareProcessName  {
                type  cml_data_types:CML_STRING_T;
                description "Protocol module name";
            } // END of cmmSoftwareProcessName definition.

            leaf cmmSoftwareProcessState  {
                type  cml_data_types:CML_PSSTATE_T;
                description "state of the process, whether its runnning or not running.";
            } // END of cmmSoftwareProcessState definition.

            leaf cmmSoftwareProcessStartTime  {
                type  cml_data_types:CML_DATE_TIME_T;
                description "The starting time of a protocol module, given in date and time.";
            } // END of cmmSoftwareProcessStartTime definition.

            leaf cmmSoftwareProcessLastRestartReason  {
                type  cml_data_types:CML_LINE_T;
                description "Reason for process to shutdown provided it was running.This value will be the signal description";
            } // END of cmmSoftwareProcessLastRestartReason definition.

        } // End of cmmSoftwareProcessObjects-list
    } // END of cmmSoftwareProcessObjects-grouping definition.

    grouping  pservd-grouping {
    description
        "System Software status";
    container pservd {
        presence "yes";
        description
            "System Software status";
        leaf featureWatchdog  {
            if-feature feature_list:HAVE_PSERVD;
            type  cml_data_types:CML_WATCHDOG_T;
            mandatory true;
            description "";
        } // END of featureWatchdog definition.

        leaf keepalivetime  {
            if-feature feature_list:HAVE_PSERVD;
            type  cml_data_types:CML_UINT32_T {
                 range "30..1800";
            }
            default "60";
            description "";
        } // END of keepalivetime definition.


        list watchdog {
            key "moduleName";
            description
                "watchdog";
            leaf moduleName  {
                type  cml_data_types:CML_WATCHDOG_MODULE_NAME_T;
                description "";
            } // END of moduleName definition.

            leaf status  {
                type  cml_data_types:CML_WATCHDOG_MODULE_STATUS_T;
                mandatory true;
                description "";
            } // END of status definition.

        } // End of watchdog-list
    } // END of pservd-container definition.
    } // END of pservd-container definition.

    grouping  cmmSoftwareProcessMgmt-grouping {
    description
        "system mib objects";
    container cmmSoftwareProcessMgmt {
        config false;
        description
            "system mib objects";
        leaf cmmSoftwareProcessKeepaliveTime  {
            type  cml_data_types:CML_UINT32_T {
                 range "30..1800";
            }
            default "60";
            description "software watchdog keep-alive time interval in seconds. Software watchdog monitors various module and restarts module on detection of any software anomalies like crash or hang.Device is rebooted on detection of NSM/HSL  crash or hang.";
        } // END of cmmSoftwareProcessKeepaliveTime definition.

        leaf cmmSoftwareProcessWatchdogStatus  {
            type  cml_data_types:CML_WATCHDOGSTATUS_T;
            description "This object indicates status of software watchdog monitoring . If value of this object is enabled then software watchdog is active and is monitoring software anomalies for various modules.";
        } // END of cmmSoftwareProcessWatchdogStatus definition.

        leaf cmmSoftwareProcessStatus  {
            type  cml_data_types:CML_GLOBAL_PSSTATE_T;
            description "Global process status of all modules, if all process are running then this value will be true otherwise it wil be false";
        } // END of cmmSoftwareProcessStatus definition.

    } // END of cmmSoftwareProcessMgmt-container definition.
    } // END of cmmSoftwareProcessMgmt-container definition.


}
