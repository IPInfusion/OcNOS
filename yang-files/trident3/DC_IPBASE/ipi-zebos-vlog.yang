/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-zebos-vlog.yang
*
*/

submodule ipi-zebos-vlog {

    belongs-to  ipi-zebos { prefix ipi-zebos; }

    import cml-data-types {
        prefix cml-data-types;
    }

    organization
        "IP Infusion Inc.";

    contact
        "Address: 3965 Freedom Circle, Suite 200, Santa Clara, CA 95054
        Phone: +1 408-400-1900
        E-mail: support@ipinfusion.com
        Web: http://www.ipinfusion.com/";

    description
        "vlog Managed Object";


    revision "2018-06-21" {
        description " Initial Version.";
        reference "";
    }


    grouping  logging-grouping {
    description
        "for logging cli's";
    container logging {
        description
            "for logging cli's";
        leaf vlog  {
            type  cml-data-types:CML_UINT8_T {
                 range "0..7";
            }
            default "2";
            description "";
        } // END of vlog definition.

    } // END of logging-container definition.
    } // END of logging-container definition.


}
