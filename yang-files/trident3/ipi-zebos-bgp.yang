/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-zebos-bgp.yang
*
*/

submodule ipi-zebos-bgp {

    belongs-to  ipi-zebos { prefix ipi-zebos; }

    import cml-data-types {
        prefix cml-data-types;
    }

    import feature-list {
        prefix feature-list;
    }

    organization
        "IP Infusion Inc.";

    contact
        "Address: 3965 Freedom Circle, Suite 200, Santa Clara, CA 95054
        Phone: +1 408-400-1900
        E-mail: support@ipinfusion.com
        Web: http://www.ipinfusion.com/";

    description
        "";


    revision "2018-06-21" {
        description " Initial Version.";
        reference "";
    }



    grouping bgp-grouping {
    description
        "bgp";
        list bgp {
            key "bgpAs";
            description
                "bgp";
            leaf bgpAs  {
                type  cml-data-types:CML_UINT32_T {
                     range "1..4294967295";
                }
                description "AS number";
            } // END of bgpAs definition.


            list view {
                key "view";
                description
                    "view";
                leaf view  {
                    type  cml-data-types:CML_STRING_T;
                    description "view name";
                } // END of view definition.

            } // End of view-list
            container bgpStats {
                config false;
                description
                    "This describes bgp Statistics";
                leaf bgpNeighborSntRcvMsgs  {
                    type  cml-data-types:CML_STRING_T;
                    description "Neighbor aggregated statistics sent/recived messages";
                } // END of bgpNeighborSntRcvMsgs definition.

                leaf bgpNeighborSntRcvBytes  {
                    type  cml-data-types:CML_STRING_T;
                    description "Neighbor aggregated statistics sent/recived bytes";
                } // END of bgpNeighborSntRcvBytes definition.

                leaf bgpNeighborSntRcvOpens  {
                    type  cml-data-types:CML_STRING_T;
                    description "Neighbor aggregated statistics sent/recived opens";
                } // END of bgpNeighborSntRcvOpens definition.

                leaf bgpNeighborSntRcvUpdates  {
                    type  cml-data-types:CML_STRING_T;
                    description "Neighbor aggregated statistics sent/recived Updates";
                } // END of bgpNeighborSntRcvUpdates definition.

                leaf bgpNeighborSntRcvKeepalive  {
                    type  cml-data-types:CML_STRING_T;
                    description "Neighbor aggregated statistics sent/recived keepalives";
                } // END of bgpNeighborSntRcvKeepalive definition.

                leaf bgpNeighborSntRcvNotif  {
                    type  cml-data-types:CML_STRING_T;
                    description "Neighbor aggregated statistics sent/recived Notifications";
                } // END of bgpNeighborSntRcvNotif definition.

                leaf bgpNeighborSntRcvRoutRf  {
                    type  cml-data-types:CML_STRING_T;
                    description "Neighbor aggregated statistics sent/recived route-refresh";
                } // END of bgpNeighborSntRcvRoutRf definition.

                leaf bgpNeighborSntRcvCap  {
                    type  cml-data-types:CML_STRING_T;
                    description "Neighbor aggregated statistics sent/recived Capabilities";
                } // END of bgpNeighborSntRcvCap definition.

                leaf bgpActiveOpen  {
                    type  cml-data-types:CML_UINT16_T;
                    description "Active Open attempts";
                } // END of bgpActiveOpen definition.

                leaf bgpPassiveOpen  {
                    type  cml-data-types:CML_UINT16_T;
                    description "Passive Open attempts ";
                } // END of bgpPassiveOpen definition.

                leaf bgpIoOpenLoops  {
                    type  cml-data-types:CML_UINT16_T;
                    description "BGP I/O Open loops ";
                } // END of bgpIoOpenLoops definition.

                leaf bgpIoOpenCalls  {
                    type  cml-data-types:CML_UINT16_T;
                    description "BGP I/O Open calls";
                } // END of bgpIoOpenCalls definition.

                leaf bgpOpenIoRcvCalls  {
                    type  cml-data-types:CML_UINT16_T;
                    description "BGP I/O Open recv calls";
                } // END of bgpOpenIoRcvCalls definition.

                leaf bgpIoSendCalls  {
                    type  cml-data-types:CML_UINT16_T;
                    description "BGP I/O Send calls";
                } // END of bgpIoSendCalls definition.

                leaf bgpIoRecvCalls  {
                    type  cml-data-types:CML_UINT16_T;
                    description "BGP I/O Recv calls";
                } // END of bgpIoRecvCalls definition.

                leaf bgpIoWriteCalls  {
                    type  cml-data-types:CML_UINT16_T;
                    description "BGP I/O Write calls";
                } // END of bgpIoWriteCalls definition.

                leaf bgpIoWriteLoops  {
                    type  cml-data-types:CML_UINT16_T;
                    description "BGP I/O Write loops";
                } // END of bgpIoWriteLoops definition.

                leaf bgpIoWrloopYield  {
                    type  cml-data-types:CML_UINT16_T;
                    description "BGP I/O Write loop yields";
                } // END of bgpIoWrloopYield definition.

                leaf bgpIoReadloopCall  {
                    type  cml-data-types:CML_UINT16_T;
                    description "BGP I/O Read calls";
                } // END of bgpIoReadloopCall definition.

                leaf bgpIoReadloops  {
                    type  cml-data-types:CML_UINT16_T;
                    description "BGP I/O Read loops";
                } // END of bgpIoReadloops definition.

                leaf bgpIoReadloopYield  {
                    type  cml-data-types:CML_UINT16_T;
                    description "BGP I/O Read loop yields";
                } // END of bgpIoReadloopYield definition.

                leaf bgpIoProcNlriYld  {
                    type  cml-data-types:CML_UINT16_T;
                    description "BGP I/O process nlri yields";
                } // END of bgpIoProcNlriYld definition.

                leaf bgpIoProcWithdrawYld  {
                    type  cml-data-types:CML_UINT16_T;
                    description "BGP I/O process withdraw yields";
                } // END of bgpIoProcWithdrawYld definition.

                leaf bgpReadTimeExceed  {
                    type  cml-data-types:CML_UINT16_T;
                    description "BGP Read time exceeded";
                } // END of bgpReadTimeExceed definition.

                leaf bgpUpdateSndPending  {
                    type  cml-data-types:CML_UINT16_T;
                    description "BGP Update send pending";
                } // END of bgpUpdateSndPending definition.

                leaf bgpUpdateBufferNA  {
                    type  cml-data-types:CML_UINT16_T;
                    description "BGP Update buffer not available";
                } // END of bgpUpdateBufferNA definition.

                leaf bgpUpdateWalkSuspend  {
                    type  cml-data-types:CML_UINT16_T;
                    description "BGP Update walk suspended";
                } // END of bgpUpdateWalkSuspend definition.

                leaf bgpYldInUpdate  {
                    type  cml-data-types:CML_UINT16_T;
                    description "BGP Yielded in updates";
                } // END of bgpYldInUpdate definition.

                leaf bgpYldInPack  {
                    type  cml-data-types:CML_UINT16_T;
                    description "BGP Yielded in packing";
                } // END of bgpYldInPack definition.

                leaf bgpNoSendPeerBuf  {
                    type  cml-data-types:CML_UINT16_T;
                    description "BGP No sendbuf for peer";
                } // END of bgpNoSendPeerBuf definition.

                leaf bgpNoWdrwPeerBuf  {
                    type  cml-data-types:CML_UINT16_T;
                    description "BGP No withdraw buf for peer";
                } // END of bgpNoWdrwPeerBuf definition.

                leaf bgpYldInUpPeerLoop  {
                    type  cml-data-types:CML_UINT16_T;
                    description "BGP Yields in update peer loop";
                } // END of bgpYldInUpPeerLoop definition.

                leaf bgpNoUpPenRNobuf  {
                    type  cml-data-types:CML_UINT16_T;
                    description "No updates pending or no buffers";
                } // END of bgpNoUpPenRNobuf definition.

                leaf bgpNoDataToWr  {
                    type  cml-data-types:CML_UINT16_T;
                    description "No data to write";
                } // END of bgpNoDataToWr definition.

                leaf bgpMsgQRcvErr  {
                    type  cml-data-types:CML_UINT16_T;
                    description "Msg queue recv errors";
                } // END of bgpMsgQRcvErr definition.

                leaf bgpSocCreateAccClose  {
                    type  cml-data-types:CML_STRING_T;
                    description "Sockets create/accept/close";
                } // END of bgpSocCreateAccClose definition.

                leaf bgpSocCreateRtrOrFail  {
                    type  cml-data-types:CML_STRING_T;
                    description "Sockets create retries/failures";
                } // END of bgpSocCreateRtrOrFail definition.

                leaf bgpSocFdCloseSess  {
                    type  cml-data-types:CML_UINT32_T;
                    description "Socket fd-close session";
                } // END of bgpSocFdCloseSess definition.

                leaf bgpMemPoolAdvCnt  {
                    type  cml-data-types:CML_UINT32_T;
                    description "MemPool count- Advertise";
                } // END of bgpMemPoolAdvCnt definition.

                leaf bgpMemPoolAdvTime  {
                    type  cml-data-types:CML_STRING_T;
                    description "MemPool time in microsec - Advertise";
                } // END of bgpMemPoolAdvTime definition.

                leaf bgpMemPoolAdvSlotSect  {
                    type  cml-data-types:CML_STRING_T;
                    description "MemPool slot sector count - Advertise";
                } // END of bgpMemPoolAdvSlotSect definition.

                leaf bgpMemPoolAdvTotalCnt  {
                    type  cml-data-types:CML_UINT32_T;
                    description "MemPool total count - Advertise";
                } // END of bgpMemPoolAdvTotalCnt definition.

                leaf bgpMemPoolAdvTotalBlkSize  {
                    type  cml-data-types:CML_UINT32_T;
                    description "MemPool Total block size - Advertise";
                } // END of bgpMemPoolAdvTotalBlkSize definition.

                leaf bgpMemPoolAdvBlkSize  {
                    type  cml-data-types:CML_UINT32_T;
                    description "MemPool Adjusted block size - Advertise";
                } // END of bgpMemPoolAdvBlkSize definition.

                leaf bgpMemPoolAdjCnt  {
                    type  cml-data-types:CML_UINT32_T;
                    description "MemPool count- Adjout";
                } // END of bgpMemPoolAdjCnt definition.

                leaf bgpMemPoolAdjTime  {
                    type  cml-data-types:CML_STRING_T;
                    description "MemPool time in microsec - Adjout";
                } // END of bgpMemPoolAdjTime definition.

                leaf bgpMemPoolAdjSlotSect  {
                    type  cml-data-types:CML_STRING_T;
                    description "MemPool slot sector count - Adjout";
                } // END of bgpMemPoolAdjSlotSect definition.

                leaf bgpMemPoolAdjTotalCnt  {
                    type  cml-data-types:CML_UINT32_T;
                    description "MemPool total count - Adjout";
                } // END of bgpMemPoolAdjTotalCnt definition.

                leaf bgpMemPoolAdjTotalBlkSize  {
                    type  cml-data-types:CML_UINT32_T;
                    description "MemPool Total block size - Adjout";
                } // END of bgpMemPoolAdjTotalBlkSize definition.

                leaf bgpMemPoolAdjBlkSize  {
                    type  cml-data-types:CML_UINT32_T;
                    description "MemPool Adjusted block size - Adjout";
                } // END of bgpMemPoolAdjBlkSize definition.

            } // END of bgpStats-container definition.
            uses bgpAttrs;
        } // End of bgp-list
    } // END of bgp-grouping definition.
    grouping bgpAttrs {
        description
            "bgpAttrs";
        leaf bgpVersion  {
            type  cml-data-types:CML_INT32_T;
            config false;
            description "BGP version";
        } // END of bgpVersion definition.

        leaf bgpTableVersion  {
            type  cml-data-types:CML_INT32_T;
            config false;
            description "BGP table version";
        } // END of bgpTableVersion definition.

        leaf ntwkPrefixCount  {
            type  cml-data-types:CML_INT32_T;
            config false;
            description "Network prefix count";
        } // END of ntwkPrefixCount definition.

        leaf nhtConfigured  {
            type  cml-data-types:CML_BOOL_T;
            config false;
            description "Configured NHT";
        } // END of nhtConfigured definition.

        leaf nhtDlyTime  {
            type  cml-data-types:CML_INT32_T;
            config false;
            description "NHT Delay time-interval";
        } // END of nhtDlyTime definition.

        leaf nhtRcvMsgCnt  {
            type  cml-data-types:CML_STRING_T;
            config false;
            description "Recvd Msg count from RIB/NSM";
        } // END of nhtRcvMsgCnt definition.

        leaf nhtIpv4Cnt  {
            type  cml-data-types:CML_INT32_T;
            config false;
            description "Total number of IPV4 nexthops";
        } // END of nhtIpv4Cnt definition.

        leaf nhtIpv6Cnt  {
            type  cml-data-types:CML_INT32_T;
            config false;
            description "Total number of IPV6 nexthops";
        } // END of nhtIpv6Cnt definition.

        leaf nhtDlyTimeRemain  {
            type  cml-data-types:CML_INT32_T;
            config false;
            description "NHT delay-timer remaining seconds";
        } // END of nhtDlyTimeRemain definition.

        leaf routerIpAddr  {
            type  cml-data-types:CML_IPV4_ADDR_T;
            description "bgp manually configure router-id";
        } // END of routerIpAddr definition.

        leaf routerRunIpAddr  {
            type  cml-data-types:CML_STRING_T;
            config false;
            description "bgp router-id";
        } // END of routerRunIpAddr definition.

        leaf clusterId  {
            type  cml-data-types:CML_CLUSTER_ID_T;
            description "BGP route reflector cluster ID";
        } // END of clusterId definition.

        leaf confedId  {
            type  cml-data-types:CML_UINT32_T {
                 range "1..4294967295";
            }
            description "Confederation ID";
        } // END of confedId definition.

        leaf keepAlive  {
            type  cml-data-types:CML_UINT16_T {
                 range "0..65535";
            }
            default "30";
            description "BGP keepalive time";
        } // END of keepAlive definition.

        leaf holdTime  {
            type  cml-data-types:CML_UINT16_T {
                 range "0..65535";
            }
            default "90";
            description "BGP holdtime";
        } // END of holdTime definition.

        leaf localPref  {
            type  cml-data-types:CML_UINT32_T {
                 range "0..4294967295";
            }
            default "100";
            description "BGP default local preference";
        } // END of localPref definition.

        leaf setGshutCapable  {
            type  cml-data-types:CML_BOOL_T;
            description "bgp g-shut capable";
        } // END of setGshutCapable definition.

        leaf setGshut  {
            type  cml-data-types:CML_BOOL_T;
            description "bgp g-shut";
        } // END of setGshut definition.

        leaf gshutLocalPref  {
            type  cml-data-types:CML_UINT32_T {
                 range "0..4294967295";
            }
            default "0";
            description "bgp g-shut local preference";
        } // END of gshutLocalPref definition.

        leaf setInboundRouteFilter  {
            if-feature feature-list:HAVE_VRF;
            type  cml-data-types:CML_BOOL_T;
            description "bgp inbound route-filter";
        } // END of setInboundRouteFilter definition.

        leaf setLogNbrChanges  {
            type  cml-data-types:CML_BOOL_T;
            description "bgp log-neighbor changes";
        } // END of setLogNbrChanges definition.

        leaf scanInterval  {
            type  cml-data-types:CML_UINT32_T {
                 range "0..60";
            }
            default "60";
            description "Scan interval (sec)";
        } // END of scanInterval definition.

        leaf distance  {
            type  cml-data-types:CML_UINT8_T {
                 range "1..255";
            }
            description "bgp distance";
        } // END of distance definition.

        leaf distanceSrcIp  {
            type  cml-data-types:CML_IPV4_PREFIX_T;
            description "bgp distance source ip";
        } // END of distanceSrcIp definition.

        leaf distanceACLName  {
            type  cml-data-types:CML_STRING_T;
            description "Access list name";
        } // END of distanceACLName definition.

        leaf setMplsResolution  {
            if-feature feature-list:HAVE_MPLS;
            type  cml-data-types:CML_BOOL_T;
            description "MPLS LSP resolution for BGP prefixes";
        } // END of setMplsResolution definition.

        leaf restartTime  {
            if-feature feature-list:HAVE_RESTART;
            type  cml-data-types:CML_UINT32_T {
                 range "1..3600";
            }
            default "90";
            description "Max time needed for Neighbor(s) to restart";
        } // END of restartTime definition.

        leaf stalepathTime  {
            if-feature feature-list:HAVE_RESTART;
            type  cml-data-types:CML_UINT32_T {
                 range "1..3600";
            }
            default "360";
            description "Max time to retain stale paths from restarting Neighbor";
        } // END of stalepathTime definition.

        leaf deferTime  {
            if-feature feature-list:HAVE_RESTART;
            type  cml-data-types:CML_UINT32_T {
                 range "1..3600";
            }
            default "120";
            description "Max time to defer initial route-selection";
        } // END of deferTime definition.

        leaf bestpathDontCompareOriginator  {
            type  cml-data-types:CML_BOOL_T;
            description "Don't Compare originator-id";
        } // END of bestpathDontCompareOriginator definition.

        leaf noBestpathTieBreak  {
            type  cml-data-types:CML_BOOL_T;
            description "tie break on age";
        } // END of noBestpathTieBreak definition.

        leaf noIpv4Unicast  {
            type  cml-data-types:CML_BOOL_T;
            description "ipv4-unicast for a peer";
        } // END of noIpv4Unicast definition.

        leaf deterministicMed  {
            type  cml-data-types:CML_BOOL_T;
            description "deterministic med";
        } // END of deterministicMed definition.

        leaf compareMed  {
            type  cml-data-types:CML_BOOL_T;
            description "always compare med";
        } // END of compareMed definition.

        leaf bestpathAspath  {
            type  cml-data-types:CML_BOOL_T;
            description "as-path ignore";
        } // END of bestpathAspath definition.

        leaf bestpathCompareConfed  {
            type  cml-data-types:CML_BOOL_T;
            description "compare confed aspath";
        } // END of bestpathCompareConfed definition.

        leaf bestpathCompareRouterId  {
            type  cml-data-types:CML_BOOL_T;
            description "compare router-id";
        } // END of bestpathCompareRouterId definition.

        leaf enforceFirst  {
            type  cml-data-types:CML_BOOL_T;
            description "enforce first as";
        } // END of enforceFirst definition.

        leaf noExternalFailover  {
            type  cml-data-types:CML_BOOL_T;
            description "fast external failover";
        } // END of noExternalFailover definition.

        leaf allocateLabelAll  {
            if-feature feature-list:HAVE_BGP_LU;
            type  cml-data-types:CML_BOOL_T;
            description "allocate-label all the advertised routes";
        } // END of allocateLabelAll definition.

        leaf RouteMapName  {
            if-feature feature-list:HAVE_BGP_LU;
            type  cml-data-types:CML_STRING_T;
            description "route-map name";
        } // END of RouteMapName definition.

        leaf ebgpMaxPath  {
            type  cml-data-types:CML_INT32_T {
                 range "2..64";
            }
            default "2";
            description "BGP ECMP eBGP max-paths";
        } // END of ebgpMaxPath definition.

        leaf ibgpMaxPath  {
            type  cml-data-types:CML_INT32_T {
                 range "2..64";
            }
            default "2";
            description "BGP ECMP eBGP max-paths";
        } // END of ibgpMaxPath definition.

        leaf eibgpMaxPath  {
            type  cml-data-types:CML_INT32_T {
                 range "2..64";
            }
            default "2";
            description "BGP ECMP eBGP/iBGP max-paths";
        } // END of eibgpMaxPath definition.

        leaf autoSummary  {
            type  cml-data-types:CML_BOOL_T;
            description "auto summary enable/disable";
        } // END of autoSummary definition.

        leaf setSyncFlag  {
            type  cml-data-types:CML_BOOL_T;
            description "synchronization enable/disable";
        } // END of setSyncFlag definition.

        leaf setNwSyncFlag  {
            type  cml-data-types:CML_BOOL_T;
            description "network synchronization enable/disable";
        } // END of setNwSyncFlag definition.

        leaf localAsCount  {
            type  cml-data-types:CML_UINT8_T {
                 range "2..64";
            }
            description "as local count";
        } // END of localAsCount definition.

        leaf grstSet  {
            if-feature feature-list:HAVE_RESTART;
            type  cml-data-types:CML_BOOL_T;
            description "bgp graceful restart capability enable/disable";
        } // END of grstSet definition.

        leaf noSetClientReflect  {
            type  cml-data-types:CML_BOOL_T;
            description "client-client reflection";
        } // END of noSetClientReflect definition.

        leaf rfdMaxPenaltyCeil  {
            type  cml-data-types:CML_INT32_T;
            default "0";
            config false;
            description "dampening penalty ceil";
        } // END of rfdMaxPenaltyCeil definition.

        leaf rfdMinPenaltyFloor  {
            type  cml-data-types:CML_INT32_T;
            default "0";
            config false;
            description "dampening penalty floor";
        } // END of rfdMinPenaltyFloor definition.

        leaf medType  {
            type  cml-data-types:CML_BGP_MED_TYPE_T;
            description "MED in confederation paths";
        } // END of medType definition.

        leaf gracefulReset  {
            type  cml-data-types:CML_BOOL_T;
            description "bpg graceful restart capability enable/disable";
        } // END of gracefulReset definition.

        leaf distanceEbgp  {
            type  cml-data-types:CML_UINT8_T {
                 range "1..255";
            }
            default "20";
            description "Distance for routes external to the AS";
        } // END of distanceEbgp definition.

        leaf distanceIbgp  {
            type  cml-data-types:CML_UINT8_T {
                 range "1..255";
            }
            default "200";
            description "Distance for routes internal to the AS";
        } // END of distanceIbgp definition.

        leaf distanceLocal  {
            type  cml-data-types:CML_UINT8_T {
                 range "1..255";
            }
            default "200";
            description "Distance for local routes <1-255>";
        } // END of distanceLocal definition.

        leaf multipathRelax  {
            type  cml-data-types:CML_BOOL_T;
            description "Relax as-path in selecting a route";
        } // END of multipathRelax definition.

        leaf tableMap  {
            if-feature feature-list:HAVE_BGP_TABLE_MAP;
            type  cml-data-types:CML_STRING_T;
            description "bgp table map name";
        } // END of tableMap definition.

        leaf tableMapFilter  {
            if-feature feature-list:HAVE_BGP_TABLE_MAP;
            type  cml-data-types:CML_BOOL_T;
            description "bgp table-map filter enable/disable";
        } // END of tableMapFilter definition.

        leaf SetAddPathFlag  {
            if-feature feature-list:HAVE_BGP_PIC_CORE_EDGE;
            type  cml-data-types:CML_BOOL_T;
            description "BGP additional-paths set flag";
        } // END of SetAddPathFlag definition.

        leaf SetAddPathFrrFlag  {
            if-feature feature-list:HAVE_BGP_PIC_CORE_EDGE;
            type  cml-data-types:CML_BOOL_T;
            description "bgp additional-paths frr set flag";
        } // END of SetAddPathFrrFlag definition.

        leaf additionalPaths  {
            if-feature feature-list:HAVE_BGP_ADD_PATH;
            type  cml-data-types:BGP_ADDITIONAL_PATH_TYPE_T;
            description "bgp additional-paths";
        } // END of additionalPaths definition.

        leaf addPathSelectAll  {
            if-feature feature-list:HAVE_BGP_ADD_PATH;
            type  cml-data-types:CML_BOOL_T;
            description "bgp additional-paths select all path";
        } // END of addPathSelectAll definition.

        leaf bestCount  {
            if-feature feature-list:HAVE_BGP_ADD_PATH;
            type  cml-data-types:CML_UINT8_T {
                 range "2..3";
            }
            description "bgp additional-paths select n best path";
        } // END of bestCount definition.


        list bgpConfed {
            key "peerConfedId";
            description
                "bgpConfed";
            leaf peerConfedId  {
                type  cml-data-types:CML_UINT32_T {
                     range "1..4294967295";
                }
                description "Peer confederation ID";
            } // END of peerConfedId definition.

        } // End of bgpConfed-list

        list bgpNetworkList {
            key "localAddr";
            description
                "bgpNetworkList";
            leaf localAddr  {
                type  cml-data-types:CML_BGP_NETWORK_T;
                description "network address";
            } // END of localAddr definition.

            leaf networkRmapName  {
                type  cml-data-types:CML_STRING_T;
                description "route-map name";
            } // END of networkRmapName definition.

            leaf backdoor  {
                type  cml-data-types:CML_BOOL_T;
                default false;
                description "network address with backdoor option set/unset";
            } // END of backdoor definition.

            uses nwRunTimeAttr;
        } // End of bgpNetworkList-list

        list bgpAggregateAddrList {
            key "aggregateAddr";
            description
                "bgpAggregateAddrList";
            leaf aggregateAddr  {
                type  cml-data-types:CML_IPV4_PREFIX_T;
                description "aggregate prefix to minimize the size of routing tables";
            } // END of aggregateAddr definition.

            leaf aggregateAsSet  {
                type  cml-data-types:CML_BOOL_T;
                default true;
                description "aggregate as set/unset";
            } // END of aggregateAsSet definition.

            leaf aggregateSummOnly  {
                type  cml-data-types:CML_BOOL_T;
                default true;
                description "aggregate summary-only set/unset";
            } // END of aggregateSummOnly definition.

        } // End of bgpAggregateAddrList-list

        list bgpRedistList {
            key "redistType";
            description
                "bgpRedistList";
            leaf redistType  {
                type  cml-data-types:CML_BGP_REDISTRIBUTE_TYPE_T;
                description "bgp redistribute route";
            } // END of redistType definition.

            leaf redistRmapName  {
                type  cml-data-types:CML_STRING_T;
                description "bgp route redistribute type";
            } // END of redistRmapName definition.

        } // End of bgpRedistList-list

        list bgpRedistOspfNo {
            key "redistOspfNo";
            description
                "bgpRedistOspfNo";
            leaf redistOspfNo  {
                type  cml-data-types:CML_UINT32_T {
                     range "0..65535";
                }
                description "bgp redistribute route OSPF process ID";
            } // END of redistOspfNo definition.

            leaf redistOspfRmap  {
                type  cml-data-types:CML_STRING_T;
                description "bgp redistribute route OSPF route-map name";
            } // END of redistOspfRmap definition.

        } // End of bgpRedistOspfNo-list

        list bgpPeerGroup {
            key "peerGroupTag";
            description
                "bgpPeerGroup";
            leaf peerGroupTag  {
                type  cml-data-types:CML_STRING_T;
                description "bgp peer-group name";
            } // END of peerGroupTag definition.

            leaf peerGroupRange  {
                type  cml-data-types:CML_STRING_T;
                description "bgp peer-group network range";
            } // END of peerGroupRange definition.

            leaf groupLimit  {
                type  cml-data-types:CML_UINT8_T {
                     range "1..200";
                }
                description "bgp dynamic peer-group limit";
            } // END of groupLimit definition.


            list OptionalASList {
                key "optionalAS";
                description
                    "OptionalASList";
                leaf optionalAS  {
                    type  cml-data-types:CML_UINT32_T {
                         range "1..4294967295";
                    }
                    description "Optional AS number";
                } // END of optionalAS definition.

            } // End of OptionalASList-list
            uses peerAndPeerGroupAttrs;
        } // End of bgpPeerGroup-list

        list bgpAddressFamily {
            key "afi";
            description
                "bgpAddressFamily";
            leaf afi  {
                type  cml-data-types:CML_AFI_TYPE_T;
                description "bgp address family type";
            } // END of afi definition.


            list bgpSubAddressFamily {
                key "safi";
                description
                    "bgpSubAddressFamily";
                leaf safi  {
                    type  cml-data-types:CML_SAFI_TYPE_T;
                    description "bgp sub address family";
                } // END of safi definition.

                leaf SetAddPathFrrFlagAf  {
                    if-feature feature-list:HAVE_BGP_PIC_CORE_EDGE;
                    type  cml-data-types:CML_BOOL_T;
                    description "bgp additional-paths frr set flag for address-family";
                } // END of SetAddPathFrrFlagAf definition.

                leaf additionalPathsAf  {
                    if-feature feature-list:HAVE_BGP_ADD_PATH;
                    type  cml-data-types:BGP_ADDITIONAL_PATH_TYPE_T;
                    description "bgp additional-paths for address-family";
                } // END of additionalPathsAf definition.

                leaf addPathSelectAllAf  {
                    if-feature feature-list:HAVE_BGP_ADD_PATH;
                    type  cml-data-types:CML_BOOL_T;
                    description "bgp additional-paths select all path at address-family level";
                } // END of addPathSelectAllAf definition.

                leaf bestCountAf  {
                    if-feature feature-list:HAVE_BGP_ADD_PATH;
                    type  cml-data-types:CML_UINT8_T {
                         range "2..3";
                    }
                    description "bgp additional-paths select best path at address-family level";
                } // END of bestCountAf definition.

                leaf noSetClientReflectAf  {
                    type  cml-data-types:CML_BOOL_T;
                    description "bgp set/unset client-to-client reflection for address-family";
                } // END of noSetClientReflectAf definition.


                list bgpAddressFamilyAggregateAddrList {
                    key "aggregateAddrAf";
                    description
                        "bgpAddressFamilyAggregateAddrList";
                    leaf aggregateAddrAf  {
                        type  cml-data-types:CML_IPV6_PREFIX_T;
                        description "aggregate prefix to minimize the size of routing tables for address-family";
                    } // END of aggregateAddrAf definition.

                    leaf aggregateAsSetAf  {
                        type  cml-data-types:CML_BOOL_T;
                        default false;
                        description "aggregate as set/unset for address family";
                    } // END of aggregateAsSetAf definition.

                    leaf aggregateSummOnlyAf  {
                        type  cml-data-types:CML_BOOL_T;
                        default false;
                        description "aggregate summary-only set/unset for address family";
                    } // END of aggregateSummOnlyAf definition.

                } // End of bgpAddressFamilyAggregateAddrList-list
                uses bgpAfAttrs;
                uses networkAfAttrs;
            } // End of bgpSubAddressFamily-list
        } // End of bgpAddressFamily-list

        list vrfAddressFamily {
            key "afi";
            description
                "vrfAddressFamily";
            leaf afi  {
                type  cml-data-types:CML_VRF_AFI_TYPE_T;
                description "bgp address family vrf";
            } // END of afi definition.


            list vrfSubAddressFamily {
                key "safi";
                description
                    "vrfSubAddressFamily";
                leaf safi  {
                    type  cml-data-types:CML_VRF_SAFI_TYPE_T;
                    description "bgp sub-address family vrf";
                } // END of safi definition.


                list afVrfObj {
                    key "vrfName";
                    description
                        "afVrfObj";
                    leaf vrfName  {
                        type  cml-data-types:CML_STRING_T;
                        description "bgp vrf name ";
                    } // END of vrfName definition.

                    leaf setGshutAf  {
                        type  cml-data-types:CML_BOOL_T;
                        description "bgp g-shut for address family";
                    } // END of setGshutAf definition.

                    leaf setGshutCapableAf  {
                        type  cml-data-types:CML_BOOL_T;
                        description "bgp g-shut-capable for address-family";
                    } // END of setGshutCapableAf definition.

                    leaf gshutLocalPrefAf  {
                        type  cml-data-types:CML_UINT32_T {
                             range "0..4294967295";
                        }
                        default "0";
                        description "bgp g-shut-local-preference for address-family";
                    } // END of gshutLocalPrefAf definition.

                    leaf confedIdAf  {
                        type  cml-data-types:CML_UINT32_T {
                             range "1..4294967295";
                        }
                        description "bgp confederation id for address-family";
                    } // END of confedIdAf definition.


                    list bgpConfed {
                        key "peerConfedIdAf";
                        description
                            "bgpConfed";
                        leaf peerConfedIdAf  {
                            type  cml-data-types:CML_UINT32_T {
                                 range "1..4294967295";
                            }
                            description "Confederation ID <1-4294967295>";
                        } // END of peerConfedIdAf definition.

                    } // End of bgpConfed-list

                    list vrfPeer {
                        key "peerAddr";
                        description
                            "vrfPeer";
                        leaf peerAddr  {
                            type  cml-data-types:CML_HOSTNAME_T;
                            description "The peer address or Tag";
                        } // END of peerAddr definition.

                        leaf peerAsAf  {
                            type  cml-data-types:CML_UINT32_T {
                                 range "1..4294967295";
                            }
                            description "Remote AS number for Address-family";
                        } // END of peerAsAf definition.

                        leaf sourceIdAf  {
                            type  cml-data-types:CML_STRING_T;
                            default "NULL";
                            description "bgp neighbor update-source for address-family";
                        } // END of sourceIdAf definition.

                        leaf peerLocalAsAf  {
                            type  cml-data-types:CML_UINT32_T {
                                 range "1..4294967295";
                            }
                            description "neighbor local-as for address family";
                        } // END of peerLocalAsAf definition.

                        leaf sendLabelAf  {
                            type  cml-data-types:CML_BOOL_T;
                            description "bgp send-label to neighbour for address-family";
                        } // END of sendLabelAf definition.

                        leaf sendLabelExplicitNullAf  {
                            type  cml-data-types:CML_BOOL_T;
                            description "bgp send-label explicit-null to neighbour for address-family";
                        } // END of sendLabelExplicitNullAf definition.

                        leaf bgpVersionAf  {
                            type  cml-data-types:CML_UINT8_T;
                            default "4";
                            description "BGP Version for Address Family";
                        } // END of bgpVersionAf definition.

                        leaf peerConnectIntervalAf  {
                            type  cml-data-types:CML_UINT32_T {
                                 range "1..65535";
                            }
                            default "1";
                            description "Connect timer value for address-family";
                        } // END of peerConnectIntervalAf definition.

                        leaf peerKeepAliveAf  {
                            type  cml-data-types:CML_UINT16_T {
                                 range "0..65535";
                            }
                            default "30";
                            description "BGP keepalive time address-family";
                        } // END of peerKeepAliveAf definition.

                        leaf peerHoldTimeAf  {
                            type  cml-data-types:CML_UINT16_T {
                                 range "0..65535";
                            }
                            default "90";
                            description "BGP holdtime for address-family";
                        } // END of peerHoldTimeAf definition.

                        leaf enforceMultihopAf  {
                            type  cml-data-types:CML_BOOL_T;
                            description "bgp neighbor enforce-multihop set/unset for address-family";
                        } // END of enforceMultihopAf definition.

                        leaf peerShutdownAf  {
                            type  cml-data-types:CML_BOOL_T;
                            description "bgp neighbor set/unset shutdown for address-family";
                        } // END of peerShutdownAf definition.

                        leaf peerGroupStrAf  {
                            type  cml-data-types:CML_BOOL_T;
                            description "bgp peer-group name for address family";
                        } // END of peerGroupStrAf definition.

                        leaf peerGroupRangeAf  {
                            type  cml-data-types:CML_STRING_T;
                            description "bgp peer-group network range for address-family";
                        } // END of peerGroupRangeAf definition.

                        leaf groupLimitAf  {
                            type  cml-data-types:CML_UINT8_T {
                                 range "1..200";
                            }
                            description "bgp dynamic peer-group limit for address-family";
                        } // END of groupLimitAf definition.

                        leaf passwordAf  {
                            if-feature feature-list:HAVE_TCP_MD5SIG;
                            type  cml-data-types:CML_MD5_PASSWORD_T;
                            default "NULL";
                            description "bgp neighbor authentication password for address-family";
                        } // END of passwordAf definition.

                        leaf transportConnectionPassiveAf  {
                            type  cml-data-types:CML_BOOL_T;
                            description "bgp neighbor set/unset passive for address-family";
                        } // END of transportConnectionPassiveAf definition.

                        leaf maxHopCountAf  {
                            type  cml-data-types:CML_UINT8_T {
                                 range "1..255";
                            }
                            default "255";
                            description "bgp neighbor max ebgp-multihop count for address-family";
                        } // END of maxHopCountAf definition.

                        leaf timeToLiveAf  {
                            type  cml-data-types:CML_BOOL_T;
                            description "bgp neighbor set/unset time-to-live for address-family";
                        } // END of timeToLiveAf definition.

                        leaf dontCapabilityNegotiateAf  {
                            type  cml-data-types:CML_BOOL_T;
                            description "bgp neighbor set/unset dont-capability-negotiate for address-family";
                        } // END of dontCapabilityNegotiateAf definition.

                        leaf connRetryIntervalAf  {
                            type  cml-data-types:CML_INT32_T {
                                 range "1..65535";
                            }
                            default "120";
                            description "bgp Connect timer value for address-family";
                        } // END of connRetryIntervalAf definition.

                        leaf dynamicCapabilityAf  {
                            type  cml-data-types:CML_BOOL_T;
                            description "bgp neighbor dynamic capability set/unset for address-family";
                        } // END of dynamicCapabilityAf definition.

                        leaf peerRaIntervalAf  {
                            type  cml-data-types:CML_UINT32_T {
                                 range "0..65535";
                            }
                            default "0";
                            description "Minimum route advertisement interval for address-family";
                        } // END of peerRaIntervalAf definition.

                        leaf peerAsorigIntervalAf  {
                            type  cml-data-types:CML_UINT32_T {
                                 range "1..65535";
                            }
                            default "1";
                            description "bgp neighbor as-origination-interval for address-family";
                        } // END of peerAsorigIntervalAf definition.

                        leaf neighborAsOverrideAf  {
                            type  cml-data-types:CML_BOOL_T;
                            description "Override AS set/unset for address-family";
                        } // END of neighborAsOverrideAf definition.

                        leaf peerIfNameAf  {
                            if-feature feature-list:HAVE_VRF;
                            type  cml-data-types:CML_STRING_T;
                            description "Interface name for address-family";
                        } // END of peerIfNameAf definition.

                        leaf peerDescAf  {
                            type  cml-data-types:CML_LINE_T;
                            description "bgp neighbor description for address-family";
                        } // END of peerDescAf definition.

                        leaf peerRestartTimeAf  {
                            if-feature feature-list:HAVE_RESTART;
                            if-feature feature-list:HAVE_VRF;
                            type  cml-data-types:CML_UINT32_T {
                                 range "1..3600";
                            }
                            description "Max time needed for Neighbor to restart for address-family";
                        } // END of peerRestartTimeAf definition.

                        leaf siteOriginIdAf  {
                            if-feature feature-list:HAVE_VRF;
                            type  cml-data-types:CML_STRING_T;
                            description "site of origin for address family";
                        } // END of siteOriginIdAf definition.

                        leaf setGracefulShutAf  {
                            type  cml-data-types:CML_BOOL_T;
                            description "Gracefully shutdown set/unset for address-family";
                        } // END of setGracefulShutAf definition.

                        leaf gshutTimerAf  {
                            type  cml-data-types:CML_UINT32_T {
                                 range "10..65535";
                            }
                            description "Gracefully shutdown timer for address-family";
                        } // END of gshutTimerAf definition.


                        list OptionalASAfList {
                            key "optionalASAf";
                            description
                                "OptionalASAfList";
                            leaf optionalASAf  {
                                type  cml-data-types:CML_UINT32_T {
                                     range "1..4294967295";
                                }
                                description "bgp dynamic peer-group optional as number for address-family";
                            } // END of optionalASAf definition.

                        } // End of OptionalASAfList-list
                        uses peerVrfAttrs;
                        uses peerRuntimeAttr;
                        uses peerAdjOutRouteAttrs;
                        uses peerAdjInRouteAttrs;
                    } // End of vrfPeer-list
                    uses bgpAfAttrs;
                    uses networkAfAttrs;
                } // End of afVrfObj-list
            } // End of vrfSubAddressFamily-list
        } // End of vrfAddressFamily-list

        list bgpPeer {
            key "peerAddr";
            description
                "bgpPeer";
            leaf peerAddr  {
                type  cml-data-types:CML_HOSTNAME_T;
                description "The peer address or Tag or Interface Name";
            } // END of peerAddr definition.

            leaf peerAs  {
                type  cml-data-types:CML_BGP_AS_T;
                description "Remote AS number";
            } // END of peerAs definition.

            leaf vrfName  {
                type  cml-data-types:CML_STRING_T;
                config false;
                description "vrf name";
            } // END of vrfName definition.

            leaf bgpPeerState  {
                type  cml-data-types:CML_BGP_PEER_STATUS_T;
                config false;
                description "Bgp peer session state. If there is change in state of the session , notification will be published only if the current state or the previous state is in establised state ";
            } // END of bgpPeerState definition.

            leaf peerAdditionalPaths  {
                if-feature feature-list:HAVE_BGP_ADD_PATH;
                type  cml-data-types:BGP_PEER_ADDITIONAL_PATH_TYPE_T;
                description "bgp peer additional-paths";
            } // END of peerAdditionalPaths definition.

            leaf peerAddPathSelectAll  {
                if-feature feature-list:HAVE_BGP_ADD_PATH;
                type  cml-data-types:CML_BOOL_T;
                description "bgp peer additional-paths select all path";
            } // END of peerAddPathSelectAll definition.

            leaf peerBestCount  {
                if-feature feature-list:HAVE_BGP_ADD_PATH;
                type  cml-data-types:CML_UINT8_T {
                     range "2..3";
                }
                description "bgp peer additional-paths select n best path";
            } // END of peerBestCount definition.

            leaf setGracefulShut  {
                type  cml-data-types:CML_BOOL_T;
                description "Gracefully shutdown set/unset";
            } // END of setGracefulShut definition.

            leaf bgpPeerBfd  {
                type  cml-data-types:CML_BOOL_T;
                description "bgp peer bfd set/unset";
            } // END of bgpPeerBfd definition.

            leaf peerBfdMh  {
                type  cml-data-types:CML_BOOL_T;
                description "bgp peer bfd multihop set/unset";
            } // END of peerBfdMh definition.

            leaf gshutTimer  {
                type  cml-data-types:CML_UINT32_T {
                     range "10..65535";
                }
                description "Gracefully shutdown timer";
            } // END of gshutTimer definition.

            leaf peerRestartTime  {
                if-feature feature-list:HAVE_RESTART;
                type  cml-data-types:CML_UINT32_T {
                     range "1..3600";
                }
                description "Max time needed for Neighbor to restart";
            } // END of peerRestartTime definition.

            leaf peerLocalAs  {
                type  cml-data-types:CML_UINT32_T {
                     range "1..4294967295";
                }
                description "neighbor local-as";
            } // END of peerLocalAs definition.

            leaf neighborAttrUnchanged  {
                type  cml-data-types:CML_ATTRIBUTE_UNCHANGED_TYPE_T;
                description "bgp attribute advertise unchanged to neighbor";
            } // END of neighborAttrUnchanged definition.

            leaf neighborCapabilityGrst  {
                if-feature feature-list:HAVE_RESTART;
                type  cml-data-types:CML_BOOL_T;
                description "bgp neighbor capability graceful restart set/unset";
            } // END of neighborCapabilityGrst definition.

            leaf peerRemovePvtAs  {
                type  cml-data-types:CML_BOOL_T;
                description "bgp neighbor remove private AS set/unset";
            } // END of peerRemovePvtAs definition.

            leaf sendCommunity  {
                type  cml-data-types:CML_BOOL_T;
                description "bgp neighbor send-community set/unset";
            } // END of sendCommunity definition.

            leaf sendCommunityType  {
                type  cml-data-types:CML_BGP_SEND_COMMU_TYPE_T;
                description "bgp neighbor send-community type";
            } // END of sendCommunityType definition.

            leaf neighborRouteServerClient  {
                type  cml-data-types:CML_BOOL_T;
                description "bgp neighbor set/unset as route-server-client";
            } // END of neighborRouteServerClient definition.

            leaf peerRouteReflector  {
                type  cml-data-types:CML_BOOL_T;
                description "bgp neighbor set/unset as route-reflector-client";
            } // END of peerRouteReflector definition.

            leaf peerAdminFlag  {
                type  cml-data-types:CML_INT32_T;
                description "peer administrative flag";
            } // END of peerAdminFlag definition.

            leaf connRetryInterval  {
                type  cml-data-types:CML_INT32_T {
                     range "1..65535";
                }
                default "120";
                description "bgp neighbor connection retry interval";
            } // END of connRetryInterval definition.

            leaf peerDesc  {
                type  cml-data-types:CML_LINE_T;
                description "bgp neighbor description";
            } // END of peerDesc definition.

            leaf sendLabel  {
                type  cml-data-types:CML_BOOL_T;
                description "bgp send-label to neighbour";
            } // END of sendLabel definition.

            leaf sendLabelExplicitNull  {
                type  cml-data-types:CML_BOOL_T;
                description "bgp send-label explicit-null to neighbour";
            } // END of sendLabelExplicitNull definition.

            leaf timeToLive  {
                type  cml-data-types:CML_BOOL_T;
                description "bgp neighbor set/unset time-to-live";
            } // END of timeToLive definition.

            leaf maxHopCount  {
                type  cml-data-types:CML_UINT8_T {
                     range "1..255";
                }
                default "255";
                description "bgp neighbor max ebgp-multihop count";
            } // END of maxHopCount definition.

            leaf peerConnectInterval  {
                type  cml-data-types:CML_UINT32_T {
                     range "1..65535";
                }
                default "1";
                description "Connect timer value";
            } // END of peerConnectInterval definition.

            leaf peerAsorigInterval  {
                type  cml-data-types:CML_UINT32_T {
                     range "1..65535";
                }
                default "1";
                description "bgp neighbor as-origination-interval";
            } // END of peerAsorigInterval definition.

            leaf peerRaInterval  {
                type  cml-data-types:CML_UINT32_T {
                     range "0..65535";
                }
                default "0";
                description "Minimum route advertisement interval";
            } // END of peerRaInterval definition.

            leaf dynamicCapability  {
                type  cml-data-types:CML_BOOL_T;
                description "bgp neighbor dynamic capability set/unset";
            } // END of dynamicCapability definition.

            leaf collideEstablished  {
                type  cml-data-types:CML_BOOL_T;
                description "bgp neighbor collide established set/unset";
            } // END of collideEstablished definition.

            leaf sourceId  {
                type  cml-data-types:CML_STRING_T;
                default "NULL";
                description "bgp neighbor update-source";
            } // END of sourceId definition.

            leaf enforceMultihop  {
                type  cml-data-types:CML_BOOL_T;
                description "bgp neighbor enforce-multihop set/unset";
            } // END of enforceMultihop definition.

            leaf neighborOverrideCapability  {
                type  cml-data-types:CML_BOOL_T;
                description "bgp neighbor override capability negotiation set/unset";
            } // END of neighborOverrideCapability definition.

            leaf neighborStrictCapability  {
                type  cml-data-types:CML_BOOL_T;
                description "bgp neighbor strict capability match set/unset";
            } // END of neighborStrictCapability definition.

            leaf disallowHoldtimer  {
                type  cml-data-types:CML_BOOL_T;
                description "bgp neighbor disallow-infinite-holdtime set/unset";
            } // END of disallowHoldtimer definition.

            leaf dontCapabilityNegotiate  {
                type  cml-data-types:CML_BOOL_T;
                description "bgp neighbor disable capability negotiate set/unset";
            } // END of dontCapabilityNegotiate definition.

            leaf transportConnectionPassive  {
                type  cml-data-types:CML_BOOL_T;
                description "bgp neighbor set/unset passive";
            } // END of transportConnectionPassive definition.

            leaf peerShutdown  {
                type  cml-data-types:CML_BOOL_T;
                description "bgp neighbor set/unset shutdown";
            } // END of peerShutdown definition.

            leaf bgpPort  {
                type  cml-data-types:CML_UINT16_T {
                     range "0..65535";
                }
                default "179";
                description "tcp port number";
            } // END of bgpPort definition.

            leaf bgpVersion  {
                type  cml-data-types:CML_UINT8_T;
                default "4";
                description "BGP Version";
            } // END of bgpVersion definition.

            leaf peerIfName  {
                type  cml-data-types:CML_STRING_T;
                description "Interface name";
            } // END of peerIfName definition.

            leaf softReconfigInbound  {
                type  cml-data-types:CML_BOOL_T;
                description "neighbor inbound soft reconfiguration set/unset";
            } // END of softReconfigInbound definition.

            leaf weight  {
                type  cml-data-types:CML_UINT16_T {
                     range "0..65535";
                }
                default "0";
                description "Weight for routes";
            } // END of weight definition.

            leaf maxPrefixes  {
                type  cml-data-types:CML_UINT32_T {
                     range "1..4294967295";
                }
                description "Maximum number of prefixes";
            } // END of maxPrefixes definition.

            leaf stopUpdate  {
                type  cml-data-types:CML_BOOL_T;
                description "stop installing the routes when limit is exceeded";
            } // END of stopUpdate definition.

            leaf maxPrefixeWarning  {
                type  cml-data-types:CML_BOOL_T;
                description "Throw warning if exceeds threshold-value Yes/No flag";
            } // END of maxPrefixeWarning definition.

            leaf threshold  {
                type  cml-data-types:CML_UINT8_T {
                     range "1..100";
                }
                default "75";
                description "Threshold-value in percent";
            } // END of threshold definition.

            leaf warning  {
                type  cml-data-types:CML_BOOL_T;
                description "Throw warning if exceeds threshold-value Yes/No flag";
            } // END of warning definition.

            leaf allowAsNum  {
                type  cml-data-types:CML_UINT32_T {
                     range "1..10";
                }
                default "3";
                description "Allow AS number";
            } // END of allowAsNum definition.

            leaf peerGroupTag  {
                type  cml-data-types:CML_STRING_T;
                description "BGP peer group name";
            } // END of peerGroupTag definition.

            leaf peerActivate  {
                type  cml-data-types:CML_BOOL_T;
                default true;
                description "Activate/Deactivate neighbor";
            } // END of peerActivate definition.

            leaf unSuppressAclInfo  {
                type  cml-data-types:CML_STRING_T;
                description "unsuppress map name";
            } // END of unSuppressAclInfo definition.

            leaf peerRmapOriName  {
                type  cml-data-types:CML_STRING_T;
                description "Route-map name";
            } // END of peerRmapOriName definition.

            leaf defaultPeerRmapName  {
                type  cml-data-types:CML_BOOL_T;
                description "default originate set/unset";
            } // END of defaultPeerRmapName definition.

            leaf orfPrefixOpt  {
                type  cml-data-types:CML_BGP_ORF_PREFIX_TYPE_T;
                description "advertise outbound router filtering (ORF) capability";
            } // END of orfPrefixOpt definition.

            leaf peerKeepAlive  {
                type  cml-data-types:CML_UINT16_T {
                     range "0..65535";
                }
                default "30";
                description "BGP keepalive time";
            } // END of peerKeepAlive definition.

            leaf peerHoldTime  {
                type  cml-data-types:CML_UINT16_T {
                     range "0..65535";
                }
                default "90";
                description "BGP holdtime";
            } // END of peerHoldTime definition.

            leaf nextHopSelf  {
                type  cml-data-types:CML_BOOL_T;
                description "bgp router next hop self enable/disable";
            } // END of nextHopSelf definition.


            list bgpDlistFilter {
                key "distributeListDirection";
                description
                    "bgpDlistFilter";
                leaf aclInfo  {
                    type  cml-data-types:CML_STRING_T;
                    mandatory true;
                    description "ip access-list name";
                } // END of aclInfo definition.

                leaf distributeListDirection  {
                    type  cml-data-types:CML_BGP_DISTRIBUTE_LIST_ACTION_T;
                    description "neighbor distribute-list to filter route updates";
                } // END of distributeListDirection definition.

            } // End of bgpDlistFilter-list

            list bgpPlistFilter {
                key "prefixListDirection";
                description
                    "bgpPlistFilter";
                leaf prefixListAclInfo  {
                    type  cml-data-types:CML_STRING_T;
                    mandatory true;
                    description "prefix list name";
                } // END of prefixListAclInfo definition.

                leaf prefixListDirection  {
                    type  cml-data-types:CML_BGP_DISTRIBUTE_LIST_ACTION_T;
                    description "neighbor prefix-list to filter route updates";
                } // END of prefixListDirection definition.

            } // End of bgpPlistFilter-list

            list bgpAslistFilter {
                key "asListDirection";
                description
                    "bgpAslistFilter";
                leaf asListAclInfo  {
                    type  cml-data-types:CML_STRING_T;
                    mandatory true;
                    description "as path access-list name";
                } // END of asListAclInfo definition.

                leaf asListDirection  {
                    type  cml-data-types:CML_BGP_DISTRIBUTE_LIST_ACTION_T;
                    description "neighbor aspath-list to filter route updates";
                } // END of asListDirection definition.

            } // End of bgpAslistFilter-list

            list bgpRmapFilter {
                key "peerRmapDirection";
                description
                    "bgpRmapFilter";
                leaf peerRmapName  {
                    type  cml-data-types:CML_STRING_T;
                    mandatory true;
                    description "route map name";
                } // END of peerRmapName definition.

                leaf peerRmapDirection  {
                    type  cml-data-types:CML_BGP_DISTRIBUTE_LIST_ACTION_T;
                    description "neighbor route-map to filter route updates";
                } // END of peerRmapDirection definition.

            } // End of bgpRmapFilter-list

            list bgpPeerAddressFamily {
                key "afi";
                description
                    "bgpPeerAddressFamily";
                leaf afi  {
                    type  cml-data-types:CML_AFI_TYPE_T;
                    description "bgp address family type";
                } // END of afi definition.


                list bgpPeerSubAddressFamily {
                    key "safi";
                    description
                        "bgpPeerSubAddressFamily";
                    leaf safi  {
                        type  cml-data-types:CML_SAFI_TYPE_T;
                        description "bgp sub-address family type";
                    } // END of safi definition.

                    leaf peerAdditionalPathsAf  {
                        if-feature feature-list:HAVE_BGP_ADD_PATH;
                        type  cml-data-types:BGP_PEER_ADDITIONAL_PATH_TYPE_T;
                        description "bgp additional-paths for address-family";
                    } // END of peerAdditionalPathsAf definition.

                    leaf peerAddPathSelectAllAf  {
                        if-feature feature-list:HAVE_BGP_ADD_PATH;
                        type  cml-data-types:CML_BOOL_T;
                        description "bgp additional-paths select all path at address-family level";
                    } // END of peerAddPathSelectAllAf definition.

                    leaf peerBestCountAf  {
                        if-feature feature-list:HAVE_BGP_ADD_PATH;
                        type  cml-data-types:CML_UINT8_T {
                             range "2..3";
                        }
                        description "bgp additional-paths select best path at address-family level";
                    } // END of peerBestCountAf definition.

                    leaf neighborRouteServerClientAf  {
                        type  cml-data-types:CML_BOOL_T;
                        description "bgp neighbor set/unset as route-server-client for address-family";
                    } // END of neighborRouteServerClientAf definition.

                    leaf nextHopSelfAf  {
                        type  cml-data-types:CML_BOOL_T;
                        description "bgp router next hop self enable/disable for address-family";
                    } // END of nextHopSelfAf definition.

                    uses peerVrfAttrs;
                    uses peerRuntimeAttr;
                    uses peerAdjInRouteAttrs;
                    uses peerAdjOutRouteAttrs;
                } // End of bgpPeerSubAddressFamily-list
            } // End of bgpPeerAddressFamily-list
            uses peerAndPeerGroupAttrs;
            uses peerRuntimeAttr;
            uses peerAdjOutRouteAttrs;
            uses peerAdjInRouteAttrs;
        } // End of bgpPeer-list
        container bgpRfdCbCfgParam {
            description
                "BGP Route Flap Dampening User Configurable Parameters";
            leaf halfLife  {
                type  cml-data-types:CML_UINT32_T {
                     range "1..45";
                }
                default "15";
                description "bgp route dampening reachability half-life time";
            } // END of halfLife definition.

            leaf reusePenalty  {
                type  cml-data-types:CML_UINT32_T {
                     range "1..20000";
                }
                default "750";
                description "bgp reusing a route value";
            } // END of reusePenalty definition.

            leaf suppressPenalty  {
                type  cml-data-types:CML_UINT32_T {
                     range "1..20000";
                }
                default "2000";
                description "bgp suppress a route value";
            } // END of suppressPenalty definition.

            leaf maxSuppress  {
                type  cml-data-types:CML_UINT32_T {
                     range "1..255";
                }
                default "60";
                description "bgp max suppress timer for route";
            } // END of maxSuppress definition.

            leaf unreachHalfLife  {
                type  cml-data-types:CML_UINT32_T {
                     range "1..45";
                }
                default "15";
                description "bgp route dampening Un-reachability Half-life time";
            } // END of unreachHalfLife definition.

            leaf dampeningRmapName  {
                type  cml-data-types:CML_STRING_T;
                default "NULL";
                description "bgp dampening route-map name";
            } // END of dampeningRmapName definition.

        } // END of bgpRfdCbCfgParam-container definition.
    } // END of bgpAttrs definition.
    grouping peerAndPeerGroupAttrs {
        description
            "peerAndPeerGroupAttrs";
        leaf password  {
            if-feature feature-list:HAVE_TCP_MD5SIG;
            type  cml-data-types:CML_MD5_PASSWORD_T;
            default "NULL";
            description "bgp neighbor authentication password";
        } // END of password definition.

    } // END of peerAndPeerGroupAttrs definition.
    grouping bgpAfAttrs {
        description
            "bgpAfAttrs";
        leaf allocateLabelAllAf  {
            if-feature feature-list:HAVE_BGP_LU;
            type  cml-data-types:CML_BOOL_T;
            description "allocate-label all the advertised routes for address-family";
        } // END of allocateLabelAllAf definition.

        leaf RouteMapNameAf  {
            if-feature feature-list:HAVE_BGP_LU;
            type  cml-data-types:CML_STRING_T;
            description "route-map name for address-family";
        } // END of RouteMapNameAf definition.

        leaf autoSummaryAf  {
            type  cml-data-types:CML_BOOL_T;
            description "auto summary enable/disable for address-family";
        } // END of autoSummaryAf definition.

        leaf SetAddPathFlagAf  {
            if-feature feature-list:HAVE_BGP_PIC_CORE_EDGE;
            type  cml-data-types:CML_BOOL_T;
            description "BGP additional-paths set flag for address-family";
        } // END of SetAddPathFlagAf definition.

        leaf setNwSyncFlagAf  {
            type  cml-data-types:CML_BOOL_T;
            description "network synchronization enable/disable for address-family";
        } // END of setNwSyncFlagAf definition.

        leaf tableMapAf  {
            if-feature feature-list:HAVE_BGP_TABLE_MAP;
            type  cml-data-types:CML_STRING_T;
            description "bgp table map name for address-family";
        } // END of tableMapAf definition.

        leaf tableMapFilterAf  {
            if-feature feature-list:HAVE_BGP_TABLE_MAP;
            type  cml-data-types:CML_BOOL_T;
            description "bgp table-map filter enable/disable for address-family";
        } // END of tableMapFilterAf definition.

        leaf distanceEbgpAf  {
            type  cml-data-types:CML_UINT8_T {
                 range "1..255";
            }
            default "20";
            description "Distance for routes external to the AS for address-family";
        } // END of distanceEbgpAf definition.

        leaf distanceIbgpAf  {
            type  cml-data-types:CML_UINT8_T {
                 range "1..255";
            }
            default "200";
            description "Distance for routes internal to the AS for address-family";
        } // END of distanceIbgpAf definition.

        leaf distanceLocalAf  {
            type  cml-data-types:CML_UINT8_T {
                 range "1..255";
            }
            default "200";
            description "Distance for local routes for address-family";
        } // END of distanceLocalAf definition.

        leaf setSyncFlagAf  {
            type  cml-data-types:CML_BOOL_T;
            description "synchronization enable/disable for address-family";
        } // END of setSyncFlagAf definition.

        leaf ebgpMaxPathAf  {
            type  cml-data-types:CML_INT32_T {
                 range "2..64";
            }
            default "2";
            description "BGP ECMP eBGP max-paths for address-family";
        } // END of ebgpMaxPathAf definition.

        leaf ibgpMaxPathAf  {
            type  cml-data-types:CML_INT32_T {
                 range "2..64";
            }
            default "2";
            description "BGP ECMP eBGP max-paths for address-family";
        } // END of ibgpMaxPathAf definition.

        leaf eibgpMaxPathAf  {
            type  cml-data-types:CML_INT32_T {
                 range "2..64";
            }
            default "2";
            description "BGP ECMP eBGP/iBGP max-paths for address-family";
        } // END of eibgpMaxPathAf definition.


        list bgpAddressFamilyRedistList {
            key "redistTypeAf";
            description
                "bgpAddressFamilyRedistList";
            leaf redistTypeAf  {
                type  cml-data-types:CML_BGP_REDISTRIBUTE_TYPE_T;
                description "bgp redistribute route for address-family";
            } // END of redistTypeAf definition.

            leaf redistRmapNameAf  {
                type  cml-data-types:CML_STRING_T;
                description "bgp route redistribute type for address-family";
            } // END of redistRmapNameAf definition.

        } // End of bgpAddressFamilyRedistList-list

        list bgpRedistOspfAf {
            key "redistOspfNoAf";
            description
                "bgpRedistOspfAf";
            leaf redistOspfNoAf  {
                type  cml-data-types:CML_UINT32_T {
                     range "0..65535";
                }
                description "bgp redistribute route OSPF process ID for address-family";
            } // END of redistOspfNoAf definition.

            leaf redistOspfRmapAf  {
                type  cml-data-types:CML_STRING_T;
                description "bgp redistribute route OSPF route-map name for address-family";
            } // END of redistOspfRmapAf definition.

        } // End of bgpRedistOspfAf-list
        container bgpRfdCbCfgParam {
            description
                "BGP Route Flap Dampening User Configurable Parameters";
            leaf halfLifeAf  {
                type  cml-data-types:CML_UINT32_T {
                     range "1..45";
                }
                default "15";
                description "bgp route dampening reachability half-life time for address-family";
            } // END of halfLifeAf definition.

            leaf reusePenaltyAf  {
                type  cml-data-types:CML_UINT32_T {
                     range "1..20000";
                }
                description "bgp reusing a route value for address-family";
            } // END of reusePenaltyAf definition.

            leaf suppressPenaltyAf  {
                type  cml-data-types:CML_UINT32_T {
                     range "1..20000";
                }
                description ">bgp suppress a route value for address-family";
            } // END of suppressPenaltyAf definition.

            leaf maxSuppressAf  {
                type  cml-data-types:CML_UINT32_T {
                     range "1..255";
                }
                description "bgp max suppress timer for route for address-family";
            } // END of maxSuppressAf definition.

            leaf unreachHalfLifeAf  {
                type  cml-data-types:CML_UINT32_T {
                     range "1..45";
                }
                description "bgp route dampening Un-reachability Half-life time for address-family";
            } // END of unreachHalfLifeAf definition.

            leaf dampeningRmapNameAf  {
                type  cml-data-types:CML_STRING_T;
                description "bgp dampening route-map name for address-family";
            } // END of dampeningRmapNameAf definition.

        } // END of bgpRfdCbCfgParam-container definition.
    } // END of bgpAfAttrs definition.
    grouping networkAfAttrs {
        description
            "networkAfAttrs";

        list bgpAddressFamilyNetworkList {
            key "localAddrAf";
            description
                "bgpAddressFamilyNetworkList";
            leaf localAddrAf  {
                type  cml-data-types:CML_BGP_IP_NETWORK_T;
                description "network address for address-family";
            } // END of localAddrAf definition.

            leaf networkRmapNameAf  {
                type  cml-data-types:CML_STRING_T;
                description "route-map name for address-family";
            } // END of networkRmapNameAf definition.

            leaf backdoorAf  {
                type  cml-data-types:CML_BOOL_T;
                default false;
                description "network address with backdoor option set/unset for address family";
            } // END of backdoorAf definition.

            uses nwRunTimeAttr;
        } // End of bgpAddressFamilyNetworkList-list
    } // END of networkAfAttrs definition.
    grouping peerRuntimeAttr {
        description
            "peerRuntimeAttr";
        leaf maxPathIbgp  {
            type  cml-data-types:CML_INT16_T;
            config false;
            description "ECMP multipath ibgp maxpath";
        } // END of maxPathIbgp definition.

        leaf asLocalCount  {
            type  cml-data-types:CML_INT32_T;
            default "1";
            config false;
            description "as-local count";
        } // END of asLocalCount definition.

        leaf cfgMaxPathEbgp  {
            type  cml-data-types:CML_INT16_T;
            config false;
            description "Configured ebgp ECMP multipath";
        } // END of cfgMaxPathEbgp definition.

        leaf maxPathEbgp  {
            type  cml-data-types:CML_INT16_T;
            config false;
            description "ECMP multipath ebgp maxpath";
        } // END of maxPathEbgp definition.

        leaf cfgMaxPathIbgp  {
            type  cml-data-types:CML_INT16_T;
            config false;
            description "Configured ibgp ECMP multipath";
        } // END of cfgMaxPathIbgp definition.

        leaf bgpCommunityCount  {
            type  cml-data-types:CML_INT32_T;
            config false;
            description "bgp community count ";
        } // END of bgpCommunityCount definition.

        leaf peerConfedIdCheck  {
            type  cml-data-types:CML_BOOL_T;
            config false;
            description "Check if AS is part of the confed ";
        } // END of peerConfedIdCheck definition.

        leaf peerAndExtAsnCap  {
            type  cml-data-types:BGP_ADV_RCV_TYPE_T;
            config false;
            description "4-Octet ASN Capability: 1(advertise), 2(receive), 3(both advertise and receive)";
        } // END of peerAndExtAsnCap definition.

        leaf addFamilystring  {
            type  cml-data-types:BGP_ADV_RCV_TYPE_T;
            config false;
            description "Address family IPv4 Unicast: 1(advertise), 2(receive),3(both advertise and receive)";
        } // END of addFamilystring definition.

        leaf keepAliveIn  {
            type  cml-data-types:CML_INT32_T;
            config false;
            description "Keepalive input count";
        } // END of keepAliveIn definition.

        leaf keepAliveOut  {
            type  cml-data-types:CML_INT32_T;
            config false;
            description "Keepalive output count";
        } // END of keepAliveOut definition.

        leaf openMsgIn  {
            type  cml-data-types:CML_INT32_T;
            config false;
            description "Open message input count";
        } // END of openMsgIn definition.

        leaf openMsgOut  {
            type  cml-data-types:CML_INT32_T;
            config false;
            description "Open message output count";
        } // END of openMsgOut definition.

        leaf bgpAsPathCount  {
            type  cml-data-types:CML_INT32_T;
            config false;
            description "BGP AS-PATH entries";
        } // END of bgpAsPathCount definition.

        leaf bgpAsPath4BCount  {
            type  cml-data-types:CML_INT32_T;
            config false;
            description "BGP AS-PATH entries";
        } // END of bgpAsPath4BCount definition.

        leaf updateMsgIn  {
            type  cml-data-types:CML_INT32_T;
            default "0";
            config false;
            description "Update message input count";
        } // END of updateMsgIn definition.

        leaf updateMsgOut  {
            type  cml-data-types:CML_INT32_T;
            default "0";
            config false;
            description "Update message ouput count";
        } // END of updateMsgOut definition.

        leaf nextHopGlobal  {
            type  cml-data-types:CML_STRING_T;
            config false;
            description "Nexthop global";
        } // END of nextHopGlobal definition.

        leaf nextHopLocal  {
            type  cml-data-types:CML_STRING_T;
            config false;
            description "Nexthop local";
        } // END of nextHopLocal definition.

        leaf peerRemotePort  {
            type  cml-data-types:CML_INT32_T;
            config false;
            description "Peer remote port";
        } // END of peerRemotePort definition.

        leaf peerRemoteAddr  {
            type  cml-data-types:CML_HOSTNAME_T;
            config false;
            description "Peer remote address";
        } // END of peerRemoteAddr definition.

        leaf peerLocalHost  {
            type  cml-data-types:CML_HOSTNAME_T;
            config false;
            description "Peer Local host";
        } // END of peerLocalHost definition.

        leaf nextHop  {
            type  cml-data-types:CML_STRING_T;
            config false;
            description "Nexthop";
        } // END of nextHop definition.

        leaf peerLocalPort  {
            type  cml-data-types:CML_INT32_T;
            config false;
            description "Peer local port";
        } // END of peerLocalPort definition.

        leaf prefixListCount  {
            type  cml-data-types:CML_INT32_T;
            config false;
            description "Prefix list count";
        } // END of prefixListCount definition.

        leaf defInfoOri  {
            type  cml-data-types:CML_BOOL_T;
            config false;
            description "Default information originate";
        } // END of defInfoOri definition.

        leaf InboundPathPolicy  {
            type  cml-data-types:CML_BOOL_T;
            config false;
            description "Inbound path policy configured";
        } // END of InboundPathPolicy definition.

        leaf OutboundPathPolicy  {
            type  cml-data-types:CML_BOOL_T;
            config false;
            description "Outbound path policy configured";
        } // END of OutboundPathPolicy definition.

        leaf defOriInfoSent  {
            type  cml-data-types:CML_STRING_T;
            config false;
            description "default sent";
        } // END of defOriInfoSent definition.

        leaf orfPrefixStr  {
            type  cml-data-types:CML_BOOL_T;
            config false;
            description "Outbound Route Filter (ORF)";
        } // END of orfPrefixStr definition.

        leaf orfPrefixSend  {
            type  cml-data-types:CML_STRING_T;
            config false;
            description "Outbound Route Filter (ORF) sent";
        } // END of orfPrefixSend definition.

        leaf orfPrefixCount  {
            type  cml-data-types:CML_STRING_T;
            config false;
            description "Outbound Route Filter (ORF) received entries";
        } // END of orfPrefixCount definition.

        leaf orfWaitRefresh  {
            type  cml-data-types:CML_BOOL_T;
            config false;
            description "First update is deferred until ORF or ROUTE-REFRESH is received";
        } // END of orfWaitRefresh definition.

        leaf grstRestart  {
            type  cml-data-types:CML_STRING_T;
            config false;
            description "Graceful restart-advertised/received";
        } // END of grstRestart definition.

        leaf afDependentCap  {
            type  cml-data-types:CML_BOOL_T;
            config false;
            description "AF-dependant capabilities";
        } // END of afDependentCap definition.

        leaf peerAfTableVersion  {
            type  cml-data-types:CML_INT32_T;
            config false;
            description "neighbor version";
        } // END of peerAfTableVersion definition.

        leaf peerBgpAfTableVersion  {
            type  cml-data-types:CML_INT32_T;
            config false;
            description "BGP table version";
        } // END of peerBgpAfTableVersion definition.

        leaf fwdStatusPreserve  {
            type  cml-data-types:CML_STRING_T;
            config false;
            description "Graceful restart:Forwarding states are being preserved";
        } // END of fwdStatusPreserve definition.

        leaf orfTypePrefix  {
            type  cml-data-types:CML_STRING_T;
            config false;
            description "Outbound Route Filter (ORF) type Prefix-list";
        } // END of orfTypePrefix definition.

        leaf orfTypePrefixSendMode  {
            type  cml-data-types:CML_STRING_T;
            config false;
            description "ORF Send-mode advertised and received";
        } // END of orfTypePrefixSendMode definition.

        leaf orfTypePrefixRecvMode  {
            type  cml-data-types:CML_STRING_T;
            config false;
            description "ORF Receive-mode advertised and received";
        } // END of orfTypePrefixRecvMode definition.

        leaf orfTypePrefixOld  {
            type  cml-data-types:CML_STRING_T;
            config false;
            description "Outbound Route Filter (ORF) type Prefix-list";
        } // END of orfTypePrefixOld definition.

        leaf orfTypePrefixSendModeOld  {
            type  cml-data-types:CML_STRING_T;
            config false;
            description "peer afi orf cap Send-Mode";
        } // END of orfTypePrefixSendModeOld definition.

        leaf orfTypePrefixRecvModeOld  {
            type  cml-data-types:CML_STRING_T;
            config false;
            description "peer afi orf cap Receive-mode";
        } // END of orfTypePrefixRecvModeOld definition.

        leaf peerPrefixCount  {
            type  cml-data-types:CML_INT32_T;
            config false;
            description "accepted prefixes";
        } // END of peerPrefixCount definition.

        leaf peerSendPrefixCount  {
            type  cml-data-types:CML_INT32_T;
            config false;
            description "announced prefixes";
        } // END of peerSendPrefixCount definition.

        leaf peerFlagShutDown  {
            type  cml-data-types:CML_PEERFLAG_SHUTDOWN_T;
            config false;
            description "peer flag shutdown status: 1(Idle), 2(Connect), 3(Active), 4(Opensent), 5(Openconfirm), 6(Established), 7(Idle Admin), 8(Idle PfxCt), 9(Idle G-shut)";
        } // END of peerFlagShutDown definition.

        leaf peerCount  {
            type  cml-data-types:CML_INT32_T;
            config false;
            description "peer count";
        } // END of peerCount definition.

        leaf peerNotifyInfo  {
            type  cml-data-types:CML_BOOL_T;
            config false;
            description "BGP notify open error";
        } // END of peerNotifyInfo definition.

        leaf peerNotifyDirect  {
            type  cml-data-types:CML_BOOL_T;
            config false;
            description "Last reset due to notification type 0(sent), 1(received)";
        } // END of peerNotifyDirect definition.

        leaf peerNotifyLastReset  {
            type  cml-data-types:CML_STRING_T;
            config false;
            description "Last reset in week:day:hour:min:sec format string";
        } // END of peerNotifyLastReset definition.

        leaf notifyCodeStr  {
            type  cml-data-types:CML_STRING_T;
            config false;
            description "Notification Error Message code and subcode";
        } // END of notifyCodeStr definition.

        leaf bgpConnection  {
            type  cml-data-types:CML_BGP_CONNECTION_TYPE_T;
            config false;
            description "Connection: shared network, non shared network";
        } // END of bgpConnection definition.

        leaf nextConnectTimer  {
            type  cml-data-types:CML_INT32_T;
            config false;
            description "Next connect timer due in seconds";
        } // END of nextConnectTimer definition.

        leaf conEstCount  {
            type  cml-data-types:CML_INT32_T;
            config false;
            description "BGP state established count";
        } // END of conEstCount definition.

        leaf conDroppedCount  {
            type  cml-data-types:CML_INT32_T;
            config false;
            description "BGP state drop count";
        } // END of conDroppedCount definition.

        leaf peerGstatusAcceptGrst  {
            type  cml-data-types:CML_STRING_T;
            config false;
            description "Graceful Restart Status";
        } // END of peerGstatusAcceptGrst definition.

        leaf peerGrstRestart  {
            type  cml-data-types:CML_INT32_T;
            config false;
            description "Remote restart-time in sec";
        } // END of peerGrstRestart definition.

        leaf bpfEstUpTime  {
            type  cml-data-types:CML_GAUGE32_T;
            config false;
            description "up time";
        } // END of bpfEstUpTime definition.

        leaf lastReadTime  {
            type  cml-data-types:CML_GAUGE32_T;
            config false;
            description "Last read time";
        } // END of lastReadTime definition.

        leaf bpfState  {
            type  cml-data-types:CML_BGP_PEER_STATUS_T;
            config false;
            description "The bgp state of the session with following representation 1(Idle), 2(Connect), 3(Active), 4(Opensent), 5(Openconfirm), 6(Established)
        ";
        } // END of bpfState definition.

        leaf peerLinkType  {
            type  cml-data-types:CML_BGP_LINK_TYPE_T;
            config false;
            description "Link type: internal, external";
        } // END of peerLinkType definition.

        leaf hopAwayCount  {
            type  cml-data-types:CML_INT32_T;
            config false;
            description "External BGP neighbor may be up to given hops away.";
        } // END of hopAwayCount definition.

        leaf peerRouterId  {
            type  cml-data-types:CML_IPV4_PREFIX_T;
            config false;
            description "peer router id";
        } // END of peerRouterId definition.

        leaf recvPacketCount  {
            type  cml-data-types:CML_INT32_T;
            config false;
            description "Received messages";
        } // END of recvPacketCount definition.

        leaf notificationIn  {
            type  cml-data-types:CML_INT32_T;
            config false;
            description "Notify input count";
        } // END of notificationIn definition.

        leaf notificationOut  {
            type  cml-data-types:CML_INT32_T;
            config false;
            description "Notify output count";
        } // END of notificationOut definition.

        leaf pktInQue  {
            type  cml-data-types:CML_INT32_T;
            config false;
            description "messages queued to be processed from the neighbor";
        } // END of pktInQue definition.

        leaf pktOutQue  {
            type  cml-data-types:CML_INT32_T;
            config false;
            description "messages queued to be sent to the neighbor";
        } // END of pktOutQue definition.

        leaf sentPacketCount  {
            type  cml-data-types:CML_INT32_T;
            config false;
            description "Sent messages";
        } // END of sentPacketCount definition.

        leaf refreshRecvPacketCount  {
            type  cml-data-types:CML_INT32_T;
            config false;
            description "Route Refresh input count";
        } // END of refreshRecvPacketCount definition.

        leaf refreshSentPacketCount  {
            type  cml-data-types:CML_INT32_T;
            config false;
            description "Route Refresh output count";
        } // END of refreshSentPacketCount definition.

        leaf advertisementInterval  {
            type  cml-data-types:CML_INT32_T;
            config false;
            description "Minimum time between advertisement runs in seconds";
        } // END of advertisementInterval definition.

        leaf peerHoldTimeRun  {
            type  cml-data-types:CML_INT32_T;
            config false;
            description "hold time in seconds";
        } // END of peerHoldTimeRun definition.

        leaf peerKeepAliveRun  {
            type  cml-data-types:CML_INT32_T;
            config false;
            description "keepalive interval in seconds";
        } // END of peerKeepAliveRun definition.

        leaf advCapabilityDynamic  {
            type  cml-data-types:BGP_ADV_RCV_TYPE_T;
            config false;
            description "Dynamic capability ";
        } // END of advCapabilityDynamic definition.

        leaf advCapabilityRefresh  {
            type  cml-data-types:BGP_ADV_RCV_TYPE_T;
            config false;
            description "Route Refresh capability";
        } // END of advCapabilityRefresh definition.

        leaf noIfBinding  {
            type  cml-data-types:CML_BOOL_T;
            config false;
            description "No Interfaces bound to BGP Instance";
        } // END of noIfBinding definition.

        leaf advAddPathCapabilitySend  {
            if-feature feature-list:HAVE_BGP_ADD_PATH;
            type  cml-data-types:CML_STRING_T;
            config false;
            description "Add-Path Send Capability";
        } // END of advAddPathCapabilitySend definition.

        leaf advAddPathCapabilityRec  {
            if-feature feature-list:HAVE_BGP_ADD_PATH;
            type  cml-data-types:CML_STRING_T;
            config false;
            description "Add-Path Receive Capability";
        } // END of advAddPathCapabilityRec definition.

        leaf advCapablityIpv4Multicast  {
            type  cml-data-types:CML_STRING_T;
            config false;
            description "IPV4 Multicast neighbour Capability";
        } // END of advCapablityIpv4Multicast definition.

        leaf advCapablityVpnv4Unicast  {
            type  cml-data-types:CML_STRING_T;
            config false;
            description "Vpnv4 Unicast neighbour Capability";
        } // END of advCapablityVpnv4Unicast definition.

        leaf advCapablityVpnv6Unicast  {
            type  cml-data-types:CML_STRING_T;
            config false;
            description "Vpnv6 Unicast neighbour Capability";
        } // END of advCapablityVpnv6Unicast definition.

        leaf advCapablityRtfilterUnicast  {
            type  cml-data-types:CML_STRING_T;
            config false;
            description "Rtfilter Unicast neighbour Capability";
        } // END of advCapablityRtfilterUnicast definition.

        leaf advCapablityL2vpnEvpn  {
            type  cml-data-types:CML_STRING_T;
            config false;
            description "L2vpn Evpn neighbour Capability";
        } // END of advCapablityL2vpnEvpn definition.

        leaf advCapablityIpv6Unicast  {
            type  cml-data-types:BGP_ADV_RCV_TYPE_T;
            config false;
            description "Ipv6 Unicast neighbour Capability";
        } // END of advCapablityIpv6Unicast definition.

        leaf advCapablityIpv6Multicast  {
            type  cml-data-types:CML_STRING_T;
            config false;
            description "Ipv6 Multicast neighbour Capability";
        } // END of advCapablityIpv6Multicast definition.

        leaf advCapablityIpv6LabelUnicast  {
            type  cml-data-types:CML_STRING_T;
            config false;
            description "Ipv6 Label Unicast neighbour Capability";
        } // END of advCapablityIpv6LabelUnicast definition.


        list peerPrefix {
            key "prefixEntrySeq";
            config false;
            description
                "peerPrefix";
            leaf prefixEntrySeq  {
                type  cml-data-types:CML_INT32_T;
                description "Prefix sequence number";
            } // END of prefixEntrySeq definition.

            leaf prefixEntryType  {
                type  cml-data-types:CML_BGP_PREFIX_ENTRY_TYPE_T;
                description "Prefix type 1(no_match), 2(deny), 3(permit)";
            } // END of prefixEntryType definition.

            leaf prefixEntryGe  {
                type  cml-data-types:CML_INT32_T;
                description "Maximum prefix length to be matched";
            } // END of prefixEntryGe definition.

            leaf prefixEntryLe  {
                type  cml-data-types:CML_INT32_T;
                description "Minimum prefix length to be matched";
            } // END of prefixEntryLe definition.

            leaf peerPrefixLen  {
                type  cml-data-types:CML_INT32_T;
                description "Prefix length";
            } // END of peerPrefixLen definition.

        } // End of peerPrefix-list
        container bgpPeerIndex {
            config false;
            description
                "BGP Peer Adj_RIBs_out index";
            leaf peerIndex  {
                type  cml-data-types:CML_INT32_T;
                description "Peer index";
            } // END of peerIndex definition.

            leaf peerOffset  {
                type  cml-data-types:CML_INT32_T;
                description "Peer offset";
            } // END of peerOffset definition.

            leaf peerMask  {
                type  cml-data-types:CML_STRING_T;
                description "Peer mask";
            } // END of peerMask definition.

        } // END of bgpPeerIndex-container definition.
    } // END of peerRuntimeAttr definition.
    grouping peerAdjInRouteAttrs {
        description
            "peerAdjInRouteAttrs";

        list peerAdjInRoute {
            key "networkAddr";
            config false;
            description
                "peerAdjInRoute";
            leaf networkAddr  {
                type  cml-data-types:CML_BGP_IP_NETWORK_T;
                description "Peer Adj-In Network address";
            } // END of networkAddr definition.


            list nextHop {
                key "nextHopAddr";
                config false;
                description
                    "nextHop";
                leaf nextHopAddr  {
                    type  cml-data-types:CML_HOSTNAME_T;
                    description " Peer Adj-In Nexthop address";
                } // END of nextHopAddr definition.

                uses nextHopRunTimeAttr;
            } // End of nextHop-list
        } // End of peerAdjInRoute-list
    } // END of peerAdjInRouteAttrs definition.
    grouping peerAdjOutRouteAttrs {
        description
            "peerAdjOutRouteAttrs";

        list peerAdjOutRoute {
            key "networkAddr";
            config false;
            description
                "peerAdjOutRoute";
            leaf networkAddr  {
                type  cml-data-types:CML_BGP_IP_NETWORK_T;
                description "Peer Adj-Out Network address";
            } // END of networkAddr definition.


            list nextHop {
                key "nextHopAddr";
                config false;
                description
                    "nextHop";
                leaf nextHopAddr  {
                    type  cml-data-types:CML_HOSTNAME_T;
                    description "Peer Adj-Out Nexthop address";
                } // END of nextHopAddr definition.

                uses nextHopRunTimeAttr;
            } // End of nextHop-list
        } // End of peerAdjOutRoute-list
    } // END of peerAdjOutRouteAttrs definition.
    grouping nextHopRunTimeAttr {
        description
            "nextHopRunTimeAttr";
        leaf peerNtwkWeight  {
            type  cml-data-types:CML_INT32_T;
            config false;
            description "BGP attribute weight";
        } // END of peerNtwkWeight definition.

        leaf flapTimeReuseList  {
            type  cml-data-types:CML_STRING_T;
            config false;
            description "Dampinfo: reuse in";
        } // END of flapTimeReuseList definition.

        leaf flapRecordDuration  {
            type  cml-data-types:CML_STRING_T;
            config false;
            description "Flap record duration";
        } // END of flapRecordDuration definition.

        leaf dampTimeToReuse  {
            type  cml-data-types:CML_STRING_T;
            config false;
            description "Damp time to reuse";
        } // END of dampTimeToReuse definition.

        leaf bgpMedVal  {
            type  cml-data-types:CML_INT32_T;
            config false;
            description "Metric";
        } // END of bgpMedVal definition.

        leaf-list bgpAsPathStr  {
            type  cml-data-types:CML_STRING_T;
            config false;
            description "AS-path";
        } // END of bgpAsPathStr definition.

        leaf-list bgpAsPath4BStr  {
            type  cml-data-types:CML_STRING_T;
            config false;
            description "AS-path for extended asn capability";
        } // END of bgpAsPath4BStr definition.

        leaf bgpAsPath4BOrigin  {
            type  cml-data-types:CML_BGP_ORIGIN_T;
            config false;
            description "Origin: 0(IGP), 1(EGP), 2(Incomplete)";
        } // END of bgpAsPath4BOrigin definition.

        leaf ibgpMetricRoute  {
            type  cml-data-types:CML_INT32_T;
            config false;
            description "IGP metric value for route selection.";
        } // END of ibgpMetricRoute definition.

        leaf aggregateAsRoute  {
            type  cml-data-types:CML_INT32_T;
            config false;
            description "aggregated by as";
        } // END of aggregateAsRoute definition.

        leaf aggregatorAddrRoute  {
            type  cml-data-types:CML_HOSTNAME_T;
            config false;
            description "aggregated by address";
        } // END of aggregatorAddrRoute definition.

        leaf networkRemoteAddrRoute  {
            type  cml-data-types:CML_HOSTNAME_T;
            config false;
            description "Remote id";
        } // END of networkRemoteAddrRoute definition.

        leaf originatorIdRoute  {
            type  cml-data-types:CML_HOSTNAME_T;
            config false;
            description "Originator id";
        } // END of originatorIdRoute definition.

        leaf routePeerAddrRoute  {
            type  cml-data-types:CML_HOSTNAME_T;
            config false;
            description "address of the peer";
        } // END of routePeerAddrRoute definition.

        leaf routeLocalPrefRoute  {
            type  cml-data-types:CML_INT32_T;
            config false;
            description "local-preference";
        } // END of routeLocalPrefRoute definition.

        leaf routeCommNameRoute  {
            type  cml-data-types:CML_STRING_T;
            config false;
            description "Community";
        } // END of routeCommNameRoute definition.

        leaf-list clusterListRoute  {
            type  cml-data-types:CML_HOSTNAME_T;
            config false;
            description "Cluster list";
        } // END of clusterListRoute definition.

        leaf routeGetPenaltyRoute  {
            type  cml-data-types:CML_INT32_T;
            config false;
            description "Dampinfo: penalty";
        } // END of routeGetPenaltyRoute definition.

        leaf routeGetFlapCountRoute  {
            type  cml-data-types:CML_INT32_T;
            config false;
            description "Dampinfo: no of times flapped ";
        } // END of routeGetFlapCountRoute definition.

        leaf lastUpdateRoute  {
            type  cml-data-types:CML_DATE_TIME_T;
            config false;
            description "Last Update time of route";
        } // END of lastUpdateRoute definition.

        leaf reflectorClientRoute  {
            type  cml-data-types:CML_BOOL_T;
            config false;
            description "Received from a RR-client";
        } // END of reflectorClientRoute definition.

        leaf routeDampeningFlagRoute  {
            type  cml-data-types:CML_BOOL_T;
            config false;
            description "suppressed due to dampening";
        } // END of routeDampeningFlagRoute definition.

        leaf historyRoute  {
            type  cml-data-types:CML_BOOL_T;
            config false;
            description "history entry";
        } // END of historyRoute definition.

        leaf nhopValidRoute  {
            type  cml-data-types:CML_BOOL_T;
            config false;
            description "Active redistribute routes";
        } // END of nhopValidRoute definition.

        leaf routeMedFlagTypeRoute  {
            type  cml-data-types:CML_BOOL_T;
            config false;
            description "if remove med flag is enabled";
        } // END of routeMedFlagTypeRoute definition.

        leaf routeValidStateRoute  {
            type  cml-data-types:CML_BOOL_T;
            config false;
            description "Check if state is valid";
        } // END of routeValidStateRoute definition.

        leaf bgpInfoStaleRoute  {
            type  cml-data-types:CML_BOOL_T;
            config false;
            description "Check BGP info stale";
        } // END of bgpInfoStaleRoute definition.

        leaf bgpInfoTypeRoute  {
            type  cml-data-types:CML_BGP_RI_TYPE_T;
            config false;
            description "BGP route info type - internal, confed-external, external, sourced, aggregated, local";
        } // END of bgpInfoTypeRoute definition.

        leaf ecmpMultiCandidateRoute  {
            type  cml-data-types:CML_BOOL_T;
            config false;
            description "if ecmp multipath candidate";
        } // END of ecmpMultiCandidateRoute definition.

        leaf multiInstalledRoute  {
            type  cml-data-types:CML_BOOL_T;
            config false;
            description "if bgp info multi install- 1(installed)";
        } // END of multiInstalledRoute definition.

        leaf routeSyncFlagRoute  {
            type  cml-data-types:CML_BOOL_T;
            config false;
            description "BGP info status - 0(not synchronized) 1(synchronized)";
        } // END of routeSyncFlagRoute definition.

        leaf atomicAggregateRoute  {
            type  cml-data-types:CML_BOOL_T;
            config false;
            description "atomic-aggregate";
        } // END of atomicAggregateRoute definition.

        leaf bgpInfoSelectedRoute  {
            type  cml-data-types:CML_BOOL_T;
            config false;
            description "BGP info best selected route";
        } // END of bgpInfoSelectedRoute definition.

        leaf bgpTxPathId  {
            if-feature feature-list:HAVE_BGP_ADD_PATH;
            type  cml-data-types:CML_UINT8_T;
            config false;
            description "bgp add path Tx Id";
        } // END of bgpTxPathId definition.

        leaf bgpRxPathId  {
            if-feature feature-list:HAVE_BGP_ADD_PATH;
            type  cml-data-types:CML_UINT8_T;
            config false;
            description "bgp add path Rx Id";
        } // END of bgpRxPathId definition.

        leaf advCapablityIpv4Multicast  {
            type  cml-data-types:CML_STRING_T;
            config false;
            description "IPV4 Multicast neighbour Capability";
        } // END of advCapablityIpv4Multicast definition.

        leaf advCapablityVpnv4Unicast  {
            type  cml-data-types:CML_STRING_T;
            config false;
            description "Vpnv4 Unicast neighbour Capability";
        } // END of advCapablityVpnv4Unicast definition.

        leaf advCapablityRtfilterUnicast  {
            type  cml-data-types:CML_STRING_T;
            config false;
            description "Rtfilter Unicast neighbour Capability";
        } // END of advCapablityRtfilterUnicast definition.

        leaf advCapablityL2vpnEvpn  {
            type  cml-data-types:CML_STRING_T;
            config false;
            description "L2vpn Evpn neighbour Capability";
        } // END of advCapablityL2vpnEvpn definition.

        leaf advCapablityIpv6Unicast  {
            type  cml-data-types:CML_STRING_T;
            config false;
            description "Ipv6 Unicast neighbour Capability";
        } // END of advCapablityIpv6Unicast definition.

        leaf advCapablityIpv6Multicast  {
            type  cml-data-types:CML_STRING_T;
            config false;
            description "Ipv6 Multicast neighbour Capability";
        } // END of advCapablityIpv6Multicast definition.

        leaf advCapablityIpv6LabelUnicast  {
            type  cml-data-types:CML_STRING_T;
            config false;
            description "Ipv6 Label Unicast neighbour Capability";
        } // END of advCapablityIpv6LabelUnicast definition.

    } // END of nextHopRunTimeAttr definition.
    grouping nwRunTimeAttr {
        description
            "nwRunTimeAttr";
        leaf ntwkPathCountRoute  {
            type  cml-data-types:CML_INT32_T;
            config false;
            description "Network path count";
        } // END of ntwkPathCountRoute definition.

        leaf noAdvertiseRoute  {
            type  cml-data-types:CML_BOOL_T;
            config false;
            description "not advertised to any peer";
        } // END of noAdvertiseRoute definition.

        leaf noExportRoute  {
            type  cml-data-types:CML_BOOL_T;
            config false;
            description "not advertised to EBGP peer";
        } // END of noExportRoute definition.

        leaf localAsRoute  {
            type  cml-data-types:CML_BOOL_T;
            config false;
            description "not advertised outside local AS";
        } // END of localAsRoute definition.

        leaf suppressRoute  {
            type  cml-data-types:CML_BOOL_T;
            config false;
            description "Advertisements suppressed by an aggregate.";
        } // END of suppressRoute definition.

        leaf ntwkBestPathCountRoute  {
            type  cml-data-types:CML_INT32_T;
            config false;
            description "best path count";
        } // END of ntwkBestPathCountRoute definition.

        leaf defIPRoutingTbl  {
            type  cml-data-types:CML_STRING_T;
            config false;
            description "IP-Routing-Table";
        } // END of defIPRoutingTbl definition.

        leaf-list advNonPeerGroupAddr  {
            type  cml-data-types:CML_HOSTNAME_T;
            config false;
            description "Advertised non peer-group peers.";
        } // END of advNonPeerGroupAddr definition.

        leaf-list advPeerGroupNameRoute  {
            type  cml-data-types:CML_STRING_T;
            config false;
            description "Advertised peer-groups";
        } // END of advPeerGroupNameRoute definition.

        leaf advAnyPeer  {
            type  cml-data-types:CML_BOOL_T;
            config false;
            description "Advertised to any peer";
        } // END of advAnyPeer definition.

        leaf rdStr  {
            if-feature feature-list:HAVE_MPLS;
            type  cml-data-types:CML_STRING_T;
            config false;
            description "route distinguisher";
        } // END of rdStr definition.


        list nextHop {
            key "nextHopAddr";
            config false;
            description
                "nextHop";
            leaf nextHopAddr  {
                type  cml-data-types:CML_HOSTNAME_T;
                description "NextHop Address";
            } // END of nextHopAddr definition.

            uses nextHopRunTimeAttr;
        } // End of nextHop-list
    } // END of nwRunTimeAttr definition.
    grouping peerVrfAttrs {
        description
            "peerVrfAttrs";
        leaf bgpPortAf  {
            type  cml-data-types:CML_UINT16_T {
                 range "0..65535";
            }
            default "179";
            description "tcp port number";
        } // END of bgpPortAf definition.

        leaf peerActivateAf  {
            type  cml-data-types:CML_BOOL_T;
            description "Activate/Deactivate neighbor for address-family";
        } // END of peerActivateAf definition.

        leaf defaultPeerRmapNameAf  {
            type  cml-data-types:CML_BOOL_T;
            description "default originate set/unset for address-family";
        } // END of defaultPeerRmapNameAf definition.

        leaf peerRmapOriNameAf  {
            type  cml-data-types:CML_STRING_T;
            description "Route-map name for address-family";
        } // END of peerRmapOriNameAf definition.

        leaf softReconfigInboundAf  {
            type  cml-data-types:CML_BOOL_T;
            description "neighbor inbound soft reconfiguration set/unset for address-family";
        } // END of softReconfigInboundAf definition.

        leaf weightAf  {
            type  cml-data-types:CML_UINT16_T {
                 range "0..65535";
            }
            default "0";
            description "Weight for routes for address-family";
        } // END of weightAf definition.

        leaf peerRouteReflectorAf  {
            type  cml-data-types:CML_BOOL_T;
            description "bgp neighbor set/unset as route-reflector-client for address-family";
        } // END of peerRouteReflectorAf definition.

        leaf peerRemovePvtAsAf  {
            type  cml-data-types:CML_BOOL_T;
            description "bgp neighbor remove private AS set/unset for address-family";
        } // END of peerRemovePvtAsAf definition.

        leaf sendCommunityAf  {
            type  cml-data-types:CML_BOOL_T;
            description "bgp neighbor send-community set/unset for address-family";
        } // END of sendCommunityAf definition.

        leaf sendCommunityTypeAf  {
            type  cml-data-types:CML_BGP_SEND_COMMU_TYPE_T;
            description "bgp neighbor send-community type for address-family";
        } // END of sendCommunityTypeAf definition.

        leaf neighborAttrUnchangedAf  {
            type  cml-data-types:CML_ATTRIBUTE_UNCHANGED_TYPE_T;
            description "bgp attribute advertise unchanged to neighbor for address-family";
        } // END of neighborAttrUnchangedAf definition.

        leaf orfPrefixOptAf  {
            type  cml-data-types:CML_BGP_ORF_PREFIX_TYPE_T;
            description "advertise outbound router filtering (ORF) capability for address-family";
        } // END of orfPrefixOptAf definition.

        leaf peerAllowEbgpVpnAf  {
            if-feature feature-list:HAVE_VRF;
            type  cml-data-types:CML_BOOL_T;
            description "Allow VPN Routes";
        } // END of peerAllowEbgpVpnAf definition.

        leaf allowAsNumAf  {
            type  cml-data-types:CML_UINT32_T {
                 range "1..10";
            }
            default "3";
            description "Allow AS number for address-family";
        } // END of allowAsNumAf definition.

        leaf neighborCapabilityGrstAf  {
            type  cml-data-types:CML_BOOL_T;
            description "bgp neighbor capability graceful restart set/unset for address-family";
        } // END of neighborCapabilityGrstAf definition.

        leaf peerGroupTagAf  {
            type  cml-data-types:CML_STRING_T;
            description "BGP peer group name for address-family";
        } // END of peerGroupTagAf definition.

        leaf maxPrefixesAf  {
            type  cml-data-types:CML_UINT32_T {
                 range "1..4294967295";
            }
            description "Maximum number of prefixes for address-family";
        } // END of maxPrefixesAf definition.

        leaf stopUpdateAf  {
            type  cml-data-types:CML_BOOL_T;
            description "stop installing the routes when limit is exceeded for address-family";
        } // END of stopUpdateAf definition.

        leaf maxPrefixeWarningAf  {
            type  cml-data-types:CML_BOOL_T;
            description "Throw warning if exceeds threshold-value Yes/No flag for address-family";
        } // END of maxPrefixeWarningAf definition.

        leaf thresholdAf  {
            type  cml-data-types:CML_UINT8_T {
                 range "1..100";
            }
            default "75";
            description "Threshold-value in percent for address-family";
        } // END of thresholdAf definition.

        leaf warningAf  {
            type  cml-data-types:CML_BOOL_T;
            description "Throw warning if exceeds threshold-value Yes/No flag for address-family";
        } // END of warningAf definition.

        leaf unSuppressAclInfoAf  {
            type  cml-data-types:CML_STRING_T;
            description "unsuppress map name for address-family";
        } // END of unSuppressAclInfoAf definition.


        list bgpDlistFilter {
            key "distributeListDirectionAf";
            description
                "bgpDlistFilter";
            leaf aclInfoAf  {
                type  cml-data-types:CML_STRING_T;
                mandatory true;
                description "ip access-list name for address-family";
            } // END of aclInfoAf definition.

            leaf distributeListDirectionAf  {
                type  cml-data-types:CML_BGP_DISTRIBUTE_LIST_ACTION_T;
                description "neighbor distribute-list to filter route update for address-family";
            } // END of distributeListDirectionAf definition.

        } // End of bgpDlistFilter-list

        list bgpAslistFilter {
            key "asListDirectionAf";
            description
                "bgpAslistFilter";
            leaf asListAclInfoAf  {
                type  cml-data-types:CML_STRING_T;
                mandatory true;
                description "as path access-list name for address-family";
            } // END of asListAclInfoAf definition.

            leaf asListDirectionAf  {
                type  cml-data-types:CML_BGP_DISTRIBUTE_LIST_ACTION_T;
                description "neighbor aspath-list to filter route updates for address-family";
            } // END of asListDirectionAf definition.

        } // End of bgpAslistFilter-list

        list bgpPlistFilter {
            key "prefixListDirectionAf";
            description
                "bgpPlistFilter";
            leaf prefixListAclInfoAf  {
                type  cml-data-types:CML_STRING_T;
                mandatory true;
                description "prefix list name for address-family";
            } // END of prefixListAclInfoAf definition.

            leaf prefixListDirectionAf  {
                type  cml-data-types:CML_BGP_DISTRIBUTE_LIST_ACTION_T;
                description "neighbor prefix-list to filter route updates for address-family";
            } // END of prefixListDirectionAf definition.

        } // End of bgpPlistFilter-list

        list bgpRmapFilter {
            key "peerRmapDirectionAf";
            description
                "bgpRmapFilter";
            leaf peerRmapNameAf  {
                type  cml-data-types:CML_STRING_T;
                mandatory true;
                description "route map name for address-family";
            } // END of peerRmapNameAf definition.

            leaf peerRmapDirectionAf  {
                type  cml-data-types:CML_BGP_DISTRIBUTE_LIST_ACTION_T;
                description "neighbor route-map to filter route updates for address-family";
            } // END of peerRmapDirectionAf definition.

        } // End of bgpRmapFilter-list
    } // END of peerVrfAttrs definition.

    grouping  bgpGlobal-grouping {
    description
        "BGP global commands";
    container bgpGlobal {
        description
            "BGP global commands";
        leaf snmpRestart  {
            if-feature feature-list:HAVE_SNMP;
            type  cml-data-types:CML_BOOL_T;
            description "snmp restart set/unset";
        } // END of snmpRestart definition.

        leaf aggNexthop  {
            type  cml-data-types:CML_BOOL_T;
            description "aggregate nexthop check set/unset";
        } // END of aggNexthop definition.

        leaf pathSelect  {
            type  cml-data-types:CML_BOOL_T;
            description "RFC1771 path selection set/unset";
        } // END of pathSelect definition.

        leaf setDisableAdjOut  {
            type  cml-data-types:CML_BOOL_T;
            description "disable adj out set/unset";
        } // END of setDisableAdjOut definition.

        leaf setExtAsnCap  {
            if-feature feature-list:HAVE_EXT_CAP_ASN;
            type  cml-data-types:CML_BOOL_T;
            description "extended ASN capability set/unset";
        } // END of setExtAsnCap definition.

        leaf setNexthopTriggerEnable  {
            type  cml-data-types:CML_BOOL_T;
            description "bgp nexthop tracking functionality enable/disable";
        } // END of setNexthopTriggerEnable definition.

        leaf delayInterval  {
            type  cml-data-types:CML_UINT8_T {
                 range "1..100";
            }
            default "5";
            description "nexthop trigger delay time";
        } // END of delayInterval definition.

        leaf rfc1771StrictSet  {
            type  cml-data-types:CML_BOOL_T;
            description "rfc1771 strict behavior set/unset";
        } // END of rfc1771StrictSet definition.

        leaf configType  {
            type  cml-data-types:CML_BGP_CONFIG_T;
            description "config-type (standard|zebos)";
        } // END of configType definition.


        list communityList {
            key "commListName";
            description
                "communityList";
            leaf commListName  {
                type  cml-data-types:CML_STRING_T;
                description "Community list name";
            } // END of commListName definition.


            list commListAction {
                key "action";
                description
                    "commListAction";
                leaf action  {
                    type  cml-data-types:CML_BGP_COMMUNITY_LIST_ACTION_T;
                    description "bgp community type";
                } // END of action definition.


                list commListVal {
                    key "commListValue";
                    description
                        "commListVal";
                    leaf commListValue  {
                        type  cml-data-types:CML_STRING_T {
                            pattern "[^?'=,>|]*";
                            }
                            description "bgp community attributes value";
                        } // END of commListValue definition.

                } // End of commListVal-list
            } // End of commListAction-list
        } // End of communityList-list

        list communityListNo {
            key "commListStandNo";
            description
                "communityListNo";
            leaf commListStandNo  {
                type  cml-data-types:CML_UINT32_T {
                     range "1..99";
                }
                description "Community list standard number";
            } // END of commListStandNo definition.


            list commListAction {
                key "action";
                description
                    "commListAction";
                leaf action  {
                    type  cml-data-types:CML_BGP_COMMUNITY_LIST_ACTION_T;
                    description "Community list type";
                } // END of action definition.

            } // End of commListAction-list

            list actionListVal {
                key "actionListVal";
                description
                    "actionListVal";
                leaf actionListVal  {
                    type  cml-data-types:CML_BGP_COMMUNITY_LIST_ACTION_T;
                    description "Community list type";
                } // END of actionListVal definition.


                list commListVal {
                    key "commListValue";
                    description
                        "commListVal";
                    leaf commListValue  {
                        type  cml-data-types:CML_STRING_T {
                            pattern "[^?'=,>|]*";
                            }
                            description "bgp community attributes value";
                        } // END of commListValue definition.

                } // End of commListVal-list
            } // End of actionListVal-list
        } // End of communityListNo-list

        list communityListStand {
            key "commListName";
            description
                "communityListStand";
            leaf commListName  {
                type  cml-data-types:CML_STRING_T;
                description "Community list standard name";
            } // END of commListName definition.


            list commListAction {
                key "actionStandardList";
                description
                    "commListAction";
                leaf actionStandardList  {
                    type  cml-data-types:CML_BGP_COMMUNITY_LIST_ACTION_T;
                    description "Community list type";
                } // END of actionStandardList definition.

            } // End of commListAction-list

            list actionListVal {
                key "actionListVal";
                description
                    "actionListVal";
                leaf actionListVal  {
                    type  cml-data-types:CML_BGP_COMMUNITY_LIST_ACTION_T;
                    description "Community list type";
                } // END of actionListVal definition.


                list commListVal {
                    key "commListStandValue";
                    description
                        "commListVal";
                    leaf commListStandValue  {
                        type  cml-data-types:CML_STRING_T {
                            pattern "[^?'=,>|]*";
                            }
                            description "Community list value";
                        } // END of commListStandValue definition.

                } // End of commListVal-list
            } // End of actionListVal-list
        } // End of communityListStand-list

        list communityListExp {
            key "commListNo";
            description
                "communityListExp";
            leaf commListNo  {
                type  cml-data-types:CML_UINT32_T {
                     range "100..500";
                }
                description "Community list extended value";
            } // END of commListNo definition.


            list commListAction {
                key "commListaction";
                description
                    "commListAction";
                leaf commListaction  {
                    type  cml-data-types:CML_BGP_COMMUNITY_LIST_ACTION_T;
                    description "Community list extended type";
                } // END of commListaction definition.


                list commListrouteTargetOrSoo {
                    key "commListrtSoo";
                    description
                        "commListrouteTargetOrSoo";
                    leaf commListrtSoo  {
                        type  cml-data-types:CML_BGP_ROUTE_TARGET_T;
                        description "route-target soo";
                    } // END of commListrtSoo definition.


                    list CommListVal {
                        key "commListValueExp";
                        description
                            "CommListVal";
                        leaf commListValueExp  {
                            type  cml-data-types:CML_STRING_T;
                            description "Community list expanded value";
                        } // END of commListValueExp definition.

                    } // End of CommListVal-list
                } // End of commListrouteTargetOrSoo-list
            } // End of commListAction-list
        } // End of communityListExp-list

        list communityListExpand {
            key "commListExpName";
            description
                "communityListExpand";
            leaf commListExpName  {
                type  cml-data-types:CML_STRING_T;
                description "Community list expanded name";
            } // END of commListExpName definition.


            list commListExpAction {
                key "commListExpaction";
                description
                    "commListExpAction";
                leaf commListExpaction  {
                    type  cml-data-types:CML_BGP_COMMUNITY_LIST_ACTION_T;
                    description "Community list expanded type";
                } // END of commListExpaction definition.


                list commListExprouteTargetOrSoo {
                    key "commListExprtSoo";
                    description
                        "commListExprouteTargetOrSoo";
                    leaf commListExprtSoo  {
                        type  cml-data-types:CML_BGP_ROUTE_TARGET_T;
                        description "route-target soo";
                    } // END of commListExprtSoo definition.


                    list CommListExpVal {
                        key "commListExpvalue";
                        description
                            "CommListExpVal";
                        leaf commListExpvalue  {
                            type  cml-data-types:CML_STRING_T;
                            description "Community list expanded value";
                        } // END of commListExpvalue definition.

                    } // End of CommListExpVal-list
                } // End of commListExprouteTargetOrSoo-list
            } // End of commListExpAction-list
        } // End of communityListExpand-list

        list extCommuListNo {
            key "extCommListNo";
            description
                "extCommuListNo";
            leaf extCommListNo  {
                type  cml-data-types:CML_UINT32_T {
                     range "1..99";
                }
                description "Extended Community list number";
            } // END of extCommListNo definition.


            list extCommListAction {
                key "extAction";
                description
                    "extCommListAction";
                leaf extAction  {
                    type  cml-data-types:CML_BGP_COMMUNITY_LIST_ACTION_T;
                    description "Extended Community list type";
                } // END of extAction definition.


                list extCommListrouteTargetOrSoo {
                    key "rtSoo";
                    description
                        "extCommListrouteTargetOrSoo";
                    leaf rtSoo  {
                        type  cml-data-types:CML_BGP_ROUTE_TARGET_T;
                        description "route-target soo";
                    } // END of rtSoo definition.


                    list extCommListVal {
                        key "extCommListValue";
                        description
                            "extCommListVal";
                        leaf extCommListValue  {
                            type  cml-data-types:CML_STRING_T;
                            description "extcommunity Community list value";
                        } // END of extCommListValue definition.

                    } // End of extCommListVal-list
                } // End of extCommListrouteTargetOrSoo-list
            } // End of extCommListAction-list
        } // End of extCommuListNo-list

        list extCommListStand {
            key "extCommListStandName";
            description
                "extCommListStand";
            leaf extCommListStandName  {
                type  cml-data-types:CML_STRING_T;
                description "extcommunity Community list name";
            } // END of extCommListStandName definition.


            list extCommListStandAction {
                key "extStandAction";
                description
                    "extCommListStandAction";
                leaf extStandAction  {
                    type  cml-data-types:CML_BGP_COMMUNITY_LIST_ACTION_T;
                    description "extcommunity Community list type";
                } // END of extStandAction definition.


                list extCommListStandrouteTargetSoo {
                    key "extStandrtSoo";
                    description
                        "extCommListStandrouteTargetSoo";
                    leaf extStandrtSoo  {
                        type  cml-data-types:CML_BGP_ROUTE_TARGET_T;
                        description "route-target soo";
                    } // END of extStandrtSoo definition.


                    list extCommListStandVal {
                        key "extStandValue";
                        description
                            "extCommListStandVal";
                        leaf extStandValue  {
                            type  cml-data-types:CML_STRING_T;
                            description "extcommunity Community list value";
                        } // END of extStandValue definition.

                    } // End of extCommListStandVal-list
                } // End of extCommListStandrouteTargetSoo-list
            } // End of extCommListStandAction-list
        } // End of extCommListStand-list

        list extCommunityListExp {
            key "extCommListNoExp";
            description
                "extCommunityListExp";
            leaf extCommListNoExp  {
                type  cml-data-types:CML_UINT32_T {
                     range "100..500";
                }
                description "extcommunity Extended Community number";
            } // END of extCommListNoExp definition.


            list extCommListActionExp {
                key "extActionExp";
                description
                    "extCommListActionExp";
                leaf extActionExp  {
                    type  cml-data-types:CML_BGP_COMMUNITY_LIST_ACTION_T;
                    description "extcommunity Extended Community type";
                } // END of extActionExp definition.


                list extCommListrouteTargetSooExp {
                    key "extCommListrtSooExp";
                    description
                        "extCommListrouteTargetSooExp";
                    leaf extCommListrtSooExp  {
                        type  cml-data-types:CML_BGP_ROUTE_TARGET_T;
                        description "route-target soo";
                    } // END of extCommListrtSooExp definition.


                    list extCommListValExp {
                        key "extCommListValueExp";
                        description
                            "extCommListValExp";
                        leaf extCommListValueExp  {
                            type  cml-data-types:CML_STRING_T;
                            description "extcommunity Community list value";
                        } // END of extCommListValueExp definition.

                    } // End of extCommListValExp-list
                } // End of extCommListrouteTargetSooExp-list
            } // End of extCommListActionExp-list
        } // End of extCommunityListExp-list

        list extCommListExpand {
            key "extCommListExpName";
            description
                "extCommListExpand";
            leaf extCommListExpName  {
                type  cml-data-types:CML_STRING_T;
                description "extcommunity expanded Community name";
            } // END of extCommListExpName definition.


            list extCommListAction {
                key "extCommListExpAction";
                description
                    "extCommListAction";
                leaf extCommListExpAction  {
                    type  cml-data-types:CML_BGP_COMMUNITY_LIST_ACTION_T;
                    description "extcommunity expanded Community type";
                } // END of extCommListExpAction definition.


                list extCommListExprouteTargetSoo {
                    key "extCommListExprtSoo";
                    description
                        "extCommListExprouteTargetSoo";
                    leaf extCommListExprtSoo  {
                        type  cml-data-types:CML_BGP_ROUTE_TARGET_T;
                        description "route-target soo";
                    } // END of extCommListExprtSoo definition.


                    list extCommListExpVal {
                        key "extCommListExpValue";
                        description
                            "extCommListExpVal";
                        leaf extCommListExpValue  {
                            type  cml-data-types:CML_STRING_T;
                            description "extcommunity Community list value";
                        } // END of extCommListExpValue definition.

                    } // End of extCommListExpVal-list
                } // End of extCommListExprouteTargetSoo-list
            } // End of extCommListAction-list
        } // End of extCommListExpand-list

        list accessList {
            key "accessListName";
            description
                "accessList";
            leaf accessListName  {
                type  cml-data-types:CML_STRING_T;
                description "list_name AS path access list name";
            } // END of accessListName definition.


            list accessListDirection {
                key "accessListDirection";
                description
                    "accessListDirection";
                leaf accessListDirection  {
                    type  cml-data-types:CML_BGP_COMMUNITY_LIST_ACTION_T;
                    description "Action type <0-1> 0 - Deny 1 - Permit";
                } // END of accessListDirection definition.


                list bgpRegExp {
                    key "bgpRegExp";
                    description
                        "bgpRegExp";
                    leaf bgpRegExp  {
                        type  cml-data-types:CML_LINE_T;
                        description "Regular expression to match BGP AS paths";
                    } // END of bgpRegExp definition.

                } // End of bgpRegExp-list
            } // End of accessListDirection-list
        } // End of accessList-list
    } // END of bgpGlobal-container definition.
    } // END of bgpGlobal-container definition.

    grouping  bgpDebug-grouping {
    description
        "bgpDebug";
    container bgpDebug {
        description
            "bgpDebug";
        leaf debugFlag  {
            type  cml-data-types:CML_BGP_DEBUG_TYPE_T;
            description "bgp debug flag";
        } // END of debugFlag definition.

        leaf debugTermFlag  {
            type  cml-data-types:CML_BGP_DEBUG_TYPE_T;
            description "bgp term debug flag";
        } // END of debugTermFlag definition.

        leaf undebugFlag  {
            type  cml-data-types:CML_BGP_DEBUG_TYPE_T;
            description "bgp undebug flag";
        } // END of undebugFlag definition.

        leaf debugUpdateTypeFlag  {
            type  cml-data-types:CML_BGP_UPDATE_DEBUG_TYPE_T;
            description "bgp debug update flag";
        } // END of debugUpdateTypeFlag definition.

        leaf debugTermUpdateTypeFlag  {
            type  cml-data-types:CML_BGP_UPDATE_DEBUG_TYPE_T;
            description "bgp term debug update flag";
        } // END of debugTermUpdateTypeFlag definition.

    } // END of bgpDebug-container definition.
    } // END of bgpDebug-container definition.

    grouping  vrfTable-grouping {
    description
        "vrfTable";
    container vrfTable {
        if-feature feature-list:HAVE_VRF;
        description
            "vrfTable";
        leaf importMap  {
            type  cml-data-types:CML_STRING_T;
            description "import map name";
        } // END of importMap definition.

        leaf rdStr  {
            type  cml-data-types:CML_STRING_T {
                length "1..32";
            }
            description "route distinguisher value";
        } // END of rdStr definition.


        list routeTarget {
            key "rtRdStr";
            description
                "routeTarget";
            leaf rtRdStr  {
                type  cml-data-types:CML_STRING_T {
                    length "1..32";
                }
                description "route distinguisher";
            } // END of rtRdStr definition.

            leaf direct  {
                type  cml-data-types:CML_RT_T;
                mandatory true;
                description "route-target value";
            } // END of direct definition.

        } // End of routeTarget-list
        container bgpRd {
            config false;
            description
                "BGP router distinguisher value";
            container bgpRdAs {
                config false;
                description
                    "BGP Router Distinguisher AS-Type";
                leaf brdAs  {
                    type  cml-data-types:CML_INT32_T;
                    description "Route-Distinguisher As";
                } // END of brdAs definition.

                leaf brdAsNum  {
                    type  cml-data-types:CML_INT32_T;
                    description "Route-Distinguisher As num";
                } // END of brdAsNum definition.

            } // END of bgpRdAs-container definition.
            container bgpRdAs4 {
                config false;
                description
                    "BGP Router Distinguisher 4-octect-AS-Type";
                leaf brdAs4  {
                    type  cml-data-types:CML_INT32_T;
                    description "Route-Distinguisher brd as4";
                } // END of brdAs4 definition.

                leaf brdAsNum4  {
                    type  cml-data-types:CML_INT32_T;
                    description "Route-Distinguisher brd asnum4";
                } // END of brdAsNum4 definition.

            } // END of bgpRdAs4-container definition.
            container bgpRdIp {
                config false;
                description
                    "BGP Router Distinguisher IP-Type";
                leaf brdIp  {
                    type  cml-data-types:CML_STRING_T;
                    description "BGP Router Distinguisher ip";
                } // END of brdIp definition.

                leaf brdIpNum  {
                    type  cml-data-types:CML_INT32_T;
                    description "BGP Router Distinguisher ip num";
                } // END of brdIpNum definition.

            } // END of bgpRdIp-container definition.
        } // END of bgpRd-container definition.
    } // END of vrfTable-container definition.
    } // END of vrfTable-container definition.


}
