/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-zebos-ospfv3.yang
*
*/

submodule ipi-zebos-ospfv3 {

    belongs-to  ipi-zebos { prefix ipi-zebos; }

    import cml-data-types {
        prefix cml-data-types;
    }

    import feature-list {
        prefix feature-list;
    }

    include ipi-zebos-interface;
    include ipi-zebos-vrf;
    organization
        "IP Infusion Inc.";

    contact
        "Address: 3965 Freedom Circle, Suite 200, Santa Clara, CA 95054
        Phone: +1 408-400-1900
        E-mail: support@ipinfusion.com
        Web: http://www.ipinfusion.com/";

    description
        "Layer-3 OSPFv3 configurations";


    revision "2018-06-21" {
        description " Initial Version.";
        reference "";
    }

    grouping lsdb {
        description
            "lsdb";
        leaf lsdbIfName  {
            type  cml-data-types:CML_STRING_T;
            config false;
            description "LSDB Interface Name";
        } // END of lsdbIfName definition.

        leaf lsdbAreaId  {
            type  cml-data-types:CML_STRING_T;
            config false;
            description "LSDB Area ID";
        } // END of lsdbAreaId definition.


        list lsdbSlot {
            key "lsdbSlotType";
            config false;
            description
                "LSDB of AS-external-LSAs.";
            leaf lsdbSlotType  {
                type  cml-data-types:CML_UINT32_T;
                description "Type of LSDB Slot";
            } // END of lsdbSlotType definition.


            list lsa {
                key "lsaLinkId";
                config false;
                description
                    "OSPFv3 Link State Advertisement (LSA) list";
                leaf lsaLinkId  {
                    type  cml-data-types:CML_STRING_T;
                    description "LSA Link ID";
                } // END of lsaLinkId definition.

                leaf lsaAge  {
                    type  cml-data-types:CML_UINT32_T;
                    description "LSA Age";
                } // END of lsaAge definition.

                leaf lsaType  {
                    type  cml-data-types:CML_UINT32_T;
                    description "Type of LSA";
                } // END of lsaType definition.

                leaf lsaLength  {
                    type  cml-data-types:CML_UINT32_T;
                    description "Length of LSA";
                } // END of lsaLength definition.

                leaf lsaAdvRouter  {
                    type  cml-data-types:CML_STRING_T;
                    description "Advertising Router of LSA";
                } // END of lsaAdvRouter definition.

                leaf lsaSeqNum  {
                    type  cml-data-types:CML_STRING_T;
                    description "LSA Sequence Number";
                } // END of lsaSeqNum definition.

                leaf lsaCheckSum  {
                    type  cml-data-types:CML_STRING_T;
                    description "LSA Checksum";
                } // END of lsaCheckSum definition.

                leaf isLsaInterRouter  {
                    type  cml-data-types:CML_BOOL_T;
                    description "Bool parameter for LsaInterRouter";
                } // END of isLsaInterRouter definition.

                leaf lsaRouterLinkCount  {
                    type  cml-data-types:CML_UINT32_T;
                    description "Link Count for Router LSA";
                } // END of lsaRouterLinkCount definition.

                leaf lsaRefTypeStr  {
                    type  cml-data-types:CML_STRING_T;
                    description "lsaRefTypeStr";
                } // END of lsaRefTypeStr definition.

            } // End of lsa-list
        } // End of lsdbSlot-list
    } // END of lsdb definition.
    grouping Route {
        description
            "Route";

        list ospf6Route {
            key "routeIPV6Prefix";
            config false;
            description
                "OSPFv3 Route";
            leaf routeIPV6Prefix  {
                type  cml-data-types:CML_STRING_T;
                description "IPV6 Prefix Route";
            } // END of routeIPV6Prefix definition.

            leaf routeDistance  {
                type  cml-data-types:CML_UINT8_T;
                description "Route Distance";
            } // END of routeDistance definition.

            container ospf6Path {
                config false;
                description
                    "OSPFv3 path details for different routes";
                leaf pathType  {
                    type  cml-data-types:CML_OSPF6_PATH_TYPE_T;
                    description "Path Type";
                } // END of pathType definition.

                leaf pathCode  {
                    type  cml-data-types:CML_STRING_T;
                    description "Path Code";
                } // END of pathCode definition.

                leaf pathDiscardConnection  {
                    type  cml-data-types:CML_STRING_T;
                    description "Discarded Path Connection";
                } // END of pathDiscardConnection definition.

                leaf pathCost  {
                    type  cml-data-types:CML_UINT32_T;
                    description "Path Cost";
                } // END of pathCost definition.

                leaf pathType2Cost  {
                    type  cml-data-types:CML_UINT32_T;
                    description "Path Type to Cost";
                } // END of pathType2Cost definition.

                leaf pathFlags  {
                    type  cml-data-types:CML_OSPF6_PATH_FLAGS_T;
                    description "Path Flags";
                } // END of pathFlags definition.

            } // END of ospf6Path-container definition.
            uses ospf6NextHop;
        } // End of ospf6Route-list
    } // END of Route definition.
    grouping ospf6NextHop {
        description
            "ospf6NextHop";

        list nextHop {
            key "nextHopAddr";
            config false;
            description
                "OSPFv3 next hop details";
            leaf nextHopAddr  {
                type  cml-data-types:CML_STRING_T;
                description "Next Hop Address";
            } // END of nextHopAddr definition.

            leaf nextHopInterfaceName  {
                type  cml-data-types:CML_STRING_T;
                description "Next hop Interface Name";
            } // END of nextHopInterfaceName definition.

            leaf nextHopTransitAreaId  {
                type  cml-data-types:CML_STRING_T;
                description "Next Hop Transit Area ID";
            } // END of nextHopTransitAreaId definition.

            leaf nextHopAreaId  {
                type  cml-data-types:CML_STRING_T;
                description "Next Hop Area ID";
            } // END of nextHopAreaId definition.

            leaf isNextHopConnected  {
                type  cml-data-types:CML_BOOL_T;
                description "Bool Parameter for NextHopConnected";
            } // END of isNextHopConnected definition.

            leaf nextHopIsAreaTransit  {
                type  cml-data-types:CML_BOOL_T;
                description "Bool Parameter for NextHopTransitArea";
            } // END of nextHopIsAreaTransit definition.

            leaf IsnextHopInvalid  {
                type  cml-data-types:CML_BOOL_T;
                description "Bool parameter for NextHopInvalid";
            } // END of IsnextHopInvalid definition.

            leaf nextHopCode  {
                type  cml-data-types:CML_STRING_T;
                description "Next Hop Code";
            } // END of nextHopCode definition.

        } // End of nextHop-list
    } // END of ospf6NextHop definition.
    grouping ospf6LsaHeader {
        description
            "ospf6LsaHeader";
        leaf lsaLength  {
            type  cml-data-types:CML_UINT32_T;
            description "LSA Length";
        } // END of lsaLength definition.

        leaf lsaCheckSum  {
            type  cml-data-types:CML_STRING_T;
            description "LSA Checksum";
        } // END of lsaCheckSum definition.

        leaf lsaSeqNum  {
            type  cml-data-types:CML_STRING_T;
            description "LSA Sequence Number";
        } // END of lsaSeqNum definition.

        leaf lsaLinkId  {
            type  cml-data-types:CML_STRING_T;
            description "LSA Link ID";
        } // END of lsaLinkId definition.

        leaf lsaType  {
            type  cml-data-types:CML_STRING_T;
            description "LSA Type";
        } // END of lsaType definition.

        leaf lsaAge  {
            type  cml-data-types:CML_UINT32_T;
            description "LSA Age";
        } // END of lsaAge definition.

    } // END of ospf6LsaHeader definition.
    grouping helper {
        description
            "helper";
        leaf restartHelperOnlyReload  {
            if-feature feature-list:HAVE_RESTART;
            type  cml-data-types:CML_BOOL_T;
            description "Bool Parameter for Helper Reload restart";
        } // END of restartHelperOnlyReload definition.

        leaf restartHelperOnlyGracePeriod  {
            if-feature feature-list:HAVE_RESTART;
            type  cml-data-types:CML_UINT16_T {
                 range "2..1800";
            }
            description "Grace Period for Helper Only Restart";
        } // END of restartHelperOnlyGracePeriod definition.

        leaf restartHelperOnlyUpgrade  {
            if-feature feature-list:HAVE_RESTART;
            type  cml-data-types:CML_BOOL_T;
            description "Bool parameter for Helper Only Upgrade Restart";
        } // END of restartHelperOnlyUpgrade definition.

        leaf-list restartHelperRouterId  {
            if-feature feature-list:HAVE_RESTART;
            type  cml-data-types:CML_STRING_T;
            description "Router ID in an IPv4 format";
        } // END of restartHelperRouterId definition.

    } // END of helper definition.
    grouping default-information-originate {
        description
            "defaultCMLSEPinformationCMLSEPoriginate";

        list default-information {
            key "defaultInformationOriginate";
            description
                "Default external route Information";
            leaf defaultInformationOriginate  {
                type  cml-data-types:CML_BOOL_T;
                description "Default Information Originate";
            } // END of defaultInformationOriginate definition.

            container default-information-always {
                description
                    "Default external route Information Always";
                leaf alwaysSet  {
                    type  cml-data-types:CML_BOOL_T;
                    description "Bool Parameter for External Route Information";
                } // END of alwaysSet definition.

                uses metric-group;
            } // END of default-information-always-container definition.
        } // End of default-information-list
    } // END of default-information-originate definition.
    grouping redistribute {
        description
            "redistribute";

        list ospf6_redist_conf {
            key "ospf6RedistProtocol";
            description
                "Redistribute IPv4 routes ";
            leaf ospf6RedistProtocol  {
                type  cml-data-types:CML_OSPF6_ROUTE_SOURCE_TYPE_T;
                description "OSPFv3 Redistribute Protocol";
            } // END of ospf6RedistProtocol definition.

            container redistribute-tag {
                description
                    "Redistribute IPv4 routes tag options";
                leaf ospf6RedistTagVal  {
                    type  cml-data-types:CML_UINT32_T {
                         range "0..4294967295";
                    }
                    default "0";
                    description "OSPFv3 Redistribute Tag Value";
                } // END of ospf6RedistTagVal definition.

                uses metric-group;
            } // END of redistribute-tag-container definition.
        } // End of ospf6_redist_conf-list

        list ospf6_redist_ospf {
            key "ospf6RedistOspfProtocol";
            description
                "Redistribute IPv4 routes for OSPF option";
            leaf ospf6RedistOspfProtocol  {
                type  cml-data-types:CML_OSPF_AREA_ID_T;
                description "OSPFv3 redistribute OSPF Protocol";
            } // END of ospf6RedistOspfProtocol definition.

            container redistribute-tag {
                description
                    "Redistribute IPv4 routes for OSPF tag option";
                leaf ospf6RedistOspfTagVal  {
                    type  cml-data-types:CML_UINT32_T {
                         range "0..4294967295";
                    }
                    default "0";
                    description "Redistribute OSPF Tag Value";
                } // END of ospf6RedistOspfTagVal definition.

                uses metric-group;
            } // END of redistribute-tag-container definition.
        } // End of ospf6_redist_ospf-list
    } // END of redistribute definition.
    grouping metric-group {
        description
            "metricCMLSEPgroup";
        leaf metric  {
            type  cml-data-types:CML_UINT32_T {
                 range "0..16777214";
            }
            description "Metric Value";
        } // END of metric definition.

        leaf metricType  {
            type  cml-data-types:CML_OSPF_METRIC_TYPE_T;
            description "Metric Type";
        } // END of metricType definition.

        leaf routeMap  {
            type  cml-data-types:CML_STRING_T;
            description "Route Map";
        } // END of routeMap definition.

    } // END of metric-group definition.

    grouping  ospf6Master-grouping {
    description
        "OSPFv3 master for system wide configurations and variables.";
    container ospf6Master {
        description
            "OSPFv3 master for system wide configurations and variables.";
        leaf displaySingleLine  {
            type  cml-data-types:CML_BOOL_T;
            description "Bool Paremeter for Single Line Display";
        } // END of displaySingleLine definition.

        leaf gracePeriod  {
            if-feature feature-list:HAVE_RESTART;
            type  cml-data-types:CML_UINT16_T {
                 range "2..1800";
            }
            description "Grace period in seconds ";
        } // END of gracePeriod definition.

        leaf restartPlannedOnly  {
            if-feature feature-list:HAVE_RESTART;
            type  cml-data-types:CML_BOOL_T;
            description "Bool Parameter for Planned restart";
        } // END of restartPlannedOnly definition.


        list ospf6 {
            key "ospf6ProcessTag";
            description
                "OSPFv3 datastructure is for system-wide configuration and variables.";
            leaf ospf6ProcessTag  {
                type  cml-data-types:CML_STRING_T;
                description "OSPFv3 Process tag";
            } // END of ospf6ProcessTag definition.

            leaf vrfName  {
                if-feature feature-list:HAVE_VRF_OSPF6;
                type  cml-data-types:CML_STRING_T;
                description "VRF Name";
            } // END of vrfName definition.

            leaf routerId  {
                type  cml-data-types:CML_IPV4_ADDR_T;
                description "Router ID in IPV4 Address Format";
            } // END of routerId definition.

            leaf config_frr  {
                if-feature feature-list:HAVE_OSPF6_LFA;
                type  cml-data-types:CML_BOOL_T;
                description "Bool Parameter for FRR Config";
            } // END of config_frr definition.

            leaf abrType  {
                type  cml-data-types:CML_OSPF6_ABR_TYPE_T;
                default "cisco";
                description "The type of area border router";
            } // END of abrType definition.

            leaf teEnabled  {
                if-feature feature-list:HAVE_OSPF6_TE;
                type  cml-data-types:CML_BOOL_T;
                description "Bool Parameter for TE Enable";
            } // END of teEnabled definition.

            leaf restartMethod  {
                if-feature feature-list:HAVE_RESTART;
                type  cml-data-types:CML_BOOL_T;
                description "Graceful restart";
            } // END of restartMethod definition.

            leaf dbSummaryOpt  {
                type  cml-data-types:CML_BOOL_T;
                description "Bool Parameter for Database Summary";
            } // END of dbSummaryOpt definition.

            leaf bfdEnabled  {
                if-feature feature-list:HAVE_BFD;
                type  cml-data-types:CML_BOOL_T;
                description "Bool Parameter for BFD Enable";
            } // END of bfdEnabled definition.

            leaf floodReductionEnabled  {
                if-feature feature-list:HAVE_OSPF6_OD;
                type  cml-data-types:CML_BOOL_T;
                description "Bool Parameter for Flood Reduction";
            } // END of floodReductionEnabled definition.

            leaf defaultMetric  {
                type  cml-data-types:CML_UINT32_T {
                     range "1..16777214";
                }
                default "20";
                description "Default metric";
            } // END of defaultMetric definition.

            leaf minspfDelay  {
                type  cml-data-types:CML_UINT32_T {
                     range "0..2147483647";
                }
                default "500";
                description "Minimum SPF Delay";
            } // END of minspfDelay definition.

            leaf maxspfDelay  {
                type  cml-data-types:CML_UINT32_T {
                     range "0..2147483647";
                }
                default "50000";
                description "Maximum SPF Delay";
            } // END of maxspfDelay definition.

            leaf minDelay  {
                type  cml-data-types:CML_UINT32_T {
                     range "0..2147483647";
                }
                default "500";
                description "The minimum SPF hold delay time in milliseconds";
            } // END of minDelay definition.

            leaf maxDelay  {
                type  cml-data-types:CML_UINT32_T {
                     range "0..2147483647";
                }
                default "50000";
                description "The maximum SPF hold delay time in milliseconds";
            } // END of maxDelay definition.

            leaf refBandwidth  {
                type  cml-data-types:CML_UINT32_T {
                     range "1..4294967";
                }
                default "100000";
                description "The reference bandwidth in Mbits/sec numeric";
            } // END of refBandwidth definition.

            leaf maxConcurrentDd  {
                type  cml-data-types:CML_UINT16_T {
                     range "1..65535";
                }
                default "5";
                description "The maximum number of database descriptor processes numeric ";
            } // END of maxConcurrentDd definition.

            leaf maxUnusePacket  {
                type  cml-data-types:CML_UINT32_T {
                     range "0..65535";
                }
                default "200";
                description "Maximum number of unused OSPFv3 packets";
            } // END of maxUnusePacket definition.

            leaf maxUnuseLsa  {
                type  cml-data-types:CML_UINT32_T {
                     range "0..65535";
                }
                default "200";
                description " Maximum no LSA packets";
            } // END of maxUnuseLsa definition.

            leaf distanceAll  {
                type  cml-data-types:CML_UINT16_T {
                     range "1..254";
                }
                default "110";
                description "Admin Distance";
            } // END of distanceAll definition.

            leaf shutDown  {
                type  cml-data-types:CML_BOOL_T;
                description "Bool Parameter for Shutdown";
            } // END of shutDown definition.

            leaf logAdjChanges  {
                type  cml-data-types:CML_BOOL_T;
                description "Bool Parameter for Log Adjacency Changes";
            } // END of logAdjChanges definition.

            leaf logAdjChangesDetail  {
                type  cml-data-types:CML_BOOL_T;
                description "Bool Parameter for Log Adjacency Change Details";
            } // END of logAdjChangesDetail definition.

            leaf ospfv3VersionNumber  {
                type  cml-data-types:CML_UINT32_T;
                config false;
                description "OSPFv3 Version Number";
            } // END of ospfv3VersionNumber definition.

            leaf ospfv3AreaBdrRtrStatus  {
                type  cml-data-types:CML_BOOL_T;
                config false;
                description "Bool Parameter for  OSPFv3 Area Border Router Status";
            } // END of ospfv3AreaBdrRtrStatus definition.

            leaf ospfv3ASBdrRtrStatus  {
                type  cml-data-types:CML_BOOL_T;
                config false;
                description "Bool Parameter for OSPFv3 AS Border Router Status";
            } // END of ospfv3ASBdrRtrStatus definition.

            leaf processUpTime  {
                type  cml-data-types:CML_STRING_T;
                config false;
                description "Process Up Time";
            } // END of processUpTime definition.

            leaf ddCountIn  {
                type  cml-data-types:CML_UINT16_T;
                config false;
                description "Received DD Count";
            } // END of ddCountIn definition.

            leaf ddCountOut  {
                type  cml-data-types:CML_UINT16_T;
                config false;
                description "Sent DD Count";
            } // END of ddCountOut definition.

            leaf extenalLSACount  {
                type  cml-data-types:CML_UINT32_T;
                config false;
                description "External LSA Count";
            } // END of extenalLSACount definition.

            leaf lsdbChecksum  {
                type  cml-data-types:CML_STRING_T;
                config false;
                description "LSDB Checksum";
            } // END of lsdbChecksum definition.

            leaf unknownLSACount  {
                type  cml-data-types:CML_UINT32_T;
                config false;
                description "Unknown LSA Count";
            } // END of unknownLSACount definition.

            leaf lSASelfCount  {
                type  cml-data-types:CML_UINT32_T;
                config false;
                description "Self LSA Count";
            } // END of lSASelfCount definition.

            leaf lSARxCount  {
                type  cml-data-types:CML_UINT32_T;
                config false;
                description "Received LSA Count";
            } // END of lSARxCount definition.

            leaf areaCount  {
                type  cml-data-types:CML_UINT32_T;
                config false;
                description "Area Count";
            } // END of areaCount definition.

            leaf isDsteEnabled  {
                type  cml-data-types:CML_BOOL_T;
                config false;
                description "Bool Parameter for Dste Enable";
            } // END of isDsteEnabled definition.


            list passive {
                key "passiveIfName";
                description
                    "Suppress routing updates";
                leaf passiveIfName  {
                    type  cml-data-types:CML_STRING_T;
                    description "Passive Interface Name";
                } // END of passiveIfName definition.

            } // End of passive-list

            list frr_pref {
                if-feature feature-list:HAVE_OSPF6_LFA;
                key "frrPrefIndex";
                description
                    "Keeps user preferences, lower index in the array is higher priority";
                leaf frrPrefIndex  {
                    type  cml-data-types:CML_UINT32_T {
                         range "1..4";
                    }
                    description "FRR Preference Index";
                } // END of frrPrefIndex definition.

                leaf frrPrefVal  {
                    if-feature feature-list:HAVE_OSPF6_LFA;
                    type  cml-data-types:CML_OSPF_FRR_TIE_BREAK_VAL_T;
                    mandatory true;
                    description "FRR Preference Value";
                } // END of frrPrefVal definition.

            } // End of frr_pref-list

            list Ospf6LinkLsa {
                key "LinkLsaIndex";
                config false;
                description
                    "OSPFv3 Link Lsa Info";
                leaf LinkLsaIndex  {
                    type  cml-data-types:CML_INT32_T;
                    description "Link LSA Index";
                } // END of LinkLsaIndex definition.

                leaf NumberOfPrefixes  {
                    type  cml-data-types:CML_UINT32_T;
                    description "Number of prefixes";
                } // END of NumberOfPrefixes definition.

                leaf LinkLocalAddress  {
                    type  cml-data-types:CML_IPV6_ADDR_T;
                    description "Link Local Address";
                } // END of LinkLocalAddress definition.

                leaf LinkLsaOptions  {
                    type  cml-data-types:CML_STRING_T;
                    description "Link LSA Options";
                } // END of LinkLsaOptions definition.

                leaf Priority  {
                    type  cml-data-types:CML_UINT32_T;
                    description "Priority";
                } // END of Priority definition.

                leaf LinklsaAdvRouter  {
                    type  cml-data-types:CML_STRING_T;
                    description "Link LSA Advertising Router";
                } // END of LinklsaAdvRouter definition.

                leaf LinkLsaIfName  {
                    type  cml-data-types:CML_STRING_T;
                    description "Link LSA Interface Name";
                } // END of LinkLsaIfName definition.


                list Ospf6LinkLsaPrefixes {
                    key "LinkLsaPrefix";
                    config false;
                    description
                        "OSPFv3 Link Lsa Prefixes";
                    leaf LinkLsaPrefixNUbit  {
                        type  cml-data-types:CML_STRING_T;
                        description "Link LSA Prefix NU Bit";
                    } // END of LinkLsaPrefixNUbit definition.

                    leaf LinkLsaPrefixOptions  {
                        type  cml-data-types:CML_STRING_T;
                        description "Link LSA Prefix Options";
                    } // END of LinkLsaPrefixOptions definition.

                    leaf LinkLsaPrefix  {
                        type  cml-data-types:CML_STRING_T;
                        description "Link LSA Prefix";
                    } // END of LinkLsaPrefix definition.

                } // End of Ospf6LinkLsaPrefixes-list
                uses ospf6LsaHeader;
            } // End of Ospf6LinkLsa-list

            list Ospf6RouterLsa {
                key "RouterLsaIndex";
                config false;
                description
                    "OSPFv3 Router Lsa Info";
                leaf LsaAreaId  {
                    type  cml-data-types:CML_STRING_T;
                    description "LSA Area ID";
                } // END of LsaAreaId definition.

                leaf RouterLsaIndex  {
                    type  cml-data-types:CML_INT32_T;
                    description "Router LSA Index";
                } // END of RouterLsaIndex definition.

                leaf LsaOptions  {
                    type  cml-data-types:CML_STRING_T;
                    description "LSA Options";
                } // END of LsaOptions definition.

                leaf LsaFlag  {
                    type  cml-data-types:CML_STRING_T;
                    description "LSA Flag";
                } // END of LsaFlag definition.

                leaf RouterlsaAdvRouter  {
                    type  cml-data-types:CML_STRING_T;
                    description "Router LSA Advertising Router";
                } // END of RouterlsaAdvRouter definition.


                list RouterLsaLink {
                    key "LinkIndex";
                    config false;
                    description
                        "OSPFv3 Router Lsa Transit";
                    leaf LinkIndex  {
                        type  cml-data-types:CML_INT32_T;
                        description "Link Index";
                    } // END of LinkIndex definition.

                    leaf nbrRouterId  {
                        type  cml-data-types:CML_STRING_T;
                        description "Neighbor Router ID";
                    } // END of nbrRouterId definition.

                    leaf NbrInterfaceId  {
                        type  cml-data-types:CML_UINT32_T;
                        description "Neighbor Interface ID";
                    } // END of NbrInterfaceId definition.

                    leaf InterfaceId  {
                        type  cml-data-types:CML_UINT32_T;
                        description "Interface ID";
                    } // END of InterfaceId definition.

                    leaf LinkMetric  {
                        type  cml-data-types:CML_UINT32_T;
                        description "Link Metric";
                    } // END of LinkMetric definition.

                    leaf LinkType  {
                        type  cml-data-types:CML_STRING_T;
                        description "Link Type";
                    } // END of LinkType definition.

                } // End of RouterLsaLink-list
                uses ospf6LsaHeader;
            } // End of Ospf6RouterLsa-list

            list Ospf6NetworkLsa {
                key "NetworklsaAdvRouter";
                config false;
                description
                    "OSPFv3 Network Lsa Info";
                leaf NetworkLsaOptions  {
                    type  cml-data-types:CML_STRING_T;
                    description "Network LSA Options";
                } // END of NetworkLsaOptions definition.

                leaf NetworklsaAdvRouter  {
                    type  cml-data-types:CML_STRING_T;
                    description "Network LSA Advertising Router";
                } // END of NetworklsaAdvRouter definition.


                list NetworkLsaAttachedRouters {
                    key "AttachedRouter";
                    config false;
                    description
                        "OSPFv3 Lsa Attached Routers";
                    leaf AttachedRouter  {
                        type  cml-data-types:CML_STRING_T;
                        description "Attached Router";
                    } // END of AttachedRouter definition.

                } // End of NetworkLsaAttachedRouters-list
                uses ospf6LsaHeader;
            } // End of Ospf6NetworkLsa-list

            list Ospf6IntraPrefixLsa {
                key "IntraPrefixLsaIndex";
                config false;
                description
                    "OSPFv3 Intra-Prefix Lsa Info";
                leaf IntraPrefixLsaIndex  {
                    type  cml-data-types:CML_INT32_T;
                    description "LSA Index For Intra Prefix";
                } // END of IntraPrefixLsaIndex definition.

                leaf IntraLsaAreaId  {
                    type  cml-data-types:CML_STRING_T;
                    description "Intra LSA Area ID";
                } // END of IntraLsaAreaId definition.

                leaf IntraPrefixReferencedAdvRouter  {
                    type  cml-data-types:CML_STRING_T;
                    description "Intra Prefix Refrence Advertising Router";
                } // END of IntraPrefixReferencedAdvRouter definition.

                leaf IntraPrefixReferencedLinkId  {
                    type  cml-data-types:CML_STRING_T;
                    description "Intra Prefix Reference Link ID";
                } // END of IntraPrefixReferencedLinkId definition.

                leaf IntraPrefixReferencedLsType  {
                    type  cml-data-types:CML_STRING_T;
                    description "Intra Prefix Reference LS Type";
                } // END of IntraPrefixReferencedLsType definition.

                leaf NumberOfPrefixes  {
                    type  cml-data-types:CML_UINT32_T;
                    description "Number Of Prefixes";
                } // END of NumberOfPrefixes definition.

                leaf IntraPrefixlsaAdvRouter  {
                    type  cml-data-types:CML_STRING_T;
                    description "Advertisg Router for Intra Prefix LSA";
                } // END of IntraPrefixlsaAdvRouter definition.


                list Ospf6IntraPrefixLsaPrefixes {
                    key "IntraPrefixLsaPrefix";
                    config false;
                    description
                        "OSPFv3 Link Lsa Prefixes";
                    leaf IntraPrefixLsaPrefixNUbit  {
                        type  cml-data-types:CML_STRING_T;
                        description "Intra Prefix LSA Prefix NU Bit";
                    } // END of IntraPrefixLsaPrefixNUbit definition.

                    leaf IntraPrefixLsaPrefixMetric  {
                        type  cml-data-types:CML_UINT32_T;
                        description "Prefix Metric in Intra Prefix LSA";
                    } // END of IntraPrefixLsaPrefixMetric definition.

                    leaf IntraPrefixLsaPrefixOptions  {
                        type  cml-data-types:CML_STRING_T;
                        description "prefix Options in Intra Prefix LSA";
                    } // END of IntraPrefixLsaPrefixOptions definition.

                    leaf IntraPrefixLsaPrefix  {
                        type  cml-data-types:CML_STRING_T;
                        description "Prefix in Intra Prefix LSA";
                    } // END of IntraPrefixLsaPrefix definition.

                } // End of Ospf6IntraPrefixLsaPrefixes-list
                uses ospf6LsaHeader;
            } // End of Ospf6IntraPrefixLsa-list

            list Ospf6InterPrefixLsa {
                key "InterPrefixLsaIndex";
                config false;
                description
                    "OSPFv3 Inter-Prefix Lsa Info";
                leaf InterPrefixLsaIndex  {
                    type  cml-data-types:CML_INT32_T;
                    description "Index in Inter Prefix LSA";
                } // END of InterPrefixLsaIndex definition.

                leaf InterLsaAreaId  {
                    type  cml-data-types:CML_STRING_T;
                    description "Area ID in Inter LSA";
                } // END of InterLsaAreaId definition.

                leaf InterPrefixNUbit  {
                    type  cml-data-types:CML_STRING_T;
                    description "Inter Prefix NU Bit";
                } // END of InterPrefixNUbit definition.

                leaf InterPrefixLsaPrefixMetric  {
                    type  cml-data-types:CML_UINT32_T;
                    description "Prefix Metric in Inter Prefix LSA";
                } // END of InterPrefixLsaPrefixMetric definition.

                leaf InterPrefixLsaPrefixOptions  {
                    type  cml-data-types:CML_UINT32_T;
                    description "Prefix Options in Inter Prefix LSA";
                } // END of InterPrefixLsaPrefixOptions definition.

                leaf InterPrefixLsaPrefix  {
                    type  cml-data-types:CML_STRING_T;
                    description "Prefix in Inter Prefix LSA";
                } // END of InterPrefixLsaPrefix definition.

                leaf InterPrefixlsaAdvRouter  {
                    type  cml-data-types:CML_STRING_T;
                    description "Advertising Router of Inter Prefix LSA";
                } // END of InterPrefixlsaAdvRouter definition.

                uses ospf6LsaHeader;
            } // End of Ospf6InterPrefixLsa-list

            list Ospf6InterRouterLsa {
                key "InterRouterLsaIndex";
                config false;
                description
                    "OSPFv3 Inter-Router Lsa Info";
                leaf InterRouterLsaIndex  {
                    type  cml-data-types:CML_INT32_T;
                    description "Index value of Inter Router LSA";
                } // END of InterRouterLsaIndex definition.

                leaf InterRouterLsaAreaId  {
                    type  cml-data-types:CML_STRING_T;
                    description "Area ID in Inter Router LSA";
                } // END of InterRouterLsaAreaId definition.

                leaf InterRouterDestRouter  {
                    type  cml-data-types:CML_STRING_T;
                    description "Inter Router Dest Router";
                } // END of InterRouterDestRouter definition.

                leaf InterRouterLsaPrefixMetric  {
                    type  cml-data-types:CML_UINT32_T;
                    description "Prefix Metric in Inter Router LSA";
                } // END of InterRouterLsaPrefixMetric definition.

                leaf InterRouterLsaOptions  {
                    type  cml-data-types:CML_STRING_T;
                    description "Inter Router LSA Options";
                } // END of InterRouterLsaOptions definition.

                leaf InterRouterlsaAdvRouter  {
                    type  cml-data-types:CML_STRING_T;
                    description "Advertising Router of Inter Router LSA";
                } // END of InterRouterlsaAdvRouter definition.

                uses ospf6LsaHeader;
            } // End of Ospf6InterRouterLsa-list

            list Ospf6ExternalLsa {
                key "ExternalLsaIndex";
                config false;
                description
                    "OSPFv3 External Lsa Info";
                leaf ExternalLsaIndex  {
                    type  cml-data-types:CML_INT32_T;
                    description "External LSA Index";
                } // END of ExternalLsaIndex definition.

                leaf ExternalLsaPrefixNUbit  {
                    type  cml-data-types:CML_STRING_T;
                    description "External LSA Prefix NU Bit";
                } // END of ExternalLsaPrefixNUbit definition.

                leaf ExternalReferencedLinkId  {
                    type  cml-data-types:CML_STRING_T;
                    description "External Reference Link ID";
                } // END of ExternalReferencedLinkId definition.

                leaf ExternalReferencedLsType  {
                    type  cml-data-types:CML_UINT32_T;
                    description "External Referenced LS Type";
                } // END of ExternalReferencedLsType definition.

                leaf ExternalRouteTag  {
                    type  cml-data-types:CML_UINT32_T;
                    description "External Route Tag";
                } // END of ExternalRouteTag definition.

                leaf ExternalForwardingAddress  {
                    type  cml-data-types:CML_STRING_T;
                    description "External Forwarding Address";
                } // END of ExternalForwardingAddress definition.

                leaf ExternalPrefixOptions  {
                    type  cml-data-types:CML_STRING_T;
                    description "External Prefix Options";
                } // END of ExternalPrefixOptions definition.

                leaf ExternalPrefix  {
                    type  cml-data-types:CML_STRING_T;
                    description "External Prefix";
                } // END of ExternalPrefix definition.

                leaf ExternalLsaMetric  {
                    type  cml-data-types:CML_UINT32_T;
                    description "External LSA Metric";
                } // END of ExternalLsaMetric definition.

                leaf ExternalLsaMetricType  {
                    type  cml-data-types:CML_STRING_T;
                    description "External LSA Metric Type";
                } // END of ExternalLsaMetricType definition.

                leaf ExternallsaAdvRouter  {
                    type  cml-data-types:CML_STRING_T;
                    description "Advertising Router of External LSA";
                } // END of ExternallsaAdvRouter definition.

                uses ospf6LsaHeader;
            } // End of Ospf6ExternalLsa-list

            list Ospf6NssaExternalLsa {
                key "NssaExternalLsaIndex";
                config false;
                description
                    "OSPFv3 Nssa-External Lsa Info";
                leaf NssaExternalLsaIndex  {
                    type  cml-data-types:CML_INT32_T;
                    description "Index of NSSA External LSA";
                } // END of NssaExternalLsaIndex definition.

                leaf NssaExternalLsaPrefixNUbit  {
                    type  cml-data-types:CML_STRING_T;
                    description "Prefix NU Bit of NSSA External LSA";
                } // END of NssaExternalLsaPrefixNUbit definition.

                leaf NssaExternalReferencedLsType  {
                    type  cml-data-types:CML_STRING_T;
                    description "NSSA External Referenced LS Type";
                } // END of NssaExternalReferencedLsType definition.

                leaf NssaExternalReferencedLinkId  {
                    type  cml-data-types:CML_STRING_T;
                    description "NSSA External Referenced Link ID";
                } // END of NssaExternalReferencedLinkId definition.

                leaf NssaExternalRouteTag  {
                    type  cml-data-types:CML_UINT32_T;
                    description "NSSA External Route Tag";
                } // END of NssaExternalRouteTag definition.

                leaf NssaExternalForwardingAddress  {
                    type  cml-data-types:CML_STRING_T;
                    description "NSSA External Forwarding Address";
                } // END of NssaExternalForwardingAddress definition.

                leaf NssaExternalPrefixOptions  {
                    type  cml-data-types:CML_STRING_T;
                    description "NSSA External Prefix Options";
                } // END of NssaExternalPrefixOptions definition.

                leaf NssaExternalPrefix  {
                    type  cml-data-types:CML_STRING_T;
                    description "NSSA External Prefix";
                } // END of NssaExternalPrefix definition.

                leaf NssaExternalLsaMetric  {
                    type  cml-data-types:CML_UINT32_T;
                    description "NSSA External LSA Metric";
                } // END of NssaExternalLsaMetric definition.

                leaf NssaExternalLsaMetricType  {
                    type  cml-data-types:CML_STRING_T;
                    description "NSSA External LSA Metric Type";
                } // END of NssaExternalLsaMetricType definition.

                leaf NssaExternallsaAdvRouter  {
                    type  cml-data-types:CML_STRING_T;
                    description "NSSA External LSA Advertising Router";
                } // END of NssaExternallsaAdvRouter definition.

                uses ospf6LsaHeader;
            } // End of Ospf6NssaExternalLsa-list

            list areaTable {
                key "areaId";
                description
                    "OSPFv3 area structure.";
                leaf areaId  {
                    type  cml-data-types:CML_AREA_T;
                    description "OSPFv3 area ID in an IPv4 address format";
                } // END of areaId definition.

                leaf areaDefaultCost  {
                    type  cml-data-types:CML_UINT32_T {
                         range "0..16777215";
                    }
                    default "1";
                    description "Stub advertised cost";
                } // END of areaDefaultCost definition.

                leaf isAreaBackbone  {
                    type  cml-data-types:CML_BOOL_T;
                    config false;
                    description "Bool Parameter for Backbone Area";
                } // END of isAreaBackbone definition.

                leaf isAreaActive  {
                    type  cml-data-types:CML_BOOL_T;
                    config false;
                    description "Bool Parameter for Active Area";
                } // END of isAreaActive definition.

                leaf activeIfCount  {
                    type  cml-data-types:CML_UINT32_T;
                    config false;
                    description "Active Interface Count";
                } // END of activeIfCount definition.

                leaf areaIfCount  {
                    type  cml-data-types:CML_UINT32_T;
                    config false;
                    description "Area Interface Count";
                } // END of areaIfCount definition.

                leaf spfCalcCount  {
                    type  cml-data-types:CML_UINT32_T;
                    config false;
                    description "SPF Count";
                } // END of spfCalcCount definition.

                leaf lsaCount  {
                    type  cml-data-types:CML_UINT32_T;
                    config false;
                    description "LSA Count";
                } // END of lsaCount definition.

                leaf lsdbChecksum  {
                    type  cml-data-types:CML_STRING_T;
                    config false;
                    description "LSDB Checksum";
                } // END of lsdbChecksum definition.

                leaf unknownLSACount  {
                    type  cml-data-types:CML_UINT32_T;
                    config false;
                    description "Unknown LSA Count";
                } // END of unknownLSACount definition.

                leaf isAreaAsbr  {
                    type  cml-data-types:CML_BOOL_T;
                    config false;
                    description "Bool Parameter for Area ASBR";
                } // END of isAreaAsbr definition.


                list Stub {
                    key "isAreaStub";
                    description
                        "ospf area stub configuration";
                    leaf isAreaStub  {
                        type  cml-data-types:CML_OSPF_STUB_T;
                        description "Bool Parameter for Stub Area";
                    } // END of isAreaStub definition.

                    leaf isAreaStubNoSummary  {
                        type  cml-data-types:CML_BOOL_T;
                        description "Bool Parameter for Stub No Summary Area";
                    } // END of isAreaStubNoSummary definition.

                } // End of Stub-list

                list Nssa {
                    if-feature feature-list:HAVE_NSSA;
                    key "isAreaNssa";
                    description
                        "ospf area stub configuration";
                    leaf isAreaNssa  {
                        type  cml-data-types:CML_OSPF_NSSA_T;
                        description "isAreaNssa";
                    } // END of isAreaNssa definition.

                    leaf nssaStabilityInterval  {
                        type  cml-data-types:CML_INT32_T {
                             range "0..2147483647";
                        }
                        default "40";
                        description "Stability interval in seconds";
                    } // END of nssaStabilityInterval definition.

                    leaf nssaTranslatorRole  {
                        type  cml-data-types:CML_OSPF_TRANSLATOR_ROLE_T;
                        default "candidate";
                        description "NSSA-ABR translator role 1-OSPF_NSSA_TRANSLATE_ALWAYS 2-OSPF_NSSA_TRANSLATE_CANDIDATE";
                    } // END of nssaTranslatorRole definition.

                    leaf nssaDefaultOriginMetric  {
                        type  cml-data-types:CML_INT32_T {
                             range "0..16777214";
                        }
                        default "0";
                        description "NSSA Default Origin Metric";
                    } // END of nssaDefaultOriginMetric definition.

                    leaf nssaDefaultOriginMetricType  {
                        type  cml-data-types:CML_INT32_T {
                             range "1..2";
                        }
                        default "2";
                        description "NSSA Default Origin Metric Type";
                    } // END of nssaDefaultOriginMetricType definition.

                    leaf isNssaNoDist  {
                        type  cml-data-types:CML_BOOL_T;
                        description "isNssaNoDist";
                    } // END of isNssaNoDist definition.

                    leaf isNssaDefaultOriginate  {
                        type  cml-data-types:CML_BOOL_T;
                        description "Bool Parameter for NSSA Default Originate";
                    } // END of isNssaDefaultOriginate definition.

                    leaf nssaAreaNoSummary  {
                        type  cml-data-types:CML_BOOL_T;
                        description "Bool Parameter for NSSA No Summary Area";
                    } // END of nssaAreaNoSummary definition.

                    leaf nssarouteMap  {
                        type  cml-data-types:CML_STRING_T;
                        description "NSSA Route Map";
                    } // END of nssarouteMap definition.

                } // End of Nssa-list

                list ospf6Vertex {
                    key "vertexlinkId";
                    config false;
                    description
                        "Shortest Path Tree/ABR table.";
                    leaf vertexlinkId  {
                        type  cml-data-types:CML_STRING_T;
                        description "Vertex Link ID";
                    } // END of vertexlinkId definition.

                    leaf vertexDistance  {
                        type  cml-data-types:CML_UINT32_T;
                        description "Vertex Distance";
                    } // END of vertexDistance definition.

                    uses ospf6NextHop;
                } // End of ospf6Vertex-list

                list areaRangeIPv6 {
                    key "rangeAddr";
                    description
                        "OSPFv3 Intra-area IPv4 routes";
                    leaf rangeAddr  {
                        type  cml-data-types:CML_IPV6_PREFIX_T;
                        description "IPv6 Area range address";
                    } // END of rangeAddr definition.

                    leaf rangeStatus  {
                        type  cml-data-types:CML_OSPF6_AREA_RANGE_T;
                        description "Range Status";
                    } // END of rangeStatus definition.

                } // End of areaRangeIPv6-list

                list areaVirtualLink {
                    key "peerId";
                    description
                        "OSPFv3 Area Virtual-link";
                    leaf peerId  {
                        type  cml-data-types:CML_IPV4_ADDR_T;
                        description "Peer ID";
                    } // END of peerId definition.

                    leaf helloInterval  {
                        type  cml-data-types:CML_UINT32_T {
                             range "1..65535";
                        }
                        default "10";
                        description "Hello Interval";
                    } // END of helloInterval definition.

                    leaf deadInterval  {
                        type  cml-data-types:CML_UINT32_T {
                             range "1..65535";
                        }
                        default "40";
                        description "Dead Interval";
                    } // END of deadInterval definition.

                    leaf retransmitInterval  {
                        type  cml-data-types:CML_UINT32_T {
                             range "1..1800";
                        }
                        default "5";
                        description "Retransmit Interval";
                    } // END of retransmitInterval definition.

                    leaf transmitDelay  {
                        type  cml-data-types:CML_UINT32_T {
                             range "1..1800";
                        }
                        default "1";
                        description "Transmit Delay";
                    } // END of transmitDelay definition.

                    leaf fallOverBfd  {
                        if-feature feature-list:HAVE_BFD;
                        type  cml-data-types:CML_BOOL_T;
                        description "Bool Parameter for Fall Over BFD";
                    } // END of fallOverBfd definition.

                    leaf instanceId  {
                        type  cml-data-types:CML_UINT32_T {
                             range "0..31 | 64..95";
                        }
                        description "Instance ID";
                    } // END of instanceId definition.

                    leaf vlinkName  {
                        type  cml-data-types:CML_STRING_T;
                        config false;
                        description "Virtual Link Name";
                    } // END of vlinkName definition.

                    leaf vlinkStatus  {
                        type  cml-data-types:CML_OSPFV3_LINK_STATUS_T;
                        config false;
                        description "Virtual link Status";
                    } // END of vlinkStatus definition.

                    leaf vlinkInterfaceName  {
                        type  cml-data-types:CML_STRING_T;
                        config false;
                        description "Virtual Link Interface Name";
                    } // END of vlinkInterfaceName definition.

                    leaf vlinkInstanceId  {
                        type  cml-data-types:CML_UINT32_T;
                        config false;
                        description "Virtual Link Instance ID";
                    } // END of vlinkInstanceId definition.

                    leaf vlinkisHelloSupEnabled  {
                        type  cml-data-types:CML_BOOL_T;
                        config false;
                        description "Is Virtual Link Hello Sup Enabled";
                    } // END of vlinkisHelloSupEnabled definition.

                    leaf vlinkIsDNAEnabled  {
                        type  cml-data-types:CML_BOOL_T;
                        config false;
                        description "Is Virtual Link DNA Enabled";
                    } // END of vlinkIsDNAEnabled definition.

                    leaf vlinkLocalAddress  {
                        type  cml-data-types:CML_STRING_T;
                        config false;
                        description "Virtual Link Local Address";
                    } // END of vlinkLocalAddress definition.

                    leaf vlinkRemoteAddress  {
                        type  cml-data-types:CML_STRING_T;
                        config false;
                        description "Virtual Link Remote Address";
                    } // END of vlinkRemoteAddress definition.

                    leaf vlinkState  {
                        type  cml-data-types:CML_STRING_T;
                        config false;
                        description "Virtual Link State";
                    } // END of vlinkState definition.

                    leaf vlinkHelloDueTime  {
                        type  cml-data-types:CML_STRING_T;
                        config false;
                        description "Virtual Link Hello Due Time";
                    } // END of vlinkHelloDueTime definition.

                    leaf vlinkAdjacencyState  {
                        type  cml-data-types:CML_STRING_T;
                        config false;
                        description "Virtual Link Adjacency State";
                    } // END of vlinkAdjacencyState definition.

                } // End of areaVirtualLink-list
                uses lsdb;
            } // End of areaTable-list

            list addressFamily {
                key "isAddrFamily";
                description
                    " OSPFv3 Address Family.";
                leaf isAddrFamily  {
                    type  cml-data-types:CML_BOOL_T;
                    description "Is Address Family";
                } // END of isAddrFamily definition.


                list areaTable {
                    key "areaId";
                    description
                        "OSPFv3 area structure.";
                    leaf areaId  {
                        type  cml-data-types:CML_AREA_T;
                        description "Area ID";
                    } // END of areaId definition.


                    list areaRangeIPv4 {
                        key "rangeAddrIPV4";
                        description
                            "Area Range IPv4 address list";
                        leaf rangeAddrIPV4  {
                            type  cml-data-types:CML_IPV4_ADDR_PREFIX_T;
                            description "Range Address in IPv4 Format";
                        } // END of rangeAddrIPV4 definition.

                        leaf rangeStatusIPv4  {
                            type  cml-data-types:CML_OSPF6_AREA_RANGE_T;
                            description "Range Status";
                        } // END of rangeStatusIPv4 definition.

                    } // End of areaRangeIPv4-list
                } // End of areaTable-list

                list summaryAddressIpv4 {
                    key "summaryIpv4Addr";
                    description
                        "OSPFv3 IPv4 Summary Address list";
                    leaf summaryIpv4Addr  {
                        type  cml-data-types:CML_IPV4_PREFIX_T;
                        description "IPv4 Summary Address";
                    } // END of summaryIpv4Addr definition.

                    leaf setTag  {
                        type  cml-data-types:CML_UINT32_T {
                             range "0..4294967295";
                        }
                        description "Tag";
                    } // END of setTag definition.

                    leaf not-advertise  {
                        type  cml-data-types:CML_BOOL_T;
                        description "Bool Parameter for not-advertise";
                    } // END of not-advertise definition.

                } // End of summaryAddressIpv4-list
                uses redistribute;
                uses default-information-originate;
            } // End of addressFamily-list

            list distributeList {
                if-feature feature-list:HAVE_ACL;
                key "accessListName";
                description
                    "Distribute list for OSPFv3 Protocol";
                leaf accessListName  {
                    type  cml-data-types:CML_STRING_T;
                    description "Access-list name";
                } // END of accessListName definition.

                leaf ospf6DistIn  {
                    type  cml-data-types:CML_BOOL_T;
                    description "ospf6DistIn";
                } // END of ospf6DistIn definition.


                list distributeListProtocol {
                    key "ospf6distProtocol";
                    description
                        "Distribute list for OSPFv3 Protocol";
                    leaf ospf6distProtocol  {
                        type  cml-data-types:CML_OSPF6_ROUTE_SOURCE_TYPE_T;
                        description "proto Redistributed protocol type 1-IPI_ROUTE_KERNEL, 2-IPI_ROUTE_CONNECT, 3-IPI_ROUTE_STATIC, 4-IPI_ROUTE_RIP, 5-IPI_ROUTE_RIPNG, 6-IPI_ROUTE_OSPF, 7-IPI_ROUTE_OSPF6, 8-IPI_ROUTE_BGP, 9-IPI_ROUTE_ISIS";
                    } // END of ospf6distProtocol definition.

                } // End of distributeListProtocol-list

                list distributeListOspf {
                    key "ospf6distOspfProtocol";
                    description
                        "Distribute list for OSPFv3 Protocol";
                    leaf ospf6distOspfProtocol  {
                        type  cml-data-types:CML_OSPF_AREA_ID_T;
                        description "OSPFv3 Distribute OSPF Protocol";
                    } // END of ospf6distOspfProtocol definition.

                } // End of distributeListOspf-list
            } // End of distributeList-list

            list summaryAddressIpv6 {
                key "summaryIpv6Addr";
                description
                    "OSPFv3 IPv6 Summary Address";
                leaf summaryIpv6Addr  {
                    type  cml-data-types:CML_IPV6_PREFIX_T;
                    description "summaryIpv6Addr";
                } // END of summaryIpv6Addr definition.

                leaf all-tag  {
                    type  cml-data-types:CML_UINT32_T {
                         range "0..4294967295";
                    }
                    default "0";
                    description "To summarize or suppress external routes with the specified address range";
                } // END of all-tag definition.

                leaf not-advertise6  {
                    type  cml-data-types:CML_BOOL_T;
                    description "Bool parameter for not-advertise";
                } // END of not-advertise6 definition.

                leaf translate-tag  {
                    type  cml-data-types:CML_UINT32_T {
                         range "0..4294967295";
                    }
                    default "0";
                    description "Translate Tag";
                } // END of translate-tag definition.

            } // End of summaryAddressIpv6-list
            container cspf {
                if-feature feature-list:HAVE_OSPF6_CSPF;
                description
                    "Constrained Shortest Path First (CSPF) Instance";
                leaf cspfEnabled  {
                    if-feature feature-list:HAVE_OSPF6_CSPF;
                    type  cml-data-types:CML_BOOL_T;
                    description "cspfEnabled";
                } // END of cspfEnabled definition.

                leaf cspfTieBreak  {
                    if-feature feature-list:HAVE_OSPF6_CSPF;
                    type  cml-data-types:CML_OSPF6_CSPF_TYPE_T;
                    description "SPF Tie Break";
                } // END of cspfTieBreak definition.

                leaf cspfDefRetryInterval  {
                    if-feature feature-list:HAVE_OSPF6_CSPF;
                    type  cml-data-types:CML_UINT16_T {
                         range "1..3600";
                    }
                    description "Compute SPF Retry Interval";
                } // END of cspfDefRetryInterval definition.

            } // END of cspf-container definition.
            container distance {
                description
                    "Define an administrative distance";
                leaf distanceIntra  {
                    type  cml-data-types:CML_UINT32_T {
                         range "1..254";
                    }
                    default "110";
                    description "Intra Distance";
                } // END of distanceIntra definition.

                leaf distanceInter  {
                    type  cml-data-types:CML_UINT32_T {
                         range "1..254";
                    }
                    default "110";
                    description "Inter Distance";
                } // END of distanceInter definition.

                leaf distanceExternal  {
                    type  cml-data-types:CML_UINT32_T {
                         range "1..254";
                    }
                    default "110";
                    description "External Distance";
                } // END of distanceExternal definition.

            } // END of distance-container definition.
            uses redistribute;
            uses default-information-originate;
            uses lsdb;
            uses Route;
        } // End of ospf6-list

        list ospf6Interface {
            key "ifName";
            description
                "OSPFv3 interface related operations";
            leaf ifName  {
                type  cml-data-types:CML_STRING_T;
                description "Interface Name";
            } // END of ifName definition.

            leaf ifShutDown  {
                type  cml-data-types:CML_BOOL_T;
                description "Unconfigure OSPFV3 on an interface";
            } // END of ifShutDown definition.


            list ospf6IfinstanceId {
                key "instanceId6";
                description
                    "OSPFv3 instanceId of interface related operations";
                leaf instanceId6  {
                    type  cml-data-types:CML_INT32_T {
                         range "0..31 | 64..95";
                    }
                    description "Interface instance ID <0-255>.";
                } // END of instanceId6 definition.

                leaf networkType  {
                    type  cml-data-types:CML_OSPF6_NETWORK_T;
                    description "The network type.";
                } // END of networkType definition.

                leaf cost  {
                    type  cml-data-types:CML_UINT32_T {
                         range "1..65535";
                    }
                    description "Interface output cost <1-65535>";
                } // END of cost definition.

                leaf teMetric  {
                    if-feature feature-list:HAVE_OSPF6_TE;
                    type  cml-data-types:CML_UINT32_T {
                         range "1..65535";
                    }
                    description "Interface TE metric";
                } // END of teMetric definition.

                leaf ifHelloInterval  {
                    type  cml-data-types:CML_UINT32_T {
                         range "1..65535";
                    }
                    description "Hello interval in seconds <1-65535>";
                } // END of ifHelloInterval definition.

                leaf ifDeadInterval  {
                    type  cml-data-types:CML_UINT32_T {
                         range "1..65535";
                    }
                    default "40";
                    description "Router dead interval in seconds <1-65535>";
                } // END of ifDeadInterval definition.

                leaf ifRetransmitInterval  {
                    type  cml-data-types:CML_UINT32_T {
                         range "1..1800";
                    }
                    default "5";
                    description "Retransmit Interval in seconds <1-65535>";
                } // END of ifRetransmitInterval definition.

                leaf ifPriority  {
                    type  cml-data-types:CML_UINT8_T {
                         range "0..255";
                    }
                    default "1";
                    description "Router priority of the interface <0-255>";
                } // END of ifPriority definition.

                leaf ifTransmitDelay  {
                    type  cml-data-types:CML_UINT32_T {
                         range "1..1800";
                    }
                    default "1";
                    description "Transmit Delay in seconds <1-65535>";
                } // END of ifTransmitDelay definition.

                leaf ifMtuIgnore  {
                    type  cml-data-types:CML_BOOL_T;
                    description "Ignore MTU size check";
                } // END of ifMtuIgnore definition.

                leaf ifDemandCircuit  {
                    if-feature feature-list:HAVE_OSPF6_OD;
                    type  cml-data-types:CML_BOOL_T;
                    description "Bool Parameter for Demand Circuit";
                } // END of ifDemandCircuit definition.

                leaf ifFloodReduction  {
                    if-feature feature-list:HAVE_OSPF6_OD;
                    type  cml-data-types:CML_BOOL_T;
                    description "Bool Parameter for Flood Reduction";
                } // END of ifFloodReduction definition.

                leaf ifFrrDisable  {
                    if-feature feature-list:HAVE_OSPF6_LFA;
                    type  cml-data-types:CML_BOOL_T;
                    description "Bool Parameter for FRR Disable";
                } // END of ifFrrDisable definition.

                leaf ifAreaId  {
                    type  cml-data-types:CML_AREA_T;
                    description "OSPFv3 area ID in an IPv4 address format";
                } // END of ifAreaId definition.

                leaf ifTagId  {
                    type  cml-data-types:CML_STRING_T;
                    description "OSPFv3 process tag";
                } // END of ifTagId definition.

                leaf ifLinkLsaSuppression  {
                    type  cml-data-types:CML_OSPF6_LSA_SUPRESSION_STATE_T;
                    description " Whether to enable/disable link LSA suppression";
                } // END of ifLinkLsaSuppression definition.

                leaf ifBfdEnable  {
                    if-feature feature-list:HAVE_BFD;
                    type  cml-data-types:CML_OSPF_BFD_STATE;
                    description "Whether to enable/disable BFD";
                } // END of ifBfdEnable definition.

                leaf InterfaceLineProtocolState  {
                    type  cml-data-types:CML_INTERFACE_ADMIN_STATE_T;
                    config false;
                    description "Interface Line Protocol State";
                } // END of InterfaceLineProtocolState definition.

                leaf InterfaceIfIndex  {
                    type  cml-data-types:CML_UINT32_T;
                    config false;
                    description "Interface Index";
                } // END of InterfaceIfIndex definition.

                leaf InterfaceIPV6Address  {
                    type  cml-data-types:CML_STRING_T;
                    config false;
                    description "IPv6 Interface Address";
                } // END of InterfaceIPV6Address definition.

                leaf InterfaceIPV6LinkLocalAddress  {
                    type  cml-data-types:CML_STRING_T;
                    config false;
                    description "IPv6 Interface Link Local Address";
                } // END of InterfaceIPV6LinkLocalAddress definition.

                leaf Ospfv3ProcessId  {
                    type  cml-data-types:CML_STRING_T;
                    config false;
                    description "Process ID";
                } // END of Ospfv3ProcessId definition.

                leaf Ospfv3RouterId  {
                    type  cml-data-types:CML_STRING_T;
                    config false;
                    description "Router ID";
                } // END of Ospfv3RouterId definition.

                leaf InterfaceState  {
                    type  cml-data-types:CML_OSPF_INTERFACE_STATE_MSG_T;
                    config false;
                    description "Interface State";
                } // END of InterfaceState definition.

                leaf DesignatedRouter  {
                    type  cml-data-types:CML_STRING_T;
                    config false;
                    description "Designated Router";
                } // END of DesignatedRouter definition.

                leaf DRInterfaceAddr  {
                    type  cml-data-types:CML_STRING_T;
                    config false;
                    description "Designated Router Interface Address";
                } // END of DRInterfaceAddr definition.

                leaf BackUpDesignatedRouter  {
                    type  cml-data-types:CML_STRING_T;
                    config false;
                    description "BackUp Designated Router";
                } // END of BackUpDesignatedRouter definition.

                leaf BackUpDRInterfaceAddr  {
                    type  cml-data-types:CML_STRING_T;
                    config false;
                    description "BackUp Designated Router Interface Address";
                } // END of BackUpDRInterfaceAddr definition.

                leaf HelloDueIn  {
                    type  cml-data-types:CML_STRING_T;
                    config false;
                    description "Hello Due Time";
                } // END of HelloDueIn definition.

                leaf NeighborCount  {
                    type  cml-data-types:CML_UINT32_T;
                    config false;
                    description "Neighbor Count";
                } // END of NeighborCount definition.

                leaf AdjacentNeighborCount  {
                    type  cml-data-types:CML_UINT32_T;
                    config false;
                    description "Adjacency Neighbor Count";
                } // END of AdjacentNeighborCount definition.

                leaf SuppressHelloCount  {
                    if-feature feature-list:HAVE_OSPF6_OD;
                    type  cml-data-types:CML_UINT32_T;
                    config false;
                    description "Hello Count";
                } // END of SuppressHelloCount definition.

                leaf HelloReceived  {
                    type  cml-data-types:CML_UINT32_T;
                    config false;
                    description "Hello received";
                } // END of HelloReceived definition.

                leaf HelloSent  {
                    type  cml-data-types:CML_UINT32_T;
                    config false;
                    description "Hello Sent";
                } // END of HelloSent definition.

                leaf DDReceived  {
                    type  cml-data-types:CML_UINT32_T;
                    config false;
                    description "DD Received";
                } // END of DDReceived definition.

                leaf DDSent  {
                    type  cml-data-types:CML_UINT32_T;
                    config false;
                    description "DD Sent";
                } // END of DDSent definition.

                leaf LSReqReceived  {
                    type  cml-data-types:CML_UINT32_T;
                    config false;
                    description "LS Request Received";
                } // END of LSReqReceived definition.

                leaf LSReqSent  {
                    type  cml-data-types:CML_UINT32_T;
                    config false;
                    description "LS Request Sent";
                } // END of LSReqSent definition.

                leaf LSUpdReceived  {
                    type  cml-data-types:CML_UINT32_T;
                    config false;
                    description "LS Update Received";
                } // END of LSUpdReceived definition.

                leaf LSUpdSent  {
                    type  cml-data-types:CML_UINT32_T;
                    config false;
                    description "LS Update Sent";
                } // END of LSUpdSent definition.

                leaf LSAckReceived  {
                    type  cml-data-types:CML_UINT32_T;
                    config false;
                    description "LSA Acknoledge Received";
                } // END of LSAckReceived definition.

                leaf LSAckSent  {
                    type  cml-data-types:CML_UINT32_T;
                    config false;
                    description "LSA Acknowledge Sent";
                } // END of LSAckSent definition.

                leaf LSAckDiscarded  {
                    type  cml-data-types:CML_UINT32_T;
                    config false;
                    description "LSA Ack Discarded";
                } // END of LSAckDiscarded definition.


                list nbrStatic {
                    key "nbrStaticAddr";
                    description
                        "Static neighbor data structure.";
                    leaf nbrStaticAddr  {
                        type  cml-data-types:CML_IPV6_ADDR_T;
                        description "Neighbor address in an IPv6 format";
                    } // END of nbrStaticAddr definition.

                    leaf nbrStaticPollInterval  {
                        type  cml-data-types:CML_UINT32_T {
                             range "0..4294967295";
                        }
                        description "Poll interval for neighbor <1-65535>";
                    } // END of nbrStaticPollInterval definition.

                    leaf nbrStaticCost  {
                        type  cml-data-types:CML_UINT32_T {
                             range "1..65535";
                        }
                        description "Cost for neighbor <1-65535>";
                    } // END of nbrStaticCost definition.

                    leaf nbrStaticPriority  {
                        type  cml-data-types:CML_UINT8_T {
                             range "0..255";
                        }
                        description "Priority for neighbor <1-65535>";
                    } // END of nbrStaticPriority definition.

                    leaf nbrInterfaceState  {
                        type  cml-data-types:CML_STRING_T;
                        config false;
                        description "Neighbor Interface State";
                    } // END of nbrInterfaceState definition.

                    leaf nbrInterfaceDesc  {
                        type  cml-data-types:CML_STRING_T;
                        config false;
                        description "Neighbor Interface Description";
                    } // END of nbrInterfaceDesc definition.

                } // End of nbrStatic-list

                list ospf6_neighbor {
                    key "nbrRouterId";
                    config false;
                    description
                        "Neighbor Data Structure";
                    leaf nbrRouterId  {
                        type  cml-data-types:CML_STRING_T;
                        description "Neighbor Router ID";
                    } // END of nbrRouterId definition.

                    leaf nbrInterfaceAddress  {
                        type  cml-data-types:CML_STRING_T;
                        description "Neighbor Interface Address";
                    } // END of nbrInterfaceAddress definition.

                    leaf nbrAreaId  {
                        type  cml-data-types:CML_STRING_T;
                        description "Neighbor Area ID";
                    } // END of nbrAreaId definition.

                    leaf nbrTimerDump  {
                        type  cml-data-types:CML_STRING_T;
                        description "Neighbor Timer Dump";
                    } // END of nbrTimerDump definition.

                    leaf nbrState  {
                        type  cml-data-types:CML_STRING_T;
                        description "Neighbor State";
                    } // END of nbrState definition.

                    leaf nbrStateMessage  {
                        type  cml-data-types:CML_STRING_T;
                        description "Neighbor State Message";
                    } // END of nbrStateMessage definition.

                    leaf nbrStateChange  {
                        type  cml-data-types:CML_UINT32_T;
                        description "Neighbor State Change";
                    } // END of nbrStateChange definition.

                    leaf nbrPriority  {
                        type  cml-data-types:CML_UINT8_T;
                        description "Neighbor Priority";
                    } // END of nbrPriority definition.

                    leaf nbrisHelloSuppressed  {
                        type  cml-data-types:CML_BOOL_T;
                        description "Neighbor Hello Suppressed Enable/Disable";
                    } // END of nbrisHelloSuppressed definition.

                    leaf nbrDRouter  {
                        type  cml-data-types:CML_STRING_T;
                        description "Neighbor Designated Router";
                    } // END of nbrDRouter definition.

                    leaf nbrBDRouter  {
                        type  cml-data-types:CML_STRING_T;
                        description "Neighbor BackUp Designated Router";
                    } // END of nbrBDRouter definition.

                    leaf nbrOptions  {
                        type  cml-data-types:CML_STRING_T;
                        description "Neighbor Options";
                    } // END of nbrOptions definition.

                    leaf nbrDeadTimer  {
                        type  cml-data-types:CML_STRING_T;
                        description "Neighbor Dead Timer";
                    } // END of nbrDeadTimer definition.

                    leaf nbrDbSummaryCount  {
                        type  cml-data-types:CML_UINT32_T;
                        description "Neighbor DB Summary Count";
                    } // END of nbrDbSummaryCount definition.

                    leaf nbrLsRequestCount  {
                        type  cml-data-types:CML_UINT32_T;
                        description "Neighbor LSA Request Count";
                    } // END of nbrLsRequestCount definition.

                    leaf nbrLsRetransmissionCount  {
                        type  cml-data-types:CML_UINT32_T;
                        description "Neighbor LSA Retransmission Count";
                    } // END of nbrLsRetransmissionCount definition.

                    leaf nbrBfdEnabled  {
                        type  cml-data-types:CML_BOOL_T;
                        description "Whether BFD Enable/Disable on Neighbor";
                    } // END of nbrBfdEnabled definition.

                    container asbr {
                        config false;
                        description
                            "ASBR routing table.";
                        uses Route;
                    } // END of asbr-container definition.
                    uses Route;
                } // End of ospf6_neighbor-list
                uses lsdb;
            } // End of ospf6IfinstanceId-list
        } // End of ospf6Interface-list
        container ospf6Helper {
            description
                "OSPFv3 Restart module properties";
            uses helper;
        } // END of ospf6Helper-container definition.
        container ospf6HitlessRestartHelper {
            description
                "OSPFv3 Restart module properties";
            uses helper;
        } // END of ospf6HitlessRestartHelper-container definition.
        container ospf6Debug {
            description
                "OSPFv3 Debug Configurations";
            leaf debugIfsm  {
                type  cml-data-types:CML_OSPF6_DEBUG_IFSM_T;
                description "Debug Interface State Machine";
            } // END of debugIfsm definition.

            leaf debugNfsm  {
                type  cml-data-types:CML_OSPF6_DEBUG_NFSM_T;
                description "Debug Neighbor Finite State Machine";
            } // END of debugNfsm definition.

            leaf debugLsa  {
                type  cml-data-types:CML_OSPF6_DEBUG_LSA_T;
                description "Debug LSA";
            } // END of debugLsa definition.

            leaf debugNsm  {
                type  cml-data-types:CML_OSPF6_DEBUG_NSM_T;
                description "Debug NSM";
            } // END of debugNsm definition.

            leaf debugRib  {
                if-feature feature-list:HAVE_RIBD;
                type  cml-data-types:CML_OSPF6_DEBUG_RIB_T;
                description "Debug RIB";
            } // END of debugRib definition.

            leaf debugRoute  {
                type  cml-data-types:CML_OSPF6_DEBUG_ROUTE_T;
                description "Debug Route";
            } // END of debugRoute definition.

            leaf debugRetransmission  {
                type  cml-data-types:CML_BOOL_T;
                description "Debug Retransmission";
            } // END of debugRetransmission definition.

            leaf debugBfd  {
                if-feature feature-list:HAVE_BFD;
                type  cml-data-types:CML_BOOL_T;
                description "Debug BFD";
            } // END of debugBfd definition.

            leaf debugEvent  {
                type  cml-data-types:CML_OSPF6_DEBUG_EVENT_T;
                description "Debug Event";
            } // END of debugEvent definition.

            leaf debugPacket  {
                type  cml-data-types:CML_OSPF6_DEBUG_PACKET_TYPE_T;
                description "Debug Packet";
            } // END of debugPacket definition.

            leaf debugLfa  {
                if-feature feature-list:HAVE_OSPF6_LFA;
                type  cml-data-types:CML_BOOL_T;
                description "Debug LFA";
            } // END of debugLfa definition.

            leaf debugAll  {
                type  cml-data-types:CML_BOOL_T;
                description "Debug All";
            } // END of debugAll definition.

        } // END of ospf6Debug-container definition.
        container ospf6TermDebug {
            description
                "OSPFv3 Term Debug Configurations";
            leaf TermdebugIfsm  {
                type  cml-data-types:CML_OSPF6_DEBUG_IFSM_T;
                description "Terminal Debug Interface State Machine";
            } // END of TermdebugIfsm definition.

            leaf TermdebugNfsm  {
                type  cml-data-types:CML_OSPF6_DEBUG_NFSM_T;
                description "Terminal Debug NFSM";
            } // END of TermdebugNfsm definition.

            leaf TermdebugLsa  {
                type  cml-data-types:CML_OSPF6_DEBUG_LSA_T;
                description "Terminal Debug LSA";
            } // END of TermdebugLsa definition.

            leaf TermdebugNsm  {
                type  cml-data-types:CML_OSPF6_DEBUG_NSM_T;
                description "Terminal Debug NSM";
            } // END of TermdebugNsm definition.

            leaf TermdebugRib  {
                if-feature feature-list:HAVE_RIBD;
                type  cml-data-types:CML_OSPF6_DEBUG_RIB_T;
                description "Terminal Debug RIB";
            } // END of TermdebugRib definition.

            leaf TermdebugRoute  {
                type  cml-data-types:CML_OSPF6_DEBUG_ROUTE_T;
                description "Terminal Debug Route";
            } // END of TermdebugRoute definition.

            leaf TermdebugRetransmission  {
                type  cml-data-types:CML_BOOL_T;
                description "Terminal Debug Retransmission";
            } // END of TermdebugRetransmission definition.

            leaf TermdebugBfd  {
                if-feature feature-list:HAVE_BFD;
                type  cml-data-types:CML_BOOL_T;
                description "Terminal Debug BFD";
            } // END of TermdebugBfd definition.

            leaf TermdebugEvent  {
                type  cml-data-types:CML_OSPF6_DEBUG_EVENT_T;
                description "Terminal Debug Event";
            } // END of TermdebugEvent definition.

            leaf TermdebugPacket  {
                type  cml-data-types:CML_OSPF6_DEBUG_PACKET_TYPE_T;
                description "Terminal Debug Packet";
            } // END of TermdebugPacket definition.

            leaf TermdebugLfa  {
                if-feature feature-list:HAVE_OSPF6_LFA;
                type  cml-data-types:CML_BOOL_T;
                description "Terminal Debug LFA";
            } // END of TermdebugLfa definition.

            leaf TermdebugAll  {
                type  cml-data-types:CML_BOOL_T;
                description "Terminal Debug All";
            } // END of TermdebugAll definition.

        } // END of ospf6TermDebug-container definition.
    } // END of ospf6Master-container definition.
    } // END of ospf6Master-container definition.


}
