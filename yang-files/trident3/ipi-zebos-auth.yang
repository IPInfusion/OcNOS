/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-zebos-auth.yang
*
*/

submodule ipi-zebos-auth {

    belongs-to  ipi-zebos { prefix ipi-zebos; }

    import cml-data-types {
        prefix cml-data-types;
    }

    import feature-list {
        prefix feature-list;
    }

    include ipi-zebos-interface;
    organization
        "IP Infusion Inc.";

    contact
        "Address: 3965 Freedom Circle, Suite 200, Santa Clara, CA 95054
        Phone: +1 408-400-1900
        E-mail: support@ipinfusion.com
        Web: http://www.ipinfusion.com/";

    description
        "auth configurations";


    revision "2018-06-21" {
        description " Initial Version.";
        reference "";
    }



    grouping authPort-grouping {
    description
        "AUTH interface related operations";
        list authPort {
            key "ifName";
            description
                "AUTH interface related operations";
            leaf ifName  {
                type  cml-data-types:CML_STRING_T;
                description "";
            } // END of ifName definition.

            leaf dot1xinitialize  {
                type  cml-data-types:CML_BOOL_T;
                description "";
            } // END of dot1xinitialize definition.

            leaf authmacPortControl  {
                if-feature feature-list:HAVE_MAC_AUTH;
                type  cml-data-types:CML_ENABLE_DISABLE_T;
                description "";
            } // END of authmacPortControl definition.

            leaf authmacPortMode  {
                if-feature feature-list:HAVE_MAC_AUTH;
                type  cml-data-types:CML_AUTH_PORT_SEC_MODE;
                default "shutdown";
                description "";
            } // END of authmacPortMode definition.

            leaf RestrictVlan  {
                if-feature feature-list:HAVE_MAC_AUTH;
                type  cml-data-types:CML_UINT32_T {
                     range "2..4094";
                }
                description "";
            } // END of RestrictVlan definition.

            leaf DropTraffic  {
                if-feature feature-list:HAVE_MAC_AUTH;
                type  cml-data-types:CML_BOOL_T;
                default true;
                description "";
            } // END of DropTraffic definition.

            leaf dynamicVlanCreation  {
                if-feature feature-list:HAVE_MAC_AUTH;
                type  cml-data-types:CML_ENABLE_DISABLE_T;
                default "disable";
                description "";
            } // END of dynamicVlanCreation definition.

            leaf macAddressAging  {
                if-feature feature-list:HAVE_MAC_AUTH;
                type  cml-data-types:CML_ENABLE_DISABLE_T;
                default "enable";
                description "";
            } // END of macAddressAging definition.

            leaf protocolVersion  {
                type  cml-data-types:CML_UINT32_T {
                     range "1..2";
                }
                default "2";
                description "";
            } // END of protocolVersion definition.

            leaf portCtrl  {
                type  cml-data-types:CML_AUTH_PORT_CTRL;
                default "force-authorized";
                description "";
            } // END of portCtrl definition.

            container authCtrlDir {
                description
                    "authCtrlDir";
                leaf adminControlledDirections  {
                    type  cml-data-types:CML_AUTH_CTRL_DIR_T;
                    description "";
                } // END of adminControlledDirections definition.

            } // END of authCtrlDir-container definition.
            container authPae {
                description
                    "Authenticator PAE state machine";
                leaf quietPeriod  {
                    type  cml-data-types:CML_UINT32_T {
                         range "1..65535";
                    }
                    default "60";
                    description "";
                } // END of quietPeriod definition.

                leaf reauthMax  {
                    type  cml-data-types:CML_UINT32_T {
                         range "1..10";
                    }
                    default "2";
                    description "";
                } // END of reauthMax definition.

                leaf txPeriod  {
                    type  cml-data-types:CML_UINT32_T {
                         range "1..65535";
                    }
                    default "30";
                    description "";
                } // END of txPeriod definition.

            } // END of authPae-container definition.
            container reauthTimer {
                description
                    "Reauthentication Timer state machine";
                leaf reAuthPeriod  {
                    type  cml-data-types:CML_UINT32_T {
                         range "1..4294967295";
                    }
                    default "3600";
                    description "";
                } // END of reAuthPeriod definition.

                leaf reAuthEnabled  {
                    type  cml-data-types:CML_BOOL_T;
                    description "";
                } // END of reAuthEnabled definition.

            } // END of reauthTimer-container definition.
            container authBe {
                description
                    "authenticator be state machine";
                leaf suppTimeout  {
                    type  cml-data-types:CML_UINT32_T {
                         range "1..65535";
                    }
                    default "30";
                    description "";
                } // END of suppTimeout definition.

                leaf serverTimeout  {
                    type  cml-data-types:CML_UINT32_T {
                         range "1..65535";
                    }
                    default "30";
                    description "";
                } // END of serverTimeout definition.

            } // END of authBe-container definition.
            container authKeyXmit {
                description
                    "Authenticator Key Transmit State Machine";
                leaf keyTxEnabled  {
                    type  cml-data-types:CML_BOOL_T;
                    description "";
                } // END of keyTxEnabled definition.

            } // END of authKeyXmit-container definition.
        } // End of authPort-list
    } // END of authPort-grouping definition.

    grouping  authmac-grouping {
    description
        "authmac";
    container authmac {
        description
            "authmac";
        leaf systemAuthCtrl  {
            type  cml-data-types:CML_BOOL_T;
            description "";
        } // END of systemAuthCtrl definition.

        leaf portControl  {
            type  cml-data-types:CML_BOOL_T;
            description "";
        } // END of portControl definition.

        leaf initialize  {
            type  cml-data-types:CML_STRING_T;
            description "";
        } // END of initialize definition.

        leaf reauthenticate  {
            type  cml-data-types:CML_STRING_T;
            description "";
        } // END of reauthenticate definition.

    } // END of authmac-container definition.
    } // END of authmac-container definition.

    grouping  debugdot1x-grouping {
    description
        "debugdot1x";
    container debugdot1x {
        description
            "debugdot1x";
        leaf debugtermFlag  {
            type  cml-data-types:CML_DOT1X_DEBUG_T;
            description "";
        } // END of debugtermFlag definition.

        leaf debugconfFlag  {
            type  cml-data-types:CML_DOT1X_DEBUG_T;
            description "";
        } // END of debugconfFlag definition.

    } // END of debugdot1x-container definition.
    } // END of debugdot1x-container definition.


}
