/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-zebos-aclinterface.yang
*
*/

submodule ipi-zebos-aclinterface {

    belongs-to  ipi-zebos { prefix ipi-zebos; }

    import cml-data-types {
        prefix cml-data-types;
    }

    organization
        "IP Infusion Inc.";

    contact
        "Address: 3965 Freedom Circle, Suite 200, Santa Clara, CA 95054
        Phone: +1 408-400-1900
        E-mail: support@ipinfusion.com
        Web: http://www.ipinfusion.com/";

    description
        "Access List Interface Related Configurations";


    revision "2016-11-17" {
        description " Initial Version.";
        reference "";
    }


    grouping  aclVty-grouping {
    description
        "ACL interface related operations";
    container aclVty {
        description
            "ACL interface related operations";

        list vtyAclTypeList {
            key "vtyAclType";
            description
                "vtyAclTypeList";
            leaf vtyAclType  {
                type  cml-data-types:CML_VTY_ACL_TYPES_T;
                description "";
            } // END of vtyAclType definition.


            list vtyAclDirList {
                key "vtyAclDir";
                description
                    "vtyAclDirList";
                leaf vtyAclName  {
                    type  cml-data-types:CML_STRING_T;
                    description "";
                } // END of vtyAclName definition.

                leaf vtyAclDir  {
                    type  cml-data-types:CML_ACL_PACKET_DIR_T;
                    description "";
                } // END of vtyAclDir definition.

            } // End of vtyAclDirList-list
        } // End of vtyAclTypeList-list
    } // END of aclVty-container definition.
    } // END of aclVty-container definition.

    grouping  aclInterface-grouping {
    description
        "ACL interface related operations";
    container aclInterface {
        description
            "ACL interface related operations";

        list aclIntfTypeList {
            key "ifAclType";
            description
                "aclIntfTypeList";
            leaf ifAclType  {
                type  cml-data-types:CML_ACL_TYPES_T;
                description "";
            } // END of ifAclType definition.


            list aclIntfDirList {
                key "ifAclDir";
                description
                    "aclIntfDirList";
                leaf ifAclName  {
                    type  cml-data-types:CML_STRING_T;
                    description "";
                } // END of ifAclName definition.

                leaf ifAclDir  {
                    type  cml-data-types:CML_ACL_PACKET_DIR_T;
                    description "";
                } // END of ifAclDir definition.

            } // End of aclIntfDirList-list
        } // End of aclIntfTypeList-list
    } // END of aclInterface-container definition.
    } // END of aclInterface-container definition.


}
