/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-zebos-aaa.yang
*
*/

submodule ipi-zebos-aaa {

    belongs-to  ipi-zebos { prefix ipi-zebos; }

    import cml-data-types {
        prefix cml-data-types;
    }

    import feature-list {
        prefix feature-list;
    }

    include ipi-zebos-vrf;
    include ipi-zebos-tacacs;
    include ipi-zebos-radius;
    organization
        "IP Infusion Inc.";

    contact
        "Address: 3965 Freedom Circle, Suite 200, Santa Clara, CA 95054
        Phone: +1 408-400-1900
        E-mail: support@ipinfusion.com
        Web: http://www.ipinfusion.com/";

    description
        "Layer-3 aaa configurations";


    revision "2018-06-21" {
        description " Initial Version.";
        reference "";
    }



    grouping aaa-grouping {
    description
        "aaa related commands";
        list aaa {
            key "vrfName";
            description
                "aaa related commands";
            leaf vrfName  {
                type  cml-data-types:CML_STRING_T;
                description "";
            } // END of vrfName definition.

            leaf accountingRule  {
                type  cml-data-types:CML_LINE_T;
                description "";
            } // END of accountingRule definition.

            leaf authenticationRule  {
                type  cml-data-types:CML_LINE_T;
                description "";
            } // END of authenticationRule definition.


            list aaaGroupServerNameRadius {
                if-feature feature-list:HAVE_RADIUS_CLIENT;
                key "groupWordRadius";
                description
                    "aaaGroupServerNameRadius";
                leaf groupWordRadius  {
                    type  cml-data-types:CML_STRING_T {
                        length "1..127";
                    }
                    description "";
                } // END of groupWordRadius definition.


                list aaaRadiusServer {
                    if-feature feature-list:HAVE_RADIUS_CLIENT;
                    key "hostAddr";
                    description
                        "aaaRadiusServer";
                    leaf hostAddr  {
                        type  cml-data-types:CML_STRING_T {
                            length "1..63";
                        }
                        description "";
                    } // END of hostAddr definition.

                } // End of aaaRadiusServer-list
            } // End of aaaGroupServerNameRadius-list

            list aaaGroupServerNameTacacs {
                if-feature feature-list:HAVE_TACACS_CLIENT;
                key "groupWordTacacs";
                description
                    "aaaGroupServerNameTacacs";
                leaf groupWordTacacs  {
                    type  cml-data-types:CML_STRING_T {
                        length "1..127";
                    }
                    description "";
                } // END of groupWordTacacs definition.


                list aaaTacacsServer {
                    if-feature feature-list:HAVE_TACACS_CLIENT;
                    key "hostAddr";
                    description
                        "aaaTacacsServer";
                    leaf hostAddr  {
                        type  cml-data-types:CML_STRING_T {
                            length "1..63";
                        }
                        description "";
                    } // END of hostAddr definition.

                } // End of aaaTacacsServer-list
            } // End of aaaGroupServerNameTacacs-list
        } // End of aaa-list
    } // END of aaa-grouping definition.


    grouping aaaAuthOptions-grouping {
    description
        "aaa related commands";
        list aaaAuthOptions {
            key "vrfName";
            description
                "aaa related commands";
            leaf vrfName  {
                type  cml-data-types:CML_STRING_T;
                description "";
            } // END of vrfName definition.

            leaf errorEnable  {
                type  cml-data-types:CML_BOOL_T;
                description "";
            } // END of errorEnable definition.

            leaf authDefaultFallback  {
                type  cml-data-types:CML_BOOL_T;
                description "";
            } // END of authDefaultFallback definition.

        } // End of aaaAuthOptions-list
    } // END of aaaAuthOptions-grouping definition.

    grouping  AAAUserConfigs-grouping {
    description
        "AAAUserConfigs";
    container AAAUserConfigs {
        description
            "AAAUserConfigs";
        leaf authMaxfail  {
            type  cml-data-types:CML_UINT8_T {
                 range "1..25";
            }
            default "3";
            description "";
        } // END of authMaxfail definition.

        leaf localUserUnlockTimeout  {
            type  cml-data-types:CML_UINT16_T {
                 range "1..3600";
            }
            default "1200";
            description "";
        } // END of localUserUnlockTimeout definition.

    } // END of AAAUserConfigs-container definition.
    } // END of AAAUserConfigs-container definition.

    grouping  console-grouping {
    description
        "console";
    container console {
        description
            "console";
        leaf authConsoleGroup  {
            type  cml-data-types:CML_LINE_T;
            description "";
        } // END of authConsoleGroup definition.

        leaf authConsoleFallback  {
            type  cml-data-types:CML_BOOL_T;
            description "";
        } // END of authConsoleFallback definition.

        leaf authLocal  {
            type  cml-data-types:CML_BOOL_T;
            description "";
        } // END of authLocal definition.

        leaf authNone  {
            type  cml-data-types:CML_BOOL_T;
            description "";
        } // END of authNone definition.

    } // END of console-container definition.
    } // END of console-container definition.

    grouping  debugAaa-grouping {
    description
        "debugAaa";
    container debugAaa {
        description
            "debugAaa";
        leaf debugaaa  {
            type  cml-data-types:CML_BOOL_T;
            description "";
        } // END of debugaaa definition.

        leaf debugaaaConfig  {
            type  cml-data-types:CML_BOOL_T;
            description "";
        } // END of debugaaaConfig definition.

    } // END of debugAaa-container definition.
    } // END of debugAaa-container definition.


}
