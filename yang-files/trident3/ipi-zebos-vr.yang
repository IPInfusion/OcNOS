/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-zebos-vr.yang
*
*/

submodule ipi-zebos-vr {

    belongs-to  ipi-zebos { prefix ipi-zebos; }

    import cml-data-types {
        prefix cml-data-types;
    }

    import feature-list {
        prefix feature-list;
    }

    include ipi-zebos-vrf;
    include ipi-zebos-interface;
    include ipi-zebos-broadcom;
    include ipi-zebos-vlan;
    include ipi-zebos-bridge;
    include ipi-zebos-mstp;
    include ipi-zebos-lldpv2;
    include ipi-zebos-rib;
    include ipi-zebos-ospf;
    include ipi-zebos-ospfv3;
    include ipi-zebos-bgp;
    include ipi-zebos-oambfd;
    include ipi-zebos-vrrp;
    include ipi-zebos-plist;
    include ipi-zebos-isis;
    include ipi-zebos-keychain;
    include ipi-zebos-pim;
    include ipi-zebos-pim4;
    include ipi-zebos-vxlan;
    include ipi-zebos-featuredhcp;
    include ipi-zebos-mrib4;
    include ipi-zebos-igmp;
    include ipi-zebos-routemap;
    include ipi-zebos-hqos;
    include ipi-zebos-auth;
    include ipi-zebos-rip;
    include ipi-zebos-acl;
    include ipi-zebos-aclinterface;
    include ipi-zebos-rpf;
    include ipi-zebos-pmirror;
    include ipi-zebos-authradius;
    include ipi-zebos-ripng;
    include ipi-zebos-dcb;
    include ipi-zebos-ndd;
    include ipi-zebos-imi;
    include ipi-zebos-rbac;
    include ipi-zebos-vm;
    organization
        "IP Infusion Inc.";

    contact
        "Address: 3965 Freedom Circle, Suite 200, Santa Clara, CA 95054
        Phone: +1 408-400-1900
        E-mail: support@ipinfusion.com
        Web: http://www.ipinfusion.com/";

    description
        "Virtual router";


    revision "2018-06-21" {
        description " Initial Version.";
        reference "";
    }



    grouping vr-grouping {
    description
        "Virtual router object";
        list vr {
            key "vrId";
            description
                "Virtual router object";
            leaf vrId  {
                type  cml-data-types:CML_UINT32_T {
                     range "0..255";
                }
                description "Virtual router id";
            } // END of vrId definition.

            leaf vrInstanceName  {
                type  cml-data-types:CML_STRING_T;
                config false;
                description "";
            } // END of vrInstanceName definition.


            list vrInstances {
                if-feature feature-list:HAVE_VR;
                key "vrName";
                description
                    "object for virtual router configurations";
                leaf vrName  {
                    type  cml-data-types:CML_STRING_T {
                        length "1..12";
                    }
                    description "Virtual router name";
                } // END of vrName definition.

                leaf description  {
                    type  cml-data-types:CML_LINE_T;
                    description "Virtual router description";
                } // END of description definition.

                leaf protocol  {
                    type  cml-data-types:CML_VR_PROTOCOL_T;
                    description "protocol load";
                } // END of protocol definition.

                leaf configurationFile  {
                    type  cml-data-types:CML_STRING_T;
                    description "Virtual router configuration file";
                } // END of configurationFile definition.

                leaf configReadWrite  {
                    type  cml-data-types:CML_VR_CONFIG_T;
                    description "Virtual router configuration file";
                } // END of configReadWrite definition.

            } // End of vrInstances-list
            uses vrf-grouping;
            uses interface-grouping;
            uses ifIndexList-grouping;
            uses nsmMaster-grouping;
            uses libhwconf-grouping;
            uses nsmVlanAccess-grouping;
            uses vlanClassifierRule-grouping;
            uses vlanClassifierGroup-grouping;
            uses debugConfigMode-grouping;
            uses debugExecMode-grouping;
            uses bridge-grouping;
            uses spanningTree-grouping;
            uses spanningPort-grouping;
            uses mstpPort-grouping;
            uses backboneBridgePort-grouping;
            uses customerSpanningtree-grouping;
            uses mstpDebugMode-grouping;
            uses mstpExecMode-grouping;
            uses lldpMaster-grouping;
            uses rib-grouping;
            uses ospf-grouping;
            uses teLinkOspf-grouping;
            uses ospfMaster-grouping;
            uses ospf6Master-grouping;
            uses bgp-grouping;
            uses bgpGlobal-grouping;
            uses bgpDebug-grouping;
            uses bfdInterface-grouping;
            uses bfd-grouping;
            uses Vrrp4Instance-grouping;
            uses Vrrp6Instance-grouping;
            uses vrrp-grouping;
            uses VrrpDebug-grouping;
            uses prefixMaster-grouping;
            uses prefixMaster6-grouping;
            uses isismaster-grouping;
            uses keychain-grouping;
            uses pimDebug-grouping;
            uses pimTermDebug-grouping;
            uses pim4Vrf-grouping;
            uses pim4Debug-grouping;
            uses nsmipv4prefixroute-grouping;
            uses nsmipv6prefixroute-grouping;
            uses anycastGwMac-grouping;
            uses esiHoldTime-grouping;
            uses nvo-grouping;
            uses featuredhcp-grouping;
            uses mrib4Vrf-grouping;
            uses mrib4Igmp-grouping;
            uses pbrConfig-grouping;
            uses qos-grouping;
            uses authPort-grouping;
            uses authmac-grouping;
            uses ripConfiguration-grouping;
            uses accessMasterIPv4-grouping;
            uses accessMasterARP-grouping;
            uses accessMasterIPv6-grouping;
            uses aclVty-grouping;
            uses rpf-grouping;
            uses pmNode-grouping;
            uses pmNodeALternate-grouping;
            uses Hostradius-grouping;
            uses authradius-grouping;
            uses ripngConfiguration-grouping;
            uses nsmDcbIf-grouping;
            uses Dcbdebug-grouping;
            uses ndstaticarpentry-grouping;
            uses debugndd-grouping;
            uses webUser-grouping;
            uses rbacFeature-grouping;
            uses vmtemplate-grouping;
            uses guestVmList-grouping;
            uses iptable-grouping;
            uses restoreList-grouping;
            uses srcNatList-grouping;
            uses dstNatList-grouping;
            uses guestVm-grouping;
            uses debugVmEvents-grouping;
        } // End of vr-list
    } // END of vr-grouping definition.


}
