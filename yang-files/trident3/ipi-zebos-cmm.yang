/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-zebos-cmm.yang
*
*/

submodule ipi-zebos-cmm {

    belongs-to  ipi-zebos { prefix ipi-zebos; }

    import cml-data-types {
        prefix cml-data-types;
    }

    import feature-list {
        prefix feature-list;
    }

    organization
        "IP Infusion Inc.";

    contact
        "Address: 3965 Freedom Circle, Suite 200, Santa Clara, CA 95054
        Phone: +1 408-400-1900
        E-mail: support@ipinfusion.com
        Web: http://www.ipinfusion.com/";

    description
        "Chassis Monitoring Module";


    revision "2018-06-21" {
        description " Initial Version.";
        reference "";
    }



    typedef  CML_CMM_MOD_ADMIN_STATUS_T {
        type enumeration {
            enum down {
                value 1;
                description "down";
            }
            enum up {
                value 2;
                description "up";
            }
        }
        description "";
        reference "";
    }

    typedef  CML_CMM_MOD_SERVICE_ENABLE_T {
        type enumeration {
            enum disable {
                value 0;
                description "To disable the coherent module";
            }
            enum enable {
                value 1;
                description "To enable the coherent module";
            }
        }
        description "";
        reference "";
    }

    typedef  CML_CMM_CARD_TYPE_T {
        type enumeration {
            enum UNKNOWN {
                value 0;
                description "UNKNOWN";
            }
            enum DCO {
                value 1;
                description "DCO";
            }
            enum ACO {
                value 2;
                description "ACO";
            }
            enum NON_COHERENT {
                value 3;
                description "NON_COHERENT";
            }
        }
        description "";
        reference "";
    }

    typedef  CML_CMM_CFP_PRESENCE_T {
        type enumeration {
            enum PRESENT {
                value 1;
                description "present";
            }
            enum NOT_PRESENT {
                value 2;
                description "notpresent";
            }
            enum UNKNOWN {
                value 3;
                description "unknown";
            }
            enum NOT_APPLICABLE {
                value 4;
                description "notapplicable";
            }
        }
        description "";
        reference "";
    }

    typedef  CML_CMM_MOD_OPER_STATUS_T {
        type enumeration {
            enum initialize {
                value 1;
                description "initialize";
            }
            enum ready {
                value 2;
                description "ready";
            }
        }
        description "";
        reference "";
    }

    typedef  CML_CMM_NETIF_OPER_STATUS_T {
        type enumeration {
            enum unknown {
                value 0;
                description "unknown";
            }
            enum reset {
                value 1;
                description "reset";
            }
            enum initialize {
                value 2;
                description "initialize";
            }
            enum low-power {
                value 3;
                description "low-power";
            }
            enum high-power-up {
                value 4;
                description "high-power-up";
            }
            enum tx-off {
                value 5;
                description "tx-off";
            }
            enum tx-turn-on {
                value 6;
                description "tx-turn-on";
            }
            enum ready {
                value 7;
                description "ready";
            }
            enum tx-turn-off {
                value 8;
                description "tx-turn-off";
            }
            enum high-power-down {
                value 9;
                description "high-power-down";
            }
            enum fault {
                value 10;
                description "fault";
            }
        }
        description "";
        reference "";
    }

    typedef  CML_CMM_DSP_OPER_STATUS_T {
        type enumeration {
            enum no-module {
                value 1;
                description "no-module";
            }
            enum waiting-configuration {
                value 2;
                description "waiting-configuration";
            }
            enum booting-first-half {
                value 3;
                description "booting-first-half";
            }
            enum waiting-aco-module {
                value 4;
                description "waiting-aco-module";
            }
            enum booting-aco-module {
                value 5;
                description "booting-aco-module";
            }
            enum waiting-rx-signal {
                value 6;
                description "waiting-rx-signal";
            }
            enum booting-second-half {
                value 7;
                description "booting-second-half";
            }
            enum ready {
                value 8;
                description "ready";
            }
            enum misc-config {
                value 9;
                description "misc-config";
            }
        }
        description "";
        reference "";
    }

    typedef  CML_CMM_PRBS_TYPE {
        type enumeration {
            enum none {
                value 0;
                description "none";
            }
            enum prbs7 {
                value 1;
                description "generates prbs 7 sequence";
            }
            enum prbs9 {
                value 2;
                description "generates prbs 9 sequence";
            }
            enum prbs11 {
                value 3;
                description "generates prbs 11 sequence";
            }
            enum prbs15 {
                value 4;
                description "generates prbs 15 sequence";
            }
            enum prbs20 {
                value 5;
                description "generates prbs 20 sequence";
            }
            enum prbs23 {
                value 6;
                description "generates prbs 23 sequence";
            }
            enum prbs31 {
                value 7;
                description "generates prbs 31 sequence";
            }
        }
        description "";
        reference "";
    }

    typedef  CML_CMM_MODULATION_FORMAT {
        type enumeration {
            enum bpsk {
                value 1;
                description "Binary phase shift keying modulation scheme";
            }
            enum dp-bpsk {
                value 2;
                description "Dual polarization binary phase-shift keying";
            }
            enum qpsk {
                value 3;
                description "Quadrature phase shift keying";
            }
            enum dp-qpsk {
                value 4;
                description "Dual polarization quadrature phase shift keying";
            }
            enum 8-qam {
                value 5;
                description "8-quadrature amplitude modulation format";
            }
            enum dp-8-qam {
                value 6;
                description "Dual polarization 8-ary quadrature amplitude modulation format";
            }
            enum 16-qam {
                value 7;
                description "16-quadrature amplitude modulation format";
            }
            enum dp-16-qam {
                value 8;
                description "Dual polarization 16-ary quadrature amplitude modulation format";
            }
            enum 32-qam {
                value 9;
                description "32-quadrature amplitude modulation format";
            }
            enum dp-32-qam {
                value 10;
                description "Dual polarization 32-ary quadrature amplitude modulation format";
            }
            enum 64-qam {
                value 11;
                description "64-quadrature amplitude modulation format";
            }
            enum dp-64-qam {
                value 12;
                description "Dual polarization 64-ary quadrature amplitude modulation format";
            }
        }
        description "";
        reference "";
    }

    typedef  CML_CMM_FEC_MODE {
        type enumeration {
            enum 15per-everest {
                value 1;
                description "15percent Everest Compatible";
            }
            enum 15per-denali {
                value 2;
                description "15percent Denali Compatible";
            }
            enum otu4-g709 {
                value 3;
                description "OTU-4 G.709";
            }
            enum otu4-7per-staircase {
                value 5;
                description "OTU-4 7percent Staircase";
            }
        }
        description "";
        reference "";
    }

    typedef  CML_CMM_OPTICAL_LOOPBACK_T {
        type enumeration {
            enum none {
                value 0;
                description "Set to default value";
            }
            enum shallow {
                value 1;
                description "Set line loopback to shallow";
            }
            enum deep {
                value 2;
                description "Set line loopback to deep";
            }
        }
        description "";
        reference "";
    }

    typedef  CML_CMM_OPTICAL_FEC_T {
        type enumeration {
            enum none {
                value 0;
                description "none";
            }
            enum rs {
                value 1;
                description "Set FEC to Reed Solomon FEC type";
            }
            enum fc {
                value 2;
                description "Set FEC to Fire Code FEC type";
            }
        }
        description "";
        reference "";
    }

    typedef  CML_CMM_GRID_SPACING_T {
        type enumeration {
            enum 6.25-ghz {
                value 0;
                description "6.25-ghz";
            }
            enum 12.5-ghz {
                value 1;
                description "12.5-ghz";
            }
            enum 25-ghz {
                value 2;
                description "25-ghz";
            }
            enum 33-ghz {
                value 3;
                description "33-ghz";
            }
            enum 50-ghz {
                value 4;
                description "50-ghz";
            }
            enum 100-ghz {
                value 5;
                description "100-ghz";
            }
        }
        description "";
        reference "";
    }

    typedef  CML_CMM_NETIF_RX_OTU_ALARM_T {
        type bits {
            bit loss-of-frame {
                position 0;
                description "loss of frame";
            }
            bit loss-of-multiframe {
                position 1;
                description "loss-of-multiframe";
            }
            bit backward-defect-detection {
                position 2;
                description "backward-defect-detection";
            }
            bit alarm-indication-signal {
                position 3;
                description "alarm-indication-signal";
            }
        }
        description "";
        reference "";
    }

    typedef  CML_CMM_NETIF_RX_ODU_ALARM_T {
        type bits {
            bit backward-defect-indication {
                position 0;
                description "backward-defect-indication";
            }
            bit alarm-indication-signal {
                position 1;
                description "alarm-indication-signal";
            }
            bit open-connection-indication {
                position 2;
                description "open-connection-indication";
            }
            bit locked-defect {
                position 3;
                description "locked-defect";
            }
        }
        description "";
        reference "";
    }

    typedef  CML_CMM_NETIF_RX_OPU_ALARM_T {
        type bits {
            bit payload-Mismatch {
                position 0;
                description "payload-Mismatch";
            }
            bit client-signal-fail {
                position 1;
                description "client-signal-fail";
            }
        }
        description "";
        reference "";
    }

    typedef  CML_CMM_NETIF_RX_TS_ALARM_T {
        type bits {
            bit loss-of-lock {
                position 0;
                description "loss-of-lock";
            }
        }
        description "";
        reference "";
    }

    typedef  CML_CMM_NETIF_PRE_FEC_BER_SIGNAL_ALARM_T {
        type enumeration {
            enum pre-fec-ber-signal-degrade {
                value 1;
                description "pre-fec-ber-signal-degrade";
            }
            enum pre-fec-ber-signal-failure {
                value 2;
                description "pre-fec-ber-signal-failure";
            }
        }
        description "";
        reference "";
    }

    typedef  CML_CMM_NETIF_INPUT_POWER_ALARM_T {
        type enumeration {
            enum input-power-low-alarm {
                value 1;
                description "input-power-low-alarm";
            }
            enum input-power-low-warning {
                value 2;
                description "input-power-low-warning";
            }
            enum input-power-high-warning {
                value 3;
                description "input-power-high-warning";
            }
            enum input-power-high-alarm {
                value 4;
                description "input-power-high-alarm";
            }
        }
        description "";
        reference "";
    }

    typedef  CML_CMM_NETIF_OUTPUT_POWER_ALARM_T {
        type enumeration {
            enum output-power-low-alarm {
                value 1;
                description "output-power-low-alarm";
            }
            enum output-power-low-warning {
                value 2;
                description "output-power-low-warning";
            }
            enum output-power-high-warning {
                value 3;
                description "output-power-high-warning";
            }
            enum output-power-high-alarm {
                value 4;
                description "output-power-high-alarm";
            }
        }
        description "";
        reference "";
    }

    typedef  CML_CMM_HOSTIF_PCS_ALARM_T {
        type bits {
            bit loss-of-signal {
                position 0;
                description "loss-of-signal";
            }
            bit loss-of-frame {
                position 1;
                description "loss-of-frame";
            }
            bit illegal-alignment-marker {
                position 2;
                description "illegal-alignment-marker";
            }
            bit remote-fault {
                position 3;
                description "remote-fault";
            }
            bit local-fault {
                position 4;
                description "local-fault";
            }
            bit high-BER {
                position 5;
                description "high-BER";
            }
            bit BIP-error {
                position 6;
                description "BIP-error";
            }
            bit deskew-error {
                position 7;
                description "deskew-error";
            }
            bit loss-of-block-lock {
                position 8;
                description "loss-of-block-lock";
            }
            bit loss-of-alignment-marker-lock {
                position 9;
                description "loss-of-alignment-marker-lock";
            }
            bit loss-of-alignment {
                position 10;
                description "loss-of-alignment";
            }
            bit OPU-client-signal-fail {
                position 11;
                description "OPU-client-signal-fail";
            }
            bit error-blocks-detected {
                position 12;
                description "error-blocks-detected";
            }
        }
        description "";
        reference "";
    }

    typedef  CML_CMM_HOSTIF_FAULT_STATUS_ALARM_T {
        type bits {
            bit tx-host-lol-l0 {
                position 0;
                description "tx-host-lol-l0";
            }
            bit tx-host-lol-l1 {
                position 1;
                description "tx-host-lol-l1";
            }
            bit tx-host-lol-l2 {
                position 2;
                description "tx-host-lol-l2";
            }
            bit tx-host-lol-l3 {
                position 3;
                description "tx-host-lol-l3";
            }
            bit ingress-aps-msg-rcvd {
                position 4;
                description "ingress-aps-msg-rcvd";
            }
            bit deskew-lock-fault {
                position 5;
                description "deskew-lock-fault";
            }
            bit out-of-align {
                position 6;
                description "out-of-align";
            }
            bit loss-of-align {
                position 7;
                description "loss-of-align";
            }
        }
        description "";
        reference "";
    }

    typedef  CML_CMM_MOD_TEMP_ALARM_T {
        type enumeration {
            enum temperature-low-alarm {
                value 1;
                description "temperature-low-alarm";
            }
            enum temperature-low-waring {
                value 2;
                description "temperature-low-waring";
            }
            enum temperature-high-warning {
                value 3;
                description "temperature-high-warning";
            }
            enum temperature-high-alarm {
                value 4;
                description "temperature-high-alarm";
            }
        }
        description "";
        reference "";
    }

    typedef  CML_CMM_MOD_VOLT_ALARM_T {
        type enumeration {
            enum power-low-alarm {
                value 1;
                description "power-low-alarm";
            }
            enum power-low-waring {
                value 2;
                description "power-low-waring";
            }
            enum power-high-warning {
                value 3;
                description "power-high-warning";
            }
            enum power-high-alarm {
                value 4;
                description "power-high-alarm";
            }
        }
        description "";
        reference "";
    }

    typedef  CML_CMM_MOD_GENERAL_STATUS_ALARM_T {
        type bits {
            bit hw-interlock {
                position 0;
                description "hw-interlock";
            }
            bit tx-loss-of-signal-functionality {
                position 1;
                description "tx-loss-of-signal-functionality";
            }
            bit rx-loss-of-signal {
                position 2;
                description "rx-loss-of-signal";
            }
            bit rx-network-loss-of-lock {
                position 3;
                description "rx-network-loss-of-lock";
            }
            bit tx-host-loss-of-lock {
                position 4;
                description "tx-host-loss-of-lock";
            }
            bit hostlane-out-of-alignment {
                position 5;
                description "hostlane-out-of-alignment";
            }
        }
        description "";
        reference "";
    }

    typedef  CML_CMM_MOD_FAULT_STATUS_ALARM_T {
        type bits {
            bit over-temperature-fault {
                position 0;
                description "over-temperature-fault";
            }
            bit hardware-fault {
                position 1;
                description "hardware-fault";
            }
            bit initialization-fault {
                position 2;
                description "initialization-fault";
            }
            bit power-supply-fault {
                position 3;
                description "power-supply-fault";
            }
            bit checksum-fault {
                position 4;
                description "checksum-fault";
            }
        }
        description "";
        reference "";
    }

    typedef  CML_TAI_DEBUG_FLAG_T {
        type bits {
            bit module {
                position 0;
                description "TAI module-level";
            }
            bit netif {
                position 1;
                description "TAI netif-level";
            }
            bit hostif {
                position 2;
                description "TAI hostif-level";
            }
        }
        description "";
        reference "";
    }

    typedef  CML_CMM_GRID_SUPPORT_T {
        type bits {
            bit grid-6.25-ghz {
                position 0;
                description "grid-6.25-ghz";
            }
            bit grid-12.5-ghz {
                position 1;
                description "grid-12.5-ghz";
            }
            bit grid-25-ghz {
                position 2;
                description "grid-25-ghz";
            }
            bit grid-33-ghz {
                position 3;
                description "grid-33-ghz";
            }
            bit grid-50-ghz {
                position 4;
                description "grid-50-ghz";
            }
            bit grid-100-ghz {
                position 5;
                description "grid-100-ghz";
            }
        }
        description "";
        reference "";
    }

    grouping cmmCoherentConfigTable-grouping {
    description
        "A table to store all the config attributes.";
        list cmmCoherentConfigTable {
            if-feature feature-list:HAVE_COHERENT_OPTICS;
            key "slotIndex";
            description
                "A table to store all the config attributes.";
            leaf slotIndex  {
                type  cml-data-types:CML_UINT8_T {
                     range "1..255";
                }
                description "Index to select a optical module slot.";
            } // END of slotIndex definition.

            leaf serviceenable  {
                type  CML_CMM_MOD_SERVICE_ENABLE_T;
                default "disable";
                description "Enable service for  controller optical module";
            } // END of serviceenable definition.

            leaf adminStatus  {
                type  cml-data-types:CML_BOOL_T;
                description "Shutdowns the coherent optical module";
            } // END of adminStatus definition.

            leaf slotDescription  {
                type  cml-data-types:CML_STRING_T;
                description "Coherent Optics slot Description";
            } // END of slotDescription definition.


            list cmmCoherentChannelConfigTable {
                if-feature feature-list:HAVE_COHERENT_OPTICS;
                key "netIndex";
                description
                    "Network Interface config";
                leaf netIndex  {
                    type  cml-data-types:CML_UINT8_T {
                         range "0..15";
                    }
                    description "Index of network interface in a coherent optical module.";
                } // END of netIndex definition.

                leaf softTxDisable  {
                    type  cml-data-types:CML_BOOL_T;
                    description "Disable transmission of data on a network interface.";
                } // END of softTxDisable definition.

                leaf lossOfSignal  {
                    type  cml-data-types:CML_BOOL_T;
                    description "Enable loss of signal alarm on a network interface.";
                } // END of lossOfSignal definition.

                leaf differentialEncoding  {
                    type  cml-data-types:CML_BOOL_T;
                    description "Enable differential encoding on a optical network interface.";
                } // END of differentialEncoding definition.

                leaf outputPower  {
                    type  cml-data-types:CML_FLOAT_T;
                    units "dBm";
                    description "Specifies the output power of the optical network interface.";
                } // END of outputPower definition.

                leaf laserFreq  {
                    type  cml-data-types:CML_STRING_T;
                    description "Specifies the output laser frequency for the optical network interface in terms of Hz.";
                } // END of laserFreq definition.

                leaf modulationFormat  {
                    type  CML_CMM_MODULATION_FORMAT;
                    default "dp-16-qam";
                    description "Specifies the modulation format of the optical signal.";
                } // END of modulationFormat definition.

                leaf rxPulseShaping  {
                    type  cml-data-types:CML_BOOL_T;
                    description "Enable or disable rx pulse shaping of the signal.";
                } // END of rxPulseShaping definition.

                leaf txPulseShaping  {
                    type  cml-data-types:CML_BOOL_T;
                    description "Enable or disable tx pulse shaping of the signal.";
                } // END of txPulseShaping definition.

                leaf loopbackType  {
                    type  CML_CMM_OPTICAL_LOOPBACK_T;
                    default "none";
                    description "";
                } // END of loopbackType definition.

                leaf prbsType  {
                    type  CML_CMM_PRBS_TYPE;
                    default "none";
                    description "Simulate random data for transmission across the network interface if set.";
                } // END of prbsType definition.

                leaf fecMode  {
                    type  CML_CMM_FEC_MODE;
                    default "15per-denali";
                    description "FEC mode for network interface.";
                } // END of fecMode definition.

                container cmmCoherentChannelMonitorConfig {
                    if-feature feature-list:HAVE_COHERENT_OPTICS;
                    description
                        "Network interface monitor thresholds config";
                    container rxPowerThresholds {
                        description
                            "rx-power thresholds config";
                        leaf inputPowerHighAlarm  {
                            type  cml-data-types:CML_FLOAT_T;
                            description "Set user-config input power threshold value for high alarm.";
                        } // END of inputPowerHighAlarm definition.

                        leaf inputPowerHighWarn  {
                            type  cml-data-types:CML_FLOAT_T;
                            description "Set user-config input power threshold value for high warning.";
                        } // END of inputPowerHighWarn definition.

                        leaf inputPowerLowWarn  {
                            type  cml-data-types:CML_FLOAT_T;
                            description "Set user-config input power threshold value for low warning.";
                        } // END of inputPowerLowWarn definition.

                        leaf inputPowerLowAlarm  {
                            type  cml-data-types:CML_FLOAT_T;
                            description "Set user-config input power threshold value for low alarm.";
                        } // END of inputPowerLowAlarm definition.

                    } // END of rxPowerThresholds-container definition.
                    container preFecBerThresholds {
                        description
                            "pre-fec-ber thresholds config";
                        leaf preFecBerSigFailure  {
                            type  cml-data-types:CML_STRING_T;
                            description "Set user-config pre frc ber threshold value for signal failure.";
                        } // END of preFecBerSigFailure definition.

                        leaf preFecBerSigDegrade  {
                            type  cml-data-types:CML_STRING_T;
                            description "Set user-config pre frc ber threshold value for signal degrade.";
                        } // END of preFecBerSigDegrade definition.

                        leaf preFecBerClear  {
                            type  cml-data-types:CML_STRING_T;
                            description "Set user-config pre frc ber threshold value for clear.";
                        } // END of preFecBerClear definition.

                    } // END of preFecBerThresholds-container definition.
                    container rxQmarginThreshold {
                        description
                            "rx q-margin threshold config";
                        leaf rxQmarginThresh  {
                            type  cml-data-types:CML_FLOAT_T;
                            description "Set user-config rx q-margin threshold.";
                        } // END of rxQmarginThresh definition.

                    } // END of rxQmarginThreshold-container definition.
                    container rxSnrThreshold {
                        description
                            "rx snr threshold config";
                        leaf rxSnrThresh  {
                            type  cml-data-types:CML_FLOAT_T;
                            description "Set user-config rx snr threshold.";
                        } // END of rxSnrThresh definition.

                    } // END of rxSnrThreshold-container definition.
                    container rxChromaticDispersionThreshold {
                        description
                            "rx chromatic-dispersion threshold config";
                        leaf rxChromaticDispersionThresh  {
                            type  cml-data-types:CML_STRING_T;
                            description "Set user-config rx chromatic-dispersion threshold.";
                        } // END of rxChromaticDispersionThresh definition.

                    } // END of rxChromaticDispersionThreshold-container definition.
                } // END of cmmCoherentChannelMonitorConfig-container definition.
            } // End of cmmCoherentChannelConfigTable-list

            list cmmCoherentHostConfigTable {
                if-feature feature-list:HAVE_COHERENT_OPTICS;
                key "hostIndex";
                description
                    "Host Interface";
                leaf hostIndex  {
                    type  cml-data-types:CML_UINT8_T {
                         range "0..15";
                    }
                    description "Index of host interface in a coherent optical module.";
                } // END of hostIndex definition.

                leaf hostFecType  {
                    type  CML_CMM_OPTICAL_FEC_T;
                    default "none";
                    description "";
                } // END of hostFecType definition.

                leaf hostloopbackType  {
                    type  CML_CMM_OPTICAL_LOOPBACK_T;
                    default "none";
                    description "";
                } // END of hostloopbackType definition.

            } // End of cmmCoherentHostConfigTable-list
        } // End of cmmCoherentConfigTable-list
    } // END of cmmCoherentConfigTable-grouping definition.


    grouping cmmCoherentStateTable-grouping {
    description
        "A table to store all the runtime attributes.";
        list cmmCoherentStateTable {
            if-feature feature-list:HAVE_COHERENT_OPTICS;
            key "slotIndex";
            config false;
            description
                "A table to store all the runtime attributes.";
            leaf slotIndex  {
                type  cml-data-types:CML_UINT8_T;
                description "Index to select a optical module slot.";
            } // END of slotIndex definition.

            leaf modulePresence  {
                type  cml-data-types:CML_CMM_DEVICE_PRESENCE_T;
                description "Specifies whether coherent optical module is Present in the slot.";
            } // END of modulePresence definition.

            leaf cardType  {
                type  CML_CMM_CARD_TYPE_T;
                description "Specifies the coherent optical module Type, currently supported module types are ACO and DCO.";
            } // END of cardType definition.

            leaf vendorName  {
                type  cml-data-types:CML_STRING_T;
                description "Specifies the coherent optical module vendor name.";
            } // END of vendorName definition.

            leaf operAdminStatus  {
                type  CML_CMM_MOD_ADMIN_STATUS_T;
                description "Admin operational status of the coherent optical module.";
            } // END of operAdminStatus definition.

            leaf operationalStatus  {
                type  CML_CMM_MOD_OPER_STATUS_T;
                description "Operational status of the coherent optical module.";
            } // END of operationalStatus definition.

            leaf noOfHostInterfaces  {
                type  cml-data-types:CML_UINT32_T;
                description "Specifies the number of ethernet non-optical ports supported for the optical interface.";
            } // END of noOfHostInterfaces definition.

            leaf noOfOpticalchannelInterfaces  {
                type  cml-data-types:CML_UINT32_T;
                description "Number of optical channel interfaces.";
            } // END of noOfOpticalchannelInterfaces definition.

            leaf vendorSerialName  {
                type  cml-data-types:CML_STRING_T;
                description "Specifies the vendor serial number of the coherent optical module.";
            } // END of vendorSerialName definition.

            leaf vendorFirmwareVersion  {
                type  cml-data-types:CML_STRING_T;
                description "Specifies the vendor firmware version of the coherent optical module.";
            } // END of vendorFirmwareVersion definition.

            leaf CFPTransPresence  {
                type  CML_CMM_CFP_PRESENCE_T;
                description "Indicates Transceiver presence status.";
            } // END of CFPTransPresence definition.

            leaf CFPVendorName  {
                type  cml-data-types:CML_STRING_T;
                description "Specifies the CFP Vendor Name.";
            } // END of CFPVendorName definition.

            leaf CFPVendorOUI  {
                type  cml-data-types:CML_LINE_T;
                description "Specifies the CFP Vendor OUI.";
            } // END of CFPVendorOUI definition.

            leaf CFPVendorPart  {
                type  cml-data-types:CML_STRING_T;
                description "Specifies the CFP Vendor Part Number.";
            } // END of CFPVendorPart definition.

            leaf CFPVendorSerialNumber  {
                type  cml-data-types:CML_STRING_T;
                description "Specifies the CFP Vendor Serial Number.";
            } // END of CFPVendorSerialNumber definition.

            leaf CFPVendorFirmwareVersion  {
                type  cml-data-types:CML_STRING_T;
                description "Specifies the CFP Vendor Firmware Version.";
            } // END of CFPVendorFirmwareVersion definition.

            leaf CFPTemperature  {
                type  cml-data-types:CML_FLOAT_T;
                units "C";
                description "Specifies the CFP Module Temperature.";
            } // END of CFPTemperature definition.

            leaf CFPPower  {
                type  cml-data-types:CML_FLOAT_PRECISION_3_T;
                units "V";
                description "Specifies the CFP Module Power Supply.";
            } // END of CFPPower definition.


            list cmmCoherentChannelStateTable {
                if-feature feature-list:HAVE_COHERENT_OPTICS;
                key "netIndex";
                config false;
                description
                    "Network Interface runtime.";
                leaf netIndex  {
                    type  cml-data-types:CML_UINT8_T;
                    description "Index of network interface in a coherent optical module.";
                } // END of netIndex definition.

                leaf channelOperStatus  {
                    type  CML_CMM_NETIF_OPER_STATUS_T;
                    description "Specifies the operational status of the network interface in a coherent optical module.";
                } // END of channelOperStatus definition.

                leaf DSPOperStatus  {
                    type  CML_CMM_DSP_OPER_STATUS_T;
                    description "Specifies the operational status of the Digital Signal Processor of the network interface in a coherent optical module.";
                } // END of DSPOperStatus definition.

                leaf prbsInSync  {
                    type  cml-data-types:CML_BOOL_T;
                    description "Specifies the PRBS in SYNC.";
                } // END of prbsInSync definition.

                leaf currentPrbsBER  {
                    type  cml-data-types:CML_UINT64_T;
                    units "1e-18";
                    description "Specifies Current PRBS Bit Error Rate value divided by 1e-18.";
                } // END of currentPrbsBER definition.

                leaf currentBERPeriod  {
                    type  cml-data-types:CML_UINT32_T;
                    units "ms";
                    description "Specifies the current Bit Error Rate Period in milliseconds.";
                } // END of currentBERPeriod definition.

                leaf currentPreFecBer  {
                    type  cml-data-types:CML_UINT64_T;
                    units "1e-18";
                    description "Specifies the current PRE FEC Bit Error Rate per 1e-18 BER Period.";
                } // END of currentPreFecBer definition.

                leaf currentPostFecBer  {
                    type  cml-data-types:CML_UINT64_T;
                    units "1e-18";
                    description "Specifies current POST FEC Bit Error Rate per 1e-18 BER Period.";
                } // END of currentPostFecBer definition.

                leaf currentChromaticDispersion  {
                    type  cml-data-types:CML_INT32_T;
                    units "ps/nm";
                    description "Specifies the current Chromatic Dispersion in pico second/nano meter.";
                } // END of currentChromaticDispersion definition.

                leaf currentDifferentialGroupDelay  {
                    type  cml-data-types:CML_UINT32_T;
                    units "ps";
                    description "Specifies the current Differential Group Delay in pico second.";
                } // END of currentDifferentialGroupDelay definition.

                leaf minLaserFreq  {
                    type  cml-data-types:CML_UINT64_T;
                    units "Hz";
                    description "Specifies the Min Laser Frequency.";
                } // END of minLaserFreq definition.

                leaf maxLaserFreq  {
                    type  cml-data-types:CML_UINT64_T;
                    units "Hz";
                    description "Specifies Max Laser Frequency.";
                } // END of maxLaserFreq definition.

                leaf currentTxLaserFreq  {
                    type  cml-data-types:CML_UINT64_T;
                    units "Hz";
                    description "Specifies the current Tx-Laser Frequency.";
                } // END of currentTxLaserFreq definition.

                leaf gridSpacing  {
                    type  CML_CMM_GRID_SPACING_T;
                    description "Specifies the Grid Spacing.";
                } // END of gridSpacing definition.

                leaf laserGrid  {
                    type  CML_CMM_GRID_SUPPORT_T;
                    description "Specifies the supported Laser Grid.";
                } // END of laserGrid definition.

                leaf currentOutputPower  {
                    type  cml-data-types:CML_FLOAT_T;
                    units "dBm";
                    description "Specifies the current Output Power.";
                } // END of currentOutputPower definition.

                leaf currentInputPower  {
                    type  cml-data-types:CML_FLOAT_T;
                    units "dBm";
                    description "Specifies the current Input Power.";
                } // END of currentInputPower definition.

                leaf currentPostVOAPower  {
                    type  cml-data-types:CML_FLOAT_T;
                    units "dBm";
                    description "Specifies the current POST VOA Power.";
                } // END of currentPostVOAPower definition.

                leaf currentProviChannelPower  {
                    type  cml-data-types:CML_FLOAT_T;
                    units "dBm";
                    description "Specifies the current Province Channel Power.";
                } // END of currentProviChannelPower definition.

                leaf currentPostVOAProviChannelPower  {
                    type  cml-data-types:CML_FLOAT_T;
                    units "dBm";
                    description "Specifies the current Post VOA Provisioned Channel Power.";
                } // END of currentPostVOAProviChannelPower definition.

                leaf OSNR  {
                    type  cml-data-types:CML_FLOAT_T;
                    units "dB";
                    description "Specifies the optical signal noise ratio.";
                } // END of OSNR definition.

                leaf operSoftTxDisable  {
                    type  cml-data-types:CML_BOOL_T;
                    description "Specifies the TX Disable.";
                } // END of operSoftTxDisable definition.

                leaf operLossOfSignal  {
                    type  cml-data-types:CML_BOOL_T;
                    description "Specifies the loss of signal.";
                } // END of operLossOfSignal definition.

                leaf operDifferentialEncoding  {
                    type  cml-data-types:CML_BOOL_T;
                    description "Specifies the Differential encoding.";
                } // END of operDifferentialEncoding definition.

                leaf operOutputPower  {
                    type  cml-data-types:CML_FLOAT_T;
                    units "dBm";
                    description "Specifies the Output Power.";
                } // END of operOutputPower definition.

                leaf operLaserFreq  {
                    type  cml-data-types:CML_UINT64_T;
                    units "Hz";
                    description "Specifies the laser frequency for the optical network interface in terms of Hz.";
                } // END of operLaserFreq definition.

                leaf operModulationFormat  {
                    type  CML_CMM_MODULATION_FORMAT;
                    description "Specifies the modulation format of the optical signal.";
                } // END of operModulationFormat definition.

                leaf operFECmode  {
                    type  CML_CMM_FEC_MODE;
                    description "Specifies the FEC mode for transceiver.";
                } // END of operFECmode definition.

                leaf operRXPulseShaping  {
                    type  cml-data-types:CML_BOOL_T;
                    description "Specifies the rx pulse shaping of the signal.";
                } // END of operRXPulseShaping definition.

                leaf operTXPulseShaping  {
                    type  cml-data-types:CML_BOOL_T;
                    description "Specifies the tx pulse shaping of the signal.";
                } // END of operTXPulseShaping definition.

                leaf operLoopbackType  {
                    type  CML_CMM_OPTICAL_LOOPBACK_T;
                    description "Specifies the loopback type of network interface.";
                } // END of operLoopbackType definition.

                leaf operPrbsType  {
                    type  CML_CMM_PRBS_TYPE;
                    description "Specifies the simulation random data for transmission across the network interface if set.";
                } // END of operPrbsType definition.

                leaf currentQMargin  {
                    type  cml-data-types:CML_FLOAT_T;
                    units "dB";
                    description "Specifies Network RX Q margin.";
                } // END of currentQMargin definition.

                leaf currentUncorrectedBlockCount  {
                    type  cml-data-types:CML_UINT32_T;
                    description "Specifies the Current Uncorrected Block-Count Value.";
                } // END of currentUncorrectedBlockCount definition.

                leaf laserAge  {
                    type  cml-data-types:CML_UINT16_T;
                    units "%";
                    description "Specifies the Tx Laser Age in Percentage.";
                } // END of laserAge definition.

                container cmmCoherentChannelFAWSTable {
                    if-feature feature-list:HAVE_COHERENT_OPTICS;
                    config false;
                    description
                        "A table to store all the Network Interface faults/alarms/warning/status.";
                    leaf inputPower  {
                        type  CML_CMM_NETIF_INPUT_POWER_ALARM_T;
                        description "Specifies current netif rx input power alarm/warning status.";
                    } // END of inputPower definition.

                    leaf outputPower  {
                        type  CML_CMM_NETIF_OUTPUT_POWER_ALARM_T;
                        description "Specifies current netif tx output power alarm/warning status.";
                    } // END of outputPower definition.

                    leaf preFecBerSignal  {
                        type  CML_CMM_NETIF_PRE_FEC_BER_SIGNAL_ALARM_T;
                        description "Specifies the signal degrade/fail alarm  based on Pre-FEC BER.";
                    } // END of preFecBerSignal definition.

                    leaf rxLos  {
                        type  cml-data-types:CML_UINT32_T;
                        description "Specifies current netif rx loss of signal status.";
                    } // END of rxLos definition.

                    leaf rxOtu  {
                        type  CML_CMM_NETIF_RX_OTU_ALARM_T;
                        description "Specifies current netif rx optical transport unit frame status.";
                    } // END of rxOtu definition.

                    leaf rxOdu  {
                        type  CML_CMM_NETIF_RX_ODU_ALARM_T;
                        description "Specifies current netif rx optical data unit frame status.";
                    } // END of rxOdu definition.

                    leaf rxOpu  {
                        type  CML_CMM_NETIF_RX_OPU_ALARM_T;
                        description "Specifies current netif rx optical payload unit frame status.";
                    } // END of rxOpu definition.

                    leaf rxTrainingSequence  {
                        type  CML_CMM_NETIF_RX_TS_ALARM_T;
                        description "Specifies current netif rx training sequence status.";
                    } // END of rxTrainingSequence definition.

                    leaf qmarginalarm  {
                        type  cml-data-types:CML_UINT32_T;
                        description "Specifies current netif q-margin alarm status.";
                    } // END of qmarginalarm definition.

                    leaf snralarm  {
                        type  cml-data-types:CML_UINT32_T;
                        description "Specifies current netif snr alarm status.";
                    } // END of snralarm definition.

                    leaf chromaticdispersionalarm  {
                        type  cml-data-types:CML_UINT32_T;
                        description "Specifies current netif chromatic dispersion alarm status.";
                    } // END of chromaticdispersionalarm definition.

                } // END of cmmCoherentChannelFAWSTable-container definition.
                container cmmCoherentChannelMonitorTable {
                    if-feature feature-list:HAVE_COHERENT_OPTICS;
                    config false;
                    description
                        "Network Interface Monitoring Threshold Attributes runtime.";
                    leaf operInputPowerHighAlarmThreshold  {
                        type  cml-data-types:CML_FLOAT_T;
                        units "dBm";
                        description "Specifies current network interface rx input power high alarm threshold.";
                    } // END of operInputPowerHighAlarmThreshold definition.

                    leaf operInputPowerHighWarnThreshold  {
                        type  cml-data-types:CML_FLOAT_T;
                        units "dBm";
                        description "Specifies current network interface rx input power high warning threshold.";
                    } // END of operInputPowerHighWarnThreshold definition.

                    leaf operInputPowerLowWarnThreshold  {
                        type  cml-data-types:CML_FLOAT_T;
                        units "dBm";
                        description "Specifies current network interface rx input power low warning threshold.";
                    } // END of operInputPowerLowWarnThreshold definition.

                    leaf operInputPowerLowAlarmThreshold  {
                        type  cml-data-types:CML_FLOAT_T;
                        units "dBm";
                        description "Specifies current network interface rx input power low alarm threshold.";
                    } // END of operInputPowerLowAlarmThreshold definition.

                    leaf permissibleInputPowerHighAlarmThresholdMin  {
                        type  cml-data-types:CML_FLOAT_T;
                        units "dBm";
                        description "Specifies current network interface rx input power minimum permissible high alarm threshold.";
                    } // END of permissibleInputPowerHighAlarmThresholdMin definition.

                    leaf permissibleInputPowerHighAlarmThresholdMax  {
                        type  cml-data-types:CML_FLOAT_T;
                        units "dBm";
                        description "Specifies current network interface rx input power maximum permissible high alarm threshold.";
                    } // END of permissibleInputPowerHighAlarmThresholdMax definition.

                    leaf permissibleInputPowerHighWarnThresholdMin  {
                        type  cml-data-types:CML_FLOAT_T;
                        units "dBm";
                        description "Specifies current network interface rx input power minimum permissible high warning threshold.";
                    } // END of permissibleInputPowerHighWarnThresholdMin definition.

                    leaf permissibleInputPowerHighWarnThresholdMax  {
                        type  cml-data-types:CML_FLOAT_T;
                        units "dBm";
                        description "Specifies current network interface rx input power maximum permissible high warning threshold.";
                    } // END of permissibleInputPowerHighWarnThresholdMax definition.

                    leaf permissibleInputPowerLowWarnThresholdMin  {
                        type  cml-data-types:CML_FLOAT_T;
                        units "dBm";
                        description "Specifies current network interface rx input power minimum permissible low warning threshold.";
                    } // END of permissibleInputPowerLowWarnThresholdMin definition.

                    leaf permissibleInputPowerLowWarnThresholdMax  {
                        type  cml-data-types:CML_FLOAT_T;
                        units "dBm";
                        description "Specifies current network interface rx input power maximum permissible low warning threshold.";
                    } // END of permissibleInputPowerLowWarnThresholdMax definition.

                    leaf permissibleInputPowerLowAlarmThresholdMin  {
                        type  cml-data-types:CML_FLOAT_T;
                        units "dBm";
                        description "Specifies current network interface rx input power minimum permissible low alarm threshold.";
                    } // END of permissibleInputPowerLowAlarmThresholdMin definition.

                    leaf permissibleInputPowerLowAlarmThresholdMax  {
                        type  cml-data-types:CML_FLOAT_T;
                        units "dBm";
                        description "Specifies current network interface rx input power maximum permissible high alarm threshold.";
                    } // END of permissibleInputPowerLowAlarmThresholdMax definition.

                    leaf outputPowerHighAlarmThreshold  {
                        type  cml-data-types:CML_FLOAT_T;
                        units "dBm";
                        description "Specifies current network interface tx output power high alarm threshold.";
                    } // END of outputPowerHighAlarmThreshold definition.

                    leaf outputPowerHighWarnThreshold  {
                        type  cml-data-types:CML_FLOAT_T;
                        units "dBm";
                        description "Specifies current network interface tx output power high warning threshold.";
                    } // END of outputPowerHighWarnThreshold definition.

                    leaf outputPowerLowWarnThreshold  {
                        type  cml-data-types:CML_FLOAT_T;
                        units "dBm";
                        description "Specifies current network interface tx output power low warning threshold.";
                    } // END of outputPowerLowWarnThreshold definition.

                    leaf outputPowerLowAlarmThreshold  {
                        type  cml-data-types:CML_FLOAT_T;
                        units "dBm";
                        description "Specifies current network interface tx output power low alarm threshold.";
                    } // END of outputPowerLowAlarmThreshold definition.

                    leaf operPrefecberSignalFailThreshold  {
                        type  cml-data-types:CML_UINT64_T;
                        units "1e-18";
                        description "Specifies the current signal failure Pre-Fec-Ber threshold value divided by 1e-18.";
                    } // END of operPrefecberSignalFailThreshold definition.

                    leaf operPrefecberSignalDegradeThreshold  {
                        type  cml-data-types:CML_UINT64_T;
                        units "1e-18";
                        description "Specifies the current signal degrade Pre-Fec-Ber threshold value divided by 1e-18.";
                    } // END of operPrefecberSignalDegradeThreshold definition.

                    leaf operPrefecberSignalClearThreshold  {
                        type  cml-data-types:CML_UINT64_T;
                        units "1e-18";
                        description "Specifies the current signal clear Pre-Fec-Ber threshold value divided by 1e-18.";
                    } // END of operPrefecberSignalClearThreshold definition.

                    leaf opercurrentQMarginThreshold  {
                        type  cml-data-types:CML_FLOAT_T;
                        units "dB";
                        description "Specifies Network RX Q margin threshold value.";
                    } // END of opercurrentQMarginThreshold definition.

                    leaf operOSNRThreshold  {
                        type  cml-data-types:CML_FLOAT_T;
                        units "dB";
                        description "Specifies the optical signal noise ratio threshold value.";
                    } // END of operOSNRThreshold definition.

                    leaf opercurrentChromaticDispersionThreshold  {
                        type  cml-data-types:CML_INT32_T;
                        units "ps/nm";
                        description "Specifies the current Chromatic Dispersion threshold value.";
                    } // END of opercurrentChromaticDispersionThreshold definition.

                } // END of cmmCoherentChannelMonitorTable-container definition.
                container cmmCoherentChannelEventCountTable {
                    if-feature feature-list:HAVE_COHERENT_OPTICS;
                    config false;
                    description
                        "Network Interface event count Attributes.";
                    leaf operInputPowerHighAlarmThresholdEC  {
                        type  cml-data-types:CML_UINT32_T;
                        description "Specifies input power high alarm threshold event count value.";
                    } // END of operInputPowerHighAlarmThresholdEC definition.

                    leaf operInputPowerHighWarnThresholdEC  {
                        type  cml-data-types:CML_UINT32_T;
                        description "Specifies input power high warning threshold event count value.";
                    } // END of operInputPowerHighWarnThresholdEC definition.

                    leaf operInputPowerLowWarnThresholdEC  {
                        type  cml-data-types:CML_UINT32_T;
                        description "Specifies input power low warning threshold event count value.";
                    } // END of operInputPowerLowWarnThresholdEC definition.

                    leaf operInputPowerLowAlarmThresholdEC  {
                        type  cml-data-types:CML_UINT32_T;
                        description "Specifies input power low alarm threshold event count value.";
                    } // END of operInputPowerLowAlarmThresholdEC definition.

                    leaf outputPowerHighAlarmThresholdEC  {
                        type  cml-data-types:CML_UINT32_T;
                        description "Specifies output power high alarm threshold event count value.";
                    } // END of outputPowerHighAlarmThresholdEC definition.

                    leaf outputPowerHighWarnThresholdEC  {
                        type  cml-data-types:CML_UINT32_T;
                        description "Specifies output power high warning threshold event count value.";
                    } // END of outputPowerHighWarnThresholdEC definition.

                    leaf outputPowerLowWarnThresholdEC  {
                        type  cml-data-types:CML_UINT32_T;
                        description "Specifies output power low warning threshold event count value.";
                    } // END of outputPowerLowWarnThresholdEC definition.

                    leaf outputPowerLowAlarmThresholdEC  {
                        type  cml-data-types:CML_UINT32_T;
                        description "Specifies output power low alarm threshold event count value.";
                    } // END of outputPowerLowAlarmThresholdEC definition.

                    leaf operPrefecberSignalFailThresholdEC  {
                        type  cml-data-types:CML_UINT32_T;
                        description "Specifies pre fec ber signal fail threshold event count value.";
                    } // END of operPrefecberSignalFailThresholdEC definition.

                    leaf operPrefecberSignalDegradeThresholdEC  {
                        type  cml-data-types:CML_UINT32_T;
                        description "Specifies pre fec ber signal degrade threshold event count value.";
                    } // END of operPrefecberSignalDegradeThresholdEC definition.

                    leaf qmarginThresholdEC  {
                        type  cml-data-types:CML_UINT32_T;
                        description "Specifies Q margin threshold event count value.";
                    } // END of qmarginThresholdEC definition.

                    leaf osnrThresholdEC  {
                        type  cml-data-types:CML_UINT32_T;
                        description "Specifies osnr threshold event count value.";
                    } // END of osnrThresholdEC definition.

                    leaf chromaticDispersionThresholdEC  {
                        type  cml-data-types:CML_UINT32_T;
                        description "Specifies chromatic disthreshold persion event count value.";
                    } // END of chromaticDispersionThresholdEC definition.

                    leaf rxLossEC  {
                        type  cml-data-types:CML_UINT32_T;
                        description "Specifies rx loss event count value.";
                    } // END of rxLossEC definition.

                } // END of cmmCoherentChannelEventCountTable-container definition.
                container cmmCoherentChannelErrorCountTable {
                    config false;
                    description
                        "A table to store all the Network Interface counters.";
                    leaf fecUncorrectedBlockCount  {
                        type  cml-data-types:CML_UINT64_T;
                        description "Specifies the Uncorrected Fec Block Count value.";
                    } // END of fecUncorrectedBlockCount definition.

                    leaf otnSmBip8ErrorCount  {
                        type  cml-data-types:CML_UINT64_T;
                        description "Specifies the OTN Section Monitoring BIP-8 Count Value .";
                    } // END of otnSmBip8ErrorCount definition.

                } // END of cmmCoherentChannelErrorCountTable-container definition.
            } // End of cmmCoherentChannelStateTable-list

            list cmmCoherentHostStateTable {
                if-feature feature-list:HAVE_COHERENT_OPTICS;
                key "hostIndex";
                config false;
                description
                    "Host Interface runtime";
                leaf hostIndex  {
                    type  cml-data-types:CML_UINT8_T;
                    description "Index of host interface in a coherent optical module.";
                } // END of hostIndex definition.

                leaf operHostFecType  {
                    type  CML_CMM_OPTICAL_FEC_T;
                    description "Specifies Fec type for Host Interface of Coherent Optics.";
                } // END of operHostFecType definition.

                leaf operHostloopBackType  {
                    type  CML_CMM_OPTICAL_LOOPBACK_T;
                    description "Specifies LoopBack Type for Host Interface of Coherent Optics.";
                } // END of operHostloopBackType definition.

                leaf hostCurrentPreFecBer  {
                    type  cml-data-types:CML_UINT64_T;
                    units "1e-18";
                    description "Specifies the Host Interface current PRE FEC Bit Error Rate per 1e-18 BER Period.";
                } // END of hostCurrentPreFecBer definition.

                container cmmCoherentHostFAWSTable {
                    if-feature feature-list:HAVE_COHERENT_OPTICS;
                    config false;
                    description
                        "A table to store all the Host Interface faults/alarms/warning/status.";
                    leaf ingressPCS  {
                        type  CML_CMM_HOSTIF_PCS_ALARM_T;
                        description "Specifies current Host interface Ingress PhysicalCodingSublayer Status.";
                    } // END of ingressPCS definition.

                    leaf egressPCS  {
                        type  CML_CMM_HOSTIF_PCS_ALARM_T;
                        description "Specifies current Host interface Egress PhysicalCodingSublayer Status.";
                    } // END of egressPCS definition.

                    leaf hostiffaultStatus  {
                        type  CML_CMM_HOSTIF_FAULT_STATUS_ALARM_T;
                        description "Specifies current Host interface Fault Status.";
                    } // END of hostiffaultStatus definition.

                } // END of cmmCoherentHostFAWSTable-container definition.
                container cmmCoherentHostEventCountTable {
                    if-feature feature-list:HAVE_COHERENT_OPTICS;
                    config false;
                    description
                        "Host interface event count attributes.";
                    leaf ingressPCSLossofSignalEC  {
                        type  cml-data-types:CML_UINT32_T;
                        description "Specifies ingress PCS loss of signal event count value.";
                    } // END of ingressPCSLossofSignalEC definition.

                    leaf ingressPCSLossofFrameEC  {
                        type  cml-data-types:CML_UINT32_T;
                        description "Specifies ingress PCS loss of frame event count value.";
                    } // END of ingressPCSLossofFrameEC definition.

                    leaf ingressPCSIllegalAlignmentMarkerEC  {
                        type  cml-data-types:CML_UINT32_T;
                        description "Specifies ingress PCS illegal alignment marker event count value.";
                    } // END of ingressPCSIllegalAlignmentMarkerEC definition.

                    leaf ingressPCSRemoteFaultEC  {
                        type  cml-data-types:CML_UINT32_T;
                        description "Specifies ingress PCS remote fault event count value.";
                    } // END of ingressPCSRemoteFaultEC definition.

                    leaf ingressPCSLocalFaultEC  {
                        type  cml-data-types:CML_UINT32_T;
                        description "Specifies ingress PCS local fault event count value.";
                    } // END of ingressPCSLocalFaultEC definition.

                    leaf ingressPCSHighBEREC  {
                        type  cml-data-types:CML_UINT32_T;
                        description "Specifies ingress PCS high BER event count value.";
                    } // END of ingressPCSHighBEREC definition.

                    leaf ingressPCSBIPErrorEC  {
                        type  cml-data-types:CML_UINT32_T;
                        description "Specifies ingress PCS BIP error event count value.";
                    } // END of ingressPCSBIPErrorEC definition.

                    leaf ingressPCSDeskewErrorEC  {
                        type  cml-data-types:CML_UINT32_T;
                        description "Specifies ingress PCS deskew error event count value.";
                    } // END of ingressPCSDeskewErrorEC definition.

                    leaf ingressPCSLossofBlocklockEC  {
                        type  cml-data-types:CML_UINT32_T;
                        description "Specifies ingress PCS loss of block lock event count value.";
                    } // END of ingressPCSLossofBlocklockEC definition.

                    leaf ingressPCSLossofAlignmentMarkerLockEC  {
                        type  cml-data-types:CML_UINT32_T;
                        description "Specifies ingress PCS loss of alignment marker event count value.";
                    } // END of ingressPCSLossofAlignmentMarkerLockEC definition.

                    leaf ingressPCSLossofAlignmentEC  {
                        type  cml-data-types:CML_UINT32_T;
                        description "Specifies ingress PCS loss of alignment lock event count value.";
                    } // END of ingressPCSLossofAlignmentEC definition.

                    leaf ingressPCSOPUClientSignalFailEC  {
                        type  cml-data-types:CML_UINT32_T;
                        description "Specifies ingress PCS OPU client signal fail event count value.";
                    } // END of ingressPCSOPUClientSignalFailEC definition.

                    leaf ingressPCSErrorBlocksDetectedEC  {
                        type  cml-data-types:CML_UINT32_T;
                        description "Specifies ingress PCS error blocks detected event count value.";
                    } // END of ingressPCSErrorBlocksDetectedEC definition.

                    leaf egressPCSLossofSignalEC  {
                        type  cml-data-types:CML_UINT32_T;
                        description "Specifies egress PCS loss of signal event count value.";
                    } // END of egressPCSLossofSignalEC definition.

                    leaf egressPCSLossofFrameEC  {
                        type  cml-data-types:CML_UINT32_T;
                        description "Specifies engress PCS loss of frame event count value.";
                    } // END of egressPCSLossofFrameEC definition.

                    leaf egressPCSIllegalAlignmentMarkerEC  {
                        type  cml-data-types:CML_UINT32_T;
                        description "Specifies egress PCS illegal alignment event count value.";
                    } // END of egressPCSIllegalAlignmentMarkerEC definition.

                    leaf egressPCSRemoteFaultEC  {
                        type  cml-data-types:CML_UINT32_T;
                        description "Specifies egress PCS remote fault event count value.";
                    } // END of egressPCSRemoteFaultEC definition.

                    leaf egressPCSLocalFaultEC  {
                        type  cml-data-types:CML_UINT32_T;
                        description "Specifies egress PCS local fault event count value.";
                    } // END of egressPCSLocalFaultEC definition.

                    leaf egressPCSHighBEREC  {
                        type  cml-data-types:CML_UINT32_T;
                        description "Specifies egress PCS high BER event count value.";
                    } // END of egressPCSHighBEREC definition.

                    leaf egressPCSBIPErrorEC  {
                        type  cml-data-types:CML_UINT32_T;
                        description "Specifies egress PCS BIP error event count value.";
                    } // END of egressPCSBIPErrorEC definition.

                    leaf egressPCSDeskewErrorEC  {
                        type  cml-data-types:CML_UINT32_T;
                        description "Specifies egress PCS deskew error event count value.";
                    } // END of egressPCSDeskewErrorEC definition.

                    leaf egressPCSLossofBlocklockEC  {
                        type  cml-data-types:CML_UINT32_T;
                        description "Specifies egress PCS loss of block lock event count value.";
                    } // END of egressPCSLossofBlocklockEC definition.

                    leaf egressPCSLossofAlignmentMarkerLockEC  {
                        type  cml-data-types:CML_UINT32_T;
                        description "Specifies egress PCS loss of alignment marker lock event count value.";
                    } // END of egressPCSLossofAlignmentMarkerLockEC definition.

                    leaf egressPCSLossofAlignmentEC  {
                        type  cml-data-types:CML_UINT32_T;
                        description "Specifies egress PCS loss of alignment event count value.";
                    } // END of egressPCSLossofAlignmentEC definition.

                    leaf egressPCSOPUClientSignalFailEC  {
                        type  cml-data-types:CML_UINT32_T;
                        description "Specifies egress PCS OPU client signal fail event count value.";
                    } // END of egressPCSOPUClientSignalFailEC definition.

                    leaf egressPCSErrorBlocksDetectedEC  {
                        type  cml-data-types:CML_UINT32_T;
                        description "Specifies egress PCS error blocks detected event count value.";
                    } // END of egressPCSErrorBlocksDetectedEC definition.

                    leaf txHostLolL0EC  {
                        type  cml-data-types:CML_UINT32_T;
                        description "Specifies tx host loss of lock lane 0 event count value.";
                    } // END of txHostLolL0EC definition.

                    leaf txHostLolL1EC  {
                        type  cml-data-types:CML_UINT32_T;
                        description "Specifies tx host loss of lock lane 1 event count value.";
                    } // END of txHostLolL1EC definition.

                    leaf txHostLolL2EC  {
                        type  cml-data-types:CML_UINT32_T;
                        description "Specifies tx host loss of lock lane 2 event count value.";
                    } // END of txHostLolL2EC definition.

                    leaf txHostLolL3EC  {
                        type  cml-data-types:CML_UINT32_T;
                        description "Specifies tx host loss of lock lane 3 event count value.";
                    } // END of txHostLolL3EC definition.

                    leaf ingressAPSMsgRcvdEC  {
                        type  cml-data-types:CML_UINT32_T;
                        description "Specifies ingress APS message received event count value.";
                    } // END of ingressAPSMsgRcvdEC definition.

                    leaf deskewLockFaultEC  {
                        type  cml-data-types:CML_UINT32_T;
                        description "Specifies deskew lock fault event count value.";
                    } // END of deskewLockFaultEC definition.

                    leaf outofAlignEC  {
                        type  cml-data-types:CML_UINT32_T;
                        description "Specifies out of alignment event count value.";
                    } // END of outofAlignEC definition.

                    leaf lossofAlignEC  {
                        type  cml-data-types:CML_UINT32_T;
                        description "Specifies loss of alignment event count value.";
                    } // END of lossofAlignEC definition.

                } // END of cmmCoherentHostEventCountTable-container definition.
                container cmmCoherentHostErrorCountTable {
                    config false;
                    description
                        "A table to store all the Host Interface counters.";
                    leaf hostFecUncorrectedBlockCount  {
                        type  cml-data-types:CML_UINT64_T;
                        description "Specifies the Host Interface Uncorrected Fec Block count value.";
                    } // END of hostFecUncorrectedBlockCount definition.

                } // END of cmmCoherentHostErrorCountTable-container definition.
            } // End of cmmCoherentHostStateTable-list
            container cmmCoherentModuleFAWSTable {
                if-feature feature-list:HAVE_COHERENT_OPTICS;
                config false;
                description
                    "A table to store all the Module faults/alarms/warning/status .";
                leaf temperature  {
                    type  CML_CMM_MOD_TEMP_ALARM_T;
                    description "Specifies current module temperature alarm/warning status, according to the threshold value.";
                } // END of temperature definition.

                leaf voltage  {
                    type  CML_CMM_MOD_VOLT_ALARM_T;
                    description "Specifies current module voltage alarm/warning status, according to the threshold value.";
                } // END of voltage definition.

                leaf generalStatus  {
                    type  CML_CMM_MOD_GENERAL_STATUS_ALARM_T;
                    description "Specifies the current module general status, if any fault/status is present.";
                } // END of generalStatus definition.

                leaf modulefaultStatus  {
                    type  CML_CMM_MOD_FAULT_STATUS_ALARM_T;
                    description "Specifies the current module fault status, if any fault/status is present.";
                } // END of modulefaultStatus definition.

            } // END of cmmCoherentModuleFAWSTable-container definition.
            container cmmCoherentModuleMonitorTable {
                if-feature feature-list:HAVE_COHERENT_OPTICS;
                config false;
                description
                    "A table to store all the monitoring threshold attributes.";
                leaf tempHighAlarmThreshold  {
                    type  cml-data-types:CML_FLOAT_T;
                    units "C";
                    description "Specifies current module temperature high alarm  threshold value.";
                } // END of tempHighAlarmThreshold definition.

                leaf tempHighWarnThreshold  {
                    type  cml-data-types:CML_FLOAT_T;
                    units "C";
                    description "Specifies current module temperature high warning threshold value.";
                } // END of tempHighWarnThreshold definition.

                leaf tempLowWarnThreshold  {
                    type  cml-data-types:CML_FLOAT_T;
                    units "C";
                    description "Specifies current module temperature low warning threshold value.";
                } // END of tempLowWarnThreshold definition.

                leaf tempLowAlarmThreshold  {
                    type  cml-data-types:CML_FLOAT_T;
                    units "C";
                    description "Specifies current module temperature low alaram threshold value.";
                } // END of tempLowAlarmThreshold definition.

                leaf voltHighAlarmThreshold  {
                    type  cml-data-types:CML_FLOAT_PRECISION_3_T;
                    units "V";
                    description "Specifies current module voltage high alarm threshold value.";
                } // END of voltHighAlarmThreshold definition.

                leaf voltHighWarnThreshold  {
                    type  cml-data-types:CML_FLOAT_PRECISION_3_T;
                    units "V";
                    description "Specifies current module voltage high warning threshold value.";
                } // END of voltHighWarnThreshold definition.

                leaf voltLowWarnThreshold  {
                    type  cml-data-types:CML_FLOAT_PRECISION_3_T;
                    units "V";
                    description "Specifies current module voltage low warning threshold value.";
                } // END of voltLowWarnThreshold definition.

                leaf voltLowAlarmThreshold  {
                    type  cml-data-types:CML_FLOAT_PRECISION_3_T;
                    units "V";
                    description "Specifies current module volatge low alarm threshold value.";
                } // END of voltLowAlarmThreshold definition.

            } // END of cmmCoherentModuleMonitorTable-container definition.
            container cmmCoherentModuleEventCountTable {
                if-feature feature-list:HAVE_COHERENT_OPTICS;
                config false;
                description
                    "A table to store all events count attributes.";
                leaf hwInterlockEC  {
                    type  cml-data-types:CML_UINT32_T;
                    description "Specifies hardware interlock event count value.";
                } // END of hwInterlockEC definition.

                leaf txLossofSignalFunctionalityEC  {
                    type  cml-data-types:CML_UINT32_T;
                    description "Specifies tx loss of signal functionality event count value.";
                } // END of txLossofSignalFunctionalityEC definition.

                leaf rxLossofSignalEC  {
                    type  cml-data-types:CML_UINT32_T;
                    description "Specifies rx loss of signal event count value.";
                } // END of rxLossofSignalEC definition.

                leaf rxNetworkLossofLockEC  {
                    type  cml-data-types:CML_UINT32_T;
                    description "Specifies rx network loss of lock event count value.";
                } // END of rxNetworkLossofLockEC definition.

                leaf txHostLossofLockEC  {
                    type  cml-data-types:CML_UINT32_T;
                    description "Specifies tx host loss of lock event count value.";
                } // END of txHostLossofLockEC definition.

                leaf hostLaneOutofAlignmentEC  {
                    type  cml-data-types:CML_UINT32_T;
                    description "Specifies host lane out of alignment event count value.";
                } // END of hostLaneOutofAlignmentEC definition.

                leaf overTemperatureFaultEC  {
                    type  cml-data-types:CML_UINT32_T;
                    description "Specifies over temperature fault event count value.";
                } // END of overTemperatureFaultEC definition.

                leaf hardwareFaultEC  {
                    type  cml-data-types:CML_UINT32_T;
                    description "Specifies harware fault event count value.";
                } // END of hardwareFaultEC definition.

                leaf initializationFaultEC  {
                    type  cml-data-types:CML_UINT32_T;
                    description "Specifies initialization fault event count value.";
                } // END of initializationFaultEC definition.

                leaf powersupplyFaultEC  {
                    type  cml-data-types:CML_UINT32_T;
                    description "Specifies power supply fault event count value.";
                } // END of powersupplyFaultEC definition.

                leaf checksumFaultEC  {
                    type  cml-data-types:CML_UINT32_T;
                    description "Specifies checksum fault event count value.";
                } // END of checksumFaultEC definition.

                leaf temperatureLowAlarmEC  {
                    type  cml-data-types:CML_UINT32_T;
                    description "Specifies temperature low alarm event count value.";
                } // END of temperatureLowAlarmEC definition.

                leaf temperatureLowWarningEC  {
                    type  cml-data-types:CML_UINT32_T;
                    description "Specifies temperature low warning event count value.";
                } // END of temperatureLowWarningEC definition.

                leaf temperatureHighWarningEC  {
                    type  cml-data-types:CML_UINT32_T;
                    description "Specifies temperature high warning event count value.";
                } // END of temperatureHighWarningEC definition.

                leaf temperatureHighAlarmEC  {
                    type  cml-data-types:CML_UINT32_T;
                    description "Specifies temperature high alarm event count value.";
                } // END of temperatureHighAlarmEC definition.

                leaf powerLowAlarmEC  {
                    type  cml-data-types:CML_UINT32_T;
                    description "Specifies power low alarm event count value.";
                } // END of powerLowAlarmEC definition.

                leaf powerLowWarningEC  {
                    type  cml-data-types:CML_UINT32_T;
                    description "Specifies power low warning event count value.";
                } // END of powerLowWarningEC definition.

                leaf powerHighWarningEC  {
                    type  cml-data-types:CML_UINT32_T;
                    description "Specifies power high warning event count value.";
                } // END of powerHighWarningEC definition.

                leaf powerHighAlarmEC  {
                    type  cml-data-types:CML_UINT32_T;
                    description "Specifies power high alarm event count value.";
                } // END of powerHighAlarmEC definition.

            } // END of cmmCoherentModuleEventCountTable-container definition.
        } // End of cmmCoherentStateTable-list
    } // END of cmmCoherentStateTable-grouping definition.


    grouping cmmStackUnitTable-grouping {
    description
        "list of stack units configured in the chassis";
        list cmmStackUnitTable {
            key "cmmStackUnitIndex";
            config false;
            description
                "list of stack units configured in the chassis";
            leaf cmmStackUnitIndex  {
                type  cml-data-types:CML_INT32_T;
                description "The unique index for this entry.Refer to the object cmmStackUnitIndexNext.";
            } // END of cmmStackUnitIndex definition.

            leaf cmmStackUnitModelName  {
                type  cml-data-types:CML_STRING_T;
                description "The plugged-in model ID for this unit. Blank indicates unavailable.";
            } // END of cmmStackUnitModelName definition.

            leaf cmmStackUnitSerialNumber  {
                type  cml-data-types:CML_STRING_T;
                description "The unit's serial number. Blank indicates unavailable.";
            } // END of cmmStackUnitSerialNumber definition.

            leaf cmmStackUnitUpTime  {
                type  cml-data-types:CML_TIMETICKS_T;
                description "The system up time of the unit.";
            } // END of cmmStackUnitUpTime definition.

            leaf cmmStackUnitMfgDate  {
                type  cml-data-types:CML_DATE_TIME_T;
                description "The date the unit is manufactured. Blank indicates unavailable.";
            } // END of cmmStackUnitMfgDate definition.

            leaf cmmStackUnitMacAddress  {
                type  cml-data-types:CML_MAC_ADDRESS_T;
                description "A 6-octet MAC Address assigned to this unit.";
            } // END of cmmStackUnitMacAddress definition.

            leaf cmmStackUnitPartNum  {
                type  cml-data-types:CML_STRING_T;
                description "The unit part number. Blank indicates unavailable";
            } // END of cmmStackUnitPartNum definition.

            leaf cmmStackLabelRevision  {
                type  cml-data-types:CML_STRING_T;
                description "The unit's label Revesion. Blank indicates unavailable";
            } // END of cmmStackLabelRevision definition.

            leaf cmmStackUnitCountryCode  {
                type  cml-data-types:CML_STRING_T;
                description "The unit manufacturer's country code";
            } // END of cmmStackUnitCountryCode definition.

            leaf cmmStackUnitNumFanTrays  {
                type  cml-data-types:CML_INT32_T;
                description "The number of fan trays on the unit.. '-100001' indicates unavailable.";
            } // END of cmmStackUnitNumFanTrays definition.

            leaf cmmStackUnitNumPowerSupplies  {
                type  cml-data-types:CML_INT32_T;
                description "The number of power supplies available to the unit.. '-100001' indicates unavailable.";
            } // END of cmmStackUnitNumPowerSupplies definition.

            leaf cmmStackUnitNumPluggableModules  {
                type  cml-data-types:CML_INT32_T;
                description "The number of pluggable modules in the stack. '-100001' indicates unavailable.";
            } // END of cmmStackUnitNumPluggableModules definition.

            leaf cmmStackUnitNumFastEtherPorts  {
                type  cml-data-types:CML_INT32_T;
                description "The number of 100M Ethernet/802.3 interfaces in this unit. '-100001' indicates unavailable.";
            } // END of cmmStackUnitNumFastEtherPorts definition.

            leaf cmmStackUnitNumGigEtherPorts  {
                type  cml-data-types:CML_INT32_T;
                description "The number of 1G Ethernet/802.3 interfaces in this unit. '-100001' indicates unavailable.";
            } // END of cmmStackUnitNumGigEtherPorts definition.

            leaf cmmStackUnitNum10GigEtherPorts  {
                type  cml-data-types:CML_INT32_T;
                description "The number of 10G Ethernet/802.3 interfaces in this unit. '-100001' indicates unavailable.";
            } // END of cmmStackUnitNum10GigEtherPorts definition.

            leaf cmmStackUnitNum25GigEtherPorts  {
                type  cml-data-types:CML_INT32_T;
                description "The number of 25G Ethernet/802.3 interfaces in this unit. '-100001' indicates unavailable.";
            } // END of cmmStackUnitNum25GigEtherPorts definition.

            leaf cmmStackUnitNum40GigEtherPorts  {
                type  cml-data-types:CML_INT32_T;
                description "The number of 40G Ethernet/802.3 interfaces in this unit. '-100001' indicates unavailable.";
            } // END of cmmStackUnitNum40GigEtherPorts definition.

            leaf cmmStackUnitNum50GigEtherPorts  {
                type  cml-data-types:CML_INT32_T;
                description "The number of 50G Ethernet/802.3 interfaces in this unit. '-100001' indicates unavailable.";
            } // END of cmmStackUnitNum50GigEtherPorts definition.

            leaf cmmStackUnitNum100GigEtherPorts  {
                type  cml-data-types:CML_INT32_T;
                description "The number of 100G Ethernet/802.3 interfaces in this unit. '-100001' indicates unavailable.";
            } // END of cmmStackUnitNum100GigEtherPorts definition.

            leaf cmmStackUnitServiceTag  {
                type  cml-data-types:CML_STRING_T;
                description "The unit's service tag. Blank indicates unavailable.";
            } // END of cmmStackUnitServiceTag definition.

            leaf cmmStackPlatformName  {
                type  cml-data-types:CML_STRING_T;
                description "The unit's Platform Name. Blank indicates unavailable.";
            } // END of cmmStackPlatformName definition.

            leaf cmmStackOnieVersion  {
                type  cml-data-types:CML_STRING_T;
                description "The unit's ONIE Version. Blank indicates unavailable.";
            } // END of cmmStackOnieVersion definition.

            leaf cmmStackMfg  {
                type  cml-data-types:CML_STRING_T;
                description "The unit's Manufacturer Name. Blank indicates unavailable.";
            } // END of cmmStackMfg definition.

            leaf cmmStackVendorName  {
                type  cml-data-types:CML_STRING_T;
                description "The unit's Vendor Name. Blank indicates unavailable.";
            } // END of cmmStackVendorName definition.

            leaf cmmStackDiagVersion  {
                type  cml-data-types:CML_STRING_T;
                description "The unit's Diagnostic Version. Blank indicates unavailable.";
            } // END of cmmStackDiagVersion definition.

            leaf cmmStackCrc32  {
                type  cml-data-types:CML_STRING_T;
                description "The unit's Cyclic Redundancy Check 32 Bit value.";
            } // END of cmmStackCrc32 definition.

            leaf cmmStackUnitSwitchChipRev  {
                type  cml-data-types:CML_STRING_T;
                description "The Unit's Switch Chip Revision. Blank indicates unavailable";
            } // END of cmmStackUnitSwitchChipRev definition.

            leaf cmmStackFanBoardId  {
                type  cml-data-types:CML_STRING_T;
                description "The Unit's Fan Board Id. Blank indicates unavailable.";
            } // END of cmmStackFanBoardId definition.

            leaf cmmStackSupportedLabelRevision  {
                type  cml-data-types:CML_STRING_T;
                description "The unit's supported label Revesion. Blank indicates unavailable";
            } // END of cmmStackSupportedLabelRevision definition.

            leaf cmmStackUnitSupportedSwitchChipRev  {
                type  cml-data-types:CML_STRING_T;
                description "The Unit's Switch Supported Chip Revision. Blank indicates unavailable";
            } // END of cmmStackUnitSupportedSwitchChipRev definition.


            list cmmTransEEPROMTable {
                key "cmmTransIndex";
                config false;
                description
                    "list of transceiver entries EEPROM information in the chassis";
                leaf cmmTransIndex  {
                    type  cml-data-types:CML_UINT32_T;
                    description "A unique index for each slot within the unit.";
                } // END of cmmTransIndex definition.

                leaf cmmTransType  {
                    type  cml-data-types:CML_CMM_TRANS_TYPE_T;
                    description "Type of the transceiver SFP/QSFP.";
                } // END of cmmTransType definition.

                leaf cmmTransNoOfChannels  {
                    type  cml-data-types:CML_INT32_T;
                    description "Number of channels available for this transceiver. '-100001' indicates unavailable.";
                } // END of cmmTransNoOfChannels definition.

                leaf cmmTransidentifier  {
                    type  cml-data-types:CML_CMM_TRANS_IDENTIFIER_T;
                    description "The Type of transceiver present eg:SFP/SFP+/SFP28/QSFP/QSFP+/QSFP28.";
                } // END of cmmTransidentifier definition.

                leaf cmmTransSFPextendedidentifier  {
                    type  cml-data-types:CML_CMM_TRANS_SFP_EXTENDED_IDENTIFIER_T;
                    description "Extended identifier of SFP transceiver for additional information.";
                } // END of cmmTransSFPextendedidentifier definition.

                leaf cmmTransQSFPextendedidentifier  {
                    type  cml-data-types:CML_CMM_QSFP_EXTENDED_IDENTIFIER_T;
                    description "Extended identifier of QSFP transceiver for additional information. null indicates unavailable.";
                } // END of cmmTransQSFPextendedidentifier definition.

                leaf cmmTransconnectortype  {
                    type  cml-data-types:CML_CMM_TRANS_CONNECTOR_TYPE_T;
                    description "Connector type for the transceiver.";
                } // END of cmmTransconnectortype definition.

                leaf cmmTransEthCompliance  {
                    type  cml-data-types:CML_CMM_TRANS_ETH_COMPLIANCE_T;
                    description "Values of Ethernet Compliance codes.";
                } // END of cmmTransEthCompliance definition.

                leaf cmmTransExtEthCompliance  {
                    type  cml-data-types:CML_CMM_TRANS_EXT_ETH_COMPLIANCE_T;
                    description "Bitmap of Extended Ethernet Compliance codes. null indicates unavailable.";
                } // END of cmmTransExtEthCompliance definition.

                leaf cmmTransSonetCompliance  {
                    type  cml-data-types:CML_CMM_TRANS_SONET_COMPLIANCE_T;
                    description "Sonet Compliance codes of transceiver. null indicates unavailable.";
                } // END of cmmTransSonetCompliance definition.

                leaf cmmTransFiberChnlLinkLen  {
                    type  cml-data-types:CML_CMM_TRANS_FIBER_CHANNEL_LINKLEN_T;
                    description "Fibre Channel Link Length. null indicates unavailable.";
                } // END of cmmTransFiberChnlLinkLen definition.

                leaf cmmTransFiberChnlTransTech  {
                    type  cml-data-types:CML_CMM_TRANS_FIBER_CHANNEL_TRANSMITTECH_T;
                    description "Fibre Channel Transmitter Technology. null indicates unavailable.";
                } // END of cmmTransFiberChnlTransTech definition.

                leaf cmmTransFiberChnlTransMedia  {
                    type  cml-data-types:CML_CMM_TRANS_FIBER_CHANNEL_TRANSMITMEDIA_T;
                    description "Fibre Channel Transmission Media. null indicates unavailable.";
                } // END of cmmTransFiberChnlTransMedia definition.

                leaf cmmTransSFPFiberChnlSpeed  {
                    type  cml-data-types:CML_CMM_TRANS_FIBER_CHANNEL_SPEED_T;
                    description "SFP Fibre Channel Speed. null indicates unavailable.";
                } // END of cmmTransSFPFiberChnlSpeed definition.

                leaf cmmTransQSFPFiberChnlSpeed  {
                    type  cml-data-types:CML_CMM_TRANS_FIBER_CHANNEL_SPEED_T;
                    description "QSFP Fibre Channel Speed. null indicates unavailable.";
                } // END of cmmTransQSFPFiberChnlSpeed definition.

                leaf cmmTransSFPInfiniBandCompliance  {
                    type  cml-data-types:CML_CMM_TRANS_SFP_INIFINBAND_COMPLIANCE_T;
                    description "SFP Infiniband Compliance";
                } // END of cmmTransSFPInfiniBandCompliance definition.

                leaf cmmTransSFPEsconCompliance  {
                    type  cml-data-types:CML_CMM_TRANS_SFP_ESCON_COMPLIANCE_T;
                    description "SFP Enterprise Systems Connection compliance.";
                } // END of cmmTransSFPEsconCompliance definition.

                leaf cmmTransSfpPlusCableTech  {
                    type  cml-data-types:CML_CMM_TRANS_SFP_PLUS_CABLE_TECH_T;
                    description "SFP+ Cable Technology";
                } // END of cmmTransSfpPlusCableTech definition.

                leaf cmmTransEncoding  {
                    type  cml-data-types:CML_CMM_TRANS_ENCODING_T;
                    description "Code for high speed serial encoding algorithm";
                } // END of cmmTransEncoding definition.

                leaf cmmTransLengthKmtrs  {
                    type  cml-data-types:CML_INT32_T;
                    units "Km";
                    description "Link length supported for single mode fiber, units of km. '-100001' indicates unavailable.";
                } // END of cmmTransLengthKmtrs definition.

                leaf cmmTransLengthMtrs  {
                    type  cml-data-types:CML_INT32_T;
                    units "100m";
                    description "Link length supported for single mode fiber, units of 100 m. '-100001' indicates unavailable.";
                } // END of cmmTransLengthMtrs definition.

                leaf cmmTransLengthOM1  {
                    type  cml-data-types:CML_INT32_T;
                    units "10m";
                    description "Link length supported for 62.5 um OM1 fiber, units of 10 m. '-100001' indicates unavailable.";
                } // END of cmmTransLengthOM1 definition.

                leaf cmmTransLengthOM2  {
                    type  cml-data-types:CML_INT32_T;
                    units "10m";
                    description "Link length supported for 50 um OM2 fiber, units of 10 m. '-100001' indicates unavailable";
                } // END of cmmTransLengthOM2 definition.

                leaf cmmTransLengthOM3  {
                    type  cml-data-types:CML_INT32_T;
                    units "10m";
                    description "Link length supported for 50 um OM3 fiber, units of 10 m. '-100001' indicates unavailable";
                } // END of cmmTransLengthOM3 definition.

                leaf cmmTransLengthOM4  {
                    type  cml-data-types:CML_INT32_T;
                    units "10m";
                    description "Link length supported for 50 um OM4 fiber, units of 10 m. '-100001' indicates unavailable";
                } // END of cmmTransLengthOM4 definition.

                leaf cmmTransVendorName  {
                    type  cml-data-types:CML_STRING_T;
                    description "Transceiver vendor name. Blank indicates unavailable.";
                } // END of cmmTransVendorName definition.

                leaf cmmTransVendorOUI  {
                    type  cml-data-types:CML_LINE_T;
                    description "SFP vendor IEEE company ID. Blank indicates unavailable.";
                } // END of cmmTransVendorOUI definition.

                leaf cmmTransVendorPartNumber  {
                    type  cml-data-types:CML_LINE_T;
                    description "Part number provided by Tranceiver vendor. Blank indicates unavailable.";
                } // END of cmmTransVendorPartNumber definition.

                leaf cmmTransVendorRevision  {
                    type  cml-data-types:CML_STRING_T;
                    description "Revision level for part number provided by vendor. Blank indicates unavailable.";
                } // END of cmmTransVendorRevision definition.

                leaf cmmTransCheckCode  {
                    type  cml-data-types:CML_STRING_T;
                    description "Check code for Base ID Fields. Blank indicates unavailable.";
                } // END of cmmTransCheckCode definition.

                leaf cmmTransCheckCodeExtended  {
                    type  cml-data-types:CML_STRING_T;
                    description "Check code for the Extended ID Fields. Blank indicates unavailable.";
                } // END of cmmTransCheckCodeExtended definition.

                leaf cmmTransNominalBitRate  {
                    type  cml-data-types:CML_INT32_T;
                    units "100MBd";
                    description "Nominal signalling rate, units of 100MBd. '-100001' indicates unavailable.";
                } // END of cmmTransNominalBitRate definition.

                leaf cmmTransBitRateMax  {
                    type  cml-data-types:CML_INT32_T;
                    description "Upper bit rate margin, units of 1% above the Nominal Bit Rate. '-100001' indicates unavailable. '-100002' indicates not-applicable.";
                } // END of cmmTransBitRateMax definition.

                leaf cmmTransBitRateMin  {
                    type  cml-data-types:CML_INT32_T;
                    description "Lower bit rate margin, units of 1% below the Nominal Bit Rate. '-100001' indicates unavailable. '-100002' indicates not-applicable.";
                } // END of cmmTransBitRateMin definition.

                leaf cmmTransVendorSerialNumber  {
                    type  cml-data-types:CML_STRING_T;
                    description "Serial number provided by vendor. Blank indicates unavailable.";
                } // END of cmmTransVendorSerialNumber definition.

                leaf cmmTransDateCode  {
                    type  cml-data-types:CML_STRING_T;
                    description "Vendor's manufacturing date code. Blank indicates unavailable.";
                } // END of cmmTransDateCode definition.

                leaf cmmTransDDMSupport  {
                    type  cml-data-types:CML_CMM_TRANS_DDM_SUPPORT_T;
                    description "Indicates which type of diagnostic monitoring is implemented";
                } // END of cmmTransDDMSupport definition.

                leaf cmmTransMaxCaseTemp  {
                    type  cml-data-types:CML_FLOAT_T;
                    units "C";
                    description "Maximum case temperature in Celsius. '-1000.01' indicates unavailable. '-1000.02' indicates not-applicable.";
                } // END of cmmTransMaxCaseTemp definition.

                leaf cmmTransSFPOptionsImp  {
                    type  cml-data-types:CML_CMM_TRANS_SFP_OPTIONS_IMPLEMENTED_T;
                    description "Transceiver Options Implemented for SFP Transceiver. null indicates unavailable.";
                } // END of cmmTransSFPOptionsImp definition.

                leaf cmmTransQSFPOptionsImp  {
                    type  cml-data-types:CML_CMM_TRANS_QSFP_OPTIONS_IMPLEMENTED_T;
                    description "Transceiver Options Implemented for QSFP Transceiver null indicates unavailable..";
                } // END of cmmTransQSFPOptionsImp definition.

                leaf cmmTransPresence  {
                    type  cml-data-types:CML_CMM_DEVICE_PRESENCE_T;
                    description "Indicates Transceiver presence status.";
                } // END of cmmTransPresence definition.


                list cmmTransDDMTable {
                    key "cmmTransChannelIndex";
                    config false;
                    description
                        "Information about Digital Optical Monitoring for each interface per channel.";
                    leaf cmmTransChannelIndex  {
                        type  cml-data-types:CML_UINT8_T;
                        description "A unique value, greater than zero, for each channel in the transceiver within the unit.For SFP transceivers, only channel '1' is applicable.";
                    } // END of cmmTransChannelIndex definition.

                    leaf cmmTransTemperature  {
                        type  cml-data-types:CML_FLOAT_T;
                        units "C";
                        description "Internally measured temperature of the transceiver.This is common across channels for a transceiver. '-1000.01' indicates unavailable";
                    } // END of cmmTransTemperature definition.

                    leaf cmmTransTempCriticalThresholdMin  {
                        type  cml-data-types:CML_FLOAT_T;
                        units "C";
                        description "Min Alarm Threshold temperature of the transceiver.This is common across channels for a transceiver. '-1000.01' indicates unavailable.";
                    } // END of cmmTransTempCriticalThresholdMin definition.

                    leaf cmmTransTempCriticalThresholdMax  {
                        type  cml-data-types:CML_FLOAT_T;
                        units "C";
                        description "Max Alarm Threshold temperature of the transceiver.This is common across channels for a transceiver. '-1000.01' indicates unavailable.";
                    } // END of cmmTransTempCriticalThresholdMax definition.

                    leaf cmmTransTempAlertThresholdMin  {
                        type  cml-data-types:CML_FLOAT_T;
                        units "C";
                        description "Min Alert Threshold temperature of the transceiver.This is common across channels for a transceiver. '-1000.01' indicates unavailable.";
                    } // END of cmmTransTempAlertThresholdMin definition.

                    leaf cmmTransTempAlertThresholdMax  {
                        type  cml-data-types:CML_FLOAT_T;
                        units "C";
                        description "Max Alert Threshold temperature of the transceiver.This is common across channels for a transceiver. '-1000.01' indicates unavailable.";
                    } // END of cmmTransTempAlertThresholdMax definition.

                    leaf cmmTransVoltage  {
                        type  cml-data-types:CML_FLOAT_PRECISION_3_T;
                        units "V";
                        description "Internally measured supply voltage of the transceiver.This is common across channels for a transceiver. '-100.001' indicates unavailable.";
                    } // END of cmmTransVoltage definition.

                    leaf cmmTransVoltCriticalThresholdMin  {
                        type  cml-data-types:CML_FLOAT_PRECISION_3_T;
                        units "V";
                        description "Min Alarm Threshold voltage of the transceiver.This is common across channels for a transceiver. '-100.001' indicates unavailable.";
                    } // END of cmmTransVoltCriticalThresholdMin definition.

                    leaf cmmTransVoltCriticalThresholdMax  {
                        type  cml-data-types:CML_FLOAT_PRECISION_3_T;
                        units "V";
                        description "Max Alarm Threshold voltage of the transceiver.This is common across channels for a transceiver. '-100.001' indicates unavailable.";
                    } // END of cmmTransVoltCriticalThresholdMax definition.

                    leaf cmmTransVoltAlertThresholdMin  {
                        type  cml-data-types:CML_FLOAT_PRECISION_3_T;
                        units "V";
                        description "Min Alert Threshold voltage of the transceiver.This is common across channels for a transceiver. '-100.001' indicates unavailable.";
                    } // END of cmmTransVoltAlertThresholdMin definition.

                    leaf cmmTransVoltAlertThresholdMax  {
                        type  cml-data-types:CML_FLOAT_PRECISION_3_T;
                        units "V";
                        description "Max Alert Threshold voltage of the transceiver.This is common across channels for a transceiver. '-100.001' indicates unavailable.";
                    } // END of cmmTransVoltAlertThresholdMax definition.

                    leaf cmmTransLaserBiasCurrent  {
                        type  cml-data-types:CML_FLOAT_PRECISION_3_T;
                        units "mA";
                        description "Internally measured TX Bias Current in Channel of transceiver. '-100.001' indicates unavailable.";
                    } // END of cmmTransLaserBiasCurrent definition.

                    leaf cmmTransLaserBiasCurrCriticalThresholdMin  {
                        type  cml-data-types:CML_FLOAT_PRECISION_3_T;
                        units "mA";
                        description "Min Alarm Threshold of Laser Bias Current per channel. '-100.001' indicates unavailable.";
                    } // END of cmmTransLaserBiasCurrCriticalThresholdMin definition.

                    leaf cmmTransLaserBiasCurrCriticalThresholdMax  {
                        type  cml-data-types:CML_FLOAT_PRECISION_3_T;
                        units "mA";
                        description "Max Alarm Threshold of Laser Bias Current per channel. '-100.001' indicates unavailable.";
                    } // END of cmmTransLaserBiasCurrCriticalThresholdMax definition.

                    leaf cmmTransLaserBiasCurrAlertThresholdMin  {
                        type  cml-data-types:CML_FLOAT_PRECISION_3_T;
                        units "mA";
                        description "Min Alert Threshold of Laser Bias Current per channel. '-100.001' indicates unavailable.";
                    } // END of cmmTransLaserBiasCurrAlertThresholdMin definition.

                    leaf cmmTransLaserBiasCurrAlertThresholdMax  {
                        type  cml-data-types:CML_FLOAT_PRECISION_3_T;
                        units "mA";
                        description "Max Alert Threshold of Laser Bias Current per channel. '-100.001' indicates unavailable.";
                    } // END of cmmTransLaserBiasCurrAlertThresholdMax definition.

                    leaf cmmTransTxPower  {
                        type  cml-data-types:CML_FLOAT_PRECISION_3_T;
                        units "dBm";
                        description "Measured TX output power in Channel of transceiver.'-100' value represents no power. '-100.001' indicates unavailable.";
                    } // END of cmmTransTxPower definition.

                    leaf cmmTransTxPowerCriticalThresholdMin  {
                        type  cml-data-types:CML_FLOAT_PRECISION_3_T;
                        units "dBm";
                        description "Min Alarm Threshold of TxOutput Power per channel.'-100' value represents no power. '-100.001' indicates unavailable.";
                    } // END of cmmTransTxPowerCriticalThresholdMin definition.

                    leaf cmmTransTxPowerCriticalThresholdMax  {
                        type  cml-data-types:CML_FLOAT_PRECISION_3_T;
                        units "dBm";
                        description "Max Alarm Threshold of TxOutput Power per channel.'-100' value represents no power. '-100.001' indicates unavailable.";
                    } // END of cmmTransTxPowerCriticalThresholdMax definition.

                    leaf cmmTransTxPowerAlertThresholdMin  {
                        type  cml-data-types:CML_FLOAT_PRECISION_3_T;
                        units "dBm";
                        description "Min Alert Threshold of TxOutput Power per channel.'-100' value represents no power. '-100.001' indicates unavailable.";
                    } // END of cmmTransTxPowerAlertThresholdMin definition.

                    leaf cmmTransTxPowerAlertThresholdMax  {
                        type  cml-data-types:CML_FLOAT_PRECISION_3_T;
                        units "dBm";
                        description "Max Alert Threshold of TxOutput Power per channel.'-100' value represents no power. '-100.001' indicates unavailable.";
                    } // END of cmmTransTxPowerAlertThresholdMax definition.

                    leaf cmmTransRxPower  {
                        type  cml-data-types:CML_FLOAT_PRECISION_3_T;
                        units "dBm";
                        description "Measured RX input power in Channel of transceiver.'-100' value represents no power. '-100.001' indicates unavailable.";
                    } // END of cmmTransRxPower definition.

                    leaf cmmTransRxPowerCriticalThresholdMin  {
                        type  cml-data-types:CML_FLOAT_PRECISION_3_T;
                        units "dBm";
                        description "Min Alarm Threshold value of Rx Input Power per channel.'-100' value represents no power. '-100.001' indicates unavailable.";
                    } // END of cmmTransRxPowerCriticalThresholdMin definition.

                    leaf cmmTransRxPowerCriticalThresholdMax  {
                        type  cml-data-types:CML_FLOAT_PRECISION_3_T;
                        units "dBm";
                        description "Max Alarm Threshold value of Rx Input Power per channel.'-100' value represents no power. '-100.001' indicates unavailable.";
                    } // END of cmmTransRxPowerCriticalThresholdMax definition.

                    leaf cmmTransRxPowerAlertThresholdMin  {
                        type  cml-data-types:CML_FLOAT_PRECISION_3_T;
                        units "dBm";
                        description "Min Alert Threshold value of Rx Input Power per channel.'-100' value represents no power. '-100.001' indicates unavailable.";
                    } // END of cmmTransRxPowerAlertThresholdMin definition.

                    leaf cmmTransRxPowerAlertThresholdMax  {
                        type  cml-data-types:CML_FLOAT_PRECISION_3_T;
                        units "dBm";
                        description "Max Alert Threshold value of Rx Input Power per channel.'-100' value represents no power. '-100.001' indicates unavailable.";
                    } // END of cmmTransRxPowerAlertThresholdMax definition.

                    leaf cmmTransTxPowerSupported  {
                        type  cml-data-types:CML_CMM_TRANS_TX_RX_POWER_SUPPORTED_T;
                        description "Value represents Transceiver TxPower supported or not.";
                    } // END of cmmTransTxPowerSupported definition.

                    leaf cmmTransRxPowerSupported  {
                        type  cml-data-types:CML_CMM_TRANS_TX_RX_POWER_SUPPORTED_T;
                        description "Value represents Transceiver RxPower supported or not.";
                    } // END of cmmTransRxPowerSupported definition.

                    leaf cmmTransDDMStatus  {
                        type  cml-data-types:CML_CMM_TRANS_DDM_STATUS_T;
                        description "Value represents Transceiver ddm status";
                    } // END of cmmTransDDMStatus definition.

                    leaf cmmTransTxState  {
                        type  cml-data-types:CML_CMM_TRANS_TX_RX_STATE_T;
                        description "Transceiver TX State";
                    } // END of cmmTransTxState definition.

                    leaf cmmTransRxLosState  {
                        type  cml-data-types:CML_CMM_TRANS_TX_RX_STATE_T;
                        description "Transceiver Rx Los State";
                    } // END of cmmTransRxLosState definition.

                    leaf cmmTransTxLosState  {
                        type  cml-data-types:CML_CMM_TRANS_TX_RX_STATE_T;
                        description "Transceiver TX Los State (applicable only for QSFP).";
                    } // END of cmmTransTxLosState definition.

                    leaf cmmTransResetState  {
                        type  cml-data-types:CML_CMM_TRANS_RESET_STATE_T;
                        description "Transceiver Reset State (applicable only for QSFP).";
                    } // END of cmmTransResetState definition.

                    leaf cmmTransPowerMode  {
                        type  cml-data-types:CML_CMM_TRANS_POWER_MODE_T;
                        description "Transceiver Power mode (applicable only for QSFP).";
                    } // END of cmmTransPowerMode definition.

                    leaf cmmTransPreFecBerVal  {
                        type  cml-data-types:CML_STRING_T;
                        units "ber/ms";
                        description "Forward error correction bit error rate value, -100002' indicates not-applicable";
                    } // END of cmmTransPreFecBerVal definition.

                    leaf cmmTransPreFecBerAlertMax  {
                        type  cml-data-types:CML_STRING_T;
                        units "ber/ms";
                        description "Max alert value for pre-forward error correction ber, -100002' indicates not-applicable";
                    } // END of cmmTransPreFecBerAlertMax definition.

                    leaf cmmTransPreFecBerAlertMin  {
                        type  cml-data-types:CML_STRING_T;
                        units "ber/ms";
                        description "Min alert value for pre-forward error correction ber, -100002' indicates not-applicable";
                    } // END of cmmTransPreFecBerAlertMin definition.

                    leaf cmmTransPreFecBerCriticMax  {
                        type  cml-data-types:CML_STRING_T;
                        units "ber/ms";
                        description "Max critical value for pre-forward error correction ber, -100002' indicates not-applicable";
                    } // END of cmmTransPreFecBerCriticMax definition.

                    leaf cmmTransPreFecBerCriticMin  {
                        type  cml-data-types:CML_STRING_T;
                        units "ber/ms";
                        description "Min critical value for pre-forward error correction ber, -100002' indicates not-applicable";
                    } // END of cmmTransPreFecBerCriticMin definition.

                    leaf cmmTransUncorrectedBerVal  {
                        type  cml-data-types:CML_STRING_T;
                        units "ber/ms";
                        description "Frame error rate value, -100002' indicates not-applicable";
                    } // END of cmmTransUncorrectedBerVal definition.

                    leaf cmmTransUncorrectedBerValAlertMax  {
                        type  cml-data-types:CML_STRING_T;
                        units "ber/ms";
                        description "Max alert value for Uncorrected BER, -100002' indicates not-applicable";
                    } // END of cmmTransUncorrectedBerValAlertMax definition.

                    leaf cmmTransUncorrectedBerValAlertMin  {
                        type  cml-data-types:CML_STRING_T;
                        units "ber/ms";
                        description "Min alert value for Uncorrected BER, -100002' indicates not-applicable";
                    } // END of cmmTransUncorrectedBerValAlertMin definition.

                    leaf cmmTransUncorrectedBerValCriticMax  {
                        type  cml-data-types:CML_STRING_T;
                        units "ber/ms";
                        description "Max critical value for Uncorrected BER, -100002' indicates not-applicable";
                    } // END of cmmTransUncorrectedBerValCriticMax definition.

                    leaf cmmTransUncorrectedBerValCriticMin  {
                        type  cml-data-types:CML_STRING_T;
                        units "ber/ms";
                        description "Min critical value for Uncorrected BER, -100002' indicates not-applicable";
                    } // END of cmmTransUncorrectedBerValCriticMin definition.

                    leaf cmmTransSnrVal  {
                        type  cml-data-types:CML_FLOAT_PRECISION_3_T;
                        units "dBm";
                        description "Signal to noise ratio on ingress lane, -100002' indicates not-applicable";
                    } // END of cmmTransSnrVal definition.

                    leaf cmmTransSnrAlertMax  {
                        type  cml-data-types:CML_FLOAT_PRECISION_3_T;
                        units "dBm";
                        description "Max alert value for signal-to-noise ratio on ingress lane, -100002' indicates not-applicable";
                    } // END of cmmTransSnrAlertMax definition.

                    leaf cmmTransSnrAlertMin  {
                        type  cml-data-types:CML_FLOAT_PRECISION_3_T;
                        units "dBm";
                        description "Min alert value for signal-to-noise ratio on ingress lane, -100002' indicates not-applicable";
                    } // END of cmmTransSnrAlertMin definition.

                    leaf cmmTransSnrCriticMax  {
                        type  cml-data-types:CML_FLOAT_PRECISION_3_T;
                        units "dBm";
                        description "Max critical value for signal-to-noise ratio on ingress lane, -100002' indicates not-applicable";
                    } // END of cmmTransSnrCriticMax definition.

                    leaf cmmTransSnrCriticMin  {
                        type  cml-data-types:CML_FLOAT_PRECISION_3_T;
                        units "dBm";
                        description "Min critical value for signal-to-noise ratio on ingress lane, -100002' indicates not-applicable";
                    } // END of cmmTransSnrCriticMin definition.

                    leaf cmmTransResIsiVal  {
                        type  cml-data-types:CML_FLOAT_PRECISION_3_T;
                        units "ps/nm";
                        description "Residual-isi value, -100002' indicates not-applicable";
                    } // END of cmmTransResIsiVal definition.

                    leaf cmmTransResIsiAlertMax  {
                        type  cml-data-types:CML_FLOAT_PRECISION_3_T;
                        units "ps/nm";
                        description "Max alert value for residual-isi, -100002' indicates not-applicable";
                    } // END of cmmTransResIsiAlertMax definition.

                    leaf cmmTransResIsiAlertMin  {
                        type  cml-data-types:CML_FLOAT_PRECISION_3_T;
                        units "ps/nm";
                        description "Min alert value for residual-isi, -100002' indicates not-applicable";
                    } // END of cmmTransResIsiAlertMin definition.

                    leaf cmmTransResIsiCriticMax  {
                        type  cml-data-types:CML_FLOAT_PRECISION_3_T;
                        units "ps/nm";
                        description "Max critical value for residual-isi, -100002' indicates not-applicable";
                    } // END of cmmTransResIsiCriticMax definition.

                    leaf cmmTransResIsiCriticMin  {
                        type  cml-data-types:CML_FLOAT_PRECISION_3_T;
                        units "ps/nm";
                        description "Min critical value for residual-isi, -100002' indicates not-applicable";
                    } // END of cmmTransResIsiCriticMin definition.

                    leaf cmmTransLvlTransVal  {
                        type  cml-data-types:CML_FLOAT_PRECISION_3_T;
                        description "Level transition value, -100002' indicates not-applicable";
                    } // END of cmmTransLvlTransVal definition.

                    leaf cmmTransLvlTransAlertMax  {
                        type  cml-data-types:CML_FLOAT_PRECISION_3_T;
                        description "Max alert value for level transition, -100002' indicates not-applicable";
                    } // END of cmmTransLvlTransAlertMax definition.

                    leaf cmmTransLvlTransAlertMin  {
                        type  cml-data-types:CML_FLOAT_PRECISION_3_T;
                        description "Min alert value for level transition, -100002' indicates not-applicable";
                    } // END of cmmTransLvlTransAlertMin definition.

                    leaf cmmTransLvlTransCriticMax  {
                        type  cml-data-types:CML_FLOAT_PRECISION_3_T;
                        description "Max critical value for level transition, -100002' indicates not-applicable";
                    } // END of cmmTransLvlTransCriticMax definition.

                    leaf cmmTransLvlTransCriticMin  {
                        type  cml-data-types:CML_FLOAT_PRECISION_3_T;
                        description "Min critical value for level transition, -100002' indicates not-applicable";
                    } // END of cmmTransLvlTransCriticMin definition.

                    leaf cmmTransTecCurrErrVal  {
                        type  cml-data-types:CML_FLOAT_PRECISION_3_T;
                        units "mA";
                        description "Thermo-elecrical cooler current value, -100002' indicates not-applicable";
                    } // END of cmmTransTecCurrErrVal definition.

                    leaf cmmTransTecCurrErrAlertMax  {
                        type  cml-data-types:CML_FLOAT_PRECISION_3_T;
                        units "mA";
                        description "Max alert value for thermo-elecrical cooler current, -100002' indicates not-applicable";
                    } // END of cmmTransTecCurrErrAlertMax definition.

                    leaf cmmTransTecCurrErrAlertMin  {
                        type  cml-data-types:CML_FLOAT_PRECISION_3_T;
                        units "mA";
                        description "Min alert value for thermo-elecrical cooler current, -100002' indicates not-applicable";
                    } // END of cmmTransTecCurrErrAlertMin definition.

                    leaf cmmTransTecCurrErrCriticMax  {
                        type  cml-data-types:CML_FLOAT_PRECISION_3_T;
                        units "mA";
                        description "Max critical value for thermo-elecrical cooler current, -100002' indicates not-applicable";
                    } // END of cmmTransTecCurrErrCriticMax definition.

                    leaf cmmTransTecCurrErrCriticMin  {
                        type  cml-data-types:CML_FLOAT_PRECISION_3_T;
                        units "mA";
                        description "Min critical value for thermo-elecrical cooler current, -100002' indicates not-applicable";
                    } // END of cmmTransTecCurrErrCriticMin definition.

                    leaf cmmTransLaserTempVal  {
                        type  cml-data-types:CML_FLOAT_PRECISION_3_T;
                        units "C";
                        description "Laser Temparature value, -100002' indicates not-applicable";
                    } // END of cmmTransLaserTempVal definition.

                    leaf cmmTransLaserTempAlertMax  {
                        type  cml-data-types:CML_FLOAT_PRECISION_3_T;
                        units "C";
                        description "Max alert value for Laser Temperature, -100002' indicates not-applicable";
                    } // END of cmmTransLaserTempAlertMax definition.

                    leaf cmmTransLaserTempAlertMin  {
                        type  cml-data-types:CML_FLOAT_PRECISION_3_T;
                        units "C";
                        description "Min alert value for Laser Temperature, -100002' indicates not-applicable";
                    } // END of cmmTransLaserTempAlertMin definition.

                    leaf cmmTransLaserTempCriticMax  {
                        type  cml-data-types:CML_FLOAT_PRECISION_3_T;
                        units "C";
                        description "Max critical value for Laser Temperature, -100002' indicates not-applicable";
                    } // END of cmmTransLaserTempCriticMax definition.

                    leaf cmmTransLaserTempCriticMin  {
                        type  cml-data-types:CML_FLOAT_PRECISION_3_T;
                        units "C";
                        description "Min critical value for Laser Temperature, -100002' indicates not-applicable";
                    } // END of cmmTransLaserTempCriticMin definition.

                } // End of cmmTransDDMTable-list
            } // End of cmmTransEEPROMTable-list

            list cmmSysPowerSupplyTable {
                key "cmmSysPSUIndex";
                config false;
                description
                    "list of power supply resident in the chassis";
                leaf cmmSysPSUIndex  {
                    type  cml-data-types:CML_INT32_T;
                    description "The unique index of the power supply.";
                } // END of cmmSysPSUIndex definition.

                container cmmSysPSUTable {
                    config false;
                    description
                        "list of power supply information resident in the chassis";
                    leaf cmmSysPowerSupplyOperStatus  {
                        type  cml-data-types:CML_CMM_POWER_SUPPLY_OPERSTATUS_T;
                        description "The status of the power supply.";
                    } // END of cmmSysPowerSupplyOperStatus definition.

                    leaf cmmSysPowerSupplyType  {
                        type  cml-data-types:CML_CMM_POWER_SUPPLY_TYPE_T;
                        description "The type of the power supply.";
                    } // END of cmmSysPowerSupplyType definition.

                    leaf cmmSysHotSwapStat  {
                        type  cml-data-types:CML_CMM_POWER_RAIL_T;
                        description "Power status for HOT SWAP";
                    } // END of cmmSysHotSwapStat definition.

                    leaf cmmSysPSConsumption  {
                        type  cml-data-types:CML_FLOAT_T;
                        units "W";
                        description "Output Power of Power supply. '-1000.01' indicates unavailable.";
                    } // END of cmmSysPSConsumption definition.

                    leaf cmmSysInputPower  {
                        type  cml-data-types:CML_FLOAT_T;
                        units "W";
                        description "Input Power of Power supply. '-1000.01' indicates unavailable.";
                    } // END of cmmSysInputPower definition.

                    leaf cmmSysInputVoltage  {
                        type  cml-data-types:CML_FLOAT_T;
                        units "V";
                        description "Input Voltage of Power supply. '-1000.01' indicates unavailable.";
                    } // END of cmmSysInputVoltage definition.

                    leaf cmmSysOutputVoltage  {
                        type  cml-data-types:CML_FLOAT_T;
                        units "V";
                        description "Output Voltage of Power supply. '-1000.01' indicates unavailable.";
                    } // END of cmmSysOutputVoltage definition.

                    leaf cmmSysInputCurrent  {
                        type  cml-data-types:CML_FLOAT_T;
                        units "A";
                        description "Input Current of Power supply. '-1000.01' indicates unavailable.";
                    } // END of cmmSysInputCurrent definition.

                    leaf cmmSysOutputCurrent  {
                        type  cml-data-types:CML_FLOAT_T;
                        units "A";
                        description "Output Current of Power supply. '-1000.01' indicates unavailable.";
                    } // END of cmmSysOutputCurrent definition.

                    leaf cmmSysPSTemperature1  {
                        type  cml-data-types:CML_FLOAT_T;
                        units "C";
                        description "Temperature of Power supply sensor1. '-1000.01' indicates unavailable.";
                    } // END of cmmSysPSTemperature1 definition.

                    leaf cmmSysPSTemperature2  {
                        type  cml-data-types:CML_FLOAT_T;
                        units "C";
                        description "Temperature of Power supply sensor2. '-1000.01' indicates unavailable.";
                    } // END of cmmSysPSTemperature2 definition.

                    leaf cmmSysPSFan1Rpm  {
                        type  cml-data-types:CML_INT32_T;
                        description "Fan1 rpm of Power supply. '-100001' indicates unavailable.";
                    } // END of cmmSysPSFan1Rpm definition.

                    leaf cmmSysPSFan2Rpm  {
                        type  cml-data-types:CML_INT32_T;
                        description "Fan2 rpm of Power supply. '-100001' indicates unavailable. '-100002' indicates notapplicable";
                    } // END of cmmSysPSFan2Rpm definition.

                    leaf cmmSysPS12VPg  {
                        type  cml-data-types:CML_CMM_POWER_RAIL_T;
                        description "Status of Output Power";
                    } // END of cmmSysPS12VPg definition.

                    leaf cmmSysPSAcAlert  {
                        type  cml-data-types:CML_CMM_POWER_RAIL_T;
                        description "Status of Input Power";
                    } // END of cmmSysPSAcAlert definition.

                    leaf cmmSysPSParamsSupport  {
                        type  cml-data-types:CML_CMM_PSU_PMBUS_PARAM_SUPPORT_T;
                        description "Bitmap of supported paramaters of PSU Unit. 0 - not supported (values only for information). 1 - supported (values can be used for monitoring). null indicates unsupported.";
                    } // END of cmmSysPSParamsSupport definition.

                } // END of cmmSysPSUTable-container definition.
                container cmmPsuFruTable {
                    config false;
                    description
                        "list of power supply fru information resident in the chassis";
                    leaf cmmPsuPpid  {
                        type  cml-data-types:CML_STRING_T;
                        description "The unique ppid of the power supply. Blank indicates unavailable.";
                    } // END of cmmPsuPpid definition.

                    leaf cmmPsuCountryofOrigin  {
                        type  cml-data-types:CML_STRING_T;
                        description "PSU Country of Origin. Blank indicates unavailable.";
                    } // END of cmmPsuCountryofOrigin definition.

                    leaf cmmPsuPpidPartNum  {
                        type  cml-data-types:CML_STRING_T;
                        description "PSU PPID Part Number. Blank indicates unavailable.";
                    } // END of cmmPsuPpidPartNum definition.

                    leaf cmmPsuPpidPartNumRev  {
                        type  cml-data-types:CML_STRING_T;
                        description "PSU PPID Part Number Rev. Blank indicates unavailable.";
                    } // END of cmmPsuPpidPartNumRev definition.

                    leaf cmmPsuManufactureId  {
                        type  cml-data-types:CML_LINE_T;
                        description "PSU Manufacturer ID. Blank indicates unavailable.";
                    } // END of cmmPsuManufactureId definition.

                    leaf cmmPsuDateCode  {
                        type  cml-data-types:CML_STRING_T;
                        description "PSU Date Code. Blank indicates unavailable.";
                    } // END of cmmPsuDateCode definition.

                    leaf cmmPsuSerialNumber  {
                        type  cml-data-types:CML_STRING_T;
                        description "PSU Date Code. Blank indicates unavailable.";
                    } // END of cmmPsuSerialNumber definition.

                    leaf cmmPsuPartNum  {
                        type  cml-data-types:CML_STRING_T;
                        description "PSU Part Number. Blank indicates unavailable.";
                    } // END of cmmPsuPartNum definition.

                    leaf cmmPsuPartNumRev  {
                        type  cml-data-types:CML_STRING_T;
                        description "PSU Part Num Rev. Blank indicates unavailable.";
                    } // END of cmmPsuPartNumRev definition.

                    leaf cmmPsuNumOfFanPerTray  {
                        type  cml-data-types:CML_INT32_T;
                        description "Number of Fans in the tray in PSU. '-100001' indicates unavailable.";
                    } // END of cmmPsuNumOfFanPerTray definition.

                    leaf cmmPsuType  {
                        type  cml-data-types:CML_UINT8_T;
                        description "The Type of PSU.";
                    } // END of cmmPsuType definition.

                    leaf cmmPsuServiceTag  {
                        type  cml-data-types:CML_STRING_T;
                        description "PSU Service Tag. Blank indicates unavailable.";
                    } // END of cmmPsuServiceTag definition.

                    leaf cmmPsuIanaNum  {
                        type  cml-data-types:CML_STRING_T;
                        description "PSU IANA Num. Blank indicates unavailable.";
                    } // END of cmmPsuIanaNum definition.

                    leaf cmmPsuFanMaxRpm  {
                        type  cml-data-types:CML_INT32_T;
                        description "PSU Fan Max RPM. '-100001' indicates unavailable.";
                    } // END of cmmPsuFanMaxRpm definition.

                    leaf cmmPsuAirFlowDir  {
                        type  cml-data-types:CML_STRING_T;
                        description "PSU Air Flow Direction.";
                    } // END of cmmPsuAirFlowDir definition.

                    leaf cmmPsuMaxOutputWatt  {
                        type  cml-data-types:CML_INT32_T;
                        description "PSU Max Output Watts.";
                    } // END of cmmPsuMaxOutputWatt definition.

                } // END of cmmPsuFruTable-container definition.
            } // End of cmmSysPowerSupplyTable-list

            list cmmFanTrayTable {
                key "cmmFanTrayNumber";
                config false;
                description
                    "list of fan tray details resident in the chassis";
                leaf cmmFanTrayNumber  {
                    type  cml-data-types:CML_INT8_T;
                    description "Value represents the fan tray Number.";
                } // END of cmmFanTrayNumber definition.


                list cmmFanTable {
                    key "cmmFanIndex";
                    config false;
                    description
                        "list of fan details resident in the chassis";
                    leaf cmmFanIndex  {
                        type  cml-data-types:CML_INT8_T;
                        description "Index of the fan per fantray.";
                    } // END of cmmFanIndex definition.

                    leaf cmmFanRpm  {
                        type  cml-data-types:CML_INT32_T;
                        description "Value represents the fan rpm. '-100001' indicates unavailable.";
                    } // END of cmmFanRpm definition.

                    leaf cmmFanRpmMin  {
                        type  cml-data-types:CML_INT32_T;
                        description "Value represents the minimum supported RPM of fan. '-100001' indicates unavailable.";
                    } // END of cmmFanRpmMin definition.

                    leaf cmmFanRpmMax  {
                        type  cml-data-types:CML_INT32_T;
                        description "Value represents the maximum supported RPM of fan. '-100001' indicates unavailable.";
                    } // END of cmmFanRpmMax definition.

                    leaf cmmFanStatus  {
                        type  cml-data-types:CML_CMM_FAN_STATUS_T;
                        description "The status of the fan.";
                    } // END of cmmFanStatus definition.

                    leaf cmmFanLocation  {
                        type  cml-data-types:CML_CMM_FAN_LOCATION_T;
                        description "The location of fan in tray.";
                    } // END of cmmFanLocation definition.

                } // End of cmmFanTable-list
                container cmmFanTrayStatusTable {
                    config false;
                    description
                        "list of fan tray details resident in the chassis";
                    leaf cmmFanTrayStatus  {
                        type  cml-data-types:CML_CMM_FAN_TRAY_STATUS_T;
                        description "Value represents the fan tray status.";
                    } // END of cmmFanTrayStatus definition.

                    leaf cmmFanTrayLedColor  {
                        type  cml-data-types:CML_CMM_LED_COLOR_CODE_T;
                        description "Value represents the Color of the fan led.";
                    } // END of cmmFanTrayLedColor definition.

                } // END of cmmFanTrayStatusTable-container definition.
                container cmmFanFruTable {
                    config false;
                    description
                        "list of fan tray details resident in the chassis";
                    leaf cmmFanPpid  {
                        type  cml-data-types:CML_STRING_T;
                        description "The unique ppid of the fan tray. Blank indicates unavailable.";
                    } // END of cmmFanPpid definition.

                    leaf cmmFanCountryofOrigin  {
                        type  cml-data-types:CML_STRING_T;
                        description "FanTray Country of Origin. Blank indicates unavailable.";
                    } // END of cmmFanCountryofOrigin definition.

                    leaf cmmFanPpidPartNum  {
                        type  cml-data-types:CML_STRING_T;
                        description "FanTray PPID Part Num. Blank indicates unavailable.";
                    } // END of cmmFanPpidPartNum definition.

                    leaf cmmFanPpidPartNumRev  {
                        type  cml-data-types:CML_STRING_T;
                        description "FanTray PPID Part Num Rev. Blank indicates unavailable.";
                    } // END of cmmFanPpidPartNumRev definition.

                    leaf cmmFanManufactureId  {
                        type  cml-data-types:CML_STRING_T;
                        description "Fan Manufacturer Id. Blank indicates unavailable.";
                    } // END of cmmFanManufactureId definition.

                    leaf cmmFanDateCode  {
                        type  cml-data-types:CML_STRING_T;
                        description "Fan Date Code. Blank indicates unavailable.";
                    } // END of cmmFanDateCode definition.

                    leaf cmmFanSerialNumber  {
                        type  cml-data-types:CML_STRING_T;
                        description "Fan Serial Number. Blank indicates unavailable.";
                    } // END of cmmFanSerialNumber definition.

                    leaf cmmFanPartNum  {
                        type  cml-data-types:CML_STRING_T;
                        description "Fan Part Number. Blank indicates unavailable.";
                    } // END of cmmFanPartNum definition.

                    leaf cmmFanPartNumRev  {
                        type  cml-data-types:CML_STRING_T;
                        description "Fan Part Number Rev. Blank indicates unavailable.";
                    } // END of cmmFanPartNumRev definition.

                    leaf cmmFanNumOfFanPerTray  {
                        type  cml-data-types:CML_INT32_T;
                        description "Number of fans in the tray. '-100001' indicates unavailable.";
                    } // END of cmmFanNumOfFanPerTray definition.

                    leaf cmmFanType  {
                        type  cml-data-types:CML_CMM_FAN_TYPE_T;
                        description "Fan Type.";
                    } // END of cmmFanType definition.

                    leaf cmmFanServiceTag  {
                        type  cml-data-types:CML_STRING_T;
                        description "Fan Service Tag. Blank indicates unavailable.";
                    } // END of cmmFanServiceTag definition.

                    leaf cmmFanIanaNum  {
                        type  cml-data-types:CML_STRING_T;
                        description "Fan IANA Num. Blank indicates unavailable.";
                    } // END of cmmFanIanaNum definition.

                    leaf cmmFanMaxRpm  {
                        type  cml-data-types:CML_INT32_T;
                        description "Max RPM of fan. '-100001' indicates unavailable";
                    } // END of cmmFanMaxRpm definition.

                } // END of cmmFanFruTable-container definition.
            } // End of cmmFanTrayTable-list

            list cmmSysTemperatureTable {
                key "cmmSysTemperatureSensorIndex";
                config false;
                description
                    "list of Temperature Entities on board";
                leaf cmmSysTemperatureSensorIndex  {
                    type  cml-data-types:CML_INT8_T;
                    description "Value represents Temperature Sensor Index";
                } // END of cmmSysTemperatureSensorIndex definition.

                leaf cmmSysTemperatureSensorName  {
                    type  cml-data-types:CML_LINE_T;
                    description "Temperature Sensor Name. Blank indicates unavailable.";
                } // END of cmmSysTemperatureSensorName definition.

                leaf cmmSysTemperatureValue  {
                    type  cml-data-types:CML_FLOAT_T;
                    units "C";
                    description "Value represents Temperature Sensor value. '-1000.01' indicates unavailable.";
                } // END of cmmSysTemperatureValue definition.

                leaf cmmSysTempEmergencyThresholdMin  {
                    type  cml-data-types:CML_FLOAT_T;
                    units "C";
                    description "Value represents Temperature Sensor Min Emergency threshold. '-1000.01' indicates unavailable.";
                } // END of cmmSysTempEmergencyThresholdMin definition.

                leaf cmmSysTempEmergencyThresholdMax  {
                    type  cml-data-types:CML_FLOAT_T;
                    units "C";
                    description "Value represents Temperature Sensor Max Emergency threshold. '-1000.01' indicates unavailable.";
                } // END of cmmSysTempEmergencyThresholdMax definition.

                leaf cmmSysTempAlertThresholdMin  {
                    type  cml-data-types:CML_FLOAT_T;
                    units "C";
                    description "Value represents Temperature Sensor Min Alert threshold. '-1000.01' indicates unavailable.";
                } // END of cmmSysTempAlertThresholdMin definition.

                leaf cmmSysTempAlertThresholdMax  {
                    type  cml-data-types:CML_FLOAT_T;
                    units "C";
                    description "Value represents Temperature Sensor Max Alert threshold. '-1000.01' indicates unavailable.";
                } // END of cmmSysTempAlertThresholdMax definition.

                leaf cmmSysTempCriticalThresholdMin  {
                    type  cml-data-types:CML_FLOAT_T;
                    units "C";
                    description "Value represents Temperature Sensor Min Critical threshold. '-1000.01' indicates unavailable.";
                } // END of cmmSysTempCriticalThresholdMin definition.

                leaf cmmSysTempCriticalThresholdMax  {
                    type  cml-data-types:CML_FLOAT_T;
                    units "C";
                    description "Value represents Temperature Sensor Min Critical threshold. '-1000.01' indicates unavailable.";
                } // END of cmmSysTempCriticalThresholdMax definition.

            } // End of cmmSysTemperatureTable-list

            list cmmSwitchTemperatureTable {
                key "cmmSwitchTemperatureSensorIndex";
                config false;
                description
                    "list of Temperature Entities inside board chip";
                leaf cmmSwitchTemperatureSensorIndex  {
                    type  cml-data-types:CML_UINT8_T;
                    description "Value represents Temperature Monitor Index inside chip. '-100001' indicates unavailable.";
                } // END of cmmSwitchTemperatureSensorIndex definition.

                leaf cmmSwitchTemperatureValue  {
                    type  cml-data-types:CML_FLOAT_T;
                    units "C";
                    description "Value represents Temperature monitor value. '-1000.01' indicates unavailable.";
                } // END of cmmSwitchTemperatureValue definition.

                leaf cmmSwitchTempPeakValue  {
                    type  cml-data-types:CML_FLOAT_T;
                    units "C";
                    description "Value represents Temperature monitor peak value since last reading. '-1000.01' indicates unavailable.";
                } // END of cmmSwitchTempPeakValue definition.

            } // End of cmmSwitchTemperatureTable-list

            list cmmCpuCoreUtilTable {
                key "cmmCpuCoreIndex";
                config false;
                description
                    "Details of CPU utilization per core";
                leaf cmmCpuCoreIndex  {
                    type  cml-data-types:CML_UINT8_T;
                    description "Cpu Core number.";
                } // END of cmmCpuCoreIndex definition.

                leaf cmmCpuCoreUtilization  {
                    type  cml-data-types:CML_FLOAT_T;
                    units "%";
                    description "Cpu Utilization per core.";
                } // END of cmmCpuCoreUtilization definition.

                leaf cmmCpuCoreModelName  {
                    type  cml-data-types:CML_LINE_T;
                    description "Displays CPU processor Model Name. Blank indicates unavailable";
                } // END of cmmCpuCoreModelName definition.

            } // End of cmmCpuCoreUtilTable-list

            list cmmSysCpldTable {
                key "cmmSysCpldIndex";
                config false;
                description
                    "list of CPLD Entities on board";
                leaf cmmSysCpldIndex  {
                    type  cml-data-types:CML_INT8_T;
                    description "Value represents CPLD Index";
                } // END of cmmSysCpldIndex definition.

                leaf cmmSysCpldName  {
                    type  cml-data-types:CML_LINE_T;
                    description "CPLD Name. Blank indicates unavailable.";
                } // END of cmmSysCpldName definition.

                leaf cmmSysCpldSupportedVer  {
                    type  cml-data-types:CML_STRING_T;
                    description "CPLD supported version on board. Blank indicates unavailable";
                } // END of cmmSysCpldSupportedVer definition.

                leaf cmmSysCpldCurrentVer  {
                    type  cml-data-types:CML_STRING_T;
                    description "CPLD current version on board. Blank indicates unavailable";
                } // END of cmmSysCpldCurrentVer definition.

            } // End of cmmSysCpldTable-list

            list cmmCoherentSlotInterfaceMapping {
                if-feature feature-list:HAVE_COHERENT_OPTICS;
                key "slotNo";
                config false;
                description
                    "List of of slot interface mapped entries";
                leaf slotNo  {
                    type  cml-data-types:CML_UINT8_T;
                    description "Specifies the Optical slot number";
                } // END of slotNo definition.

                leaf cardType  {
                    type  CML_CMM_CARD_TYPE_T;
                    description "Specifies the type of card inserted in the slot";
                } // END of cardType definition.


                list cmmCoherentSlotMappedInfo {
                    if-feature feature-list:HAVE_COHERENT_OPTICS;
                    key "mappedIfName";
                    config false;
                    description
                        "List of mapped interface names, hostif and netif number";
                    leaf mappedIfName  {
                        type  cml-data-types:CML_STRING_T;
                        description "Specifies the mapped interface names";
                    } // END of mappedIfName definition.

                    leaf hostIfNo  {
                        type  cml-data-types:CML_UINT8_T;
                        description "Specifies the mapped hostif-no when module will present and enable.";
                    } // END of hostIfNo definition.

                    leaf netIfNo  {
                        type  cml-data-types:CML_UINT8_T;
                        description "Specifies the mapped netif-no when module will present and enable.";
                    } // END of netIfNo definition.

                } // End of cmmCoherentSlotMappedInfo-list
            } // End of cmmCoherentSlotInterfaceMapping-list
            container cmmSysRamTable {
                config false;
                description
                    " An entry containing RAM related information of the Unit.";
                leaf cmmSysRamTotalMem  {
                    type  cml-data-types:CML_INT32_T;
                    units "MBytes";
                    description "CPU RAM's total free memory available for utilisation in MBytes. '-100001' indicates unavailable.";
                } // END of cmmSysRamTotalMem definition.

                leaf cmmSysRamUsedMem  {
                    type  cml-data-types:CML_INT32_T;
                    units "%";
                    description "CPU RAM's Used memory available for utilisation in MBytes. '-100001' indicates unavailable.";
                } // END of cmmSysRamUsedMem definition.

                leaf cmmSysRamFreeMem  {
                    type  cml-data-types:CML_INT32_T;
                    units "%";
                    description "CPU RAM's Free memory available for utilisation in MBytes. '-100001' indicates unavailable.";
                } // END of cmmSysRamFreeMem definition.

                leaf cmmSysRamSharedMem  {
                    type  cml-data-types:CML_INT32_T;
                    description "CPU RAM's Shared memory available for utilisation in MBytes. '-100001' indicates unavailable.";
                } // END of cmmSysRamSharedMem definition.

                leaf cmmSysRamBuffers  {
                    type  cml-data-types:CML_INT32_T;
                    description "CPU RAM's Bufffer available for utilisation in MBytes. '-100001' indicates unavailable.";
                } // END of cmmSysRamBuffers definition.

                leaf cmmSysRamTotalSwap  {
                    type  cml-data-types:CML_INT32_T;
                    description "CPU RAM's Total Swap memory available for utilisation in MBytes. '-100001' indicates unavailable.";
                } // END of cmmSysRamTotalSwap definition.

                leaf cmmSysRamFreeSwap  {
                    type  cml-data-types:CML_INT32_T;
                    description "CPU RAM's Free Swap memory available for utilisation in MBytes. '-100001' indicates unavailable.";
                } // END of cmmSysRamFreeSwap definition.

                leaf cmmSysRamCurrentProcesses  {
                    type  cml-data-types:CML_INT32_T;
                    description "Number of processes currently running in RAM. '-100001' indicates unavailable.";
                } // END of cmmSysRamCurrentProcesses definition.

                leaf cmmSysRamTotalHighMemory  {
                    type  cml-data-types:CML_INT32_T;
                    description "CPU RAM's Total High memory in MBytes. '-100001' indicates unavailable.";
                } // END of cmmSysRamTotalHighMemory definition.

                leaf cmmSysRamAvailableHighMemory  {
                    type  cml-data-types:CML_INT32_T;
                    description "CPU RAM's Available High memory in MBytes. '-100001' indicates unavailable.";
                } // END of cmmSysRamAvailableHighMemory definition.

                leaf cmmSysRamUnitSize  {
                    type  cml-data-types:CML_INT32_T;
                    description "CPU RAM's Memory unit size in Bytes. '-100001' indicates unavailable.";
                } // END of cmmSysRamUnitSize definition.

                leaf cmmSysRamCriticalThreshold  {
                    type  cml-data-types:CML_INT32_T;
                    units "%";
                    description "RAM usage threshold % for Critical level. '-100001' indicates unavailable.";
                } // END of cmmSysRamCriticalThreshold definition.

                leaf cmmSysRamAlertThreshold  {
                    type  cml-data-types:CML_INT32_T;
                    units "%";
                    description "RAM usage threshold % for Alert level. '-100001' indicates unavailable.";
                } // END of cmmSysRamAlertThreshold definition.

            } // END of cmmSysRamTable-container definition.
            container cmmStackCpuTable {
                config false;
                description
                    "list of Stack Unit Util Entries";
                leaf cmmStackUnitNumCpuProcessor  {
                    type  cml-data-types:CML_INT32_T;
                    description "The number of Online Processors Available. '-100001' indicates unavailable.";
                } // END of cmmStackUnitNumCpuProcessor definition.

                leaf cmmStackUnitCpuLoad1Min  {
                    type  cml-data-types:CML_FLOAT_T;
                    units "%";
                    description "CPU Load in percentage for last 1 minute. '-1000.01' indicates unavailable.";
                } // END of cmmStackUnitCpuLoad1Min definition.

                leaf cmmStackUnitCpuLoad5Min  {
                    type  cml-data-types:CML_FLOAT_T;
                    units "%";
                    description "CPU Load in percentage for last 5 minutes. '-1000.01' indicates unavailable.";
                } // END of cmmStackUnitCpuLoad5Min definition.

                leaf cmmStackUnitCpuLoad15Min  {
                    type  cml-data-types:CML_FLOAT_T;
                    units "%";
                    description "CPU Load in percentage for last 15 minutes. '-1000.01' indicates unavailable.";
                } // END of cmmStackUnitCpuLoad15Min definition.

                leaf cmmStackCpuLoad1minAlertThreshold  {
                    type  cml-data-types:CML_FLOAT_T;
                    units "%";
                    description "The CPU Alert Threshold percentage value for 1 min load. '-1000.01' indicates unavailable.";
                } // END of cmmStackCpuLoad1minAlertThreshold definition.

                leaf cmmStackCpuLoad1minCriticalThreshold  {
                    type  cml-data-types:CML_FLOAT_T;
                    units "%";
                    description "The CPU Critical Threshold percentage value for 1 min load. '-1000.01' indicates unavailable.";
                } // END of cmmStackCpuLoad1minCriticalThreshold definition.

                leaf cmmStackCpuLoad5minCriticalThreshold  {
                    type  cml-data-types:CML_FLOAT_T;
                    units "%";
                    description "The CPU Critical Threshold percentage value for 5 min load. '-1000.01' indicates unavailable.";
                } // END of cmmStackCpuLoad5minCriticalThreshold definition.

                leaf cmmStackCpuLoad15minCriticalThreshold  {
                    type  cml-data-types:CML_FLOAT_T;
                    units "%";
                    description "The CPU Critical Threshold percentage value for 15 min load. '-1000.01' indicates unavailable.";
                } // END of cmmStackCpuLoad15minCriticalThreshold definition.

                leaf cmmStackUnitCpuUtilization  {
                    type  cml-data-types:CML_FLOAT_T;
                    units "%";
                    description "Total cpu usage in percentage. '-1000.01' indicates unavailable.";
                } // END of cmmStackUnitCpuUtilization definition.

                leaf cmmStackUnitCpuUtilAlertThreshold  {
                    type  cml-data-types:CML_FLOAT_T;
                    units "%";
                    description "The CPU utilization Alert Threshold %. '-1000.01' indicates unavailable.";
                } // END of cmmStackUnitCpuUtilAlertThreshold definition.

                leaf cmmStackUnitCpuUtilCriticalThreshold  {
                    type  cml-data-types:CML_FLOAT_T;
                    units "%";
                    description "The CPU utilization Critical Threshold %. '-1000.01' indicates unavailable.";
                } // END of cmmStackUnitCpuUtilCriticalThreshold definition.

            } // END of cmmStackCpuTable-container definition.
            container cmmSysPowerRailTable {
                config false;
                description
                    "list of power rail information in the chassis";
                leaf cmmSysPOWERVDDR  {
                    type  cml-data-types:CML_CMM_POWER_RAIL_T;
                    description "Power statistics for VCC 3.3v on Main board";
                } // END of cmmSysPOWERVDDR definition.

                leaf cmmSysPOWERCORE  {
                    type  cml-data-types:CML_CMM_POWER_RAIL_T;
                    description "Power statistics for Mac 1v on Main board";
                } // END of cmmSysPOWERCORE definition.

                leaf cmmSysV1P1POWERRAIL  {
                    type  cml-data-types:CML_CMM_POWER_RAIL_T;
                    description "Power statistics for Mac AVS 1v on Main board";
                } // END of cmmSysV1P1POWERRAIL definition.

                leaf cmmSysMAINBOARDPOWERRAIL  {
                    type  cml-data-types:CML_CMM_POWER_RAIL_T;
                    description "Power status  for Main Board";
                } // END of cmmSysMAINBOARDPOWERRAIL definition.

                leaf cmmSysVCC5V  {
                    type  cml-data-types:CML_CMM_POWER_RAIL_T;
                    description "Power status of VCC 5V";
                } // END of cmmSysVCC5V definition.

                leaf cmmSysVCC33V  {
                    type  cml-data-types:CML_CMM_POWER_RAIL_T;
                    description "Power status of VCC 33V";
                } // END of cmmSysVCC33V definition.

                leaf cmmSysVCCMAC1V  {
                    type  cml-data-types:CML_CMM_POWER_RAIL_T;
                    description "Power status of VCCMAC1V";
                } // END of cmmSysVCCMAC1V definition.

                leaf cmmSysVCCMACAVS1V  {
                    type  cml-data-types:CML_CMM_POWER_RAIL_T;
                    description "Power status of VCCMACAVS1V";
                } // END of cmmSysVCCMACAVS1V definition.

                leaf cmmSysVCCV1P05  {
                    type  cml-data-types:CML_CMM_POWER_RAIL_T;
                    description "Power Status of VCCV1P05";
                } // END of cmmSysVCCV1P05 definition.

                leaf cmmSysVCCV1P5  {
                    type  cml-data-types:CML_CMM_POWER_RAIL_T;
                    description "Power Status of VCCV1P5";
                } // END of cmmSysVCCV1P5 definition.

                leaf cmmSysVCCV1P8  {
                    type  cml-data-types:CML_CMM_POWER_RAIL_T;
                    description "Power Status of VCCV1P8";
                } // END of cmmSysVCCV1P8 definition.

                leaf cmmSysV1P05POWERRAIL  {
                    type  cml-data-types:CML_CMM_POWER_RAIL_T;
                    description "Power status of V1P05POWERRAIL";
                } // END of cmmSysV1P05POWERRAIL definition.

                leaf cmmSysV1P5POWERRAIL  {
                    type  cml-data-types:CML_CMM_POWER_RAIL_T;
                    description "Power status of V1P5POWERRAIL";
                } // END of cmmSysV1P5POWERRAIL definition.

                leaf cmmSysVCCPOWERRAIL  {
                    type  cml-data-types:CML_CMM_POWER_RAIL_T;
                    description "Power status of VCCPOWERRAIL";
                } // END of cmmSysVCCPOWERRAIL definition.

                leaf cmmSysSBV1P5POWERRAIL  {
                    type  cml-data-types:CML_CMM_POWER_RAIL_T;
                    description "Power status of SBV1P5POWERRAIL";
                } // END of cmmSysSBV1P5POWERRAIL definition.

                leaf cmmSysV1P0POWERRAIL  {
                    type  cml-data-types:CML_CMM_POWER_RAIL_T;
                    description "Power rail 1.0V Status";
                } // END of cmmSysV1P0POWERRAIL definition.

                leaf cmmSysV3P3POWERRAIL  {
                    type  cml-data-types:CML_CMM_POWER_RAIL_T;
                    description "Power rail 3.3V Status";
                } // END of cmmSysV3P3POWERRAIL definition.

                leaf cmmSysV1P8POWERRAIL  {
                    type  cml-data-types:CML_CMM_POWER_RAIL_T;
                    description "Power rail 1.8V Status";
                } // END of cmmSysV1P8POWERRAIL definition.

                leaf cmmSysV1P35POWERRAIL  {
                    type  cml-data-types:CML_CMM_POWER_RAIL_T;
                    description "Power Rail 1.35 Status";
                } // END of cmmSysV1P35POWERRAIL definition.

                leaf cmmSysVCCAVS1V  {
                    type  cml-data-types:CML_CMM_POWER_RAIL_T;
                    description "Power status of VCCAVS1V";
                } // END of cmmSysVCCAVS1V definition.

                leaf cmmSysDDRVTT  {
                    type  cml-data-types:CML_CMM_POWER_RAIL_T;
                    description "Power statistics for VCC 5v on Main board.";
                } // END of cmmSysDDRVTT definition.

            } // END of cmmSysPowerRailTable-container definition.
            container cmmSysComponentStatusTable {
                config false;
                description
                    "Details of each component status in the Unit.";
                leaf cmmSysPsu1Status  {
                    type  cml-data-types:CML_CMM_SYS_AND_COMPONENT_STATUS_T;
                    description "Status of PSU1.";
                } // END of cmmSysPsu1Status definition.

                leaf cmmSysPsu1LedColor  {
                    type  cml-data-types:CML_CMM_LED_COLOR_CODE_T;
                    description "Color of the power led of PSU1.";
                } // END of cmmSysPsu1LedColor definition.

                leaf cmmSysPsu2Status  {
                    type  cml-data-types:CML_CMM_SYS_AND_COMPONENT_STATUS_T;
                    description "Status of PSU2.";
                } // END of cmmSysPsu2Status definition.

                leaf cmmSysPsu2LedColor  {
                    type  cml-data-types:CML_CMM_LED_COLOR_CODE_T;
                    description "Color of the power led of PSU2.";
                } // END of cmmSysPsu2LedColor definition.

                leaf cmmSysLocatorLedStatus  {
                    type  cml-data-types:CML_CMM_MASTER_LOCATOR_STATUS_T;
                    description "Status of Locator led.";
                } // END of cmmSysLocatorLedStatus definition.

                leaf cmmSysLocatorLedColor  {
                    type  cml-data-types:CML_CMM_LED_COLOR_CODE_T;
                    description "Color of Locator led";
                } // END of cmmSysLocatorLedColor definition.

                leaf cmmSysMasterLedStatus  {
                    type  cml-data-types:CML_CMM_MASTER_LOCATOR_STATUS_T;
                    description "Status of Master led";
                } // END of cmmSysMasterLedStatus definition.

                leaf cmmSysMasterLedColor  {
                    type  cml-data-types:CML_CMM_LED_COLOR_CODE_T;
                    description "Color of Master led";
                } // END of cmmSysMasterLedColor definition.

                leaf cmmSysFanStatus  {
                    type  cml-data-types:CML_CMM_SYS_AND_COMPONENT_STATUS_T;
                    description "Overall Status of Fans in the Unit.";
                } // END of cmmSysFanStatus definition.

                leaf cmmSysFrontFanLedColor  {
                    type  cml-data-types:CML_CMM_LED_COLOR_CODE_T;
                    description "Color of the Front Fan led.";
                } // END of cmmSysFrontFanLedColor definition.

                leaf cmmSysRamStatus  {
                    type  cml-data-types:CML_CMM_SYS_AND_COMPONENT_STATUS_T;
                    description "Status of RAM in the unit";
                } // END of cmmSysRamStatus definition.

                leaf cmmSysCpuStatus  {
                    type  cml-data-types:CML_CMM_SYS_AND_COMPONENT_STATUS_T;
                    description "Status of CPU in the unit";
                } // END of cmmSysCpuStatus definition.

                leaf cmmSysDiskStatus  {
                    type  cml-data-types:CML_CMM_SYS_AND_COMPONENT_STATUS_T;
                    description "Status of HARD DISK in the unit";
                } // END of cmmSysDiskStatus definition.

                leaf cmmSysTemperatureStatus  {
                    type  cml-data-types:CML_CMM_SYS_AND_COMPONENT_STATUS_T;
                    description "Status of Temperature sensors in the unit.";
                } // END of cmmSysTemperatureStatus definition.

            } // END of cmmSysComponentStatusTable-container definition.
            container cmmSysSwModuleTable {
                config false;
                description
                    "list of software version information in a processor";
                leaf cmmSysSwRuntimeImgVersion  {
                    type  cml-data-types:CML_STRING_T;
                    description "This variable indicates the software module version that is currently running on the processor.The software release version is in the format as follow: <major version>.<minor version>.<minor version>......'1.2' indicate major version of 1 and minor release of 2.";
                } // END of cmmSysSwRuntimeImgVersion definition.

                leaf cmmSysSwRuntimeImgDate  {
                    type  cml-data-types:CML_DATE_TIME_T;
                    description "The release date of this software module.";
                } // END of cmmSysSwRuntimeImgDate definition.

            } // END of cmmSysSwModuleTable-container definition.
            container cmmSysHardDiskTable {
                config false;
                description
                    "Details of Hard disk information of the Unit.";
                leaf cmmSysHarddiskSerialno  {
                    type  cml-data-types:CML_STRING_T;
                    description "Hard disk's serial number. Blank indicates unavailable.";
                } // END of cmmSysHarddiskSerialno definition.

                leaf cmmSysHarddiskModelno  {
                    type  cml-data-types:CML_STRING_T;
                    description "Hard disk's model number. Blank indicates unavailable.";
                } // END of cmmSysHarddiskModelno definition.

                leaf cmmSysHarddiskFirmwarerev  {
                    type  cml-data-types:CML_LINE_T;
                    description "Hard disk's firmware revision. Blank indicates unavailable.";
                } // END of cmmSysHarddiskFirmwarerev definition.

                leaf cmmSysHarddiskCylinders  {
                    type  cml-data-types:CML_INT32_T;
                    description "Hard disk's Cylinder unit. '-100001' indicates unavailable.";
                } // END of cmmSysHarddiskCylinders definition.

                leaf cmmSysHarddiskHeads  {
                    type  cml-data-types:CML_INT32_T;
                    description "Hard disk's Head unit. '-100001' indicates unavailable.";
                } // END of cmmSysHarddiskHeads definition.

                leaf cmmSysHarddiskSectors  {
                    type  cml-data-types:CML_INT32_T;
                    description "Hard disk's Sector unit. '-100001' indicates unavailable.";
                } // END of cmmSysHarddiskSectors definition.

                leaf cmmSysHarddiskUnformattedBytesorTrack  {
                    type  cml-data-types:CML_INT32_T;
                    description "Hard disk's unformated bytes or track. '-100001' indicates unavailable.";
                } // END of cmmSysHarddiskUnformattedBytesorTrack definition.

                leaf cmmSysHarddiskUnformattedBytesorSector  {
                    type  cml-data-types:CML_INT32_T;
                    description "Hard disk's unformated bytes or sector. '-100001' indicates unavailable.";
                } // END of cmmSysHarddiskUnformattedBytesorSector definition.

                leaf cmmSysHarddiskRevisionNum  {
                    type  cml-data-types:CML_STRING_T;
                    description "Hard disk's Revision number. Blank indicates unavailable";
                } // END of cmmSysHarddiskRevisionNum definition.

                leaf cmmSysHarddiskTotalsize  {
                    type  cml-data-types:CML_INT32_T;
                    units "MBytes";
                    description "Total memory of the Hard disk. '-100001' indicates unavailable.";
                } // END of cmmSysHarddiskTotalsize definition.

                leaf cmmSysHarddiskUsedMem  {
                    type  cml-data-types:CML_INT32_T;
                    units "%";
                    description "Used memory of the Hard disk. '-100001' indicates unavailable.";
                } // END of cmmSysHarddiskUsedMem definition.

                leaf cmmSysHarddiskFreeMem  {
                    type  cml-data-types:CML_INT32_T;
                    units "%";
                    description "Free memory of the Hard disk. '-100001' indicates unavailable.";
                } // END of cmmSysHarddiskFreeMem definition.

                leaf cmmSysHarddiskUsageCriticalThreshold  {
                    type  cml-data-types:CML_INT32_T;
                    units "%";
                    description "Harddisk usage threshold %  for Critical Level. '-100001' indicates unavailable.";
                } // END of cmmSysHarddiskUsageCriticalThreshold definition.

                leaf cmmSysHarddiskUsageAlertThreshold  {
                    type  cml-data-types:CML_INT32_T;
                    units "%";
                    description "Harddisk usage threshold %  for Alert Level. '-100001' indicates unavailable.";
                } // END of cmmSysHarddiskUsageAlertThreshold definition.

                leaf cmmSysMountPoint  {
                    type  cml-data-types:CML_STRING_T;
                    description "Path of the mounted filesystem";
                } // END of cmmSysMountPoint definition.

                leaf cmmSysHardDiskRemainLifeCriticalThreshold  {
                    type  cml-data-types:CML_INT32_T;
                    units "%";
                    description "Harddisk Remain Life threshold % for Critical Level '-100001' indicates unavailable.";
                } // END of cmmSysHardDiskRemainLifeCriticalThreshold definition.

                leaf cmmSysHardDiskRemainLifeAlertThreshold  {
                    type  cml-data-types:CML_INT32_T;
                    units "%";
                    description "Harddisk Remain Life threshold % values for Alert Level. '-100001' indicates unavailable.";
                } // END of cmmSysHardDiskRemainLifeAlertThreshold definition.

                leaf cmmSysHardDiskRemainLife  {
                    type  cml-data-types:CML_INT32_T;
                    units "%";
                    description "Harddisk Remain life % Values '-100001' indicates unavailable.";
                } // END of cmmSysHardDiskRemainLife definition.

                leaf cmmSysHardDiskAvailableReservedSpaceCriticalThreshold  {
                    type  cml-data-types:CML_INT32_T;
                    units "%";
                    description "Harddisk Available Reserved Space threshold % values for critical Level'-100001' indicates unavailable.";
                } // END of cmmSysHardDiskAvailableReservedSpaceCriticalThreshold definition.

                leaf cmmSysHardDiskAvailableReservedSpaceAlertThreshold  {
                    type  cml-data-types:CML_INT32_T;
                    units "%";
                    description "Harddisk Available Reserved Space threshold % values for Alert Level'-100001' indicates unavailable.";
                } // END of cmmSysHardDiskAvailableReservedSpaceAlertThreshold definition.

                leaf cmmSysHardDiskAvailableReservedSpace  {
                    type  cml-data-types:CML_INT32_T;
                    units "%";
                    description "Harddisk Available Reserved Space % values'-100001' indicates unavailable.";
                } // END of cmmSysHardDiskAvailableReservedSpace definition.

                leaf cmmSysHardDiskReallocSectorsCount  {
                    type  cml-data-types:CML_INT32_T;
                    units "1";
                    description "Harddisk Reallocated Sectors Count values '-100001' indicates unavailable.";
                } // END of cmmSysHardDiskReallocSectorsCount definition.

                leaf cmmSysHardDiskUncorrectSectorCount  {
                    type  cml-data-types:CML_INT32_T;
                    units "1";
                    description "Harddisk Uncorrectable Sectors Count '-100001' indicates unavailable.";
                } // END of cmmSysHardDiskUncorrectSectorCount definition.

            } // END of cmmSysHardDiskTable-container definition.
            container cmmSystemStatusTable {
                config false;
                description
                    "Details of overall system status of the Unit";
                leaf cmmSystemMinorFaultStatus  {
                    type  cml-data-types:CML_CMM_SYS_FAULT_STATUS_T;
                    description "overall Alert status caused by individual components in the unit.";
                } // END of cmmSystemMinorFaultStatus definition.

                leaf cmmSystemMajorFaultStatus  {
                    type  cml-data-types:CML_CMM_SYS_FAULT_STATUS_T;
                    description "overall Critical status caused by individual components in the unit.";
                } // END of cmmSystemMajorFaultStatus definition.

                leaf cmmSysStatus  {
                    type  cml-data-types:CML_CMM_SYS_AND_COMPONENT_STATUS_T;
                    description "Overall Status/Health of System.";
                } // END of cmmSysStatus definition.

                leaf cmmSysLedColor  {
                    type  cml-data-types:CML_CMM_LED_COLOR_CODE_T;
                    description "Color of the system led.";
                } // END of cmmSysLedColor definition.

            } // END of cmmSystemStatusTable-container definition.
        } // End of cmmStackUnitTable-list
    } // END of cmmStackUnitTable-grouping definition.

    grouping  cmmGlobals-grouping {
    description
        "cmm global structure";
    container cmmGlobals {
        description
            "cmm global structure";
        leaf locatorLed  {
            type  cml-data-types:CML_BOOL_T;
            description "To set the locator-led on or off.";
        } // END of locatorLed definition.

        leaf ddmDebugFlag  {
            type  cml-data-types:CML_BOOL_T;
            description "";
        } // END of ddmDebugFlag definition.

        leaf cmmDebugFlag  {
            type  cml-data-types:CML_BOOL_T;
            description "";
        } // END of cmmDebugFlag definition.

        leaf cmmTaiDebug  {
            if-feature feature-list:HAVE_COHERENT_OPTICS;
            type  CML_TAI_DEBUG_FLAG_T;
            description "To set tai log level severity for Module/Netif/Hostif.";
        } // END of cmmTaiDebug definition.

        leaf cmmWarningRepeat  {
            type  cml-data-types:CML_BOOL_T;
            description "To enable cmm warning level logs to repeat.";
        } // END of cmmWarningRepeat definition.

        leaf monitorTimerInterval  {
            type  cml-data-types:CML_UINT16_T {
                 range "60..3600";
            }
            description "To set DDM Monitor interval time.";
        } // END of monitorTimerInterval definition.

        leaf statusServiceUnsuppTrans  {
            type  cml-data-types:CML_BOOL_T;
            description "To enable DDM Monitor for unsupported transceivers at user risk.";
        } // END of statusServiceUnsuppTrans definition.

    } // END of cmmGlobals-container definition.
    } // END of cmmGlobals-container definition.

    grouping  cmmDdm-grouping {
    description
        "ddm monitor";
    container cmmDdm {
        description
            "ddm monitor";
    } // END of cmmDdm-container definition.
    } // END of cmmDdm-container definition.

    grouping  cmmInterface-grouping {
    description
        "CMM Interface properties";
    container cmmInterface {
        description
            "CMM Interface properties";
        leaf monitorPort  {
            type  cml-data-types:CML_BOOL_T;
            description "To enable DDM monitor for current transceiver.";
        } // END of monitorPort definition.

        leaf transceiverCode  {
            type  cml-data-types:CML_CMM_TRANSCEIVER_T;
            description "To set transceiver code for current transceiver.";
        } // END of transceiverCode definition.

    } // END of cmmInterface-container definition.
    } // END of cmmInterface-container definition.

    grouping  cmmCpuLoadThresh-grouping {
    description
        "CPU load average 1, 5, and 15 minute thresholds";
    container cmmCpuLoadThresh {
        description
            "CPU load average 1, 5, and 15 minute thresholds";
        leaf cmmCpuLoad1MinWarnVal  {
            type  cml-data-types:CML_UINT8_T {
                 range "41..100";
            }
            description "";
        } // END of cmmCpuLoad1MinWarnVal definition.

        leaf cmmCpuLoad1MinAlarmVal  {
            type  cml-data-types:CML_UINT8_T {
                 range "51..100";
            }
            description "";
        } // END of cmmCpuLoad1MinAlarmVal definition.

        leaf cmmCpuLoad5MinAlarmVal  {
            type  cml-data-types:CML_UINT8_T {
                 range "51..100";
            }
            description "";
        } // END of cmmCpuLoad5MinAlarmVal definition.

        leaf cmmCpuLoad15MinAlarmVal  {
            type  cml-data-types:CML_UINT8_T {
                 range "51..100";
            }
            description "";
        } // END of cmmCpuLoad15MinAlarmVal definition.

    } // END of cmmCpuLoadThresh-container definition.
    } // END of cmmCpuLoadThresh-container definition.

    grouping  cmmCpuCoreThresh-grouping {
    description
        "CPU core usage thresholds";
    container cmmCpuCoreThresh {
        description
            "CPU core usage thresholds";
        leaf cmmCpuCoreWarnVal  {
            type  cml-data-types:CML_UINT8_T {
                 range "51..100";
            }
            description "";
        } // END of cmmCpuCoreWarnVal definition.

        leaf cmmCpuCoreAlarmVal  {
            type  cml-data-types:CML_UINT8_T {
                 range "91..100";
            }
            description "";
        } // END of cmmCpuCoreAlarmVal definition.

    } // END of cmmCpuCoreThresh-container definition.
    } // END of cmmCpuCoreThresh-container definition.

    grouping  cmmAlarmVariable-grouping {
    description
        "cmmAlarmVariable";
    container cmmAlarmVariable {
        config false;
        description
            "cmmAlarmVariable";
        leaf cmmAlarmVarInteger  {
            type  cml-data-types:CML_INT32_T;
            description "An generic integer value in the notification object";
        } // END of cmmAlarmVarInteger definition.

        leaf cmmAlarmVarString  {
            type  cml-data-types:CML_LINE_T;
            description "An generic string value in the notification object";
        } // END of cmmAlarmVarString definition.

    } // END of cmmAlarmVariable-container definition.
    } // END of cmmAlarmVariable-container definition.


}
