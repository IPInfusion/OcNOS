/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-zebos-authradius.yang
*
*/

submodule ipi-zebos-authradius {

    belongs-to  ipi-zebos { prefix ipi-zebos; }

    import cml-data-types {
        prefix cml-data-types;
    }

    include ipi-zebos-vrf;
    organization
        "IP Infusion Inc.";

    contact
        "Address: 3965 Freedom Circle, Suite 200, Santa Clara, CA 95054
        Phone: +1 408-400-1900
        E-mail: support@ipinfusion.com
        Web: http://www.ipinfusion.com/";

    description
        "Layer-3 radius configurations";


    revision "2018-06-21" {
        description " Initial Version.";
        reference "";
    }



    grouping Hostradius-grouping {
    description
        "hostaddr structure";
        list Hostradius {
            key "hostAddr";
            description
                "hostaddr structure";
            leaf hostAddr  {
                type  cml-data-types:CML_IPV4HOSTNAME_T;
                description "";
            } // END of hostAddr definition.

            leaf key  {
                type  cml-data-types:CML_BOOL_T;
                description "";
            } // END of key definition.

            leaf keyType  {
                type  cml-data-types:CML_HOSTP_KEY_TYPE_T;
                default "0";
                description "";
            } // END of keyType definition.

            leaf keyWord  {
                type  cml-data-types:CML_STRING_T;
                description "";
            } // END of keyWord definition.

            leaf authPort  {
                type  cml-data-types:CML_UINT32_T {
                     range "0..65535";
                }
                description "";
            } // END of authPort definition.

            leaf timeout  {
                type  cml-data-types:CML_UINT32_T {
                     range "1..60";
                }
                default "5";
                description "";
            } // END of timeout definition.

            leaf hostRetransmit  {
                type  cml-data-types:CML_UINT32_T {
                     range "1..100";
                }
                description "";
            } // END of hostRetransmit definition.

        } // End of Hostradius-list
    } // END of Hostradius-grouping definition.

    grouping  authradius-grouping {
    description
        "radius related commands";
    container authradius {
        description
            "radius related commands";
        leaf sourceInterface  {
            type  cml-data-types:CML_STRING_T;
            description "";
        } // END of sourceInterface definition.

        leaf port  {
            type  cml-data-types:CML_UINT32_T;
            description "";
        } // END of port definition.

        leaf globalTimeout  {
            type  cml-data-types:CML_UINT32_T {
                 range "1..60";
            }
            default "5";
            description "";
        } // END of globalTimeout definition.

        leaf key  {
            type  cml-data-types:CML_BOOL_T;
            description "";
        } // END of key definition.

        leaf globalKeytype  {
            type  cml-data-types:CML_HOSTP_KEY_TYPE_T;
            default "0";
            description "";
        } // END of globalKeytype definition.

        leaf globalKeyword  {
            type  cml-data-types:CML_STRING_T;
            description "";
        } // END of globalKeyword definition.

        leaf deadtime  {
            type  cml-data-types:CML_UINT32_T;
            description "";
        } // END of deadtime definition.

        leaf retransmit  {
            type  cml-data-types:CML_UINT32_T;
            description "";
        } // END of retransmit definition.

    } // END of authradius-container definition.
    } // END of authradius-container definition.


}
