/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-zebos-imi.yang
*
*/

submodule ipi-zebos-imi {

    belongs-to  ipi-zebos { prefix ipi-zebos; }

    import cml-data-types {
        prefix cml-data-types;
    }

    organization
        "IP Infusion Inc.";

    contact
        "Address: 3965 Freedom Circle, Suite 200, Santa Clara, CA 95054
        Phone: +1 408-400-1900
        E-mail: support@ipinfusion.com
        Web: http://www.ipinfusion.com/";

    description
        "imi global configs";


    revision "2018-06-21" {
        description " Initial Version.";
        reference "";
    }

    grouping execTimeout {
        description
            "line mode configs for console or vty.";
        leaf min  {
            type  cml-data-types:CML_UINT32_T {
                 range "0..35791";
            }
            default "10";
            description "";
        } // END of min definition.

        leaf sec  {
            type  cml-data-types:CML_UINT32_T {
                 range "0..2147483";
            }
            default "0";
            description "";
        } // END of sec definition.

        leaf login  {
            type  cml-data-types:CML_BOOL_T;
            description "";
        } // END of login definition.

        leaf privLevel  {
            type  cml-data-types:CML_UINT8_T {
                 range "1..16";
            }
            description "";
        } // END of privLevel definition.

        leaf loginLocal  {
            type  cml-data-types:CML_BOOL_T;
            description "";
        } // END of loginLocal definition.

        leaf historyMax  {
            type  cml-data-types:CML_UINT32_T {
                 range "0..2147483647";
            }
            description "";
        } // END of historyMax definition.

    } // END of execTimeout definition.

    grouping  webUser-grouping {
    description
        "web user login credentials";
    container webUser {
        description
            "web user login credentials";
        leaf loginName  {
            type  cml-data-types:CML_STRING_T;
            description "";
        } // END of loginName definition.

        leaf loginPasswd  {
            type  cml-data-types:CML_STRING_T;
            description "";
        } // END of loginPasswd definition.

    } // END of webUser-container definition.
    } // END of webUser-container definition.

    grouping  memInfo-grouping {
    description
        "Memory Info enable";
    container memInfo {
        description
            "Memory Info enable";
        leaf memInfoIMI  {
            type  cml-data-types:CML_BOOL_T;
            description "";
        } // END of memInfoIMI definition.

    } // END of memInfo-container definition.
    } // END of memInfo-container definition.


}
