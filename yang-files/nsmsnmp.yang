/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : nsmsnmp.yang
*
*/

submodule nsmsnmp {

    belongs-to  ZebOS { prefix ZebOS; }
    include vrf;


    import cml_data_types {
        prefix cml_data_types;
    }

    import feature_list {
        prefix feature_list;
    }

    description
        "Simple Network Management Protocol";


    revision "2017-02-20" {
        description "Initial version of SNMP datamodel.";
    }


    grouping  nsmsnmp-grouping {
    container nsmsnmp {
                config true;

        description
            "snmp  related operations";

        leaf vrfName  {
            type  cml_data_types:CML_STRING_T {
                length "0..255";
            }
            default "default";
        } // END of vrfName definition.

        leaf enabled  {
            type  cml_data_types:CML_BOOL_T;  
        } // END of enabled definition.

        leaf syscontact  {
            if-feature feature_list:HAVE_SNMP_AGENT;
            type  cml_data_types:CML_STRING_T {
                length "0..255";
            }
        } // END of syscontact definition.

        leaf syslocation  {
            if-feature feature_list:HAVE_SNMP_AGENT;
            type  cml_data_types:CML_STRING_T {
                length "0..255";
            }
        } // END of syslocation definition.

    } // END of nsmsnmp-container definition.
    } // END of nsmsnmp-container definition.


}
