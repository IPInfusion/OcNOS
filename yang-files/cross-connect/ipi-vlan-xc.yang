/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-vlan-xc.yang
*
*/

module ipi-vlan-xc {

    yang-version 1.1;

    namespace   "http://www.ipinfusion.com/yang/ocnos/ipi-vlan-xc";

    prefix "ipi-vlan-xc";

    import ietf-yang-types {
        prefix yang;
        revision-date 2013-07-15;
    }

    import ipi-vlan-xc-types {
        prefix ipi-vlan-xc-types;
        revision-date 2022-06-01;
    }

    import ipi-interface {
        prefix ipi-interface;
        revision-date 2022-08-24;
    }

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for IPI VLAN XC Managed Object";


    revision "2022-06-01" {
        description "Updated the yang file with feature";
        reference " 0.2.0.";
    }

    revision "2021-03-12" {
        description "Initial Version";
        reference " 0.1.0.";
    }

    grouping crossconnect-statistics-state {
        description
            "Grouping for VLAN XC entry state";
        leaf ep1-rx-pkts  {
            type  yang:counter64;
            description "The number of packets received on Endpoint-1";
        } // END of ep1-rx-pkts definition.

        leaf ep1-rx-bytes  {
            type  yang:counter64;
            description "The number of bytes received on Endpoint-1";
        } // END of ep1-rx-bytes definition.

        leaf ep1-tx-pkts  {
            type  yang:counter64;
            description "The number of packets transmitted from Endpoint-1";
        } // END of ep1-tx-pkts definition.

        leaf ep1-tx-bytes  {
            type  yang:counter64;
            description "The number of bytes transmitted from Endpoint-1";
        } // END of ep1-tx-bytes definition.

        leaf ep2-rx-pkts  {
            type  yang:counter64;
            description "The number of packets received on Endpoint-2";
        } // END of ep2-rx-pkts definition.

        leaf ep2-rx-bytes  {
            type  yang:counter64;
            description "The number of bytes received on Endpoint-2";
        } // END of ep2-rx-bytes definition.

        leaf ep2-tx-pkts  {
            type  yang:counter64;
            description "The number of packets transmitted from Endpoint-2";
        } // END of ep2-tx-pkts definition.

        leaf ep2-tx-bytes  {
            type  yang:counter64;
            description "The number of bytes transmitted from Endpoint-2";
        } // END of ep2-tx-bytes definition.

        leaf bkp-ep1-rx-pkts  {
            type  yang:counter64;
            description "The number of packets received on Backup Endpoint-1";
        } // END of bkp-ep1-rx-pkts definition.

        leaf bkp-ep1-rx-bytes  {
            type  yang:counter64;
            description "The number of bytes received on Backup Endpoint-1";
        } // END of bkp-ep1-rx-bytes definition.

        leaf bkp-ep1-tx-pkts  {
            type  yang:counter64;
            description "The number of packets transmitted from Backup Endpoint-1";
        } // END of bkp-ep1-tx-pkts definition.

        leaf bkp-ep1-tx-bytes  {
            type  yang:counter64;
            description "The number of bytes transmitted from Backup Endpoint-1";
        } // END of bkp-ep1-tx-bytes definition.

        leaf bkp-ep2-rx-pkts  {
            type  yang:counter64;
            description "The number of packets received on Backup Endpoint-2";
        } // END of bkp-ep2-rx-pkts definition.

        leaf bkp-ep2-rx-bytes  {
            type  yang:counter64;
            description "The number of bytes received on Backup Endpoint-2";
        } // END of bkp-ep2-rx-bytes definition.

        leaf bkp-ep2-tx-pkts  {
            type  yang:counter64;
            description "The number of packets transmitted from Backup Endpoint-2";
        } // END of bkp-ep2-tx-pkts definition.

        leaf bkp-ep2-tx-bytes  {
            type  yang:counter64;
            description "The number of bytes transmitted from Backup Endpoint-2";
        } // END of bkp-ep2-tx-bytes definition.

    } // END of crossconnect-statistics-state definition.
    grouping vlan-cross-connect-entries-top {
        description
            "Grouping for VLAN XC entry config";
        container vlan-xc-entries {
            description
                "Top level container for VLAN XC Entry";

            list vlan-xc-entry {
                key "outer-vlan-range inner-vlan-range";
                description
                    "vlan xc entry list";
                leaf outer-vlan-range  {
                    type  leafref {
                        path  "../config/outer-vlan-range";
                    }
                    description "Use this attribute to set the outer vlan id for XC.";
                } // END of outer-vlan-range definition.

                leaf inner-vlan-range  {
                    type  leafref {
                        path  "../config/inner-vlan-range";
                    }
                    description "Use this attribute to set the inner vlan id for XC.";
                } // END of inner-vlan-range definition.

                container config {
                    description
                        "Configurational data for XC entry";
                    uses vlan-xc-entries-config;
                } // END of config-container definition.
                container state {
                    config false;
                    description
                        "Operational state data for XC entry";
                    uses vlan-xc-entries-config;
                    uses crossconnect-statistics-state;
                } // END of state-container definition.
            } // End of vlan-xc-entry-list
        } // END of vlan-xc-entries-container definition.
    } // END of vlan-cross-connect-entries-top definition.
    grouping vlan-xc-entries-config {
        description
            "Grouping for VLAN XC entry config";
        leaf outer-vlan-range  {
            type  string {
                length "1..1965";
                pattern "[^?' =,>|]+";
            }
            description "Use this attribute to set the outer vlan id for XC.";
        } // END of outer-vlan-range definition.

        leaf inner-vlan-range  {
            type  string {
                length "1..1965";
                pattern "[^?' =,>|]+";
            }
            description "Use this attribute to set the inner vlan id for XC.";
        } // END of inner-vlan-range definition.

    } // END of vlan-xc-entries-config definition.
    grouping crossconnect-config {
        description
            "Grouping for Cross-connect Configuration data for ethernet interfaces";
        leaf xconnect-name  {
            type  string {
                length "1..30";
                pattern "[^?' =,>|]+";
            }
            description "This attribute uniquely identifies a cross connect on the device";
        } // END of xconnect-name definition.

        leaf disable  {
            type  empty;
            description "Disable this cross connect";
        } // END of disable definition.

        leaf backup-endpoint-1  {
            type  string {
                length "1..1965";
                pattern "[^?' =,>|]+";
            }
            description "Configure backup endpoint-1";
        } // END of backup-endpoint-1 definition.

        leaf backup-endpoint-2  {
            type  string {
                length "1..1965";
                pattern "[^?' =,>|]+";
            }
            description "Configure backup endpoint-2";
        } // END of backup-endpoint-2 definition.

        leaf revertive  {
            type  empty;
            description "Enable revertive operation for this XC";
        } // END of revertive definition.

        leaf link-fault-pass-through-enable  {
            type  empty;
            description "Configure link fault pass through";
        } // END of link-fault-pass-through-enable definition.

    } // END of crossconnect-config definition.
    grouping crossconnect-port-config {
        description
            "Grouping for Port Cross-connect state variables for ethernet
                        interfaces";
        leaf port-endpoint-1  {
            type  leafref {
                path  "/ipi-interface:interfaces/ipi-interface:interface/ipi-interface:name";
            }
            mandatory true;
            description "Configure port endpoint-1";
        } // END of port-endpoint-1 definition.

        leaf port-endpoint-2  {
            when " ../port-endpoint-1 ";
            type  leafref {
                path  "/ipi-interface:interfaces/ipi-interface:interface/ipi-interface:name";
            }
            mandatory true;
            description "Configure port endpoint-2";
        } // END of port-endpoint-2 definition.

    } // END of crossconnect-port-config definition.
    grouping crossconnect-port-ep-config {
        description
            "Grouping config for port cross-connect";
        container cross-connect-port {
            description
                "Port cross-connect";
            container config {
                presence "Configuring Port cross-connect";
                description
                    "Cross-connect Configuration data for port cross-connect";
                uses crossconnect-port-config;
            } // END of config-container definition.
            container state {
                config false;
                description
                    "Cross-connect State variables for port cross-connect";
                uses crossconnect-port-config;
                uses crossconnect-statistics-state;
            } // END of state-container definition.
        } // END of cross-connect-port-container definition.
    } // END of crossconnect-port-ep-config definition.
    grouping crossconnect-vlan-config {
        description
            "Grouping for Vlan Cross-connect state variables for ethernet
                        interfaces";
        leaf vlan-endpoint-1  {
            type  leafref {
                path  "/ipi-interface:interfaces/ipi-interface:interface/ipi-interface:name";
            }
            mandatory true;
            description "Configure vlan endpoint-1";
        } // END of vlan-endpoint-1 definition.

        leaf vlan-endpoint-2  {
            when " ../vlan-endpoint-1 ";
            type  leafref {
                path  "/ipi-interface:interfaces/ipi-interface:interface/ipi-interface:name";
            }
            mandatory true;
            description "Configure vlan endpoint-2";
        } // END of vlan-endpoint-2 definition.

    } // END of crossconnect-vlan-config definition.
    grouping crossconnect-vlan-ep-config {
        description
            "Grouping config for vlan cross-connect";
        container cross-connect-vlan {
            description
                "Cross-connect Mode change";
            container config {
                presence "mode change from XC mode to vlan XC mode";
                description
                    "Cross-connect Configuration data for vlan cross-connect";
                uses crossconnect-vlan-config;
            } // END of config-container definition.
            container state {
                config false;
                description
                    "Cross-connect State variables for vlan cross-connect";
                uses crossconnect-vlan-config;
            } // END of state-container definition.
            uses vlan-cross-connect-entries-top;
        } // END of cross-connect-vlan-container definition.
    } // END of crossconnect-vlan-ep-config definition.
    grouping crossconnect-state {
        description
            "Grouping for Cross-connect state variables for ethernet interfaces";
        leaf admin-status  {
            type  ipi-vlan-xc-types:vlan_xc_admin_status_t;
            config false;
            description "Admin status of cross connect";
        } // END of admin-status definition.

        leaf oper-status  {
            type  ipi-vlan-xc-types:vlan_xc_oper_status_t;
            config false;
            description "Oper status of cross connect";
        } // END of oper-status definition.

    } // END of crossconnect-state definition.

    grouping  cross-connects-grouping {
    description
        "cross-connect top level container";
    container cross-connects {
        if-feature feature-list:HAVE_VLAN_XC;
        if-feature feature-list:HAVE_VLAN;
        description
            "cross-connect top level container";

        list cross-connect {
            if-feature feature-list:HAVE_VLAN_XC;
            key "xconnect-name";
            description
                "List of configured cross connects";
            leaf xconnect-name  {
                type  leafref {
                    path  "../config/xconnect-name";
                }
                description "This attribute uniquely identifies a cross connect on the device";
            } // END of xconnect-name definition.

            container config {
                description
                    "Cross-connect Configuration data for ethernet interfaces";
                uses crossconnect-config;
            } // END of config-container definition.
            container state {
                config false;
                description
                    "Cross-connect State variables for Ethernet interfaces";
                uses crossconnect-config;
                uses crossconnect-state;
                uses crossconnect-statistics-state;
            } // END of state-container definition.
            uses crossconnect-port-ep-config;
            uses crossconnect-vlan-ep-config;
        } // End of cross-connect-list
    } // END of cross-connects-container definition.
    } // END of cross-connects-grouping definition.

    uses cross-connects-grouping;

    rpc clear-cross-connect-counters {
        if-feature feature-list:HAVE_VLAN_XC;
        if-feature feature-list:HAVE_VLAN;
        description "Use this RPC to clear cross-connect counters.";
        input  {
            leaf xc-name  {
                type string;
                mandatory true;
                description "Configure xc name";
            }
        }
    }

}
