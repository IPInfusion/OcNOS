/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-ptp.yang
*
*/

module ipi-ptp {

    yang-version 1.1;

    namespace   "http://www.ipinfusion.com/yang/ocnos/ipi-ptp";

    prefix "ipi-ptp";

    import ietf-yang-types {
        prefix yang;
        revision-date 2013-07-15;
    }

    import ietf-inet-types {
        prefix inet;
        revision-date 2013-07-15;
    }

    import cml-data-types {
        prefix cml-data-types;
        revision-date 2022-09-30;
    }

    import ipi-ptp-types {
        prefix ipi-ptp-types;
        revision-date 2022-06-29;
    }

    import feature-list {
        prefix feature-list;
        revision-date 2023-02-21;
    }

    include ipi-ptp-notifications { revision-date 2022-06-01;}
    organization
        "IP Infusion Inc.";

    contact
        "Address: 3965 Freedom Circle, Suite 200, Santa Clara, CA 95054
         Phone: +1 408-400-1900
         E-mail: support@ipinfusion.com
         Web: http://www.ipinfusion.com/";

    description
        "Datamodel for PTP configurations";


    revision "2022-06-29" {
        description "added new cli for servo config";
        reference " 0.6.0.";
    }

    revision "2022-06-01" {
        description "Updated the yang file with feature";
        reference " 0.5.0.";
    }

    revision "2022-01-20" {
        description "implicit delete addition for ptp-instance container";
        reference " 0.4.4.";
    }

    revision "2021-09-20" {
        description "Added dependent mode synchronous flag for attributes";
        reference " 0.4.3.";
    }

    revision "2021-09-03" {
        description "Update descriptions of attribute";
        reference " 0.4.2.";
    }

    revision "2021-04-14" {
        description "Added snmp oid and fix the gps-offset command.";
        reference " 0.4.1.";
    }

    revision "2021-04-12" {
        description "Added unset command for time-of-day.";
        reference " 0.4.0.";
    }

    revision "2021-03-02" {
        description "Added port-identity attribute to port dataset.";
        reference " 0.3.0.";
    }

    revision "2021-01-15" {
        description "Updated ipi-ptp module with PTP servo history data and also foreign, master, slave and peer datasets.";
        reference " 0.2.0.";
    }

    revision "2020-12-17" {
        description "PTP restructuring according to OpenConfig style";
        reference " 0.1.0.";
    }

    grouping ptp-instance-top {
        description
            "Grouping for ptp instance configuration";

        list ptp-instance {
        when " /ipi-ptp:ptp/ipi-ptp:ptp-instance/ipi-ptp:config/ipi-ptp:profile ";
            key "instance-type";
            description
                "PTP instance list";
            leaf instance-type  {
                type  leafref {
                    path  "../config/instance-type";
                }
                description "PTP instance type";
            } // END of instance-type definition.

            container config {
                description
                    "Configuration data";
                uses ptp-instance-base-config;
            } // END of config-container definition.
            uses ptp-default-data-set-top;
            uses ptp-port-data-set-top;
            uses ptp-time-of-day-top;
            uses ptp-servo-top;
            uses ptp-current-data-set-top;
            uses ptp-parent-data-set-top;
            uses ptp-time-properties-top;
            uses ptp-statistics-top;
            uses ptp-servo-history-data-top;
        } // End of ptp-instance-list
    } // END of ptp-instance-top definition.
    grouping ptp-instance-base-config {
        description
            "Grouping for ptp instance configuration";
        leaf instance-type  {
            type  uint8 {
                 range "0..1"  {
                    description "0..1: Supported range 0 - 1";
                 }
            }
            description "PTP instance type";
        } // END of instance-type definition.

        leaf profile  {
            type  ipi-ptp-types:ptp_profile_t;
            mandatory true;
            description "Select PTP clock profile g8265.1, g8275.1, g8275.2 or default or
                        e2e-transparent";
        } // END of profile definition.

    } // END of ptp-instance-base-config definition.
    grouping ptp-debug-top {
        description
            "Grouping for ptp debug configuration";
        container debug {
            description
                "Debugging functions";
            container config {
                description
                    "Configuration data";
                uses ptp-debug-config;
            } // END of config-container definition.
            container state {
                config false;
                description
                    "Operational state data";
                uses ptp-debug-config;
                uses ptp-debug-terminal-state;
            } // END of state-container definition.
        } // END of debug-container definition.
    } // END of ptp-debug-top definition.
    grouping ptp-debug-config {
        description
            "Grouping for debug configuration for PTP";
        leaf debug-ptp-conf  {
            type  empty;
            description "Use this attribute to debug the ptp process.";
        } // END of debug-ptp-conf definition.

    } // END of ptp-debug-config definition.
    grouping ptp-debug-terminal-state {
        description
            "Grouping for ptp debug terminal state";
        leaf debug-terminal  {
            type  empty;
            description "This attribute indicates the terminal ptp debug operational state.";
        } // END of debug-terminal definition.

    } // END of ptp-debug-terminal-state definition.
    grouping ptp-port-data-set-top {
        description
            "Grouping for ptp port data set configuration";

        list port {
            if-feature feature-list:HAVE_DUNE;
            key "port-number";
            description
                "List of port data sets of the clock";
            leaf port-number  {
                type  leafref {
                    path  "../config/port-number";
                }
                description "PTP port clock number. Default value is 1.";
            } // END of port-number definition.

            container config {
                description
                    "Configuration data";
                uses ptp-port-config;
            } // END of config-container definition.
            container state {
                config false;
                description
                    "Operational state data";
                uses ptp-port-config;
                uses ptp-port-variables-state;
                uses ptp-port-identity-state;
            } // END of state-container definition.
            uses ptp-port-data-set-clock-quality-top;
            uses ptp-asymmetry-delay-top;
            uses ptp-network-interface-top;
            uses ptp-master-ipv4-address-top;
            uses ptp-master-ipv6-address-top;
            uses ptp-port-statistics-top;
            uses ptp-foreign-data-set-top;
            uses ptp-peer-data-set-top;
            uses ptp-master-data-set-top;
            uses ptp-slave-data-set-top;
            uses ptp-port-drop-counters-top;
        } // End of port-list
    } // END of ptp-port-data-set-top definition.
    grouping ptp-port-config {
        description
            "Grouping for ptp port configuration";
        leaf port-number  {
            type  uint16 {
                 range "1..31"  {
                    description "1..31: Supported range 1 - 31";
                 }
            }
            default "1";
            description "PTP port clock number. Default value is 1.";
        } // END of port-number definition.

        leaf local-priority  {
            type  uint8 {
                 range "1..255"  {
                    description "1..255: Supported range 1 - 255";
                 }
            }
            default "128";
            description "The local priority attribute of the PTP port clock";
        } // END of local-priority definition.

        leaf description  {
            type  cml-data-types:cml_line_t {
                length "1..64";
            }
            description "This parameter is used to set port clock description";
        } // END of description definition.

        leaf transport-type  {
            type  ipi-ptp-types:ptp_encap_type_t;
            description "Set transport type";
        } // END of transport-type definition.

        leaf non-forwardable-mac-addr  {
            type  empty;
            description "Set dst mac as non forwardable mac 01:80:C2:00:00:0E";
        } // END of non-forwardable-mac-addr definition.

        leaf source-ipv6-link-local-address  {
            if-feature feature-list:HAVE_IPV6;
            type  empty;
            description "When set the clock source addrress is a linklocal address";
        } // END of source-ipv6-link-local-address definition.

        leaf log-min-delay-req-interval  {
            type  int8 {
                 range "-7..5"  {
                    description "-7..5: Supported range -7 - 5";
                 }
            }
            default "-6";
            description "The base-two logarithm of the minDelayReqInterval (the minimum
                        permitted mean time interval between successive Delay_Req messages)";
        } // END of log-min-delay-req-interval definition.

        leaf log-announce-interval  {
            type  int8 {
                 range "-3..4"  {
                    description "-3..4: Supported range -3 - 4";
                 }
            }
            default "-3";
            description "The base-two logarithm of the mean announceInterval (mean time
                        interval between successive Announce messages)";
        } // END of log-announce-interval definition.

        leaf announce-receipt-timeout  {
            type  uint8 {
                 range "2..10"  {
                    description "2..10: Supported range 2 - 10";
                 }
            }
            default "3";
            description "The number of announceInterval that have to pass without receipt of an
                        Announce message before the occurrence of the event
                        ANNOUNCE_RECEIPT_TIMEOUT_ EXPIRES";
        } // END of announce-receipt-timeout definition.

        leaf log-sync-interval  {
            type  int8 {
                 range "-7..4"  {
                    description "-7..4: Supported range -7 - 4";
                 }
            }
            default "-6";
            description "The base-two logarithm of the mean SyncInterval for multicast messages";
        } // END of log-sync-interval definition.

        leaf time-to-live  {
            type  uint8 {
                 range "1..255"  {
                    description "1..255: Supported range 1 - 255";
                 }
            }
            default "64";
            description "The ttl value for clock-port";
        } // END of time-to-live definition.

        leaf ip-dscp  {
            type  uint8 {
                 range "0..63"  {
                    description "0..63: Supported range 0 - 63";
                 }
            }
            default "56";
            description "The ip-dscp value for clock-port";
        } // END of ip-dscp definition.

        leaf unicast-grant-duration  {
            type  uint16 {
                 range "60..1000"  {
                    description "60..1000: Supported range 60 - 1000";
                 }
            }
            default "300";
            description "Unicast grant duration field in signalling messages";
        } // END of unicast-grant-duration definition.

        leaf delay-mechanism  {
            type  ipi-ptp-types:ptp_delay_mechanism_t;
            default "E2E";
            description "The propagation delay measuring option used by the port in computing
                        meanPathDelay";
        } // END of delay-mechanism definition.

        leaf version-number  {
            type  int8;
            default "2";
            description "The PTP version in use on the port";
        } // END of version-number definition.

        leaf master-only  {
            type  empty;
            description "When set the port is a master-only port";
        } // END of master-only definition.

        leaf grandmaster-priority-2  {
            type  uint8 {
                 range "0..255"  {
                    description "0..255: Supported range 0 - 255";
                 }
            }
            default "128";
            description "The priority2 denotes priority2 attribute of grandmaster clock";
        } // END of grandmaster-priority-2 definition.

    } // END of ptp-port-config definition.
    grouping ptp-master-ipv4-address-top {
        description
            "Grouping for master ipv4 configuration";

        list master-ipv4-address {
            key "master-clock-source-ipv4-address";
            description
                "Port master-ipv4-address parameters";
            leaf master-clock-source-ipv4-address  {
                type  leafref {
                    path  "../config/master-clock-source-ipv4-address";
                }
                description "Set master clock ipv4 source address";
            } // END of master-clock-source-ipv4-address definition.

            container config {
                description
                    "Configuration data";
                uses ptp-master-ipv4-address-config;
            } // END of config-container definition.
            container state {
                config false;
                description
                    "Operational state data";
                uses ptp-master-ipv4-address-config;
            } // END of state-container definition.
        } // End of master-ipv4-address-list
    } // END of ptp-master-ipv4-address-top definition.
    grouping ptp-master-ipv4-address-config {
        description
            "Grouping for master ipv4 configuration";
        leaf master-clock-source-ipv4-address  {
            type  inet:ipv4-address;
            description "Set master clock ipv4 source address";
        } // END of master-clock-source-ipv4-address definition.

        leaf master-ipv4-address-priority  {
            type  uint8 {
                 range "0..15"  {
                    description "0..15: Supported range 0 - 15";
                 }
            }
            description "";
        } // END of master-ipv4-address-priority definition.

    } // END of ptp-master-ipv4-address-config definition.
    grouping ptp-master-ipv6-address-top {
        description
            "Grouping for master ipv6 configuration";

        list master-ipv6-address {
            key "master-clock-source-ipv6-address";
            description
                "master-ipv6-address parameters";
            leaf master-clock-source-ipv6-address  {
                type  leafref {
                    path  "../config/master-clock-source-ipv6-address";
                }
                description "Set master clock ipv6 source address";
            } // END of master-clock-source-ipv6-address definition.

            container config {
                description
                    "Configuration data";
                uses ptp-master-ipv6-address-config;
            } // END of config-container definition.
            container state {
                config false;
                description
                    "Operational state data";
                uses ptp-master-ipv6-address-config;
            } // END of state-container definition.
        } // End of master-ipv6-address-list
    } // END of ptp-master-ipv6-address-top definition.
    grouping ptp-master-ipv6-address-config {
        description
            "Grouping for master ipv6 configuration";
        leaf master-clock-source-ipv6-address  {
            type  inet:ipv6-address;
            description "Set master clock ipv6 source address";
        } // END of master-clock-source-ipv6-address definition.

        leaf master-ipv6-address-priority  {
            type  uint8 {
                 range "0..15"  {
                    description "0..15: Supported range 0 - 15";
                 }
            }
            description "";
        } // END of master-ipv6-address-priority definition.

    } // END of ptp-master-ipv6-address-config definition.
    grouping ptp-port-variables-state {
        description
            "Grouping for ptp port variables";
        leaf port-state  {
            type  ipi-ptp-types:ptp_port_state_t;
            description "Current state associated with the port";
        } // END of port-state definition.

        leaf peer-mean-path-delay  {
            type  ipi-ptp-types:ptp_time_interval_t;
            description "Peer Mean path delay";
        } // END of peer-mean-path-delay definition.

        leaf signal-fail  {
            type  boolean;
            description "signal fail info of PTP port";
        } // END of signal-fail definition.

    } // END of ptp-port-variables-state definition.
    grouping ptp-port-identity-state {
        description
            "Grouping for ptp port identity states";
        leaf port-identity  {
            type  string {
                length "1..1965";
                pattern "[^?' =,>|]+";
            }
            description "The identity of the port";
        } // END of port-identity definition.

    } // END of ptp-port-identity-state definition.
    grouping ptp-port-statistics-top {
        description
            "Grouping for ptp statistics";
        container statistics {
            description
                "Set of PTP statistics parameters";
            container state {
                config false;
                description
                    "Operational state data";
                uses ptp-port-statistics-state;
            } // END of state-container definition.
        } // END of statistics-container definition.
    } // END of ptp-port-statistics-top definition.
    grouping ptp-port-statistics-state {
        description
            "Grouping for ptp port statistics";
        leaf packets-transmitted  {
            type  yang:counter32;
            description "PTP port packets transmitted";
        } // END of packets-transmitted definition.

        leaf packets-received  {
            type  yang:counter32;
            description "PTP port packets received";
        } // END of packets-received definition.

        leaf packets-discarded  {
            type  yang:counter32;
            description "PTP port packets discarded";
        } // END of packets-discarded definition.

    } // END of ptp-port-statistics-state definition.
    grouping ptp-port-drop-counters-top {
        description
            "Grouping for ptp port drop counters";
        container drop-counters {
            description
                "Set of PTP port drop counters";
            container state {
                config false;
                description
                    "Operational state data";
                uses ptp-port-drop-counters-state;
            } // END of state-container definition.
        } // END of drop-counters-container definition.
    } // END of ptp-port-drop-counters-top definition.
    grouping ptp-port-drop-counters-state {
        description
            "Grouping for ptp port drop counters";
        leaf domain-mismatch  {
            type  yang:counter32;
            description "PTP domain mismatch";
        } // END of domain-mismatch definition.

        leaf memory-alloc-failure  {
            type  yang:counter32;
            description "PTP memory alloc failure";
        } // END of memory-alloc-failure definition.

        leaf pkt-len-too-short  {
            type  yang:counter32;
            description "PTP pkt len too short";
        } // END of pkt-len-too-short definition.

        leaf pkt-rcvd-on-bad-port-state  {
            type  yang:counter32;
            description "PTP pkt rcvd on bad port state";
        } // END of pkt-rcvd-on-bad-port-state definition.

        leaf pkt-profile-mismatch  {
            type  yang:counter32;
            description "PTP profile mismatch";
        } // END of pkt-profile-mismatch definition.

        leaf clock-port-mismatch  {
            type  yang:counter32;
            description "PTP clock port mismatch";
        } // END of clock-port-mismatch definition.

        leaf ptp-packet-parsing-failure  {
            type  yang:counter32;
            description "PTP pkt parsing failure";
        } // END of ptp-packet-parsing-failure definition.

        leaf delreq-from-unknown-slave  {
            type  yang:counter32;
            description "PTP unicast delreq from unknown slave";
        } // END of delreq-from-unknown-slave definition.

        leaf announce-on-master-only-port  {
            type  yang:counter32;
            description "Announce on master only port";
        } // END of announce-on-master-only-port definition.

        leaf invalid-steps-removed-field  {
            type  yang:counter32;
            description "Invalid steps removed field";
        } // END of invalid-steps-removed-field definition.

        leaf unknown-unicast-master  {
            type  yang:counter32;
            description "PTP Unknown unicast master";
        } // END of unknown-unicast-master definition.

        leaf announce-on-gps-ptp-port  {
            type  yang:counter32;
            description "PTP Announce on gps ptp port";
        } // END of announce-on-gps-ptp-port definition.

        leaf sync-rcvd-invalid  {
            type  yang:counter32;
            description "Sync rcvd invalid";
        } // END of sync-rcvd-invalid definition.

        leaf sync-rcvd-without-master  {
            type  yang:counter32;
            description "Sync rcvd without master";
        } // END of sync-rcvd-without-master definition.

    } // END of ptp-port-drop-counters-state definition.
    grouping ptp-foreign-data-set-top {
        description
            "Grouping for PTP foreign dataset";
        container foreign-data-sets {
            config false;
            description
                "PTP foreign dataset list";

            list foreign-data-set {
                key "foreign-master-id";
                config false;
                description
                    "PTP foreign dataset list";
                leaf foreign-master-id  {
                    type  leafref {
                        path  "../state/foreign-master-id";
                    }
                    description "PTP foreign dataset master id";
                } // END of foreign-master-id definition.

                container state {
                    config false;
                    description
                        "Operational data";
                    uses ptp-foreign-data-set-state;
                } // END of state-container definition.
            } // End of foreign-data-set-list
        } // END of foreign-data-sets-container definition.
    } // END of ptp-foreign-data-set-top definition.
    grouping ptp-foreign-data-set-state {
        description
            "Grouping for PTP foreign dataset operational data";
        leaf foreign-master-id  {
            type  uint8;
            description "Foreign dataset master id";
        } // END of foreign-master-id definition.

        leaf current  {
            type  boolean;
            description "Indicates whether this is the current foreign master dataset";
        } // END of current definition.

        leaf ipv4-address  {
            type  inet:ipv4-address;
            description "Foreign dataset IPv4 address";
        } // END of ipv4-address definition.

        leaf ipv6-address  {
            if-feature feature-list:HAVE_IPV6;
            type  inet:ipv6-address;
            description "Foreign dataset IPv6 address";
        } // END of ipv6-address definition.

        leaf l2-address  {
            type  yang:mac-address {
                pattern "[0-9a-fA-F]{2}(:[0-9a-fA-F]{2}){5}";
                }
                description "Foreign dataset L2 address";
            } // END of l2-address definition.

            leaf clock-identity  {
                type  string {
                    length "1..1965";
                    pattern "[^?' =,>|]+";
                }
                description "Identity of the clock";
            } // END of clock-identity definition.

            leaf port-id  {
                type  string {
                    length "1..1965";
                    pattern "[^?' =,>|]+";
                }
                description "Port id";
            } // END of port-id definition.

            leaf clock-class  {
                type  uint8;
                description "clock-class denotes the traceability of the time or frequency
                            distributed by the clock";
            } // END of clock-class definition.

            leaf clock-accuracy  {
                type  uint8;
                description "clock-accuracy indicates the expected accuracy of the clock";
            } // END of clock-accuracy definition.

            leaf offset-scaled-log-variance  {
                type  uint16;
                description "offset-scaled-log-variance provides an estimate of the variations of
                            the clock from a linear timescale when it is not synchronized to
                            another clock using the protocol";
            } // END of offset-scaled-log-variance definition.

            leaf priority-1  {
                type  uint8;
                description "priority-1 attribute of the local clock";
            } // END of priority-1 definition.

            leaf priority-2  {
                type  uint8;
                description "priority-2 attribute of the local clock";
            } // END of priority-2 definition.

            leaf steps-removed  {
                type  uint16;
                description "Maximum number of communication paths between the local clock and the
                            grandmaster clock";
            } // END of steps-removed definition.

            leaf pdv-scaled-allan-variance  {
                type  uint64;
                description "PDV scaled allan variance";
            } // END of pdv-scaled-allan-variance definition.

    } // END of ptp-foreign-data-set-state definition.
    grouping ptp-peer-data-set-top {
        description
            "Grouping for PTP peer dataset";
        container peer-data-sets {
            config false;
            description
                "PTP peer dataset list";

            list peer-data-set {
                key "peer-id";
                config false;
                description
                    "PTP peer dataset list";
                leaf peer-id  {
                    type  leafref {
                        path  "../state/peer-id";
                    }
                    description "PTP peer id";
                } // END of peer-id definition.

                container state {
                    config false;
                    description
                        "Operational data";
                    uses ptp-peer-data-set-state;
                } // END of state-container definition.
            } // End of peer-data-set-list
        } // END of peer-data-sets-container definition.
    } // END of ptp-peer-data-set-top definition.
    grouping ptp-peer-data-set-state {
        description
            "Grouping for PTP peer dataset operational data";
        leaf peer-id  {
            type  uint8;
            description "PTP peer id";
        } // END of peer-id definition.

        leaf ipv4-address  {
            type  inet:ipv4-address;
            description "Peer dataset IPv4 address";
        } // END of ipv4-address definition.

        leaf ipv6-address  {
            if-feature feature-list:HAVE_IPV6;
            type  inet:ipv6-address;
            description "Peer dataset IPv6 address";
        } // END of ipv6-address definition.

        leaf l2-address  {
            type  yang:mac-address {
                pattern "[0-9a-fA-F]{2}(:[0-9a-fA-F]{2}){5}";
                }
                description "Peer dataset L2 address";
            } // END of l2-address definition.

            leaf clock-identity  {
                type  string {
                    length "1..1965";
                    pattern "[^?' =,>|]+";
                }
                description "Identity of the clock";
            } // END of clock-identity definition.

            leaf received-announce  {
                type  yang:counter64;
                description "Received announce packets";
            } // END of received-announce definition.

            leaf received-sync  {
                type  yang:counter64;
                description "Received sync packets";
            } // END of received-sync definition.

            leaf received-followup  {
                type  yang:counter64;
                description "Received follow-up packets";
            } // END of received-followup definition.

            leaf received-reject  {
                type  yang:counter64;
                description "Received reject packets";
            } // END of received-reject definition.

            leaf received-delay-request  {
                type  yang:counter64;
                description "Received delay request packets";
            } // END of received-delay-request definition.

            leaf received-delay-response  {
                type  yang:counter64;
                description "Received delay response packets";
            } // END of received-delay-response definition.

            leaf received-management  {
                type  yang:counter64;
                description "Received management packets";
            } // END of received-management definition.

            leaf received-signaling  {
                type  yang:counter64;
                description "Received signaling packets";
            } // END of received-signaling definition.

            leaf transmitted-announce  {
                type  yang:counter64;
                description "Transmitted announce packets";
            } // END of transmitted-announce definition.

            leaf transmitted-sync  {
                type  yang:counter64;
                description "Transmitted sync packets";
            } // END of transmitted-sync definition.

            leaf transmitted-followup  {
                type  yang:counter64;
                description "Transmitted follow-up packets";
            } // END of transmitted-followup definition.

            leaf transmitted-delay-request  {
                type  yang:counter64;
                description "Transmitted delay request packets";
            } // END of transmitted-delay-request definition.

            leaf transmitted-delay-response  {
                type  yang:counter64;
                description "Transmitted delay response packets";
            } // END of transmitted-delay-response definition.

            leaf transmitted-management  {
                type  yang:counter64;
                description "Transmitted management packets";
            } // END of transmitted-management definition.

            leaf transmitted-signaling  {
                type  yang:counter64;
                description "Transmitted signaling packets";
            } // END of transmitted-signaling definition.

    } // END of ptp-peer-data-set-state definition.
    grouping ptp-master-data-set-top {
        description
            "Grouping for PTP master dataset";
        container master-data-sets {
            config false;
            description
                "PTP master dataset list";

            list master-data-set {
                key "master-id";
                config false;
                description
                    "PTP master dataset list";
                leaf master-id  {
                    type  leafref {
                        path  "../state/master-id";
                    }
                    description "PTP master id";
                } // END of master-id definition.

                container state {
                    config false;
                    description
                        "Operational data";
                    uses ptp-master-data-set-state;
                } // END of state-container definition.
            } // End of master-data-set-list
        } // END of master-data-sets-container definition.
    } // END of ptp-master-data-set-top definition.
    grouping ptp-master-data-set-state {
        description
            "Grouping for PTP master dataset operational data";
        leaf master-id  {
            type  uint8;
            description "PTP master id";
        } // END of master-id definition.

        leaf ipv4-address  {
            type  inet:ipv4-address;
            description "Master dataset IPv4 address";
        } // END of ipv4-address definition.

        leaf ipv6-address  {
            if-feature feature-list:HAVE_IPV6;
            type  inet:ipv6-address;
            description "Master dataset IPv6 address";
        } // END of ipv6-address definition.

    } // END of ptp-master-data-set-state definition.
    grouping ptp-slave-data-set-top {
        description
            "Grouping for PTP slave dataset";
        container slave-data-sets {
            config false;
            description
                "PTP slave dataset list";

            list slave-data-set {
                key "slave-id";
                config false;
                description
                    "PTP slave dataset list";
                leaf slave-id  {
                    type  leafref {
                        path  "../state/slave-id";
                    }
                    description "PTP slave id";
                } // END of slave-id definition.

                container state {
                    config false;
                    description
                        "Operational data";
                    uses ptp-slave-data-set-state;
                } // END of state-container definition.
            } // End of slave-data-set-list
        } // END of slave-data-sets-container definition.
    } // END of ptp-slave-data-set-top definition.
    grouping ptp-slave-data-set-state {
        description
            "Grouping for PTP slave dataset operational data";
        leaf slave-id  {
            type  uint8;
            description "PTP slave id";
        } // END of slave-id definition.

        leaf ipv4-address  {
            type  inet:ipv4-address;
            description "Slave dataset IPv4 address";
        } // END of ipv4-address definition.

        leaf ipv6-address  {
            if-feature feature-list:HAVE_IPV6;
            type  inet:ipv6-address;
            description "Slave dataset IPv6 address";
        } // END of ipv6-address definition.

        leaf clock-identity  {
            type  string {
                length "1..1965";
                pattern "[^?' =,>|]+";
            }
            description "Identity of the clock";
        } // END of clock-identity definition.

        leaf delay-mechanism  {
            type  ipi-ptp-types:ptp_delay_mechanism_t;
            description "The propagation delay measuring option used by the port in computing
                        the mean path delay";
        } // END of delay-mechanism definition.

        leaf log-announce-interval  {
            type  int8;
            description "The base-two logarithm of the mean announce interval (mean time
                        interval between successive Announce messages)";
        } // END of log-announce-interval definition.

        leaf log-sync-interval  {
            type  int8;
            description "The base-two logarithm of the mean sync interval for multicast
                        messages";
        } // END of log-sync-interval definition.

        leaf log-delay-request-interval  {
            type  int8;
            description "The base-two logarithm of the delay request interval";
        } // END of log-delay-request-interval definition.

    } // END of ptp-slave-data-set-state definition.
    grouping ptp-port-data-set-clock-quality-top {
        description
            "Grouping for ptp clock configuration";
        container clock-quality {
            description
                "Port clock quality parameters";
            container config {
                description
                    "Configuration data";
                uses ptp-port-data-set-clock-quality-config;
            } // END of config-container definition.
            container state {
                config false;
                description
                    "Operational state data";
                uses ptp-port-data-set-clock-quality-config;
            } // END of state-container definition.
        } // END of clock-quality-container definition.
    } // END of ptp-port-data-set-clock-quality-top definition.
    grouping ptp-port-data-set-clock-quality-config {
        description
            "Grouping for ptp clock configuration";
        leaf clock-class  {
            type  uint8 {
                 range "0..255"  {
                    description "0..255: Supported range 0 - 255";
                 }
            }
            default "6";
            description "The clock-class denotes the traceability of the time or frequency
                        distributed by the clock";
        } // END of clock-class definition.

        leaf clock-accuracy  {
            type  uint8 {
                 range "0..255"  {
                    description "0..255: Supported range 0 - 255";
                 }
            }
            default "33";
            description "The clock-accuracy indicates the expected accuracy of the clock";
        } // END of clock-accuracy definition.

        leaf offset-scaled-log-variance  {
            type  uint16 {
                 range "0..65535"  {
                    description "0..65535: Supported range 0 - 65535";
                 }
            }
            default "20061";
            description "The offset-scaled-log-variance provides an estimate of the variations
                        of the clock from a linear timescale when it is not synchronized to
                        another clock using the protocol";
        } // END of offset-scaled-log-variance definition.

    } // END of ptp-port-data-set-clock-quality-config definition.
    grouping ptp-asymmetry-delay-top {
        description
            "Grouping to asymmetry delay configuration";
        container asymmetry-delay {
            description
                "PTP asymetry delay parameters";
            container config {
                presence "yes";
                description
                    "Configuration data";
                uses ptp-asymmetry-delay-config;
            } // END of config-container definition.
            container state {
                config false;
                description
                    "Operational state data";
                uses ptp-asymmetry-delay-config;
            } // END of state-container definition.
        } // END of asymmetry-delay-container definition.
    } // END of ptp-asymmetry-delay-top definition.
    grouping ptp-asymmetry-delay-config {
        description
            "Grouping to asymmetry delay configuration";
        leaf delay-asymmetry-msec  {
            type  int8 {
                 range "-100..100"  {
                    description "-100..100: Supported range -100 - 100";
                 }
            }
            mandatory true;
            description "Set delay-asymmetry in milliseconds";
        } // END of delay-asymmetry-msec definition.

        leaf delay-asymmetry-nsec  {
            type  int32 {
                 range "-1000000..1000000"  {
                    description "-1000000..1000000: Supported range -1000000 - 1000000";
                 }
            }
            mandatory true;
            description "Set delay-asymmetry in nanoseconds";
        } // END of delay-asymmetry-nsec definition.

    } // END of ptp-asymmetry-delay-config definition.
    grouping ptp-network-interface-top {
        description
            "Grouping for ptp network interface configuration";

        list network-interface {
            key "network-interface";
            max-elements 1;
            description
                "PTP network-interface parameters";
            leaf network-interface  {
                type  leafref {
                    path  "../config/network-interface";
                }
                description "Reference to the configured underlying interface that is used by this
                            PTP Port";
            } // END of network-interface definition.

            container config {
                description
                    "Configuration data";
                uses ptp-network-interface-config;
            } // END of config-container definition.
            container state {
                config false;
                description
                    "Operational state data";
                uses ptp-network-interface-config;
            } // END of state-container definition.
        } // End of network-interface-list
    } // END of ptp-network-interface-top definition.
    grouping ptp-network-interface-config {
        description
            "Grouping for ptp network interface configuration";
        leaf network-interface  {
            type  ipi-ptp-types:ptp_network_interface_t;
            description "Reference to the configured underlying interface that is used by this
                        PTP Port";
        } // END of network-interface definition.

        leaf vlan-physical-interface-name  {
            type  cml-data-types:cml_ifname_t {
                length "1..1965";
            }
            description "Reference to the configured underlying interface that is used by this
                        vlan interface PTP Port";
        } // END of vlan-physical-interface-name definition.

        leaf vlan-physical-dot1q-vlan-id  {
            type  uint16 {
                 range "1..4095"  {
                    description "1..4095: Supported range 1 - 4095";
                 }
            }
            description "Reference to the configured underlying interface that is used by this
                        PTP Port.
                        The valid range for this attribute vlan-id is related to the value
                        configured in reserved-vlan-base which defines a
                        range of 31 reserved vlans for PTP from the configured value in
                        reserved-vlan-base. By default the range reserved vlan
                        values are 4064-4095. By default the maximum valid value for vlan-id
                        is 4063.";
        } // END of vlan-physical-dot1q-vlan-id definition.

        leaf dot1q-vlan-id  {
            type  uint16 {
                 range "1..4095"  {
                    description "1..4095: Supported range 1 - 4095";
                 }
            }
            description "Reference to the configured underlying interface that is used by this
                        PTP Port.
                        The valid range for this attribute vlan-id is related to the value
                        configured in reserved-vlan-base which defines a
                        range of 31 reserved vlans for PTP from the configured value in
                        reserved-vlan-base. By default the range reserved vlan
                        values are 4064-4095. By default the maximum valid value for vlan-id
                        is 4063.";
        } // END of dot1q-vlan-id definition.

        leaf dot1ad-vlan-id  {
            type  uint16 {
                 range "1..4095"  {
                    description "1..4095: Supported range 1 - 4095";
                 }
            }
            description "Reference to the configured underlying interface that is used by this
                        PTP Port.
                        The valid range for this attribute vlan-id is related to the value
                        configured in reserved-vlan-base which defines a
                        range of 31 reserved vlans for PTP from the configured value in
                        reserved-vlan-base. By default the range reserved vlan
                        values are 4064-4095. By default the maximum valid value for vlan-id
                        is 4063.";
        } // END of dot1ad-vlan-id definition.

        leaf inner-dot1q-vlan-id  {
            type  uint16 {
                 range "1..4095"  {
                    description "1..4095: Supported range 1 - 4095";
                 }
            }
            description "Reference to the configured underlying interface that is used by this
                        PTP Port.
                        The valid range for this attribute vlan-id is related to the value
                        configured in reserved-vlan-base which defines a
                        range of 31 reserved vlans for PTP from the configured value in
                        reserved-vlan-base. By default the range reserved vlan
                        values are 4064-4095. By default the maximum valid value for vlan-id
                        is 4063.";
        } // END of inner-dot1q-vlan-id definition.

    } // END of ptp-network-interface-config definition.
    grouping ptp-time-of-day-top {
        description
            "Grouping for ptp time of day configuration";
        container time-of-day {
            if-feature feature-list:HAVE_DUNE;
            description
                "PTP time of day parameters";
            container config {
                description
                    "Configuration data";
                uses ptp-time-of-day-config;
            } // END of config-container definition.
            container state {
                config false;
                description
                    "Operational state data";
                uses ptp-time-of-day-config;
            } // END of state-container definition.
        } // END of time-of-day-container definition.
    } // END of ptp-time-of-day-top definition.
    grouping ptp-time-of-day-config {
        description
            "Grouping for ptp time of day configuration";
        leaf io-type  {
            type  ipi-ptp-types:ptp_clock_io_type_t;
            description "Type of tod input/output. Default: output";
        } // END of io-type definition.

    } // END of ptp-time-of-day-config definition.
    grouping ptp-default-data-set-top {
        description
            "Grouping for ptp default data set configuration";
        container default-data-set {
            if-feature feature-list:HAVE_DUNE;
            description
                "The default data set of the clock";
            container config {
                description
                    "Configuration data";
                uses ptp-default-data-set-config;
            } // END of config-container definition.
            container state {
                config false;
                description
                    "Operational state data";
                uses ptp-default-data-set-config;
                uses ptp-clock-identity-state;
            } // END of state-container definition.
            uses ptp-servo-history-top;
            uses ptp-default-data-set-clock-quality-top;
            uses ptp-gps-offset-top;
        } // END of default-data-set-container definition.
    } // END of ptp-default-data-set-top definition.
    grouping ptp-default-data-set-config {
        description
            "Grouping for ptp default data set configuration";
        leaf domain  {
            type  uint8 {
                 range "0..127"  {
                    description "0..127: Supported range 0 - 127";
                 }
            }
            default "24";
            description "The domain number of the current domain";
        } // END of domain definition.

        leaf servo-config  {
            type  ipi-ptp-types:ptp_servo_config_type_t;
            description "servo config";
        } // END of servo-config definition.

        leaf external-clock-holdover-duration  {
            type  uint16 {
                 range "0..10080"  {
                    description "0..10080: Supported range 0 - 10080";
                 }
            }
            default "120";
            description "External clock holdover duration";
        } // END of external-clock-holdover-duration definition.

        leaf system-clock-sync  {
            type  uint16 {
                 range "5..600"  {
                    description "5..600: Supported range 5 - 600";
                 }
            }
            default "30";
            description "External clock holdover duration";
        } // END of system-clock-sync definition.

        leaf ptp-clock-sync  {
            type  empty;
            description "";
        } // END of ptp-clock-sync definition.

        leaf ptsf-wtr-duration  {
            type  uint16 {
                 range "1..1440"  {
                    description "1..1440: Supported range 1 - 1440";
                 }
            }
            default "5";
            description "External clock holdover duration";
        } // END of ptsf-wtr-duration definition.

        leaf g8265p1-wtr-duration  {
            type  uint64 {
                 range "0..3600"  {
                    description "0..3600: Supported range 0 - 3600";
                 }
            }
            default "0";
            description "g8265.1 master wtr";
        } // END of g8265p1-wtr-duration definition.

        leaf g8265p1-option  {
            type  ipi-ptp-types:ptp_g8265p1_option_type_t;
            default "1";
            description "g8265.1 option";
        } // END of g8265p1-option definition.

        leaf reserved-vlan-base  {
            type  uint16 {
                 range "1..4064"  {
                    description "1..4064: Supported range 1 - 4064";
                 }
            }
            default "4064";
            description "Reserved vlan base index";
        } // END of reserved-vlan-base definition.

        leaf two-step  {
            if-feature feature-list:HAVE_PTP_HW_OFFLOAD_CUSTOM1;
            type  empty;
            description "two step";
        } // END of two-step definition.

        leaf clock-type-tgm  {
            type  ipi-ptp-types:ptp_clock_type_tgm_t;
            description "clock type as tgm";
        } // END of clock-type-tgm definition.

        leaf one-way  {
            type  empty;
            description "For G.8265.1 one-way ptp";
        } // END of one-way definition.

        leaf number-ports  {
            type  uint8 {
                 range "1..31"  {
                    description "1..31: Supported range 1 - 31";
                 }
            }
            default "1";
            description "Number of ports";
        } // END of number-ports definition.

        leaf pps-pulse-offset  {
            type  int16 {
                 range "-2048..2048"  {
                    description "-2048..2048: Supported range -2048 - 2048";
                 }
            }
            default "0";
            description "1pps Out Pulse Offset in nanoseconds";
        } // END of pps-pulse-offset definition.

        leaf pps-in-smx-tod-type  {
            type  ipi-ptp-types:ptp_1pss_in_smx_tod_type_t;
            default "tod";
            description "1pps in SMX tod type";
        } // END of pps-in-smx-tod-type definition.

        leaf priority-2  {
            when " not(/ipi-ptp:ptp/ipi-ptp:ptp-instance/ipi-ptp:default-data-set/ipi-ptp:config/ipi-ptp:slave-only) ";
            type  uint8 {
                 range "0..255"  {
                    description "0..255: Supported range 0 - 255";
                 }
            }
            default "128";
            description "The priority2 attribute of the local clock";
        } // END of priority-2 definition.

        leaf slave-only  {
            type  empty;
            description "When set the clock is a slave-only clock";
        } // END of slave-only definition.

        leaf local-priority  {
            type  uint8 {
                 range "1..255"  {
                    description "1..255: Supported range 1 - 255";
                 }
            }
            default "128";
            description "The local priority attribute of the local clock";
        } // END of local-priority definition.

        leaf max-steps-removed  {
            type  uint8 {
                 range "1..255"  {
                    description "1..255: Supported range 1 - 255";
                 }
            }
            default "255";
            description "The maximum number of communication paths between the local clock and
                        the grandmaster clock";
        } // END of max-steps-removed definition.

    } // END of ptp-default-data-set-config definition.
    grouping ptp-servo-history-top {
        description
            "Grouping for ptp servo-history configuration";
        container servo-history {
            description
                "PTP servo-history parameters";
            container config {
                presence "yes";
                description
                    "Configuration data";
                uses ptp-servo-history-config;
            } // END of config-container definition.
            container state {
                config false;
                description
                    "Operational data";
                uses ptp-servo-history-config;
            } // END of state-container definition.
        } // END of servo-history-container definition.
    } // END of ptp-servo-history-top definition.
    grouping ptp-servo-history-config {
        description
            "Grouping for servo history configuration";
        leaf servo-history-enabled  {
            type  empty;
            mandatory true;
            description "PTP servo history";
        } // END of servo-history-enabled definition.

        leaf servo-history-interval  {
            type  uint8 {
                 range "1..60"  {
                    description "1..60: Supported range 1 - 60";
                 }
            }
            mandatory true;
            description "PTP servo history interval";
        } // END of servo-history-interval definition.

    } // END of ptp-servo-history-config definition.
    grouping ptp-servo-history-data-top {
        description
            "Grouping for PTP servo history data";
        container servo-history-data {
            if-feature feature-list:HAVE_DUNE;
            config false;
            description
                "PTP servo history data list";

            list servo-history-data-entry {
                key "entry-id";
                config false;
                description
                    "PTP servo history data list";
                leaf entry-id  {
                    type  leafref {
                        path  "../state/entry-id";
                    }
                    description "PTP servo history entry index";
                } // END of entry-id definition.

                container state {
                    config false;
                    description
                        "Operational data";
                    uses ptp-servo-history-data-entry-state;
                } // END of state-container definition.
            } // End of servo-history-data-entry-list
        } // END of servo-history-data-container definition.
    } // END of ptp-servo-history-data-top definition.
    grouping ptp-servo-history-data-entry-state {
        description
            "Grouping for PTP servo history data";
        leaf entry-id  {
            type  uint8;
            description "PTP servo history entry index";
        } // END of entry-id definition.

        leaf timestamp  {
            type  string {
                length "1..1965";
            }
            description "PTP servo history data timestamp";
        } // END of timestamp definition.

        leaf phase-correction  {
            type  decimal64 {
                 fraction-digits 3;            }
            description "PTP servo phase correction";
        } // END of phase-correction definition.

        leaf frequency-correction  {
            type  decimal64 {
                 fraction-digits 3;            }
            description "PTP servo frequency correction";
        } // END of frequency-correction definition.

    } // END of ptp-servo-history-data-entry-state definition.
    grouping ptp-default-data-set-clock-quality-top {
        description
            "Grouping for ptp clock configuration";
        container clock-quality {
            description
                "PTP clock quality parameters";
            container config {
                description
                    "Configuration data";
                uses ptp-default-data-set-clock-quality-config;
            } // END of config-container definition.
            container state {
                config false;
                description
                    "Operational state data";
                uses ptp-default-data-set-clock-quality-config;
            } // END of state-container definition.
        } // END of clock-quality-container definition.
    } // END of ptp-default-data-set-clock-quality-top definition.
    grouping ptp-default-data-set-clock-quality-config {
        description
            "Grouping for ptp clock quality configuration";
        leaf clock-class  {
            when " not(/ipi-ptp:ptp/ipi-ptp:ptp-instance/ipi-ptp:default-data-set/ipi-ptp:config/ipi-ptp:slave-only) ";
            type  uint8 {
                 range "0..255"  {
                    description "0..255: Supported range 0 - 255";
                 }
            }
            default "248";
            description "The clock-class denotes the traceability of the time or frequency
                        distributed by the clock";
        } // END of clock-class definition.

        leaf clock-accuracy  {
            type  uint8 {
                 range "0..255"  {
                    description "0..255: Supported range 0 - 255";
                 }
            }
            default "254";
            description "The clock-accuracy indicates the expected accuracy of the clock";
        } // END of clock-accuracy definition.

        leaf offset-scaled-log-variance  {
            type  uint16 {
                 range "0..65535"  {
                    description "0..65535: Supported range 0 - 65535";
                 }
            }
            default "65535";
            description "The offset-scaled-log-variance provides an estimate of the variations
                        of the clock from a linear timescale when it is not synchronized to
                        another clock using the protocol";
        } // END of offset-scaled-log-variance definition.

    } // END of ptp-default-data-set-clock-quality-config definition.
    grouping ptp-gps-offset-top {
        description
            "Grouping for ptp gps offset configuration";
        container gps-offset {
            description
                "GPS offset configuration parameters";
            container config {
                presence "yes";
                description
                    "Configuration data";
                uses ptp-gps-offset-config;
            } // END of config-container definition.
            container state {
                config false;
                description
                    "Operational state data";
                uses ptp-gps-offset-config;
            } // END of state-container definition.
        } // END of gps-offset-container definition.
    } // END of ptp-gps-offset-top definition.
    grouping ptp-gps-offset-config {
        description
            "Grouping for ptp gps offset configuration";
        leaf offset-seconds  {
            type  int8 {
                 range "-100..100"  {
                    description "-100..100: Supported range -100 - 100";
                 }
            }
            mandatory true;
            description "GPS offset in sec";
        } // END of offset-seconds definition.

        leaf offset-nano-seconds  {
            type  int16 {
                 range "-2048..2048"  {
                    description "-2048..2048: Supported range -2048 - 2048";
                 }
            }
            mandatory true;
            description "GPS offset in ns";
        } // END of offset-nano-seconds definition.

    } // END of ptp-gps-offset-config definition.
    grouping ptp-servo-top {
        description
            "Grouping for ptp servo state";
        container ptp-servo {
            if-feature feature-list:HAVE_DUNE;
            description
                "PTP servo state parameters";
            container state {
                config false;
                description
                    "Operational state data";
                uses ptp-servo-state;
            } // END of state-container definition.
        } // END of ptp-servo-container definition.
    } // END of ptp-servo-top definition.
    grouping ptp-servo-state {
        description
            "Grouping for ptp servo states";
        leaf config-state  {
            type  ipi-ptp-types:ptp_config_state_t;
            description "PTP servo config";
        } // END of config-state definition.

        leaf servo-config  {
            if-feature feature-list:HAVE_PTP_HW_OFFLOAD_CUSTOM1;
            type  string {
                length "1..1965";
                pattern "[^?' =,>|]+";
            }
            description "PTP servo config freq/phase correction";
        } // END of servo-config definition.

        leaf previous-state  {
            type  ipi-ptp-types:ptp_servo_state_t;
            description "Previous PTP servo state";
        } // END of previous-state definition.

        leaf current-state  {
            type  ipi-ptp-types:ptp_servo_state_t;
            description "Current PTP servo state";
        } // END of current-state definition.

        leaf previous-servo-state  {
            if-feature feature-list:HAVE_PTP_HW_OFFLOAD_CUSTOM1_OR_HAVE_PTP_HW_OFFLOAD_CUSTOM2;
            type  ipi-ptp-types:ptp_servo_state_custom_t;
            description "Previous PTP servo state";
        } // END of previous-servo-state definition.

        leaf current-servo-state  {
            if-feature feature-list:HAVE_PTP_HW_OFFLOAD_CUSTOM1_OR_HAVE_PTP_HW_OFFLOAD_CUSTOM2;
            type  ipi-ptp-types:ptp_servo_state_custom_t;
            description "Current PTP servo state";
        } // END of current-servo-state definition.

        leaf duration  {
            type  string {
                length "1..1965";
                pattern "((([0-1]?[0-9])|(2[0-3])):[0-5][0-9]:[0-5][0-9])|([0-9]+d(([0-1][0-9])|(2[0-3]))h[0-5][0-9]m)";
            }
            description "PTP servo state Duration";
        } // END of duration definition.

        leaf apts-mode  {
            type  ipi-ptp-types:ptp_servo_apts_mode_t;
            description "PTP servo APTS mode";
        } // END of apts-mode definition.

        leaf freq-correction  {
            type  decimal64 {
                 fraction-digits 3;            }
            description "PTP servo freq correction";
        } // END of freq-correction definition.

        leaf phase-correction  {
            type  decimal64 {
                 fraction-digits 3;            }
            description "PTP servo phase correction";
        } // END of phase-correction definition.

        leaf mean-path-delay  {
            type  ipi-ptp-types:ptp_time_interval_t;
            description "Peer Mean path delay";
        } // END of mean-path-delay definition.

        leaf apts-gps-to-ptp-offset  {
            type  ipi-ptp-types:ptp_time_interval_t;
            description "Offset from gps to ptp";
        } // END of apts-gps-to-ptp-offset definition.

        leaf offset-from-master  {
            type  decimal64 {
                 fraction-digits 3;            }
            description "PTP offset from master";
        } // END of offset-from-master definition.

        leaf sync-packet-rate  {
            type  uint32;
            description "Sync Packet Rate";
        } // END of sync-packet-rate definition.

        leaf delay-packet-rate  {
            type  uint32;
            description "Delay Packet Rate";
        } // END of delay-packet-rate definition.

    } // END of ptp-servo-state definition.
    grouping ptp-current-data-set-top {
        description
            "PTP current data set states";
        container current-data-set {
            if-feature feature-list:HAVE_DUNE;
            description
                "PTP current data set state parameters";
            container state {
                config false;
                description
                    "Operational state data";
                uses ptp-current-data-set-state;
            } // END of state-container definition.
        } // END of current-data-set-container definition.
    } // END of ptp-current-data-set-top definition.
    grouping ptp-current-data-set-state {
        description
            "Grouping for ptp current data set state";
        leaf steps-removed  {
            type  uint8;
            default "0";
            description "The number of communication paths traversed between the local clock
                        and the grandmaster clock";
        } // END of steps-removed definition.

        leaf offset-from-master  {
            type  ipi-ptp-types:ptp_time_interval_t;
            description "The current value of the time difference between a master and a slave
                        clock as computed by the slave";
        } // END of offset-from-master definition.

        leaf offset-from-master-in-nsec  {
            type  decimal64 {
                 fraction-digits 3;            }
            description "The current value of the time difference between a master and a slave
                        clock as computed by the slave";
        } // END of offset-from-master-in-nsec definition.

        leaf mean-path-delay  {
            type  ipi-ptp-types:ptp_time_interval_t;
            description "The current value of the mean propagation time between a master and a
                        slave clock as computed by the slave";
        } // END of mean-path-delay definition.

    } // END of ptp-current-data-set-state definition.
    grouping ptp-parent-data-set-top {
        description
            "Grouping for PTP parent data set";
        container parent-data-set {
            if-feature feature-list:HAVE_DUNE;
            description
                "PTP parent data set parameters";
            container state {
                config false;
                description
                    "Operational state data";
                uses ptp-parent-data-set-state;
            } // END of state-container definition.
            uses ptp-parent-port-identity-top;
            uses ptp-grandmaster-clock-quality-top;
        } // END of parent-data-set-container definition.
    } // END of ptp-parent-data-set-top definition.
    grouping ptp-parent-data-set-state {
        description
            "Grouping for ptp parent state";
        leaf parent-stats-enabled  {
            type  boolean;
            description "Parent stats";
        } // END of parent-stats-enabled definition.

        leaf parent-offset-scaled-log-variance  {
            type  uint16;
            description "Parent Offset Scaled Log Variance";
        } // END of parent-offset-scaled-log-variance definition.

        leaf parent-phase-change-rate  {
            type  uint32;
            description "Parent Phase Change Rate";
        } // END of parent-phase-change-rate definition.

        leaf grandmaster-identity  {
            type  ipi-ptp-types:ptp_clock_identity_t;
            description "The clockIdentity attribute of the grandmaster clock";
        } // END of grandmaster-identity definition.

        leaf grandmaster-priority-1  {
            type  uint8;
            description "The priority1 attribute of the grandmaster clock";
        } // END of grandmaster-priority-1 definition.

        leaf grandmaster-priority-2  {
            type  uint8;
            description "The priority2 attribute of the grandmaster clock";
        } // END of grandmaster-priority-2 definition.

        container port-identity {
            description
                "PTP port identity parameters";
            uses ptp-parent-port-identity-state;
        } // END of port-identity-container definition.
        container grandmaster-clock-quality {
            description
                "Grandmaster clock quality parameters";
            uses ptp-grandmaster-clock-quality-state;
        } // END of grandmaster-clock-quality-container definition.
    } // END of ptp-parent-data-set-state definition.
    grouping ptp-clock-identity-state {
        description
            "Grouping for ptp clock identity states";
        leaf clock-identity  {
            type  string {
                length "1..1965";
                pattern "[^?' =,>|]+";
            }
            description "The clock identity of the local clock";
        } // END of clock-identity definition.

    } // END of ptp-clock-identity-state definition.
    grouping ptp-parent-port-identity-top {
        description
            "Grouping for ptp parent port identity";
        container port-identity {
            description
                "PTP port identity parameters";
            container state {
                config false;
                description
                    "Operational state data";
                uses ptp-parent-port-identity-state;
            } // END of state-container definition.
        } // END of port-identity-container definition.
    } // END of ptp-parent-port-identity-top definition.
    grouping ptp-parent-port-identity-state {
        description
            "Grouping for ptp parent port identity state";
        leaf clock-identity  {
            type  string {
                length "1..1965";
                pattern "[^?' =,>|]+";
            }
            description "Identity of the clock";
        } // END of clock-identity definition.

        leaf port-number  {
            type  uint16;
            description "Port number";
        } // END of port-number definition.

    } // END of ptp-parent-port-identity-state definition.
    grouping ptp-grandmaster-clock-quality-top {
        description
            "Grouping for ptp grandmaster clock quality states";
        container grandmaster-clock-quality {
            description
                "Grandmaster clock quality parameters";
            container state {
                config false;
                description
                    "Operational state data";
                uses ptp-grandmaster-clock-quality-state;
            } // END of state-container definition.
        } // END of grandmaster-clock-quality-container definition.
    } // END of ptp-grandmaster-clock-quality-top definition.
    grouping ptp-grandmaster-clock-quality-state {
        description
            "Grouping for ptp grandmaster clock quality state";
        leaf clock-class  {
            type  uint8;
            description "The clockClass denotes the traceability of the time or frequency
                        distributed by the clock";
        } // END of clock-class definition.

        leaf clock-accuracy  {
            type  uint8;
            description "The clockAccuracy indicates the expected accuracy of the clock";
        } // END of clock-accuracy definition.

        leaf offset-scaled-log-variance  {
            type  uint16;
            description "The offsetScaledLogVariance provides an estimate of the variations of
                        the clock from a linear timescale when it is not synchronized to
                        another clock using the protocol";
        } // END of offset-scaled-log-variance definition.

    } // END of ptp-grandmaster-clock-quality-state definition.
    grouping ptp-time-properties-top {
        description
            "PTP time properties states";
        container time-properties {
            if-feature feature-list:HAVE_DUNE;
            description
                "Time properties parameters";
            container state {
                config false;
                description
                    "Operational state data";
                uses ptp-time-properties-state;
            } // END of state-container definition.
        } // END of time-properties-container definition.
    } // END of ptp-time-properties-top definition.
    grouping ptp-time-properties-state {
        description
            "Grouping for ptp time properties state";
        leaf current-utc-offset-valid  {
            type  boolean;
            description "When set, the current UTC offset is valid";
        } // END of current-utc-offset-valid definition.

        leaf current-utc-offset  {
            type  int16;
            description "The offset between TAI and UTC when the epoch of the PTP system is the
                        PTP epoch, i.e., when ptp-timescale is TRUE; otherwise, the value has
                        no meaning";
        } // END of current-utc-offset definition.

        leaf leap59  {
            type  empty;
            description "When set, the last minute of the current UTC day contains 59 seconds";
        } // END of leap59 definition.

        leaf leap61  {
            type  empty;
            description "When set, the last minute of the current UTC day contains 61 seconds";
        } // END of leap61 definition.

        leaf time-traceable  {
            type  empty;
            description "When set, the timescale and the currentUtcOffset are traceable to a
                        primary reference";
        } // END of time-traceable definition.

        leaf frequency-traceable  {
            type  empty;
            description "When set, the frequency determining the timescale is traceable to a
                        primary reference";
        } // END of frequency-traceable definition.

        leaf ptp-timescale  {
            type  empty;
            description "When set, the clock timescale of the grandmaster clock is PTP;
                        otherwise, the timescale is ARB (arbitrary)";
        } // END of ptp-timescale definition.

        leaf time-source  {
            type  ipi-ptp-types:ptp_time_source_t;
            description "The source of time used by the grandmaster clock";
        } // END of time-source definition.

        leaf ptp-time-of-day  {
            type  string {
                length "1..1965";
            }
            description "PTP time of day expressed as Coordinated Universal Time (UTC)";
        } // END of ptp-time-of-day definition.

    } // END of ptp-time-properties-state definition.
    grouping ptp-statistics-top {
        description
            "Grouping for PTP statistics";
        container statistics {
            if-feature feature-list:HAVE_DUNE;
            description
                "PTP statistics parameters";
            container state {
                config false;
                description
                    "Operational state data";
                uses ptp-statistics-state;
            } // END of state-container definition.
        } // END of statistics-container definition.
    } // END of ptp-statistics-top definition.
    grouping ptp-statistics-state {
        description
            "Grouping for ptp statistics state";
        leaf packets-transmitted  {
            type  yang:counter32;
            description "PTP packets transmitted";
        } // END of packets-transmitted definition.

        leaf packets-received  {
            type  yang:counter32;
            description "PTP packets received";
        } // END of packets-received definition.

        leaf packets-discarded  {
            type  yang:counter32;
            description "PTP packets discarded";
        } // END of packets-discarded definition.

        leaf ipv4-packets-received  {
            type  yang:counter32;
            description "PTP IPv4 packets received";
        } // END of ipv4-packets-received definition.

        leaf ipv6-packets-received  {
            if-feature feature-list:HAVE_IPV6;
            type  yang:counter32;
            description "PTP IPv6 packets received";
        } // END of ipv6-packets-received definition.

        leaf l2-packets-received  {
            type  yang:counter32;
            description "PTP L2 packets received";
        } // END of l2-packets-received definition.

        leaf rx-queue-overflows  {
            type  yang:counter32;
            description "PTP RX queue overflows";
        } // END of rx-queue-overflows definition.

    } // END of ptp-statistics-state definition.

    grouping  ptp-grouping {
    description
        "PTP clock";
    container ptp {
        if-feature feature-list:HAVE_PTP_HW_OFFLOAD;
        if-feature feature-list:HAVE_PTPD;
        description
            "PTP clock";
        uses ptp-instance-top;
        uses ptp-debug-top;
    } // END of ptp-container definition.
    } // END of ptp-grouping definition.

    uses ptp-grouping;

    rpc ptp-clear-statistics {
        if-feature feature-list:HAVE_PTP_HW_OFFLOAD;
        if-feature feature-list:HAVE_DUNE;
        if-feature feature-list:HAVE_PTPD;
        description "PTP clear statistics RPC";
        input  {
            leaf clear-clock  {
                type uint8 {
                    range "0..1";
                }
                mandatory true;
                description "clear-clock-id";
            }
        }
    }

    rpc ptp-terminal-debug-on {
        if-feature feature-list:HAVE_PTP_HW_OFFLOAD;
        if-feature feature-list:HAVE_DUNE;
        if-feature feature-list:HAVE_PTPD;
        description "PTP debug terminal on RPC";
    }

    rpc ptp-terminal-debug-off {
        if-feature feature-list:HAVE_PTP_HW_OFFLOAD;
        if-feature feature-list:HAVE_DUNE;
        if-feature feature-list:HAVE_PTPD;
        description "PTP debug terminal off RPC";
    }

    notification ptp-servo-state-change-notify {
        if-feature feature-list:HAVE_PTP_HW_OFFLOAD;
        if-feature feature-list:HAVE_PTPD;
        if-feature feature-list:HAVE_DUNE;

        description "Notify when servo state change happens.";

        leaf severity {
            type cml-data-types:cml_notif_severity_t;
            description "Notification severity level";
        }

        leaf eventClass {
            type cml-data-types:cml_notif_class_t;
            description "Notification event class (value: STATE)";
        }

        leaf instance-type {
            type  uint8;
        description
            "PTP instance type";
        }

        leaf previous-state {
            type ipi-ptp-types:ptp_servo_state_t;
        description
            "Previous PTP servo state";
        }

        leaf current-state {
            type ipi-ptp-types:ptp_servo_state_t;
        description
            "Current PTP servo state";
        }
    }

    notification ptp-servo-state-change-custom1-notify {
        if-feature feature-list:HAVE_PTP_HW_OFFLOAD;
        if-feature feature-list:HAVE_PTPD;
        if-feature feature-list:HAVE_DUNE;
        if-feature feature-list:HAVE_PTP_HW_OFFLOAD_CUSTOM1_OR_HAVE_PTP_HW_OFFLOAD_CUSTOM2;

        description "Notify when servo state change happens.";

        leaf severity {
            type cml-data-types:cml_notif_severity_t;
            description "Notification severity level";
        }

        leaf eventClass {
            type cml-data-types:cml_notif_class_t;
            description "Notification event class (value: STATE)";
        }

        leaf instance-type {
            type  uint8;
        description
            "PTP instance type";
        }

        leaf previous-servo-state {
            type ipi-ptp-types:ptp_servo_state_custom_t;
        description
            "Previous PTP servo state";
        }

        leaf current-servo-state {
            type ipi-ptp-types:ptp_servo_state_custom_t;
        description
            "Current PTP servo state";
        }
    }

}
