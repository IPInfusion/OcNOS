/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-delay-profile.yang
*
*/

module ipi-delay-profile {

    yang-version 1.1;

    namespace   "http://www.ipinfusion.com/yang/ocnos/ipi-delay-profile";

    prefix "ipi-delay-profile";

    import ipi-delay-profile-types {
        prefix ipi-delay-profile-types;
        revision-date 2022-06-01;
    }

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for configuring the delay measurement profile";


    revision "2022-06-01" {
        description "Updated the yang file with feature";
        reference " 0.2.0.";
    }

    revision "2021-09-30" {
        description "Initial release";
        reference " 0.1.0.";
    }

    grouping profile-parameters-top {
        description
            "Set the delay profile parameters";
        container profile-parameters {
            description
                "Definition of delay profile parameters";
            container config {
                description
                    "Configuration data";
                uses profile-parameters-config;
            } // END of config-container definition.
            container state {
                config false;
                description
                    "Operational state data";
                uses profile-parameters-config;
            } // END of state-container definition.
        } // END of profile-parameters-container definition.
    } // END of profile-parameters-top definition.
    grouping profile-periodic-top {
        description
            "Set the delay profile parameters";
        container periodic-advertisement {
            description
                "Definition of delay profile parameters";
            container config {
                description
                    "Configuration data";
                uses profile-periodic-config;
            } // END of config-container definition.
            container state {
                config false;
                description
                    "Operational state data";
                uses profile-periodic-config;
            } // END of state-container definition.
        } // END of periodic-advertisement-container definition.
    } // END of profile-periodic-top definition.
    grouping profile-periodic-config {
        description
            "periodic";
        leaf disable  {
            type  empty;
            description "Disable the periodic advertisement";
        } // END of disable definition.

        leaf threshold  {
            when " not(/ipi-delay-profile:delay-profiles/ipi-delay-profile:delay-profile/ipi-delay-profile:periodic-advertisement/ipi-delay-profile:config/ipi-delay-profile:disable) ";
            type  uint8 {
                 range "1..100"  {
                    description "1..100: Supported range 1 - 100";
                 }
            }
            description "Configure the periodic advertisement threshold";
        } // END of threshold definition.

        leaf minimum-change  {
            when " not(/ipi-delay-profile:delay-profiles/ipi-delay-profile:delay-profile/ipi-delay-profile:periodic-advertisement/ipi-delay-profile:config/ipi-delay-profile:disable) ";
            type  uint16 {
                 range "0..10000"  {
                    description "0..10000: Supported range 0 - 10000";
                 }
            }
            description "Configure the advertisement minimum-change in microseconds
                        (default=1000)";
        } // END of minimum-change definition.

    } // END of profile-periodic-config definition.
    grouping profile-accelerated-top {
        description
            "Set the delay profile parameters";
        container accelerated-advertisement {
            description
                "Definition of delay profile parameters";
            container config {
                presence "accelerated advertisement config";
                description
                    "Configuration data";
                uses profile-accelerated-config;
            } // END of config-container definition.
            container state {
                config false;
                description
                    "Operational state data";
                uses profile-accelerated-config;
            } // END of state-container definition.
        } // END of accelerated-advertisement-container definition.
    } // END of profile-accelerated-top definition.
    grouping profile-accelerated-config {
        description
            "accelerated";
        leaf enable  {
            type  empty;
            mandatory true;
            description "Enable the accelerated advertisement";
        } // END of enable definition.

        leaf threshold  {
            type  uint8 {
                 range "1..100"  {
                    description "1..100: Supported range 1 - 100";
                 }
            }
            description "Configure the accelerated advertisement threshold";
        } // END of threshold definition.

        leaf minimum-change  {
            type  uint16 {
                 range "0..10000"  {
                    description "0..10000: Supported range 0 - 10000";
                 }
            }
            description "Configure the advertisement minimum-change in microseconds
                        (default=1000)";
        } // END of minimum-change definition.

    } // END of profile-accelerated-config definition.
    grouping profile-parameters-config {
        description
            "Set the configuration parameters";
        leaf mode  {
            type  ipi-delay-profile-types:delay_profile_measurement_mode_t;
            description "Set the measurement mode";
        } // END of mode definition.

        leaf burst-interval  {
            type  uint16 {
                 range "1000..15000"  {
                    description "1000..15000: Supported range 1000 - 15000";
                 }
            }
            description "Configure the burst-interval";
        } // END of burst-interval definition.

        leaf burst-count  {
            type  uint8 {
                 range "1..30"  {
                    description "1..30: Supported range 1 - 30";
                 }
            }
            description "Configure the burst-count";
        } // END of burst-count definition.

        leaf interval  {
            type  uint16 {
                 range "30..3600"  {
                    description "30..3600: Supported range 30 - 3600";
                 }
            }
            description "Configure the computation interval";
        } // END of interval definition.

        leaf sender-port  {
            type  uint16 {
                 range "1025..65535"  {
                    description "1025..65535: Supported range 1025 - 65535";
                 }
            }
            description "Configure the computation interval";
        } // END of sender-port definition.

    } // END of profile-parameters-config definition.
    grouping delay-profile-config {
        description
            "DELAY profile configuration data";
        leaf profile-type  {
            type  ipi-delay-profile-types:delay_profile_type_t;
            description "The profile type for delay";
        } // END of profile-type definition.

    } // END of delay-profile-config definition.

    grouping  delay-profiles-grouping {
    description
        "Top level container for the DELAY profile configuration and
                operational data";
    container delay-profiles {
        if-feature feature-list:HAVE_TWAMP;
        description
            "Top level container for the DELAY profile configuration and
                    operational data";

        list delay-profile {
            key "profile-type";
            max-elements 1;
            description
                "This defines a YANG data model forcreating a Delay interfaces profile";
            leaf profile-type  {
                type  leafref {
                    path  "../config/profile-type";
                }
                description "The profile type for delay";
            } // END of profile-type definition.

            container config {
                description
                    "configuration data for the DELAY profile";
                uses delay-profile-config;
            } // END of config-container definition.
            container state {
                config false;
                description
                    "Operational state data of the DELAY profile";
                uses delay-profile-config;
            } // END of state-container definition.
            uses profile-parameters-top;
            uses profile-periodic-top;
            uses profile-accelerated-top;
        } // End of delay-profile-list
    } // END of delay-profiles-container definition.
    } // END of delay-profiles-grouping definition.

    uses delay-profiles-grouping;

}
