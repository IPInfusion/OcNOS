/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-udld-types.yang
*
*/

module ipi-udld-types {

    yang-version 1.1;

    namespace   "http://www.ipinfusion.com/yang/ocnos/ipi-udld-types";

    prefix "ipi-udld-types";

    organization
        "IP Infusion Inc.";

    contact
        "Address: 3965 Freedom Circle, Suite 200, Santa Clara, CA 95054
         Phone: +1 408-400-1900
         E-mail: support@ipinfusion.com
         Web: http://www.ipinfusion.com/";

    description
        "Layer-2 UnDirectional Link Detection (UDLD) types";


    revision "2022-06-01" {
        description "Updated the yang file with feature";
        reference " 0.2.0.";
    }

    revision "2021-10-25" {
        description "Restructured UDLD module in accordance with OpenConfig style";
        reference " 0.1.0.";
    }



    typedef  udld_mode_type_t {
        type enumeration {
            enum normal {
                value 0;
                description "UDLD normal mode";
            }
            enum aggressive {
                value 1;
                description "UDLD aggressive mode";
            }
        }
        description "type definition for UDLD_MODE_TYPE_T";
    }

    typedef  udld_link_state_type_t {
        type enumeration {
            enum Unknown {
                value 0;
                description "Unknown";
            }
            enum Loopback {
                value 1;
                description "Loopback";
            }
            enum Neighbor-Mismatch {
                value 2;
                description "Neighbor Mismatch";
            }
            enum Unidirectional {
                value 3;
                description "Unidirectional";
            }
            enum Undetermined {
                value 4;
                description "Undetermined";
            }
            enum Bi-Directional {
                value 5;
                description "Bi-Directional";
            }
        }
        description "type definition for UDLD_LINK_STATE_TYPE_T";
    }

}
