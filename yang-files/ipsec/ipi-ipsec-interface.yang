/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-ipsec-interface.yang
*
*/

submodule ipi-ipsec-interface {

    yang-version 1.1;

    belongs-to  ipi-ipsec { prefix ipi-ipsec; }

    import feature-list {
        prefix feature-list;
        revision-date 2023-02-21;
    }

    import ietf-inet-types {
        prefix inet;
        revision-date 2013-07-15;
    }

    import ipi-interface {
        prefix ipi-interface;
        revision-date 2022-08-24;
    }

    organization
        "IP Infusion Inc.";

    contact
        "Address: 3965 Freedom Circle, Suite 200, Santa Clara, CA 95054
         Phone: +1 408-400-1900
         E-mail: support@ipinfusion.com
         Web: http://www.ipinfusion.com/";

    description
        "Internet Protocol Security Interface";


    revision "2022-06-01" {
        description "Updated the yang file with feature";
        reference " 0.2.0.";
    }

    revision "2022-05-10" {
        description "Initial Version";
        reference " 0.1.0.";
    }

    grouping ipsec-interface-config {
        description
            "Grouping for IPsec interface attributes";
        leaf name  {
            type  leafref {
                path  "/ipi-interface:interfaces/ipi-interface:interface/ipi-interface:name";
            }
            description "Use this command to configure interface name.";
        } // END of name definition.

        leaf crypto-map-name  {
            type  string {
                length "1..127";
                pattern "[^?' =,>|]+";
            }
            description "This attribute configures the crypto map associated with this
                        interface";
        } // END of crypto-map-name definition.

    } // END of ipsec-interface-config definition.
    grouping ipsec-interface-top {
        description
            "Grouping for IPsec interface configurations";
        container interfaces {
            if-feature feature-list:HAVE_IPSEC_HW;
            description
                "IPsec interfaces configuration";

            list interface {
                key "name";
                description
                    "List of system interfaces that could be associated to crypto-map";
                leaf name  {
                    type  leafref {
                        path  "../config/name";
                    }
                    description "The interface name to configure the IPsec interface.";
                } // END of name definition.

                container config {
                    description
                        "Configuration data for IPsec interface";
                    uses ipsec-interface-config;
                } // END of config-container definition.
                container state {
                    config false;
                    description
                        "Operational state data for IPsec interface";
                    uses ipsec-interface-config;
                } // END of state-container definition.
            } // End of interface-list
        } // END of interfaces-container definition.
    } // END of ipsec-interface-top definition.
    grouping ipsec-interface-tunnel-config {
        description
            "Grouping for IPsec interfaces tunnel attributes";
        leaf name  {
            type  leafref {
                path  "/ipi-interface:interfaces/ipi-interface:interface/ipi-interface:name";
            }
            description "Use this command to configure interface ipsec tunnel name. This name
                        start with prefix 'ipsec' and a number index as sulfix, an example is
                        'ipsec2'.";
        } // END of name definition.

        leaf source  {
            type  inet:ip-address;
            description "This attribute configures the tunnel source address.";
        } // END of source definition.

        leaf destination  {
            type  inet:ip-address;
            description "This attribute configures the tunnel destination address.";
        } // END of destination definition.

    } // END of ipsec-interface-tunnel-config definition.
    grouping ipsec-interface-tunnel-top {
        description
            "Grouping for IPsec interface tunnel configurations";
        container tunnels {
            if-feature feature-list:HAVE_IPSEC_HW;
            description
                "IPsec interfaces tunnels configuration";

            list tunnel {
                key "name";
                description
                    "List of IPsec tunnel interfaces";
                leaf name  {
                    type  leafref {
                        path  "../config/name";
                    }
                    description "Use this command to configure interface IPSEC tunnel name.";
                } // END of name definition.

                container config {
                    description
                        "Configuration data for IPsec interface tunnel";
                    uses ipsec-interface-tunnel-config;
                } // END of config-container definition.
                container state {
                    config false;
                    description
                        "Operational state data for IPsec interface tunnel";
                    uses ipsec-interface-tunnel-config;
                } // END of state-container definition.
            } // End of tunnel-list
        } // END of tunnels-container definition.
    } // END of ipsec-interface-tunnel-top definition.


}
