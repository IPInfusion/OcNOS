/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ldap.yang
*
*/

submodule ldap {

    belongs-to  ZebOS { prefix ZebOS; }


    import cml_data_types {
        prefix cml_data_types;
    }

    description
        "Layer-3 ldap configurations";


    revision "2017-03-09" {
        description "Revisied on 2017-03-09.";    }

    revision "2017-03-05" {
        description "Revisied on 2017-03-05.";    }

    revision "2017-03-03" {
        description "Revisied on 2017-03-03.";    }

    revision "2017-02-27" {
        description "Revisied on 2017-02-27.";    }

    revision "2017-02-25" {
        description "Revisied on 2017-02-25.";    }

    revision "2017-02-24" {
        description "Revisied on 2017-02-24.";    }

    revision "2017-02-23" {
        description "Revisied on 2017-02-23.";    }

    revision "2017-02-22" {
        description "Revisied on 2017-02-22.";    }

    revision "2017-02-21" {
        description "Revisied on 2017-02-21.";    }

    revision "2017-02-20" {
        description "Revisied on 2017-02-20.";    }

    revision "2017-02-14" {
        description "Revisied on 2017-02-14.";    }

    revision "2017-02-13" {
        description "Revisied on 2017-02-13.";    }

    revision "2017-02-11" {
        description "Revisied on 2017-02-11.";    }

    revision "2017-02-10" {
        description "Revisied on 2017-02-10.";    }

    revision "2017-02-08" {
        description "Revisied on 2017-02-08.";    }

    revision "2017-02-07" {
        description "Revisied on 2017-02-07.";    }

    revision "2017-02-03" {
        description "Revisied on 2017-02-03.";    }

    revision "2017-02-02" {
        description "Revisied on 2017-02-02.";    }

    revision "2017-01-31" {
        description "Revisied on 2017-01-31.";    }

    revision "2017-01-30" {
        description "Revisied on 2017-01-30.";    }

    revision "2017-01-28" {
        description "Revisied on 2017-01-28.";    }

    revision "2017-01-27" {
        description "Revisied on 2017-01-27.";    }

    revision "2017-01-25" {
        description "Revisied on 2017-01-25.";    }

    revision "2017-01-23" {
        description "Revisied on 2017-01-23.";    }

    revision "2017-01-20" {
        description "Revisied on 2017-01-20.";    }

    revision "2017-01-19" {
        description "Revisied on 2017-01-19.";    }

    revision "2017-01-16" {
        description "Revisied on 2017-01-16.";    }

    revision "2017-01-12" {
        description "Revisied on 2017-01-12.";    }

    revision "2017-01-11" {
        description "Revisied on 2017-01-11.";    }

    revision "2017-01-10" {
        description "Revisied on 2017-01-10.";    }

    revision "2017-01-04" {
        description "Revisied on 2017-01-04.";    }

    revision "2016-12-30" {
        description "Revisied on 2016-12-30.";    }

    revision "2016-12-29" {
        description "Revisied on 2016-12-29.";    }

    revision "2016-12-28" {
        description "Revisied on 2016-12-28.";    }

    revision "2016-12-26" {
        description "Revisied on 2016-12-26.";    }

    revision "2016-12-22" {
        description "Revisied on 2016-12-22.";    }

    revision "2016-12-17" {
        description "Revisied on 2016-12-17.";    }

    revision "2016-10-28" {
        description "Revisied on 2016-10-28.";    }

    revision "2016-01-29" {
        description "Revisied on 2016-01-29.";    }


    grouping  ldap-grouping {
    container ldap {
                config true;

        description
            "ldap";

        leaf featureLdap  {
            type  cml_data_types:CML_BOOL_T;  
        } // END of featureLdap definition.

        leaf port  {
            type  cml_data_types:CML_UINT16_T {
                 range "1..65535";
            }
        } // END of port definition.

        leaf timeout  {
            type  cml_data_types:CML_UINT16_T {
                 range "1..60";
            }
        } // END of timeout definition.


        list ldap {
             
            description
                "ldap";

            config true;
            key "hostAddr";

            
            leaf hostAddr  {
                type  cml_data_types:CML_HOSTNAME_T;  
            } // END of hostAddr definition.

            leaf EnableSsl  {
                type  cml_data_types:CML_BOOL_T;  
            } // END of EnableSsl definition.

            leaf hostPort  {
                type  cml_data_types:CML_UINT16_T {
                     range "1..65535";
                }
            } // END of hostPort definition.

            leaf hostDNPort  {
                type  cml_data_types:CML_UINT16_T {
                     range "1..65535";
                }
                default "389";
            } // END of hostDNPort definition.

            leaf hostTimeout  {
                type  cml_data_types:CML_UINT16_T {
                     range "1..60";
                }
                default "5";
            } // END of hostTimeout definition.

            leaf hostPTimeout  {
                type  cml_data_types:CML_UINT16_T {
                     range "1..60";
                }
            } // END of hostPTimeout definition.

            leaf rootDN  {
                type  cml_data_types:CML_STRING_T {
                    length "0..255";
                }
            } // END of rootDN definition.

        } // End of ldap-list
    } // END of ldap-container definition.
    } // END of ldap-container definition.


}
