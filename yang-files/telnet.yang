/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : telnet.yang
*
*/

submodule telnet {

    belongs-to  ZebOS { prefix ZebOS; }
    include vrf;


    import cml_data_types {
        prefix cml_data_types;
    }

    import feature_list {
        prefix feature_list;
    }

    description
        "Telnet configurations";


    revision "2017-01-19" {
        description "Changed vrf name as normal attr as it is optional parameter.";
    }

    revision "2016-12-27" {
        description "Added snmp oid and documentation tag.";
    }

    revision "2016-10-28" {
        description "Initial version of TELNET datamodel.";
    }


    grouping  telnet-grouping {
    container telnet {
                config true;

        description
            "telnet related commands";

        leaf vrfName  {
            type  cml_data_types:CML_STRING_T {
                length "0..255";
            }
            default "default";
        } // END of vrfName definition.

        leaf featureTelnet  {
            type  cml_data_types:CML_BOOL_T;  
            description "feature telnet";
        } // END of featureTelnet definition.

        leaf port  {
            if-feature feature_list:HAVE_TELNET_SERVER;
            type  cml_data_types:CML_INT32_T {
                 range "1024..65535";
            }
            description "Telnet server port";
        } // END of port definition.

        leaf debugtelnet  {
            if-feature feature_list:HAVE_TELNET_SERVER;
            type  cml_data_types:CML_BOOL_T;  
            default false;
            description "debug telnet server";
        } // END of debugtelnet definition.

    } // END of telnet-container definition.
    } // END of telnet-container definition.


}
