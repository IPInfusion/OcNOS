/*
* Copyright (C) 2016 IP Infusion, Inc. 
*  All Rights Reserved.
*
*** Auto generated by zebmdc

* Unless required by applicable law or agreed to in writing,
* software distributed under the License is distributed on an
* "AS IS" BASIS, WITHOUT WARRANTIES OR CONDITIONS OF ANY
* KIND, either express or implied.

* File name : lldpv2.yang
*
*/

submodule lldpv2 {

    belongs-to  ZebOS { prefix ZebOS; }
    include interface;


    import cml_data_types {
        prefix cml_data_types;
    }

    description
        "Link Layer Discovery Protocol";


    revision "2015-10-08" {
        description "Revisied on 2015-10-08.";    }



    grouping lldpv2Interface-grouping {
        list lldpv2Interface {
             

            description
                "LLDPV2 interface related operations";

            config true;
            key "ifName";

            
            leaf ifName  {
                mandatory true;                
                type  leafref {
                    path  "/vr/interface/ifName";
                }
            } // END of ifName definition.

            leaf vrId  {
                mandatory false;                
                type  leafref {
                    path  "/vr/vrId";
                }
            } // END of vrId definition.

            leaf lldpPortDescription  {
                mandatory false;                
                type  cml_data_types:CML_STRING_T;  
                default "NULL";
                config true;
            } // END of lldpPortDescription definition.

            leaf lldpAgtCircuitId  {
                mandatory false;                
                type  cml_data_types:CML_STRING_T;  
                default "NULL";
                config true;
            } // END of lldpAgtCircuitId definition.

            leaf lldpmedDevType  {
                mandatory false;                
                type  cml_data_types:CML_LLDP_MEDDEV_T;  
                config true;
            } // END of lldpmedDevType definition.

            leaf localName  {
                mandatory false;                
                type  cml_data_types:CML_STRING_T;  
                default "NULL";
                config true;
            } // END of localName definition.


            list lldpAgent {
                 

                description
                    "LLDP configuration related operations";

                config true;
                key "lldpAgent";

                
                leaf lldpAgent  {
                    mandatory true;                    
                    type  cml_data_types:CML_LLDP_AGENT_T;  
                    config true;
                } // END of lldpAgent definition.

                leaf lldpEnable  {
                    mandatory false;                    
                    type  cml_data_types:CML_LLDP_ENABLE_T;  
                    default "rxonly";
                    config true;
                } // END of lldpEnable definition.

                leaf lldpDisable  {
                    mandatory false;                    
                    type  cml_data_types:CML_BOOL_T;  
                    config true;
                } // END of lldpDisable definition.

                leaf reinitDelay  {
                    mandatory false;                    
                    type  cml_data_types:CML_STRING_T;  
                    config true;
                } // END of reinitDelay definition.

                leaf MsgTxInterval  {
                    mandatory false;                    
                    type  cml_data_types:CML_UINT32_T {
                         range "5..3600";
                    }
                    default "30";
                    config true;
                } // END of MsgTxInterval definition.

                leaf MsgTxValue  {
                    mandatory false;                    
                    type  cml_data_types:CML_STRING_T;  
                    config true;
                } // END of MsgTxValue definition.

                leaf MsgFastTx  {
                    mandatory false;                    
                    type  cml_data_types:CML_UINT32_T {
                         range "1..3600";
                    }
                    default "1";
                    config true;
                } // END of MsgFastTx definition.

                leaf neighborLimit  {
                    mandatory false;                    
                    type  cml_data_types:CML_UINT32_T {
                         range "1..65535";
                    }
                    config true;
                } // END of neighborLimit definition.

                leaf neighborTimer  {
                    mandatory false;                    
                    type  cml_data_types:CML_UINT32_T {
                         range "1..65535";
                    }
                    config true;
                } // END of neighborTimer definition.

                leaf portLimit  {
                    mandatory false;                    
                    type  cml_data_types:CML_UINT32_T {
                         range "1..65535";
                    }
                    config true;
                } // END of portLimit definition.

                leaf portMac  {
                    mandatory false;                    
                    type  cml_data_types:CML_STRING_T;  
                    config true;
                } // END of portMac definition.

                leaf portTimer  {
                    mandatory false;                    
                    type  cml_data_types:CML_UINT32_T {
                         range "1..65535";
                    }
                    config true;
                } // END of portTimer definition.

                leaf TxMaxCredit  {
                    mandatory false;                    
                    type  cml_data_types:CML_UINT32_T {
                         range "1..10";
                    }
                    default "5";
                    config true;
                } // END of TxMaxCredit definition.

                leaf TxFastInit  {
                    mandatory false;                    
                    type  cml_data_types:CML_UINT32_T {
                         range "1..8";
                    }
                    default "4";
                    config true;
                } // END of TxFastInit definition.

                leaf portAddr  {
                    mandatory false;                    
                    type  cml_data_types:CML_LLDP_MGMT_ADDR_T;  
                    default "mac-address";
                    config true;
                } // END of portAddr definition.

                leaf chassisId  {
                    mandatory false;                    
                    type  cml_data_types:CML_LLDP_CHASSIS_T;  
                    default "mac-address";
                    config true;
                } // END of chassisId definition.

                leaf portId  {
                    mandatory false;                    
                    type  cml_data_types:CML_LLDP_PORT_T;  
                    default "mac-address";
                    config true;
                } // END of portId definition.

                leaf tlvFlag  {
                    mandatory false;                    
                    type  cml_data_types:CML_LLDP_TVL_FLAG_T;  
                    config true;
                } // END of tlvFlag definition.

                leaf TlvSelect  {
                    mandatory false;                    
                    type  cml_data_types:CML_LLDP_IEEE_8023_T;  
                    config true;
                } // END of TlvSelect definition.

                leaf TlvSelectIeee  {
                    mandatory false;                    
                    type  cml_data_types:CML_LLDP_IEEE_8021_T;  
                    config true;
                } // END of TlvSelectIeee definition.

                leaf TlvSelectBasic  {
                    mandatory false;                    
                    type  cml_data_types:CML_LLDP_BASIC_T;  
                    config true;
                } // END of TlvSelectBasic definition.

                leaf tlvMed  {
                    mandatory false;                    
                    type  cml_data_types:CML_LLDP_MED_T;  
                    default "media-capabilities";
                    config true;
                } // END of tlvMed definition.

            } // End of lldpAgent-list
        } // End of lldpv2Interface-list
    } // END of lldpv2Interface-grouping definition.

    grouping  systemDetail-grouping {
    container systemDetail {
        
        config true;

        description
            "systemDetail";

        leaf SystemName  {
            mandatory false;            
            type  cml_data_types:CML_STRING_T;  
            default "NULL";
            config true;
        } // END of SystemName definition.

        leaf lldpRun  {
            mandatory false;            
            type  cml_data_types:CML_BOOL_T;  
            config true;
        } // END of lldpRun definition.

        leaf lldpSystemDescription  {
            mandatory false;            
            type  cml_data_types:CML_STRING_T;  
            default "NULL";
            config true;
        } // END of lldpSystemDescription definition.

        leaf locallyAssigned  {
            mandatory false;            
            type  cml_data_types:CML_STRING_T;  
            default "NULL";
            config true;
        } // END of locallyAssigned definition.

    } // END of systemDetail-container definition.
    } // END of systemDetail-container definition.


}
