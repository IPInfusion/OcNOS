/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-radius.yang
*
*/

module ipi-radius {

    yang-version 1.1;

    namespace   "http://www.ipinfusion.com/yang/ocnos/ipi-radius";

    prefix "ipi-radius";

    import cml-data-types {
        prefix cml-data-types;
        revision-date 2022-09-30;
    }

    import ipi-radius-types {
        prefix ipi-radius-types;
        revision-date 2022-06-01;
    }

    import ipi-vrf {
        prefix ipi-vrf;
        revision-date 2022-07-13;
    }

    import ipi-network-instance {
        prefix ipi-network-instance;
        revision-date 2022-06-01;
    }

    import ietf-yang-types {
        prefix yang;
        revision-date 2013-07-15;
    }

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "Layer-3 radius configurations";


    revision "2022-06-01" {
        description "Updated the yang file with feature";
        reference " 0.4.0.";
    }

    revision "2022-04-27" {
        description "Updated per-server counters attr names and data types to align with OpenConfig";
        reference " 0.3.0.";
    }

    revision "2021-10-26" {
        description "Restructured module as per open-config style";
        reference " 0.2.0.";
    }

    revision "2018-06-21" {
        description "Initial Version";
        reference " 0.1.0.";
    }

    grouping radius-global-config {
        description
            "RADIUS Global Configuration items";
        leaf vrf-name  {
            type  leafref {
                path  "/ipi-network-instance:network-instances/ipi-network-instance:network-instance/ipi-vrf:vrf/ipi-vrf:config/ipi-vrf:vrf-name";
            }
            description "VRF Name associated with this instance";
        } // END of vrf-name definition.

        leaf key-type  {
            type  ipi-radius-types:radius_hostp_key_type_t;
            description "Authentication key type";
        } // END of key-type definition.

        leaf secret-key-string  {
            when " /ipi-radius:radius/ipi-radius:vrfs/ipi-radius:vrf/ipi-radius:config/ipi-radius:key-type ";
            type  string {
                length "1..1965";
                pattern "[^?' =,>|]+";
            }
            description "Shared key used between the authentication-server and the device";
        } // END of secret-key-string definition.

        leaf timeout  {
            type  uint8 {
                 range "1..60"  {
                    description "1..60: Supported range 1 - 60";
                 }
            }
            units "seconds";
            description "Use this attribute to set the global timeout which is how long the
                        device
                        waits for a response from a RADIUS server before declaring a timeout
                        failure";
        } // END of timeout definition.

    } // END of radius-global-config definition.
    grouping radius-server-config {
        description
            "RADIUS Server Configuration items";
        leaf host-address  {
            type  cml-data-types:cml_hostname_t;
            description "Use this attribute to set the RADIUS server hostname or IP address";
        } // END of host-address definition.

        leaf sequence-number  {
            type  uint8 {
                 range "1..8"  {
                    description "1..8: Supported range 1 - 8";
                 }
            }
            mandatory true;
            description "Use this attribute to set the sequence-number/priority index
                        for the RADIUS server";
        } // END of sequence-number definition.

        leaf key-type  {
            type  ipi-radius-types:radius_hostp_key_type_t;
            description "Authentication key type";
        } // END of key-type definition.

        leaf secret-key-string  {
            when " /ipi-radius:radius/ipi-radius:vrfs/ipi-radius:vrf/ipi-radius:remote-servers/ipi-radius:server/ipi-radius:config/ipi-radius:key-type ";
            type  string {
                length "1..1965";
                pattern "[^?' =,>|]+";
            }
            description "Shared key used between the authentication-server and the device";
        } // END of secret-key-string definition.

        leaf accounting-port  {
            type  uint16 {
                 range "0..65535"  {
                    description "0..65535: Supported range 0 - 65535";
                 }
            }
            description "Use this attribute to configure a RADIUS server and specify a UDP port
                        to use for
                        RADIUS accounting messages";
        } // END of accounting-port definition.

        leaf authentication-port  {
            type  uint16 {
                 range "0..65535"  {
                    description "0..65535: Supported range 0 - 65535";
                 }
            }
            description "Use this attribute to configure a RADIUS server and specify a UDP port
                        to use for
                        RADIUS authentication messages";
        } // END of authentication-port definition.

        leaf timeout  {
            type  uint8 {
                 range "1..60"  {
                    description "1..60: Supported range 1 - 60";
                 }
            }
            units "seconds";
            default "5";
            description "To represent the timeout configured by the user";
        } // END of timeout definition.

    } // END of radius-server-config definition.
    grouping radius-debug-config {
        description
            "Configuration data related to debugging";
        leaf enable-debugging  {
            type  empty;
            description "This attribute is to enable/disable RADIUS debug logging";
        } // END of enable-debugging definition.

    } // END of radius-debug-config definition.
    grouping radius-debug-state {
        description
            "State data related to RADIUS debugging status";
        leaf terminal-debug-status  {
            type  cml-data-types:cml_on_off_t;
            description "Use this attribute to display RADIUS terminal debugging information.";
        } // END of terminal-debug-status definition.

    } // END of radius-debug-state definition.
    grouping radius-server-state {
        description
            "Operational data for each RADIUS server";
        leaf last-successful-authentication-time  {
            type  yang:date-and-time {
                pattern "\\d{4}-\\d{2}-\\d{2}T\\d{2}:\\d{2}:\\d{2}(\\.\\d+)?(Z|[\\+\\-]\\d{2}:\\d{2})";
                }
                description "Timestamp for the last successful authentication to this RADIUS Server";
            } // END of last-successful-authentication-time definition.

        container counters {
            config false;
            description
                "RADIUS Server counters";
            leaf successful-authentications  {
                type  yang:counter64;
                description "Number of successful authentications to the RADIUS Server";
            } // END of successful-authentications definition.

            leaf authentication-failures  {
                type  yang:counter64;
                description "Number of authentication failures to the RADIUS Server";
            } // END of authentication-failures definition.

            leaf connection-failures  {
                type  yang:counter64;
                description "Number of connection failures to the RADIUS Server";
            } // END of connection-failures definition.

        } // END of counters-container definition.
    } // END of radius-server-state definition.

    grouping  radius-grouping {
    description
        "Top level container for RADIUS configuration and operational data";
    container radius {
        if-feature feature-list:HAVE_HOSTPD;
        if-feature feature-list:HAVE_RADIUS_CLIENT;
        description
            "Top level container for RADIUS configuration and operational data";
        container vrfs {
            description
                "This container defines RADIUS server vrf informations";

            list vrf {
                if-feature feature-list:HAVE_AAA;
                key "vrf-name";
                description
                    "Global RADIUS Configuration";
                leaf vrf-name  {
                    type  leafref {
                        path  "../config/vrf-name";
                    }
                    description "VRF Name associated with this instance";
                } // END of vrf-name definition.

                container config {
                    description
                        "radius related operation";
                    uses radius-global-config;
                } // END of config-container definition.
                container state {
                    config false;
                    description
                        "This container defines the RADIUS Global states.";
                    uses radius-global-config;
                } // END of state-container definition.
                container remote-servers {
                    description
                        "This container defines RADIUS Server informations";

                    list server {
                    when " /ipi-radius:radius/ipi-radius:vrfs/ipi-radius:vrf/ipi-radius:remote-servers/ipi-radius:server/ipi-radius:config/ipi-radius:sequence-number ";
                        if-feature feature-list:HAVE_AAA;
                        key "host-address";
                        description
                            "This objectlist defines the RADIUS Server list";
                        leaf host-address  {
                            type  leafref {
                                path  "../config/host-address";
                            }
                            description "Use this attribute to set the RADIUS server hostname or IP address";
                        } // END of host-address definition.

                        container config {
                            description
                                "This container defines RADIUS server operation";
                            uses radius-server-config;
                        } // END of config-container definition.
                        container state {
                            config false;
                            description
                                "This container defines TACACS Server state intormation.";
                            uses radius-server-config;
                            uses radius-server-state;
                        } // END of state-container definition.
                    } // End of server-list
                } // END of remote-servers-container definition.
            } // End of vrf-list
        } // END of vrfs-container definition.
        container debug {
            description
                "RADIUS debug Information";
            container config {
                description
                    "This container defines RADIUS Debug Configuration";
                uses radius-debug-config;
            } // END of config-container definition.
            container state {
                config false;
                description
                    "This container defines RADIUS Debug state";
                uses radius-debug-config;
                uses radius-debug-state;
            } // END of state-container definition.
        } // END of debug-container definition.
    } // END of radius-container definition.
    } // END of radius-grouping definition.

    uses radius-grouping;

    rpc radius-clear-all-server-counters {
        if-feature feature-list:HAVE_HOSTPD;
        if-feature feature-list:HAVE_RADIUS_CLIENT;
        description "Use this RPC to clear counters for all RADIUS servers";
        input  {
            leaf vrf-name  {
                type string;
                mandatory true;
                description "VRF Name associated with this instance";
            }
        }
    }

    rpc radius-clear-server-counters {
        if-feature feature-list:HAVE_HOSTPD;
        if-feature feature-list:HAVE_RADIUS_CLIENT;
        description "Use this RPC to clear counters for a RADIUS server by hostname or IP
                    address";
        input  {
            leaf hostname  {
                type cml-data-types:cml_hostpname_t;
                mandatory true;
                description "Use this attribute to set the RADIUS server host name or IP address";
            }
            leaf vrf-name  {
                type string;
                mandatory true;
                description "VRF Name associated with this instance";
            }
        }
    }

    rpc radius-terminal-debug-on {
        if-feature feature-list:HAVE_HOSTPD;
        if-feature feature-list:HAVE_RADIUS_CLIENT;
        description "Use this RPC to turn on RADIUS terminal debug logs";
    }

    rpc radius-terminal-debug-off {
        if-feature feature-list:HAVE_HOSTPD;
        if-feature feature-list:HAVE_RADIUS_CLIENT;
        description "Use this RPC to turn off RADIUS terminal debug logs";
    }

}
