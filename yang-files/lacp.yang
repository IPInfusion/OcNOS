/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : lacp.yang
*
*/

submodule lacp {

    belongs-to  ZebOS { prefix ZebOS; }
    include interface;
            include mlag;


    import cml_data_types {
        prefix cml_data_types;
    }

    description
        "Layer-2 lacp  configurations";


    revision "2015-10-20" {
        description "Initial version of datamodel.";
    }



    grouping nsmlacpInterface-grouping {
        list nsmlacpInterface {
             
            description
                "NSM LACP interface related operations";

            config true;
            key "ifName";

            
            leaf ifName  {
                type  cml_data_types:CML_STRING_T {
                    length "0..255";
                }
            } // END of ifName definition.

            leaf vrId  {
                type  cml_data_types:CML_INT32_T;  
                default "0";
            } // END of vrId definition.

            leaf channelGroup  {
                mandatory true;
                type  cml_data_types:CML_UINT16_T {
                     range "1..65535";
                }
            } // END of channelGroup definition.

            leaf modeOperation  {
                mandatory true;
                type  cml_data_types:CML_LACP_MODE_T;  
                description "channel-group";
            } // END of modeOperation definition.

            uses mlagAgg-grouping;
        } // End of nsmlacpInterface-list
    } // END of nsmlacpInterface-grouping definition.


    grouping nsmportInterface-grouping {
        list nsmportInterface {
             
            description
                "NSM LACP interface related operations";

            config true;
            key "ifName";

            
            leaf ifName  {
                type  cml_data_types:CML_STRING_T {
                    length "0..255";
                }
            } // END of ifName definition.

            leaf psc  {
                type  cml_data_types:CML_LACP_PSC_T;  
                default "src-dst-mac";
            } // END of psc definition.

            leaf static-channel-group  {
                type  cml_data_types:CML_UINT16_T {
                     range "1..12";
                }
                description "static channel group";
            } // END of static-channel-group definition.

        } // End of nsmportInterface-list
    } // END of nsmportInterface-grouping definition.


}
