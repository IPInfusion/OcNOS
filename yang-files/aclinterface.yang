/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : aclinterface.yang
*
*/

submodule aclinterface {

    belongs-to  ZebOS { prefix ZebOS; }


    import cml_data_types {
        prefix cml_data_types;
    }

    description
        "Access List Interface Related Configurations";


    revision "2016-11-17" {
        description "Initial version of datamodel.";
    }



    grouping aclInterface-grouping {
        list aclInterface {
             
            description
                "ACL interface related operations";

            config true;
            key "ifName";

            
            leaf ifName  {
                type  cml_data_types:CML_STRING_T {
                    length "0..255";
                }
            } // END of ifName definition.

            leaf ifAclType  {
                type  cml_data_types:CML_ACL_TYPES_T;  
            } // END of ifAclType definition.

            leaf ifAclName  {
                type  cml_data_types:CML_STRING_T {
                    length "0..255";
                }
            } // END of ifAclName definition.

            leaf ifAclDir  {
                type  cml_data_types:CML_ACL_PACKET_DIR_T;  
            } // END of ifAclDir definition.

        } // End of aclInterface-list
    } // END of aclInterface-grouping definition.


}
