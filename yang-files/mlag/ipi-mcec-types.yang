/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-mcec-types.yang
*
*/

module ipi-mcec-types {

    yang-version 1.1;

    namespace   "http://www.ipinfusion.com/yang/ocnos/ipi-mcec-types";

    prefix "ipi-mcec-types";

    organization
        "IP Infusion Inc.";

    contact
        "Address: 3965 Freedom Circle, Suite 200, Santa Clara, CA 95054
         Phone: +1 408-400-1900
         E-mail: support@ipinfusion.com
         Web: http://www.ipinfusion.com/";

    description
        "MCEC data types";


    revision "2021-06-30" {
        description "Updated data types to use standard yang types wherever applicable";
        reference " 0.1.2.";
    }

    revision "2021-04-19" {
        description "Fixed enum with wrong name";
        reference " 0.1.1.";
    }

    revision "2021-03-06" {
        description "Restructured module as per open-config";
        reference " 0.1.0.";
    }



    typedef  mcec_mode_type_t {
        type enumeration {
            enum active-standby {
                value 0;
                description "active-standby";
            }
            enum active-active {
                value 1;
                description "active-active";
            }
        }
        description "type definition for MCEC_MODE_TYPE_T";
    }

    typedef  mcec_debug_t {
        type bits {
            bit hello {
                position 0;
                description "Hello";
            }
            bit info {
                position 1;
                description "Info";
            }
            bit timer {
                position 2;
                description "Timer";
            }
            bit event {
                position 3;
                description "Event";
            }
            bit cli {
                position 4;
                description "CLI";
            }
            bit mac-sync {
                position 5;
                description "MAC Sync";
            }
            bit stp {
                position 6;
                description "STP";
            }
        }
        description "type definition for MCEC_DEBUG_T";
    }

    typedef  mcec_hello_t {
        type enumeration {
            enum long {
                value 0;
                description "Long Timeout";
            }
            enum short {
                value 1;
                description "Short Timeout";
            }
        }
        description "type definition for MCEC_HELLO_T";
    }

    typedef  mcec_domain_addr_t {
        type string {
            pattern "([0-9a-fA-F]{4}(\\.[0-9a-fA-F]{4}){2})";
        }
        description "type definition for MCEC_DOMAIN_ADDR_T";
    }

    typedef  mcec_sync_state_t {
        type enumeration {
            enum OUT-OF-SYNC {
                value 0;
                description "Out of sync state";
            }
            enum IN-SYNC {
                value 1;
                description "In sync state";
            }
        }
        description "type definition for MCEC_SYNC_STATE_T";
    }

    typedef  mcec_if_state_t {
        type enumeration {
            enum DOWN {
                value 0;
                description "Out of sync state";
            }
            enum UP {
                value 1;
                description "In sync state";
            }
        }
        description "type definition for MCEC_IF_STATE_T";
    }

    typedef  mcec_flood_state_t {
        type enumeration {
            enum DISABLED {
                value 0;
                description "Flood disabled";
            }
            enum ENABLED {
                value 1;
                description "Flood enabled";
            }
        }
        description "type definition for MCEC_FLOOD_STATE_T";
    }

    typedef  mcec_stp_sync_flags_t {
        type bits {
            bit MCEC_SEND_STP_TCN {
                position 0;
                description "Send STP TCN";
            }
            bit MCEC_SEND_ROOT_PORT_DOWN {
                position 1;
                description "Send Root Port Down";
            }
            bit MCEC_STP_IDP_IS_BLOCKING {
                position 2;
                description "STP IDP is Blocking";
            }
            bit MCEC_STP_IDP_IS_FORWARDING {
                position 3;
                description "STP IDP is Forwarding";
            }
        }
        description "type definition for MCEC_STP_SYNC_FLAGS_T";
    }

    typedef  mcec_domain_sync_status_t {
        type enumeration {
            enum OUT_OF_SYNC {
                value 0;
                description "Domain is Out-of-Sync";
            }
            enum IN_SYNC {
                value 1;
                description "Domain is in Sync";
            }
        }
        description "type definition for MCEC_DOMAIN_SYNC_STATUS_T";
    }

    typedef  mcec_stp_state_t {
        type enumeration {
            enum MCEC_PORT_DISCARDING {
                value 0;
                description "Port discarding";
            }
            enum MCEC_PORT_FORWARDING {
                value 1;
                description "Port forwarding";
            }
        }
        description "type definition for MCEC_STP_STATE_T";
    }

    typedef  mcec_domain_adjacency_state_t {
        type enumeration {
            enum DOWN {
                value 0;
                description "Out of sync state";
            }
            enum UP {
                value 1;
                description "In sync state";
            }
        }
        description "type definition for MCEC_DOMAIN_ADJACENCY_STATE_T";
    }

    typedef  mcec_info_periodic_tx_state_t {
        type enumeration {
            enum MCEC_INFO_PERIODIC_TX_INVALID {
                value 0;
                description "Invalid";
            }
            enum MCEC_INFO_PERIODIC_TX_NO_PERIODIC {
                value 1;
                description "No Periodic";
            }
            enum MCEC_INFO_PERIODIC_TX_FAST_PERIODIC {
                value 2;
                description "Fast Periodic";
            }
            enum MCEC_INFO_PERIODIC_TX_PERIODIC_TX {
                value 3;
                description "Periodic Tx";
            }
            enum MCEC_INFO_PERIODIC_TX_STANDBY {
                value 4;
                description "Standby";
            }
            enum MCEC_INFO_PERIODIC_TX_UNKNOWN {
                value 5;
                description "Unknown";
            }
        }
        description "type definition for MCEC_INFO_PERIODIC_TX_STATE_T";
    }

    typedef  mcec_hello_periodic_tx_state_t {
        type enumeration {
            enum MCEC_HELLO_PERIODIC_TX_INVALID {
                value 0;
                description "Invalid";
            }
            enum MCEC_HELLO_PERIODIC_TX_NO_PERIODIC {
                value 1;
                description "No Periodic";
            }
            enum MCEC_HELLO_PERIODIC_TX_FAST_PERIODIC {
                value 2;
                description "Fast Periodic";
            }
            enum MCEC_HELLO_PERIODIC_TX_SLOW_PERIODIC {
                value 3;
                description "Slow Periodic";
            }
            enum MCEC_HELLO_PERIODIC_TX_PERIODIC_TX {
                value 4;
                description "Periodic Tx";
            }
            enum MCEC_HELLO_PERIODIC_TX_UNKNOWN {
                value 5;
                description "Unknown";
            }
        }
        description "type definition for MCEC_HELLO_PERIODIC_TX_STATE_T";
    }

    typedef  mcec_info_receive_state_t {
        type enumeration {
            enum MCEC_INFO_RCV_INVALID {
                value 0;
                description "Invalid";
            }
            enum MCEC_INFO_RCV_INITIALIZE {
                value 1;
                description "Initialize";
            }
            enum MCEC_INFO_RCV_EXPIRED {
                value 2;
                description "Expired";
            }
            enum MCEC_INFO_RCV_PORTAL_CHECK {
                value 3;
                description "Portal Check";
            }
            enum MCEC_INFO_RCV_DISCARD {
                value 4;
                description "Discard";
            }
            enum MCEC_INFO_RCV_CURRENT {
                value 5;
                description "Current";
            }
            enum MCEC_INFO_RCV_UNKNOWN {
                value 6;
                description "Unknown";
            }
        }
        description "type definition for MCEC_INFO_RECEIVE_STATE_T";
    }

}
