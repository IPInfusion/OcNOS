/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-mpls-bfd.yang
*
*/

module ipi-mpls-bfd {

    yang-version 1.1;

    namespace   "http://www.ipinfusion.com/yang/ocnos/ipi-mpls-bfd";

    prefix "ipi-mpls-bfd";

    import ietf-inet-types {
        prefix inet;
        revision-date 2013-07-15;
    }

    import ipi-bfd-types {
        prefix ipi-bfd-types;
        revision-date 2022-08-12;
    }

    import ipi-bfd {
        prefix ipi-bfd;
        revision-date 2022-09-30;
    }

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for MPLS BFD";


    revision "2022-08-12" {
        description "Changed name of the element in OAMBFD_MPLS_LSP_TYPE_T and MPLS_BFD_ALL_LSP_TYPE_T";
        reference " 0.4.1.";
    }

    revision "2022-07-31" {
        description "Stop using inet:ipv4-prefix and inet:ipv6-prefix due to Cisco NSO iterop";
        reference " 0.4.0.";
    }

    revision "2022-06-20" {
        description "Changed name of the element in OAMBFD_MPLS_LSP_TYPE_T";
        reference " 0.3.1.";
    }

    revision "2022-06-01" {
        description "Updated the yang file with feature";
        reference " 0.3.0.";
    }

    revision "2021-08-12" {
        description "Moved MPLS BFD session runtime attributes to a separate submodule";
        reference " 0.2.0.";
    }

    revision "2021-08-11" {
        description "Initial Version";
        reference " 0.1.0.";
    }

    grouping mpls-bfd-attributes-config {
        description
            "MPLS BFD Attributes";
        leaf lsp-ping-interval  {
            type  uint16 {
                 range "0..1000"  {
                    description "0..1000: Supported range 0 - 1000";
                 }
            }
            default "5";
            description "";
        } // END of lsp-ping-interval definition.

        leaf admin-down  {
            type  empty;
            description "";
        } // END of admin-down definition.

    } // END of mpls-bfd-attributes-config definition.
    grouping mpls-bfd-interval-attributes-top {
        description
            "MPLS BFD Attributes";

        list interval {
            key "minimum-tx minimum-rx detection-multiplier";
            max-elements 1;
            description
                "Intervals values for the MPLS BFD sessions";
            leaf minimum-tx  {
                type  leafref {
                    path  "../config/minimum-tx";
                }
                description "";
            } // END of minimum-tx definition.

            leaf minimum-rx  {
                type  leafref {
                    path  "../config/minimum-rx";
                }
                description "";
            } // END of minimum-rx definition.

            leaf detection-multiplier  {
                type  leafref {
                    path  "../config/detection-multiplier";
                }
                description "";
            } // END of detection-multiplier definition.

            container config {
                description
                    "Configuration container for MPLS BFD LSP";
                uses mpls-bfd-interval-attributes-config;
            } // END of config-container definition.
            container state {
                config false;
                description
                    "Operational container for MPLS BFD LSP";
                uses mpls-bfd-interval-attributes-config;
            } // END of state-container definition.
        } // End of interval-list
    } // END of mpls-bfd-interval-attributes-top definition.
    grouping mpls-bfd-interval-attributes-config {
        description
            "MPLS BFD Attributes";
        leaf minimum-tx  {
            type  uint32 {
                 range "3..4294967"  {
                    description "3..4294967: Supported range 3 - 4294967";
                 }
            }
            description "";
        } // END of minimum-tx definition.

        leaf minimum-rx  {
            type  uint32 {
                 range "3..4294967"  {
                    description "3..4294967: Supported range 3 - 4294967";
                 }
            }
            description "";
        } // END of minimum-rx definition.

        leaf detection-multiplier  {
            type  uint8 {
                 range "1..255"  {
                    description "1..255: Supported range 1 - 255";
                 }
            }
            description "";
        } // END of detection-multiplier definition.

    } // END of mpls-bfd-interval-attributes-config definition.
    grouping mpls-bfd-lsp-config {
        description
            "MPLS BFD LSP Configs";
        leaf lsp-type  {
            type  ipi-bfd-types:mpls_bfd_lsp_type_t;
            description "This attribute is used to configure lsp type of the MPLS BFD session";
        } // END of lsp-type definition.

        leaf fec-address  {
            type  inet:ipv4-prefix;
            description "This attribute is used to configure fec address of the MPLS BFD
                        session";
        } // END of fec-address definition.

    } // END of mpls-bfd-lsp-config definition.
    grouping mpls-bfd-all-config {
        description
            "MPLS BFD all Configs";
        leaf lsp-type  {
            type  ipi-bfd-types:mpls_bfd_all_lsp_type_t;
            description "This attribute is used to configure lsp type of the MPLS BFD session";
        } // END of lsp-type definition.

    } // END of mpls-bfd-all-config definition.
    grouping mpls-bfd-te-config {
        description
            "MPLS-TE BFD Configs";
        leaf lsp-type  {
            type  ipi-bfd-types:mpls_bfd_te_type_t;
            description "This attribute is used to configure lsp type of the MPLS BFD session";
        } // END of lsp-type definition.

        leaf tunnel-name  {
            type  string {
                length "1..32";
                pattern "[^?' =,>|]+";
            }
            description "This attribute is used to configure tunnel name of the RSVP BFD
                        session";
        } // END of tunnel-name definition.

    } // END of mpls-bfd-te-config definition.

    grouping  mpls-lsp-grouping {
    description
        "MPLS BFD LSP configurations";
    container mpls-lsp {
        if-feature feature-list:HAVE_CUSTOM1_MPLS_BFD;
        if-feature feature-list:HAVE_BFD;
        description
            "MPLS BFD LSP configurations";
        container session-groups {
            description
                "MPLS BFD LSP Sessions";

            list session-group {
                key "lsp-type fec-address";
                description
                    "MPLS BFD LSP Sessions";
                leaf lsp-type  {
                    type  leafref {
                        path  "../config/lsp-type";
                    }
                    description "This attribute is used to configure lsp type of the MPLS BFD session";
                } // END of lsp-type definition.

                leaf fec-address  {
                    type  leafref {
                        path  "../config/fec-address";
                    }
                    description "This attribute is used to configure fec address of the MPLS BFD
                                session";
                } // END of fec-address definition.

                container config {
                    description
                        "Configuration container for MPLS BFD LSP";
                    uses mpls-bfd-lsp-config;
                } // END of config-container definition.
                container state {
                    config false;
                    description
                        "Operational container for MPLS BFD LSP";
                    uses mpls-bfd-lsp-config;
                } // END of state-container definition.
                container session-attributes {
                    description
                        "MPLS BFD session attributes";
                    container config {
                        description
                            "Configuration container for MPLS BFD LSP";
                        uses mpls-bfd-attributes-config;
                    } // END of config-container definition.
                    container state {
                        config false;
                        description
                            "Operational container for MPLS BFD LSP";
                        uses mpls-bfd-attributes-config;
                    } // END of state-container definition.
                    uses mpls-bfd-interval-attributes-top;
                } // END of session-attributes-container definition.
            } // End of session-group-list
        } // END of session-groups-container definition.
    } // END of mpls-lsp-container definition.
    } // END of mpls-lsp-grouping definition.

    grouping  mpls-all-lsps-grouping {
    description
        "MPLS BFD ALL LSP configurations";
    container mpls-all-lsps {
        if-feature feature-list:HAVE_CUSTOM1_MPLS_BFD;
        if-feature feature-list:HAVE_BFD;
        description
            "MPLS BFD ALL LSP configurations";

        list mpls-all-lsp {
            key "lsp-type";
            description
                "MPLS BFD ALL config";
            leaf lsp-type  {
                type  leafref {
                    path  "../config/lsp-type";
                }
                description "This attribute is used to configure lsp type of the MPLS BFD session";
            } // END of lsp-type definition.

            container config {
                description
                    "Configuration container for MPLS BFD LSP";
                uses mpls-bfd-all-config;
            } // END of config-container definition.
            container state {
                config false;
                description
                    "Operational container for MPLS BFD LSP";
                uses mpls-bfd-all-config;
            } // END of state-container definition.
            container session-attributes {
                description
                    "MPLS BFD session attributes";
                container config {
                    description
                        "Configuration container for MPLS BFD LSP";
                    uses mpls-bfd-attributes-config;
                } // END of config-container definition.
                container state {
                    config false;
                    description
                        "Operational container for MPLS BFD LSP";
                    uses mpls-bfd-attributes-config;
                } // END of state-container definition.
                uses mpls-bfd-interval-attributes-top;
            } // END of session-attributes-container definition.
        } // End of mpls-all-lsp-list
    } // END of mpls-all-lsps-container definition.
    } // END of mpls-all-lsps-grouping definition.

    grouping  mpls-tunnels-grouping {
    description
        "MPLS BFD TUNNEL configurations";
    container mpls-tunnels {
        if-feature feature-list:HAVE_CUSTOM1_MPLS_BFD;
        if-feature feature-list:HAVE_BFD;
        description
            "MPLS BFD TUNNEL configurations";

        list mpls-tunnel {
            key "lsp-type tunnel-name";
            description
                "MPLS BFD TUNNEL configurations";
            leaf lsp-type  {
                type  leafref {
                    path  "../config/lsp-type";
                }
                description "This attribute is used to configure lsp type of the MPLS BFD session";
            } // END of lsp-type definition.

            leaf tunnel-name  {
                type  leafref {
                    path  "../config/tunnel-name";
                }
                description "This attribute is used to configure tunnel-name of the RSVP BFD
                            session";
            } // END of tunnel-name definition.

            container config {
                description
                    "Configuration container for MPLS BFD";
                uses mpls-bfd-te-config;
            } // END of config-container definition.
            container state {
                config false;
                description
                    "Operational container for MPLS BFD";
                uses mpls-bfd-te-config;
            } // END of state-container definition.
            container session-attributes {
                description
                    "MPLS BFD session attributes";
                container config {
                    description
                        "Configuration container for MPLS BFD";
                    uses mpls-bfd-attributes-config;
                } // END of config-container definition.
                container state {
                    config false;
                    description
                        "Operational container for MPLS BFD";
                    uses mpls-bfd-attributes-config;
                } // END of state-container definition.
                uses mpls-bfd-interval-attributes-top;
            } // END of session-attributes-container definition.
        } // End of mpls-tunnel-list
    } // END of mpls-tunnels-container definition.
    } // END of mpls-tunnels-grouping definition.

    augment /ipi-bfd:bfd {
        if-feature feature-list:HAVE_BFD;
        description
            "MPLS BFD LSP configurations";
        uses mpls-lsp-grouping;
    }

    augment /ipi-bfd:bfd {
        if-feature feature-list:HAVE_BFD;
        description
            "MPLS BFD ALL LSP configurations";
        uses mpls-all-lsps-grouping;
    }

    augment /ipi-bfd:bfd {
        if-feature feature-list:HAVE_BFD;
        description
            "MPLS BFD TUNNEL configurations";
        uses mpls-tunnels-grouping;
    }


}
