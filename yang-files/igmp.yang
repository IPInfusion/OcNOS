/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : igmp.yang
*
*/

submodule igmp {

    belongs-to  ZebOS { prefix ZebOS; }
    include interface;


    import cml_data_types {
        prefix cml_data_types;
    }


    revision "2017-02-02" {
        description "changes for Documentation.";
    }

    revision "2017-01-27" {
        description "changes for Debug command.";
    }

    revision "2017-01-25" {
        description "Fix for JIRA-12076 must attribute.";
    }

    revision "2016-10-06" {
        description "Initial draft version.";
    }



    grouping mrib4Igmp-grouping {
        list mrib4Igmp {
             
            description
                "mrib4Igmp";

            config true;
            key "vrfName";

            
            leaf vrId  {
                type  cml_data_types:CML_INT32_T;  
            } // END of vrId definition.

            leaf vrfName  {
                type  cml_data_types:CML_STRING_T {
                    length "0..255";
                }
            } // END of vrfName definition.

            leaf setSSMEnabledFlag  {
                type  cml_data_types:CML_BOOL_T;  
                default false;
                description "ip igmp";
            } // END of setSSMEnabledFlag definition.

            leaf stateIGMPLimit  {
                type  cml_data_types:CML_UINT32_T {
                     range "1..2097152";
                }
                default "1";
                description "ip igmp limit";
            } // END of stateIGMPLimit definition.

            leaf exceptionAccessList  {
                type  cml_data_types:CML_STRING_T {
                    length "0..255";
                }
            } // END of exceptionAccessList definition.

            leaf tosCheck  {
                type  cml_data_types:CML_BOOL_T;  
            } // END of tosCheck definition.

            leaf igi_num_grecs  {
                type  cml_data_types:CML_UINT32_T;  
                config false;
            } // END of igi_num_grecs definition.

            leaf ssmStaticFlag  {
                type  cml_data_types:CML_STRING_T {
                    length "0..255";
                }
                config false;
            } // END of ssmStaticFlag definition.

            leaf debugFlag  {
                type  cml_data_types:CML_IGMP_DEBUG_T;  
            } // END of debugFlag definition.

            leaf termdebugFlag  {
                type  cml_data_types:CML_IGMP_DEBUG_T;  
            } // END of termdebugFlag definition.


            list ssmStatic {
                 
                description
                    "ssmStatic";

                config true;
                key "staticAccessListName";

                
                leaf staticAccessListName  {
                    type  cml_data_types:CML_STRING_T {
                        length "0..255";
                    }
                } // END of staticAccessListName definition.

                leaf-list staticSourceAddr  {
                    type  cml_data_types:CML_STRING_T {
                        length "0..255";
                    }
                } // END of staticSourceAddr definition.

            } // End of ssmStatic-list
        } // End of mrib4Igmp-list
    } // END of mrib4Igmp-grouping definition.


    grouping mrib4IgmpInterface-grouping {
        list mrib4IgmpInterface {
             
            description
                "IGMP interface related operations";

            config true;
            key "ifName";

            
            leaf ifName  {
                type  cml_data_types:CML_STRING_T {
                    length "0..255";
                }
            } // END of ifName definition.

            leaf proxyIfName  {
                type  cml_data_types:CML_STRING_T {
                    length "0..255";
                }
                default "NULL";
                description "ip igmp mroute-proxy";
            } // END of proxyIfName definition.

            leaf setIGMPIfFlag  {
                type  cml_data_types:CML_BOOL_T;  
            } // END of setIGMPIfFlag definition.

            leaf lastMaxQueryCount  {
                type  cml_data_types:CML_UINT32_T {
                     range "2..7";
                }
                default "2";
                description "ip igmp last-member-query-count";
            } // END of lastMaxQueryCount definition.

            leaf lastMaxQueryInterval  {
                type  cml_data_types:CML_UINT32_T {
                     range "1000..25500";
                }
                default "1000";
                description "ip igmp last-member-query-interval";
            } // END of lastMaxQueryInterval definition.

            leaf proxyreportInterval  {
                type  cml_data_types:CML_UINT32_T {
                     range "1000..25500";
                }
                default "1000";
                description "ip igmp proxy unsolicited-report-interval";
            } // END of proxyreportInterval definition.

            leaf querierTimeout  {
                type  cml_data_types:CML_UINT16_T {
                     range "60..300";
                }
                default "255";
                description "ip igmp querier-timeout";
            } // END of querierTimeout definition.

            leaf queryInterval  {
                type  cml_data_types:CML_UINT32_T {
                     range "1..18000";
                }
                default "125";
                description "ip igmp query-interval";
            } // END of queryInterval definition.

            leaf startUpQueryInterval  {
                type  cml_data_types:CML_UINT32_T {
                     range "1..18000";
                }
                default "31";
                description "ip igmp startup-query-interval";
            } // END of startUpQueryInterval definition.

            leaf queryCount  {
                type  cml_data_types:CML_UINT32_T {
                     range "2..10";
                }
                default "2";
                description "ip igmp startup-query-count";
            } // END of queryCount definition.

            leaf responseInterval  {
                type  cml_data_types:CML_UINT32_T {
                     range "1..240";
                }
                default "10";
                description "ip igmp querymax-response-time";
            } // END of responseInterval definition.

            leaf robustnessVariableVal  {
                type  cml_data_types:CML_UINT32_T {
                     range "2..7";
                }
                default "2";
                description "ip igmp robustness-variable";
            } // END of robustnessVariableVal definition.

            leaf versionNumber  {
                type  cml_data_types:CML_UINT16_T {
                     range "1..3";
                }
                default "3";
                description "ip igmp version";
            } // END of versionNumber definition.

            leaf setIGMPIfRaFlag  {
                type  cml_data_types:CML_BOOL_T;  
                description "ip igmp ra-option";
            } // END of setIGMPIfRaFlag definition.

            leaf setIGMPIfOfflinkFlag  {
                type  cml_data_types:CML_BOOL_T;  
                description "ip igmp offlink";
            } // END of setIGMPIfOfflinkFlag definition.

            leaf setIGMPIfPxyFlag  {
                type  cml_data_types:CML_BOOL_T;  
                description "ip igmp proxy-service";
            } // END of setIGMPIfPxyFlag definition.

            leaf accessListName  {
                type  cml_data_types:CML_STRING_T {
                    length "0..255";
                }
                default "NULL";
                description "ip igmp access-group";
            } // END of accessListName definition.

            leaf immediateGroupListName  {
                type  cml_data_types:CML_STRING_T {
                    length "0..255";
                }
                default "NULL";
                description "ip igmp immediate-leave";
            } // END of immediateGroupListName definition.

            leaf stateIGMPIFLimit  {
                type  cml_data_types:CML_UINT32_T {
                     range "1..2097152";
                }
                default "1";
                description "ip igmp limit";
            } // END of stateIGMPIFLimit definition.

            leaf ifExceptionAccessList  {
                type  cml_data_types:CML_STRING_T {
                    length "0..255";
                }
                default "NULL";
            } // END of ifExceptionAccessList definition.

            leaf interfaceName  {
                type  cml_data_types:CML_STRING_T {
                    length "0..255";
                }
                config false;
            } // END of interfaceName definition.

            leaf state  {
                type  cml_data_types:CML_STRING_T {
                    length "0..255";
                }
                config false;
            } // END of state definition.

            leaf hostVersion  {
                type  cml_data_types:CML_STRING_T {
                    length "0..255";
                }
                config false;
            } // END of hostVersion definition.

            leaf InternetAddr  {
                type  cml_data_types:CML_STRING_T {
                    length "0..255";
                }
                config false;
            } // END of InternetAddr definition.

            leaf proxyOperationalStatus  {
                type  cml_data_types:CML_STRING_T {
                    length "0..255";
                }
                config false;
            } // END of proxyOperationalStatus definition.

            leaf OtherQuerierAddr  {
                type  cml_data_types:CML_STRING_T {
                    length "0..255";
                }
                config false;
            } // END of OtherQuerierAddr definition.

            leaf ifIndex  {
                type  cml_data_types:CML_UINT32_T;  
                config false;
            } // END of ifIndex definition.

            leaf grpMemInterval  {
                type  cml_data_types:CML_UINT32_T;  
                config false;
            } // END of grpMemInterval definition.

            leaf joinReceivedCount  {
                type  cml_data_types:CML_UINT32_T;  
                config false;
            } // END of joinReceivedCount definition.

            leaf leaveReceivedCount  {
                type  cml_data_types:CML_UINT32_T;  
                config false;
            } // END of leaveReceivedCount definition.

            leaf stats_igif_num_reports  {
                type  cml_data_types:CML_UINT32_T;  
                config false;
            } // END of stats_igif_num_reports definition.

            leaf stat_igif_num_v1_reports  {
                type  cml_data_types:CML_UINT32_T;  
                config false;
            } // END of stat_igif_num_v1_reports definition.

            leaf stat_igif_num_v3_reports  {
                type  cml_data_types:CML_UINT32_T;  
                config false;
            } // END of stat_igif_num_v3_reports definition.

            leaf interfaceLimit  {
                type  cml_data_types:CML_UINT32_T;  
                config false;
            } // END of interfaceLimit definition.

            leaf limitExceptAccessList  {
                type  cml_data_types:CML_STRING_T {
                    length "0..255";
                }
                config false;
            } // END of limitExceptAccessList definition.

            leaf mcastgCount  {
                type  cml_data_types:CML_UINT32_T;  
                config false;
            } // END of mcastgCount definition.

            leaf querierState  {
                type  cml_data_types:CML_STRING_T {
                    length "0..255";
                }
                config false;
            } // END of querierState definition.

            leaf igmpState  {
                type  cml_data_types:CML_STRING_T {
                    length "0..255";
                }
                config false;
            } // END of igmpState definition.

            leaf igif_querier_wcount  {
                type  cml_data_types:CML_UINT16_T;  
                config false;
            } // END of igif_querier_wcount definition.

            leaf igif_num_reports  {
                type  cml_data_types:CML_UINT16_T;  
                config false;
            } // END of igif_num_reports definition.


            list staticGroup {
                 
                description
                    "staticGroup";

                config true;
                key "multicastStaticGroupAddr";

                
                leaf multicastStaticGroupAddr  {
                    type  cml_data_types:CML_IPV4_ADDR_T;  
                    description "ip igmp static-group";
                } // END of multicastStaticGroupAddr definition.

                leaf isSsmMapped  {
                    type  cml_data_types:CML_BOOL_T;  
                } // END of isSsmMapped definition.

                uses SourceGroup;
            } // End of staticGroup-list

            list joinGroup {
                 
                description
                    "joinGroup";

                config true;
                key "groupAddr";

                
                leaf groupAddr  {
                    type  cml_data_types:CML_IPV4_ADDR_T;  
                    description "ip igmp join-group";
                } // END of groupAddr definition.

                uses SourceGroup;
            } // End of joinGroup-list

            list ProxyGroup {
                 
                description
                    "ProxyGroup";

                config false;
                key "ProxyGroupAddr";

                
                leaf ProxyInterfaceName  {
                    type  cml_data_types:CML_STRING_T {
                        length "0..255";
                    }
                } // END of ProxyInterfaceName definition.

                leaf ProxyGroupAddr  {
                    type  cml_data_types:CML_STRING_T {
                        length "0..255";
                    }
                } // END of ProxyGroupAddr definition.

                leaf ProxyGroupMode  {
                    type  cml_data_types:CML_STRING_T {
                        length "0..255";
                    }
                } // END of ProxyGroupMode definition.

                leaf ProxyGroupState  {
                    type  cml_data_types:CML_STRING_T {
                        length "0..255";
                    }
                } // END of ProxyGroupState definition.

                leaf ProxyGroupMemberState  {
                    type  cml_data_types:CML_STRING_T {
                        length "0..255";
                    }
                } // END of ProxyGroupMemberState definition.

                leaf src_a_tib_addr  {
                    type  cml_data_types:CML_STRING_T {
                        length "0..255";
                    }
                } // END of src_a_tib_addr definition.

                leaf src_b_tib_addr  {
                    type  cml_data_types:CML_STRING_T {
                        length "0..255";
                    }
                } // END of src_b_tib_addr definition.

            } // End of ProxyGroup-list
        } // End of mrib4IgmpInterface-list
    } // END of mrib4IgmpInterface-grouping definition.
    grouping SourceGroup {
                leaf SGInterfaceName  {
            type  cml_data_types:CML_STRING_T {
                length "0..255";
            }
            config false;
        } // END of SGInterfaceName definition.

        leaf groupFlags  {
            type  cml_data_types:CML_STRING_T {
                length "0..255";
            }
            config false;
        } // END of groupFlags definition.

        leaf groupUpTime  {
            type  cml_data_types:CML_STRING_T {
                length "0..255";
            }
            config false;
        } // END of groupUpTime definition.

        leaf groupMode  {
            type  cml_data_types:CML_STRING_T {
                length "0..255";
            }
            config false;
        } // END of groupMode definition.

        leaf groupExpiry  {
            type  cml_data_types:CML_STRING_T {
                length "0..255";
            }
            config false;
        } // END of groupExpiry definition.

        leaf groupSFlags  {
            type  cml_data_types:CML_STRING_T {
                length "0..255";
            }
            config false;
        } // END of groupSFlags definition.

        leaf lastReporter  {
            type  cml_data_types:CML_STRING_T {
                length "0..255";
            }
            config false;
        } // END of lastReporter definition.

        leaf t_igr_v1_host_present  {
            type  cml_data_types:CML_UINT32_T;  
            config false;
        } // END of t_igr_v1_host_present definition.

        leaf t_igr_v2_host_present  {
            type  cml_data_types:CML_UINT32_T;  
            config false;
        } // END of t_igr_v2_host_present definition.


        list src_a_tib_grp {
             
            description
                "srcCMLSEPaCMLSEPtibCMLSEPgrp";

            config true;
            key "MultisourceAddr";

            
            leaf MultisourceAddr  {
                type  cml_data_types:CML_IPV4_ADDR_T;  
            } // END of MultisourceAddr definition.

            leaf srcAUpTime  {
                type  cml_data_types:CML_STRING_T {
                    length "0..255";
                }
                config false;
            } // END of srcAUpTime definition.

            leaf srcAExpiry  {
                type  cml_data_types:CML_STRING_T {
                    length "0..255";
                }
                config false;
            } // END of srcAExpiry definition.

            leaf srcAStr  {
                type  cml_data_types:CML_STRING_T {
                    length "0..255";
                }
                config false;
            } // END of srcAStr definition.

            leaf srcASFlags  {
                type  cml_data_types:CML_STRING_T {
                    length "0..255";
                }
                config false;
            } // END of srcASFlags definition.

        } // End of src_a_tib_grp-list

        list src_b_tib_grp {
             
            description
                "srcCMLSEPbCMLSEPtibCMLSEPgrp";

            config false;
            key "srcBAddr";

            
            leaf srcBAddr  {
                type  cml_data_types:CML_STRING_T {
                    length "0..255";
                }
            } // END of srcBAddr definition.

            leaf srcBUpTime  {
                type  cml_data_types:CML_STRING_T {
                    length "0..255";
                }
            } // END of srcBUpTime definition.

            leaf srcBExpiry  {
                type  cml_data_types:CML_STRING_T {
                    length "0..255";
                }
            } // END of srcBExpiry definition.

            leaf srcBstr  {
                type  cml_data_types:CML_STRING_T {
                    length "0..255";
                }
            } // END of srcBstr definition.

            leaf srcBSFlags  {
                type  cml_data_types:CML_STRING_T {
                    length "0..255";
                }
            } // END of srcBSFlags definition.

        } // End of src_b_tib_grp-list
    } // END of SourceGroup definition.


}
