/*
* Copyright (C) 2016 IP Infusion, Inc. 
*  All Rights Reserved.
*
*** Auto generated by zebmdc

* Unless required by applicable law or agreed to in writing,
* software distributed under the License is distributed on an
* "AS IS" BASIS, WITHOUT WARRANTIES OR CONDITIONS OF ANY
* KIND, either express or implied.

* File name : layer2LACP.yang
*
*/

submodule layer2LACP {

    belongs-to  ZebOS { prefix ZebOS; }
    include interface;


    import cml_data_types {
        prefix cml_data_types;
    }

    description
        "Layer-2 lacp  configurations";


    revision "2015-10-21" {
        description "Revisied on 2015-10-21.";    }



    grouping lacpInterface-grouping {
        list lacpInterface {
             

            description
                "LACP interface related operations";

            config true;
            key "ifName";

            
            leaf ifName  {
                mandatory true;                
                type  leafref {
                    path  "/vr/interface/ifName";
                }
            } // END of ifName definition.

            leaf portPriority  {
                mandatory false;                
                type  cml_data_types:CML_UINT32_T {
                     range "1..65535";
                }
                default "32768";
                config true;
            } // END of portPriority definition.

            leaf TimeOut  {
                mandatory false;                
                type  cml_data_types:CML_LACP_TIMEOUT_T;  
                default "long";
                config true;
            } // END of TimeOut definition.

            leaf bridgeType  {
                mandatory false;                
                type  cml_data_types:CML_LACP_BRIDGETYPE_T;  
                default "multicast-group-address";
                config true;
            } // END of bridgeType definition.

            leaf discardConv  {
                mandatory false;                
                type  cml_data_types:CML_LACP_DISCARD_CONV_T;  
                default "disable";
                config true;
            } // END of discardConv definition.

        } // End of lacpInterface-list
    } // END of lacpInterface-grouping definition.

    grouping  lacpSystemPriority-grouping {
    container lacpSystemPriority {
        
        config true;

        description
            "lacpSystemPriority";

        leaf systemPriority  {
            mandatory false;            
            type  cml_data_types:CML_UINT32_T {
                 range "1..65535";
            }
            default "32768";
            config true;
        } // END of systemPriority definition.

    } // END of lacpSystemPriority-container definition.
    } // END of lacpSystemPriority-container definition.


}
