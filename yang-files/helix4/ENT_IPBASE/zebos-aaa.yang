/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-aaa.yang
*
*/

submodule zebos-aaa {

    belongs-to  zebos { prefix zebos; }

    import cml_data_types {
        prefix cml_data_types;
    }

    include zebos-vrf;
    include zebos-tacacs;
    include zebos-radius;
    organization
        "IP Infusion Inc.";

    contact
        "Address: 3965 Freedom Circle, Suite 200, Santa Clara, CA 95054
        Phone: +1 408-400-1900
        E-mail: support@ipinfusion.com
        Web: http://www.ipinfusion.com/";

    description
        "Layer-3 aaa configurations";


    revision "2017-06-08" {
        description "Uplifted the changes from linx branch.";
    }

    revision "2017-06-02" {
        description "Unlock Timeout Attribute.";
    }

    revision "2016-12-27" {
        description "Added snmp oid and documentation tag.";
    }

    revision "2016-10-28" {
        description "Initial version of AAA datamodel.";
    }


    grouping  aaa-grouping {
    container aaa {
        description
            "aaa related commands";
        leaf vrfName  {
            type  cml_data_types:CML_STRING_T {
                length "0..255";
            }
            description "";
        } // END of vrfName definition.

        leaf acctGroup  {
            type  cml_data_types:CML_STRING_T {
                length "0..255";
            }
            description "";
        } // END of acctGroup definition.

        leaf acctLocal  {
            type  cml_data_types:CML_BOOL_T;
            description "";
        } // END of acctLocal definition.

        leaf errorEnable  {
            type  cml_data_types:CML_BOOL_T;
            description "";
        } // END of errorEnable definition.

        leaf authDefaultGroup  {
            type  cml_data_types:CML_STRING_T {
                length "0..255";
            }
            description "";
        } // END of authDefaultGroup definition.

        leaf authMaxfail  {
            type  cml_data_types:CML_UINT8_T {
                 range "1..25";
            }
            default "3";
            description "";
        } // END of authMaxfail definition.

        leaf localUserUnlockTimeout  {
            type  cml_data_types:CML_UINT16_T {
                 range "1..3600";
            }
            default "1200";
            description "";
        } // END of localUserUnlockTimeout definition.

        leaf authDefaultFallback  {
            type  cml_data_types:CML_BOOL_T;
            description "";
        } // END of authDefaultFallback definition.

        leaf authLocalDefault  {
            type  cml_data_types:CML_BOOL_T;
            description "";
        } // END of authLocalDefault definition.

        leaf authNoneDefault  {
            type  cml_data_types:CML_BOOL_T;
            description "";
        } // END of authNoneDefault definition.

        leaf debugaaa  {
            type  cml_data_types:CML_BOOL_T;
            description "";
        } // END of debugaaa definition.

        leaf debugaaaConfig  {
            type  cml_data_types:CML_BOOL_T;
            description "";
        } // END of debugaaaConfig definition.


        list aaaGroupServerNameRadius {
            key "groupWordRadius";
            description
                "aaaGroupServerNameRadius";
            leaf groupWordRadius  {
                type  cml_data_types:CML_STRING_T {
                    length "1..127";
                }
                description "";
            } // END of groupWordRadius definition.


            list aaaRadiusServer {
                key "hostAddr";
                description
                    "aaaRadiusServer";
                leaf vrfName  {
                    type  cml_data_types:CML_STRING_T {
                        length "0..255";
                    }
                    description "";
                } // END of vrfName definition.

                leaf hostAddr  {
                    type  cml_data_types:CML_HOSTPNAME_T;
                    description "";
                } // END of hostAddr definition.

            } // End of aaaRadiusServer-list
        } // End of aaaGroupServerNameRadius-list

        list aaaGroupServerNameTacacs {
            key "groupWordTacacs";
            description
                "aaaGroupServerNameTacacs";
            leaf groupWordTacacs  {
                type  cml_data_types:CML_STRING_T {
                    length "1..127";
                }
                description "";
            } // END of groupWordTacacs definition.


            list aaaTacacsServer {
                key "hostAddr";
                description
                    "aaaTacacsServer";
                leaf vrfName  {
                    type  cml_data_types:CML_STRING_T {
                        length "0..255";
                    }
                    description "";
                } // END of vrfName definition.

                leaf hostAddr  {
                    type  cml_data_types:CML_HOSTPNAME_T;
                    description "";
                } // END of hostAddr definition.

            } // End of aaaTacacsServer-list
        } // End of aaaGroupServerNameTacacs-list
        container console {
            description
                "console";
            leaf authConsoleGroup  {
                type  cml_data_types:CML_STRING_T {
                    length "0..255";
                }
                description "";
            } // END of authConsoleGroup definition.

            leaf authConsoleFallback  {
                type  cml_data_types:CML_BOOL_T;
                description "";
            } // END of authConsoleFallback definition.

            leaf authLocal  {
                type  cml_data_types:CML_BOOL_T;
                description "";
            } // END of authLocal definition.

            leaf authNone  {
                type  cml_data_types:CML_BOOL_T;
                description "";
            } // END of authNone definition.

        } // END of console-container definition.
    } // END of aaa-container definition.
    } // END of aaa-container definition.


}
