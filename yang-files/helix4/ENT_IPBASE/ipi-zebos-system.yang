/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-zebos-system.yang
*
*/

submodule ipi-zebos-system {

    belongs-to  ipi-zebos { prefix ipi-zebos; }

    import cml-data-types {
        prefix cml-data-types;
    }

    organization
        "IP Infusion Inc.";

    contact
        "Address: 3965 Freedom Circle, Suite 200, Santa Clara, CA 95054
        Phone: +1 408-400-1900
        E-mail: support@ipinfusion.com
        Web: http://www.ipinfusion.com/";

    description
        "system global configs";


    revision "2019-08-22" {
        description " Initial Version.";
        reference "";
    }


    grouping  systemHostname-grouping {
    description
        "system's network name";
    container systemHostname {
        description
            "system's network name";
        leaf hostname  {
            type  cml-data-types:CML_STRING_T {
                length "1..63";
            }
            description "";
        } // END of hostname definition.

    } // END of systemHostname-container definition.
    } // END of systemHostname-container definition.


}
