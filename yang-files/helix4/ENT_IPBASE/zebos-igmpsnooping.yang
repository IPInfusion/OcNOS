/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-igmpsnooping.yang
*
*/

submodule zebos-igmpsnooping {

    belongs-to  zebos { prefix zebos; }

    import cml_data_types {
        prefix cml_data_types;
    }

    organization
        "IP Infusion Inc.";

    contact
        "Address: 3965 Freedom Circle, Suite 200, Santa Clara, CA 95054
        Phone: +1 408-400-1900
        E-mail: support@ipinfusion.com
        Web: http://www.ipinfusion.com/";

    description
        "";


    revision "2018-06-21" {
        description " Initial Version.";
        reference "";
    }


    grouping  igmpConfig-grouping {
    description
        "igmpConfig";
    container igmpConfig {
        description
            "igmpConfig";
        leaf setSnoopFlag  {
            type  cml_data_types:CML_BOOL_T;
            description "";
        } // END of setSnoopFlag definition.

        leaf reportSuppressFlag  {
            type  cml_data_types:CML_BOOL_T;
            description "";
        } // END of reportSuppressFlag definition.

        leaf debugIgmpSnooping  {
            type  cml_data_types:CML_COMMON_DEBUG_TYPE_T;
            description "";
        } // END of debugIgmpSnooping definition.

        leaf termdebugIgmpSnooping  {
            type  cml_data_types:CML_COMMON_DEBUG_TYPE_T;
            description "";
        } // END of termdebugIgmpSnooping definition.

        leaf l2UnknownMcast  {
            type  cml_data_types:CML_UNKNOWN_MCAST_T;
            default "flood";
            description "";
        } // END of l2UnknownMcast definition.

    } // END of igmpConfig-container definition.
    } // END of igmpConfig-container definition.

    grouping  igmpSnoopInterface-grouping {
    description
        "igmpSnoopInterface";
    container igmpSnoopInterface {
        description
            "igmpSnoopInterface";
        leaf disableIgmpIfFlag  {
            type  cml_data_types:CML_BOOL_T;
            default true;
            description "";
        } // END of disableIgmpIfFlag definition.

        leaf setFastLeaveFlag  {
            type  cml_data_types:CML_BOOL_T;
            description "";
        } // END of setFastLeaveFlag definition.

        leaf disableIfSuppressFlag  {
            type  cml_data_types:CML_BOOL_T;
            default true;
            description "";
        } // END of disableIfSuppressFlag definition.

        leaf mrouterIfName  {
            type  cml_data_types:CML_STRING_T;
            description "";
        } // END of mrouterIfName definition.

        leaf ifQuerierFlag  {
            type  cml_data_types:CML_BOOL_T;
            description "";
        } // END of ifQuerierFlag definition.


        list igmpSnoopStaticGroup {
            key "groupAddr";
            description
                "igmpSnoopStaticGroup";
            leaf groupAddr  {
                type  cml_data_types:CML_IPV4_ADDR_T;
                description "";
            } // END of groupAddr definition.


            list igmpSnoopSourceAddress {
                key "sourceAddr";
                description
                    "igmpSnoopSourceAddress";
                leaf sourceAddr  {
                    type  cml_data_types:CML_IPV4_ADDR_T;
                    description "";
                } // END of sourceAddr definition.


                list igmpSnoopInterface {
                    key "vifName";
                    description
                        "igmpSnoopInterface";
                    leaf vifName  {
                        type  cml_data_types:CML_STRING_T;
                        description "";
                    } // END of vifName definition.

                } // End of igmpSnoopInterface-list
            } // End of igmpSnoopSourceAddress-list

            list igmpGroupInterface {
                key "staticVifName";
                description
                    "igmpGroupInterface";
                leaf staticVifName  {
                    type  cml_data_types:CML_STRING_T;
                    description "";
                } // END of staticVifName definition.

            } // End of igmpGroupInterface-list
        } // End of igmpSnoopStaticGroup-list
    } // END of igmpSnoopInterface-container definition.
    } // END of igmpSnoopInterface-container definition.


}
