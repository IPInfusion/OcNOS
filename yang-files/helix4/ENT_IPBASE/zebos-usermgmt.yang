/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-usermgmt.yang
*
*/

submodule zebos-usermgmt {

    belongs-to  zebos { prefix zebos; }

    import cml_data_types {
        prefix cml_data_types;
    }

    organization
        "IP Infusion Inc.";

    contact
        "Address: 3965 Freedom Circle, Suite 200, Santa Clara, CA 95054
        Phone: +1 408-400-1900
        E-mail: support@ipinfusion.com
        Web: http://www.ipinfusion.com/";

    description
        "Layer-3 usermgmt configurations";


    revision "2017-05-11" {
        description "Updated notif for cleartext password.";
    }

    revision "2017-01-19" {
        description "User not created properly-[jira-12851].";
    }

    revision "2016-12-27" {
        description "Added snmp oid and documentation tag.";
    }

    revision "2016-10-28" {
        description "Initial version of USERMGMT datamodel.";
    }



    grouping usermgmt-grouping {
        list usermgmt {
            key "username";
            description
                "usermgmt";
            leaf username  {
                type  cml_data_types:CML_STRING_T {
                    length "0..255";
                }
                description "";
            } // END of username definition.

            leaf encryptPassword  {
                type  cml_data_types:CML_STRING_T {
                    length "26..106";
                }
                description "";
            } // END of encryptPassword definition.

            leaf password  {
                type  cml_data_types:CML_STRING_T {
                    length "5..32";
                }
                description "";
            } // END of password definition.

            leaf role  {
                type  cml_data_types:USER_MGMT_ROLE_OPTIONS_T;
                default "network-user";
                description "";
            } // END of role definition.

        } // End of usermgmt-list
    } // END of usermgmt-grouping definition.

    grouping  userDebug-grouping {
    container userDebug {
        description
            "userDebug";
        leaf debugconfuser  {
            type  cml_data_types:CML_BOOL_T;
            description "";
        } // END of debugconfuser definition.

        leaf debuguser  {
            type  cml_data_types:CML_BOOL_T;
            description "";
        } // END of debuguser definition.

    } // END of userDebug-container definition.
    } // END of userDebug-container definition.


}
