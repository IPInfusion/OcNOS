/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-switchportinterface.yang
*
*/

submodule zebos-switchportinterface {

    belongs-to  zebos { prefix zebos; }

    import cml_data_types {
        prefix cml_data_types;
    }

    import feature_list {
        prefix feature_list;
    }

    organization
        "IP Infusion Inc.";

    contact
        "Address: 3965 Freedom Circle, Suite 200, Santa Clara, CA 95054
        Phone: +1 408-400-1900
        E-mail: support@ipinfusion.com
        Web: http://www.ipinfusion.com/";

    description
        "switchport configuration";


    revision "2017-09-18" {
        description "added delete wrapper for allowed vlan none.";
    }

    revision "2017-08-22" {
        description "added missing commands.";
    }

    revision "2017-06-27" {
        description "added trigger for allowed all and except.";
    }

    revision "2017-06-23" {
        description "l2protocol container is changed to objectlist.";
    }

    revision "2017-06-07" {
        description "modified the vlan registration issue.";
    }

    revision "2017-06-06" {
        description "opeation type changed for switchport mode command.";
    }

    revision "2017-05-29" {
        description "native vlan changes.";
    }

    revision "2017-05-02" {
        description "corrected the staticMac parent hierarchy.";
    }

    revision "2017-04-18" {
        description "corrected the datamodel as per backend structure.";
    }

    revision "2017-03-14" {
        description "Removed Manual cli for switchport mode.";
    }

    revision "2017-03-03" {
        description "vlaninterface datamodel has been changed to switchportinterface.";
    }

    revision "2017-02-25" {
        description "added support for show cml running-config.";
    }

    revision "2017-02-14" {
        description "adding missing flag for cli generation.";
    }

    revision "2017-02-10" {
        description "modified customer-edge commands.";
    }

    revision "2017-01-27" {
        description "added support for l2protocol commands.";
    }



    grouping staticMac-grouping {
        list staticMac {
            key "macAddr";
            description
                "staticMac";
            leaf ifName  {
                type  cml_data_types:CML_STRING_T {
                    length "0..255";
                }
                description "";
            } // END of ifName definition.

            leaf vlanIdMac  {
                type  cml_data_types:CML_UINT16_T {
                     range "2..4094";
                }
                description "";
            } // END of vlanIdMac definition.

            leaf svlanId  {
                type  cml_data_types:CML_UINT16_T {
                     range "2..4094";
                }
                description "";
            } // END of svlanId definition.

            leaf macAddr  {
                type  cml_data_types:CML_STRING_T {
                    length "0..255";
                }
                description "";
            } // END of macAddr definition.

            leaf discardForward  {
                type  cml_data_types:CML_DISCARDFORWARD_T;
                description "";
            } // END of discardForward definition.

            leaf priorityOverWrite  {
                type  cml_data_types:CML_UINT8_T {
                     range "0..7";
                }
                description "";
            } // END of priorityOverWrite definition.

            leaf overMacType  {
                type  cml_data_types:CML_OVERMACTYPE_T;
                description "";
            } // END of overMacType definition.

        } // End of staticMac-list
    } // END of staticMac-grouping definition.

    grouping  switchportInterface-grouping {
    container switchportInterface {
        description
            "switchportInterface";
        leaf cvlanRegWord  {
            type  cml_data_types:CML_STRING_T {
                length "0..255";
            }
            description "cvlan registration table";
        } // END of cvlanRegWord definition.

        leaf vlanStackEnable  {
            if-feature feature_list:HAVE_PROVIDER_BRIDGE;
            type  cml_data_types:CML_VLANSTACK_T;
            description "vlan stack for port";
        } // END of vlanStackEnable definition.

        leaf etherType  {
            type  cml_data_types:CML_STRING_T {
                length "0..255";
            }
            default "0x8100";
            description "";
        } // END of etherType definition.

        leaf uniName  {
            if-feature feature_list:HAVE_PROVIDER_BRIDGE;
            type  cml_data_types:CML_STRING_T {
                length "0..255";
            }
            description "ethernet uni name";
        } // END of uniName definition.

        leaf enniName  {
            if-feature feature_list:HAVE_PROVIDER_BRIDGE;
            type  cml_data_types:CML_STRING_T {
                length "0..255";
            }
            description "ethernet enni name";
        } // END of enniName definition.

        leaf uniEnniType  {
            if-feature feature_list:HAVE_PROVIDER_BRIDGE;
            type  cml_data_types:CML_UNI_ENNI_TYPE_T;
            description "ethernet type of UNI or ENNI";
        } // END of uniEnniType definition.

        leaf ethSvid  {
            if-feature feature_list:HAVE_VLAN;
            type  cml_data_types:CML_INT32_T;
            description "";
        } // END of ethSvid definition.

        leaf evcId  {
            if-feature feature_list:HAVE_PROVIDER_BRIDGE;
            type  cml_data_types:CML_STRING_T {
                length "0..255";
            }
            description "";
        } // END of evcId definition.

        leaf uniService  {
            if-feature feature_list:HAVE_PROVIDER_BRIDGE;
            type  cml_data_types:CML_UNI_SERVICE_T;
            description "ethernet uni Service";
        } // END of uniService definition.

        leaf maxEvc  {
            if-feature feature_list:HAVE_PROVIDER_BRIDGE;
            type  cml_data_types:CML_INT32_T {
                 range "1..4094";
            }
            description "ethernet uni maximum number of EVC ";
        } // END of maxEvc definition.

        leaf uniMode  {
            type  cml_data_types:CML_UNI_ENABLE_DISABLE_T;
            description "";
        } // END of uniMode definition.

        leaf bridgeId  {
            if-feature feature_list:HAVE_PROVIDER_BRIDGE;
            type  cml_data_types:CML_STRING_T {
                length "0..255";
            }
            description "";
        } // END of bridgeId definition.


        list nsmVlanPort {
            key "portMode";
            description
                "nsm vlan port";
            leaf portMode  {
                type  cml_data_types:CML_SWITCH_PORT_MODE_T;
                description "switchport mode";
            } // END of portMode definition.

            leaf vlanId  {
                type  cml_data_types:CML_UINT16_T {
                     range "2..4094";
                }
                description "vlan Id";
            } // END of vlanId definition.

            leaf nativeVlanId  {
                type  cml_data_types:CML_UINT16_T {
                     range "2..4094";
                }
                description "Native Vlan Id";
            } // END of nativeVlanId definition.

            leaf defaultsvlanId  {
                if-feature feature_list:HAVE_PROVIDER_BRIDGE;
                type  cml_data_types:CML_UINT16_T;
                description "default SVID";
            } // END of defaultsvlanId definition.

            leaf cvlanId  {
                if-feature feature_list:HAVE_PROVIDER_BRIDGE;
                type  cml_data_types:CML_UINT16_T;
                description "";
            } // END of cvlanId definition.

            leaf vlanPortIngressFilter  {
                type  cml_data_types:CML_ENABLE_DISABLE_T;
                default "enable";
                description "";
            } // END of vlanPortIngressFilter definition.

            leaf custTransVlanId  {
                if-feature feature_list:HAVE_PROVIDER_BRIDGE;
                type  cml_data_types:CML_UINT16_T;
                description "";
            } // END of custTransVlanId definition.

            leaf custVlanId  {
                if-feature feature_list:HAVE_PROVIDER_BRIDGE;
                type  cml_data_types:CML_UINT16_T;
                description "";
            } // END of custVlanId definition.

            leaf frameType  {
                type  cml_data_types:CML_VLAN_FRAME_TYPE_T;
                description "";
            } // END of frameType definition.


            list svlanTranslation {
                key "transVid";
                description
                    "svlanTranslation";
                leaf transVid  {
                    type  cml_data_types:CML_UINT16_T;
                    description "translation Vlan Id";
                } // END of transVid definition.

                leaf svId  {
                    type  cml_data_types:CML_UINT16_T;
                    description "default sVlan Id";
                } // END of svId definition.

            } // End of svlanTranslation-list

            list allowedVlan {
                key "vlanRange";
                description
                    "allowedVlan";
                leaf vlanRange  {
                    type  cml_data_types:CML_STRING_T;
                    description "VLAN range";
                } // END of vlanRange definition.

                leaf egressTagged  {
                    type  cml_data_types:CML_EGERSS_TAGGED_TYPE_T;
                    description "Egress tagging per vlan";
                } // END of egressTagged definition.

                leaf swVlanOper  {
                    type  cml_data_types:CML_SWVLANOPER_T;
                    description "";
                } // END of swVlanOper definition.

            } // End of allowedVlan-list
        } // End of nsmVlanPort-list

        list vlanUserTable {
            key "userPriority";
            description
                "vlanUserTable";
            leaf userPriority  {
                type  cml_data_types:CML_UINT8_T {
                     range "0..7";
                }
                description "";
            } // END of userPriority definition.

            leaf regenPriority  {
                type  cml_data_types:CML_UINT8_T {
                     range "0..7";
                }
                mandatory true;
                description "";
            } // END of regenPriority definition.

        } // End of vlanUserTable-list

        list vlanTraffic {
            key "userPriority";
            description
                "vlanTraffic";
            leaf userPriority  {
                type  cml_data_types:CML_UINT8_T {
                     range "0..7";
                }
                description "";
            } // END of userPriority definition.

            leaf trafficClass  {
                type  cml_data_types:CML_UINT8_T {
                     range "1..8";
                }
                description "";
            } // END of trafficClass definition.

            leaf trafficClassValue  {
                type  cml_data_types:CML_UINT8_T {
                     range "0..7";
                }
                mandatory true;
                description "";
            } // END of trafficClassValue definition.

        } // End of vlanTraffic-list

        list l2protocol {
            if-feature feature_list:HAVE_PROVIDER_BRIDGE;
            key "l2protocolType";
            description
                "l2protocol";
            leaf l2protocolType  {
                type  cml_data_types:CML_L2_PROTOCOL_T;
                description "";
            } // END of l2protocolType definition.

            leaf process  {
                type  cml_data_types:CML_BOOL_T;
                mandatory true;
                description "";
            } // END of process definition.

            leaf tunnelVlan  {
                type  cml_data_types:CML_INT32_T;
                description "";
            } // END of tunnelVlan definition.

        } // End of l2protocol-list
        container pVlanConfig {
            presence "yes";
            description
                "pVlanConfig";
            leaf pvlanMode  {
                type  cml_data_types:CML_PVLAN_MODE_T;
                mandatory true;
                description "Private VLAN port mode";
            } // END of pvlanMode definition.

            leaf pvlanConfigured  {
                type  cml_data_types:CML_BOOL_T;
                config false;
                description "";
            } // END of pvlanConfigured definition.


            list pvlanInstance {
                key "pvlanId";
                description
                    "mapped private-vlan instance with nsm pvlan struct";
                leaf pvlanId  {
                    type  cml_data_types:CML_UINT16_T {
                         range "2..4094";
                    }
                    description "Private VLAN id";
                } // END of pvlanId definition.

                leaf pvlanAssociate  {
                    type  cml_data_types:CML_UINT32_T;
                    description "Private VLAN Associate";
                } // END of pvlanAssociate definition.

                leaf pvlanMapVid  {
                    type  cml_data_types:CML_STRING_T;
                    description "private-vlan Mapping";
                } // END of pvlanMapVid definition.

            } // End of pvlanInstance-list
        } // END of pVlanConfig-container definition.
        container oepMapTable {
            if-feature feature_list:HAVE_PROVIDER_BRIDGE;
            description
                "oepMapTable";
            leaf oepMapType  {
                type  cml_data_types:CML_OEP_MAP_TYPE_T;
                description "oep map type";
            } // END of oepMapType definition.

            leaf oepMapName  {
                type  cml_data_types:CML_STRING_T {
                    length "0..255";
                }
                description "oep mapping table name";
            } // END of oepMapName definition.

        } // END of oepMapTable-container definition.
    } // END of switchportInterface-container definition.
    } // END of switchportInterface-container definition.


}
