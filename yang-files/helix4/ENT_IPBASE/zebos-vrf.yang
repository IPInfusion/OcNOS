/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-vrf.yang
*
*/

submodule zebos-vrf {

    belongs-to  zebos { prefix zebos; }

    import cml_data_types {
        prefix cml_data_types;
    }

    import feature_list {
        prefix feature_list;
    }

    include zebos-bgp;
    organization
        "IP Infusion Inc.";

    contact
        "Address: 3965 Freedom Circle, Suite 200, Santa Clara, CA 95054
        Phone: +1 408-400-1900
        E-mail: support@ipinfusion.com
        Web: http://www.ipinfusion.com/";

    description
        "VPN Routing/Forwarding";


    revision "2018-06-21" {
        description " Initial Version.";
        reference "";
    }



    grouping vrf-grouping {
    description
        "vrf";
        list vrf {
            key "vrfName";
            description
                "vrf";
            leaf vrfName  {
                type  cml_data_types:CML_STRING_T {
                    length "1..32";
                }
                description "";
            } // END of vrfName definition.

            leaf macVrf  {
                if-feature feature_list:HAVE_BGP_EVPN;
                type  cml_data_types:CML_BOOL_T;
                description "";
            } // END of macVrf definition.

            leaf vrfId  {
                type  cml_data_types:CML_UINT32_T;
                config false;
                description "";
            } // END of vrfId definition.

            leaf fibId  {
                type  cml_data_types:CML_UINT8_T;
                config false;
                description "";
            } // END of fibId definition.

            leaf description  {
                type  cml_data_types:CML_LINE_T {
                    length "0..255";
                }
                description "";
            } // END of description definition.

            leaf routerId  {
                type  cml_data_types:CML_IPV4_ADDR_T;
                description "vrf router id";
            } // END of routerId definition.

            leaf l3vniId  {
                if-feature feature_list:HAVE_BGP_EVPN;
                if-feature feature_list:HAVE_NVO;
                type  cml_data_types:CML_UINT32_T {
                     range "1..16777215";
                }
                description "L3 VXLAN Identifier";
            } // END of l3vniId definition.

            uses vrfTable-grouping;
        } // End of vrf-list
    } // END of vrf-grouping definition.


}
