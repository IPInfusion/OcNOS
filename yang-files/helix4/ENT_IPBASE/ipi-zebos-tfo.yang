/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-zebos-tfo.yang
*
*/

submodule ipi-zebos-tfo {

    belongs-to  ipi-zebos { prefix ipi-zebos; }

    import cml-data-types {
        prefix cml-data-types;
    }

    include ipi-zebos-interface;
    organization
        "IP Infusion Inc.";

    contact
        "Address: 3965 Freedom Circle, Suite 200, Santa Clara, CA 95054
        Phone: +1 408-400-1900
        E-mail: support@ipinfusion.com
        Web: http://www.ipinfusion.com/";

    description
        "tfo_configuration";


    revision "2018-06-21" {
        description " Initial Version.";
        reference "";
    }


    grouping  tfo-grouping {
    description
        "tfo";
    container tfo {
        description
            "tfo";
        leaf tfostate  {
            type  cml-data-types:CML_ENABLE_DISABLE_T;
            default "disable";
            description "";
        } // END of tfostate definition.


        list fog_id {
            key "fogid";
            description
                "structure list will be list of struct fog_info";
            leaf fogid  {
                type  cml-data-types:CML_UINT32_T {
                     range "1..64";
                }
                description "";
            } // END of fogid definition.

            leaf fogen  {
                type  cml-data-types:CML_ENABLE_DISABLE_T;
                mandatory true;
                description "";
            } // END of fogen definition.

            leaf tfc  {
                type  cml-data-types:CML_UINT32_T {
                     range "0..63";
                }
                description "";
            } // END of tfc definition.

            leaf mpg_link_failure_cnt  {
                type  cml-data-types:CML_INT64_T;
                config false;
                description "MPG Failure detection count";
            } // END of mpg_link_failure_cnt definition.

            leaf mpg_link_recover_cnt  {
                type  cml-data-types:CML_INT64_T;
                config false;
                description "MPG link recover count";
            } // END of mpg_link_recover_cnt definition.

            leaf cpg_auto_disable_cnt  {
                type  cml-data-types:CML_INT64_T;
                config false;
                description "CPG Auto Disable Count";
            } // END of cpg_auto_disable_cnt definition.

            leaf cpg_auto_enable_cnt  {
                type  cml-data-types:CML_INT64_T;
                config false;
                description "CPG auto enable count";
            } // END of cpg_auto_enable_cnt definition.

            leaf cpg_disable_status  {
                type  cml-data-types:CML_INT64_T;
                config false;
                description "To track CPG status";
            } // END of cpg_disable_status definition.

            leaf mpg_disable_status  {
                type  cml-data-types:CML_INT64_T;
                config false;
                description "To track MPG status";
            } // END of mpg_disable_status definition.

        } // End of fog_id-list

        list tfo_interface {
            key "ifName";
            description
                "structure list will be list of strict interface. which will point MPG links and CPG links";
            leaf ifName  {
                type  cml-data-types:CML_STRING_T;
                description "";
            } // END of ifName definition.

            leaf fog  {
                type  cml-data-types:CML_UINT32_T {
                     range "1..64";
                }
                description "";
            } // END of fog definition.

            leaf fog_type  {
                type  cml-data-types:CML_FOG_IFCTYPE_T;
                description "";
            } // END of fog_type definition.

            leaf link_type  {
                type  cml-data-types:CML_FOG_LINK_TYPE_T;
                description "";
            } // END of link_type definition.

        } // End of tfo_interface-list
    } // END of tfo-container definition.
    } // END of tfo-container definition.


}
