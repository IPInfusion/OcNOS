/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-zebos-snmp.yang
*
*/

submodule ipi-zebos-snmp {

    belongs-to  ipi-zebos { prefix ipi-zebos; }

    import cml-data-types {
        prefix cml-data-types;
    }

    import feature-list {
        prefix feature-list;
    }

    include ipi-zebos-vrf;
    include ipi-zebos-acl;
    organization
        "IP Infusion Inc.";

    contact
        "Address: 3965 Freedom Circle, Suite 200, Santa Clara, CA 95054
        Phone: +1 408-400-1900
        E-mail: support@ipinfusion.com
        Web: http://www.ipinfusion.com/";

    description
        "Simple Network Management Protocol";


    revision "2018-06-21" {
        description " Initial Version.";
        reference "";
    }



    grouping snmp-grouping {
    description
        "snmp  related operations";
        list snmp {
            key "vrfName";
            description
                "snmp  related operations";
            leaf vrfName  {
                type  cml-data-types:CML_STRING_T;
                description "";
            } // END of vrfName definition.

            leaf tcpsession  {
                if-feature feature-list:HAVE_SNMP_AGENT;
                type  cml-data-types:CML_BOOL_T;
                description "";
            } // END of tcpsession definition.


            list snmpCommunity {
                if-feature feature-list:HAVE_SNMP_AGENT;
                key "community";
                description
                    "List of SNMP communities configured";
                leaf community  {
                    type  cml-data-types:CML_STRING_T {
                        length "1..32";
                    }
                    description "";
                } // END of community definition.

                leaf communityView  {
                    type  cml-data-types:CML_STRING_T;
                    description "";
                } // END of communityView definition.

                leaf communityViewVersion  {
                    type  cml-data-types:CML_SNMP_VIEW_VERSION_T;
                    description "";
                } // END of communityViewVersion definition.

                leaf communityViewVersionAccess  {
                    type  cml-data-types:CML_SNMP_ACCESS_T;
                    description "";
                } // END of communityViewVersionAccess definition.

                leaf communityGroup  {
                    type  cml-data-types:CML_SNMP_GROUP_T;
                    description "";
                } // END of communityGroup definition.

                leaf communityAccess  {
                    type  cml-data-types:CML_SNMP_ACCESS_T;
                    description "";
                } // END of communityAccess definition.

                leaf aclNameIpv4Standard  {
                    type  cml-data-types:CML_STRING_T;
                    description "";
                } // END of aclNameIpv4Standard definition.

            } // End of snmpCommunity-list

            list snmpuser {
                if-feature feature-list:HAVE_SNMP_AGENT;
                if-feature feature-list:HAVE_SNMP_V3;
                key "user";
                description
                    "List of SNMP users configured";
                leaf user  {
                    type  cml-data-types:CML_STRING_T {
                        length "5..32";
                    }
                    description "";
                } // END of user definition.

                leaf usertype  {
                    type  cml-data-types:CML_SNMP_USER_T;
                    description "";
                } // END of usertype definition.

                leaf keyEncrypt  {
                    type  cml-data-types:CML_HOSTP_SNMP_KEY_TYPE_T;
                    description "";
                } // END of keyEncrypt definition.

                leaf authtype  {
                    type  cml-data-types:CML_SNMP_AUTH_T;
                    description "";
                } // END of authtype definition.

                leaf authpassword  {
                    type  cml-data-types:CML_STRING_T;
                    description "";
                } // END of authpassword definition.

                leaf privtype  {
                    type  cml-data-types:CML_SNMP_PRIV_T;
                    description "";
                } // END of privtype definition.

                leaf privpassword  {
                    type  cml-data-types:CML_STRING_T;
                    description "";
                } // END of privpassword definition.

            } // End of snmpuser-list

            list snmphost {
                if-feature feature-list:HAVE_SNMP_AGENT;
                key "host";
                description
                    "remote_trap_host_configurations";
                leaf host  {
                    type  cml-data-types:CML_STRING_T {
                        length "1..63";
                    }
                    description "";
                } // END of host definition.

                leaf hostinforms  {
                    type  cml-data-types:CML_SNMP_INFORMS_T;
                    description "";
                } // END of hostinforms definition.

                leaf hosttraps  {
                    type  cml-data-types:CML_SNMP_TRAP_T;
                    description "";
                } // END of hosttraps definition.

                leaf version  {
                    type  cml-data-types:CML_SNMP_VERSION_T;
                    description "";
                } // END of version definition.

                leaf informsversion  {
                    type  cml-data-types:CML_SNMP_INFORMS_VERSION_T;
                    description "";
                } // END of informsversion definition.

                leaf versionstr  {
                    type  cml-data-types:CML_STRING_T;
                    description "";
                } // END of versionstr definition.

                leaf version3  {
                    type  cml-data-types:CML_VERSION3_T;
                    description "";
                } // END of version3 definition.

                leaf version3str  {
                    type  cml-data-types:CML_STRING_T;
                    description "";
                } // END of version3str definition.

                leaf hostuser  {
                    type  cml-data-types:CML_STRING_T;
                    description "";
                } // END of hostuser definition.

                leaf udp  {
                    type  cml-data-types:CML_INT32_T {
                         range "1..65535";
                    }
                    default "162";
                    description "";
                } // END of udp definition.

            } // End of snmphost-list

            list snmpview {
                if-feature feature-list:HAVE_SNMP_AGENT;
                key "view";
                description
                    "List of SNMP Views configured";
                leaf view  {
                    type  cml-data-types:CML_STRING_T {
                        length "1..32";
                    }
                    description "";
                } // END of view definition.

                leaf snmpoid  {
                    type  cml-data-types:CML_STRING_T;
                    description "";
                } // END of snmpoid definition.

                leaf oidtree  {
                    type  cml-data-types:CML_SNMP_OID_TREE_T;
                    description "";
                } // END of oidtree definition.

            } // End of snmpview-list
        } // End of snmp-list
    } // END of snmp-grouping definition.

    grouping  snmpStatistics-grouping {
    description
        "snmpStatistics";
    container snmpStatistics {
        config false;
        description
            "snmpStatistics";
        leaf pktIn  {
            type  cml-data-types:CML_UINT32_T;
            description "SNMP packets input";
        } // END of pktIn definition.

        leaf pktInBadVer  {
            type  cml-data-types:CML_UINT32_T;
            description "Bad SNMP versions";
        } // END of pktInBadVer definition.

        leaf pktInUnknownCommunity  {
            type  cml-data-types:CML_UINT32_T;
            description "Unknown community name";
        } // END of pktInUnknownCommunity definition.

        leaf pktInIllOperation  {
            type  cml-data-types:CML_UINT32_T;
            description "Illegal operation for community name supplied";
        } // END of pktInIllOperation definition.

        leaf pktInEncodingError  {
            type  cml-data-types:CML_UINT32_T;
            description "Encoding errors";
        } // END of pktInEncodingError definition.

        leaf pktInRequestedVariables  {
            type  cml-data-types:CML_UINT32_T;
            description "Number of requested variables";
        } // END of pktInRequestedVariables definition.

        leaf pktInNumOfSetRequest  {
            type  cml-data-types:CML_UINT32_T;
            description "Number of altered variables";
        } // END of pktInNumOfSetRequest definition.

        leaf pktInNumOfGetPdu  {
            type  cml-data-types:CML_UINT32_T;
            description "Get-request PDUs";
        } // END of pktInNumOfGetPdu definition.

        leaf pktInNumOfGetNextPdu  {
            type  cml-data-types:CML_UINT32_T;
            description "Get-next PDUs";
        } // END of pktInNumOfGetNextPdu definition.

        leaf pktInNumOfSetPdu  {
            type  cml-data-types:CML_UINT32_T;
            description "Set-request PDUs";
        } // END of pktInNumOfSetPdu definition.

        leaf pktOut  {
            type  cml-data-types:CML_UINT32_T;
            description "SNMP packets output";
        } // END of pktOut definition.

        leaf pktOutTooBigError  {
            type  cml-data-types:CML_UINT32_T;
            description "Too big errors";
        } // END of pktOutTooBigError definition.

        leaf pktOutNoSuchNameError  {
            type  cml-data-types:CML_UINT32_T;
            description "No such name errors";
        } // END of pktOutNoSuchNameError definition.

        leaf pktOutBadValueError  {
            type  cml-data-types:CML_UINT32_T;
            description "Bad values errors";
        } // END of pktOutBadValueError definition.

        leaf pktOutGenError  {
            type  cml-data-types:CML_UINT32_T;
            description "General errors";
        } // END of pktOutGenError definition.

        leaf pktOutRespPdu  {
            type  cml-data-types:CML_UINT32_T;
            description "Response PDUs";
        } // END of pktOutRespPdu definition.

        leaf pktOutTrapPdu  {
            type  cml-data-types:CML_UINT32_T;
            description "Trap PDUs";
        } // END of pktOutTrapPdu definition.

        leaf engineID  {
            type  cml-data-types:CML_LINE_T;
            description "snmp engineId";
        } // END of engineID definition.

    } // END of snmpStatistics-container definition.
    } // END of snmpStatistics-container definition.

    grouping  debugSnmp-grouping {
    description
        "debugSnmp";
    container debugSnmp {
        description
            "debugSnmp";
        leaf debugSnmp  {
            type  cml-data-types:CML_BOOL_T;
            description "";
        } // END of debugSnmp definition.

    } // END of debugSnmp-container definition.
    } // END of debugSnmp-container definition.


}
