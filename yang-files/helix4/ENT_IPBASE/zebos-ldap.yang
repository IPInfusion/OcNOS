/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-ldap.yang
*
*/

submodule zebos-ldap {

    belongs-to  zebos { prefix zebos; }

    import cml_data_types {
        prefix cml_data_types;
    }

    organization
        "IP Infusion Inc.";

    contact
        "Address: 3965 Freedom Circle, Suite 200, Santa Clara, CA 95054
        Phone: +1 408-400-1900
        E-mail: support@ipinfusion.com
        Web: http://www.ipinfusion.com/";

    description
        "Layer-3 ldap configurations";


    revision "2017-12-18" {
        description "Revised on 2017-12-18.";    }

    revision "2017-12-17" {
        description "Revised on 2017-12-17.";    }

    revision "2017-12-15" {
        description "Revised on 2017-12-15.";    }

    revision "2017-12-13" {
        description "Revised on 2017-12-13.";    }

    revision "2017-12-11" {
        description "Revised on 2017-12-11.";    }

    revision "2017-12-07" {
        description "Revised on 2017-12-07.";    }

    revision "2017-12-06" {
        description "Revised on 2017-12-06.";    }

    revision "2017-12-04" {
        description "Revised on 2017-12-04.";    }

    revision "2017-11-27" {
        description "Revised on 2017-11-27.";    }

    revision "2017-11-22" {
        description "Revised on 2017-11-22.";    }

    revision "2017-11-20" {
        description "Revised on 2017-11-20.";    }

    revision "2017-11-10" {
        description "Revised on 2017-11-10.";    }

    revision "2017-11-09" {
        description "Revised on 2017-11-09.";    }

    revision "2017-11-07" {
        description "Revised on 2017-11-07.";    }

    revision "2017-11-02" {
        description "Revised on 2017-11-02.";    }

    revision "2017-10-30" {
        description "Revised on 2017-10-30.";    }

    revision "2017-10-26" {
        description "Revised on 2017-10-26.";    }

    revision "2017-10-23" {
        description "Revised on 2017-10-23.";    }

    revision "2017-10-18" {
        description "Revised on 2017-10-18.";    }

    revision "2017-10-10" {
        description "Revised on 2017-10-10.";    }

    revision "2017-10-09" {
        description "Revised on 2017-10-09.";    }

    revision "2017-10-05" {
        description "Revised on 2017-10-05.";    }

    revision "2017-10-04" {
        description "Revised on 2017-10-04.";    }

    revision "2017-10-03" {
        description "Revised on 2017-10-03.";    }

    revision "2017-09-27" {
        description "Revised on 2017-09-27.";    }

    revision "2017-09-25" {
        description "Revised on 2017-09-25.";    }

    revision "2017-09-21" {
        description "Revised on 2017-09-21.";    }

    revision "2017-09-19" {
        description "Revised on 2017-09-19.";    }

    revision "2017-09-18" {
        description "Revised on 2017-09-18.";    }

    revision "2017-09-15" {
        description "Revised on 2017-09-15.";    }

    revision "2017-09-14" {
        description "Revised on 2017-09-14.";    }

    revision "2017-09-13" {
        description "Revised on 2017-09-13.";    }

    revision "2017-09-07" {
        description "Revised on 2017-09-07.";    }

    revision "2017-09-05" {
        description "Revised on 2017-09-05.";    }

    revision "2017-09-03" {
        description "Revised on 2017-09-03.";    }

    revision "2017-08-29" {
        description "Revised on 2017-08-29.";    }

    revision "2017-08-28" {
        description "Revised on 2017-08-28.";    }

    revision "2017-08-23" {
        description "Revised on 2017-08-23.";    }

    revision "2017-08-22" {
        description "Revised on 2017-08-22.";    }

    revision "2017-08-11" {
        description "Revised on 2017-08-11.";    }

    revision "2017-08-10" {
        description "Revised on 2017-08-10.";    }

    revision "2017-08-01" {
        description "Revised on 2017-08-01.";    }

    revision "2017-07-27" {
        description "Revised on 2017-07-27.";    }

    revision "2017-07-26" {
        description "Revised on 2017-07-26.";    }

    revision "2017-07-18" {
        description "Revised on 2017-07-18.";    }

    revision "2017-07-11" {
        description "Revised on 2017-07-11.";    }

    revision "2017-07-10" {
        description "Revised on 2017-07-10.";    }

    revision "2017-07-05" {
        description "Revised on 2017-07-05.";    }

    revision "2017-07-03" {
        description "Revised on 2017-07-03.";    }

    revision "2017-06-30" {
        description "Revised on 2017-06-30.";    }

    revision "2017-06-23" {
        description "Revised on 2017-06-23.";    }

    revision "2017-06-20" {
        description "Revised on 2017-06-20.";    }

    revision "2017-06-14" {
        description "Revised on 2017-06-14.";    }

    revision "2017-06-13" {
        description "Revised on 2017-06-13.";    }

    revision "2017-06-12" {
        description "Revised on 2017-06-12.";    }

    revision "2017-06-10" {
        description "Revised on 2017-06-10.";    }

    revision "2017-06-08" {
        description "Revised on 2017-06-08.";    }

    revision "2017-06-07" {
        description "Revised on 2017-06-07.";    }

    revision "2017-06-06" {
        description "Revised on 2017-06-06.";    }

    revision "2017-06-02" {
        description "Revised on 2017-06-02.";    }

    revision "2017-06-01" {
        description "Revised on 2017-06-01.";    }

    revision "2017-05-29" {
        description "Revised on 2017-05-29.";    }

    revision "2017-05-24" {
        description "Revised on 2017-05-24.";    }

    revision "2017-05-23" {
        description "Revised on 2017-05-23.";    }

    revision "2017-05-16" {
        description "Revised on 2017-05-16.";    }

    revision "2017-05-11" {
        description "Revised on 2017-05-11.";    }

    revision "2017-04-27" {
        description "Revised on 2017-04-27.";    }

    revision "2017-04-18" {
        description "Revised on 2017-04-18.";    }

    revision "2017-04-11" {
        description "Revised on 2017-04-11.";    }

    revision "2017-04-07" {
        description "Revised on 2017-04-07.";    }

    revision "2017-04-06" {
        description "Revised on 2017-04-06.";    }

    revision "2017-03-28" {
        description "Revised on 2017-03-28.";    }

    revision "2017-03-25" {
        description "Revised on 2017-03-25.";    }

    revision "2017-03-24" {
        description "Revised on 2017-03-24.";    }

    revision "2017-03-21" {
        description "Revised on 2017-03-21.";    }

    revision "2017-03-15" {
        description "Revised on 2017-03-15.";    }

    revision "2017-03-09" {
        description "Revised on 2017-03-09.";    }

    revision "2017-03-05" {
        description "Revised on 2017-03-05.";    }

    revision "2017-03-03" {
        description "Revised on 2017-03-03.";    }

    revision "2017-02-27" {
        description "Revised on 2017-02-27.";    }

    revision "2017-02-25" {
        description "Revised on 2017-02-25.";    }

    revision "2017-02-24" {
        description "Revised on 2017-02-24.";    }

    revision "2017-02-23" {
        description "Revised on 2017-02-23.";    }

    revision "2017-02-22" {
        description "Revised on 2017-02-22.";    }

    revision "2017-02-21" {
        description "Revised on 2017-02-21.";    }

    revision "2017-02-20" {
        description "Revised on 2017-02-20.";    }

    revision "2017-02-14" {
        description "Revised on 2017-02-14.";    }

    revision "2017-02-13" {
        description "Revised on 2017-02-13.";    }

    revision "2017-02-11" {
        description "Revised on 2017-02-11.";    }

    revision "2017-02-10" {
        description "Revised on 2017-02-10.";    }

    revision "2017-02-08" {
        description "Revised on 2017-02-08.";    }

    revision "2017-02-07" {
        description "Revised on 2017-02-07.";    }

    revision "2017-02-03" {
        description "Revised on 2017-02-03.";    }

    revision "2017-02-02" {
        description "Revised on 2017-02-02.";    }

    revision "2017-01-31" {
        description "Revised on 2017-01-31.";    }

    revision "2017-01-30" {
        description "Revised on 2017-01-30.";    }

    revision "2017-01-28" {
        description "Revised on 2017-01-28.";    }

    revision "2017-01-27" {
        description "Revised on 2017-01-27.";    }

    revision "2017-01-25" {
        description "Revised on 2017-01-25.";    }

    revision "2017-01-23" {
        description "Revised on 2017-01-23.";    }

    revision "2017-01-20" {
        description "Revised on 2017-01-20.";    }

    revision "2017-01-19" {
        description "Revised on 2017-01-19.";    }

    revision "2017-01-16" {
        description "Revised on 2017-01-16.";    }

    revision "2017-01-12" {
        description "Revised on 2017-01-12.";    }

    revision "2017-01-11" {
        description "Revised on 2017-01-11.";    }

    revision "2017-01-10" {
        description "Revised on 2017-01-10.";    }

    revision "2017-01-04" {
        description "Revised on 2017-01-04.";    }

    revision "2016-12-30" {
        description "Revised on 2016-12-30.";    }

    revision "2016-12-29" {
        description "Revised on 2016-12-29.";    }

    revision "2016-12-28" {
        description "Revised on 2016-12-28.";    }

    revision "2016-12-26" {
        description "Revised on 2016-12-26.";    }

    revision "2016-12-22" {
        description "Revised on 2016-12-22.";    }

    revision "2016-12-17" {
        description "Revised on 2016-12-17.";    }

    revision "2016-10-28" {
        description "Revised on 2016-10-28.";    }

    revision "2016-01-29" {
        description "Revised on 2016-01-29.";    }


    grouping  ldap-grouping {
    container ldap {
        description
            "ldap";
        leaf featureLdap  {
            type  cml_data_types:CML_BOOL_T;
            description "";
        } // END of featureLdap definition.

        leaf port  {
            type  cml_data_types:CML_UINT16_T {
                 range "1..65535";
            }
            description "";
        } // END of port definition.

        leaf timeout  {
            type  cml_data_types:CML_UINT16_T {
                 range "1..60";
            }
            description "";
        } // END of timeout definition.


        list ldap {
            key "hostAddr";
            description
                "ldap";
            leaf hostAddr  {
                type  cml_data_types:CML_HOSTNAME_T;
                description "";
            } // END of hostAddr definition.

            leaf EnableSsl  {
                type  cml_data_types:CML_BOOL_T;
                description "";
            } // END of EnableSsl definition.

            leaf hostPort  {
                type  cml_data_types:CML_UINT16_T {
                     range "1..65535";
                }
                description "";
            } // END of hostPort definition.

            leaf hostDNPort  {
                type  cml_data_types:CML_UINT16_T {
                     range "1..65535";
                }
                default "389";
                description "";
            } // END of hostDNPort definition.

            leaf hostTimeout  {
                type  cml_data_types:CML_UINT16_T {
                     range "1..60";
                }
                default "5";
                description "";
            } // END of hostTimeout definition.

            leaf hostPTimeout  {
                type  cml_data_types:CML_UINT16_T {
                     range "1..60";
                }
                description "";
            } // END of hostPTimeout definition.

            leaf rootDN  {
                type  cml_data_types:CML_STRING_T {
                    length "0..255";
                }
                description "";
            } // END of rootDN definition.

        } // End of ldap-list
    } // END of ldap-container definition.
    } // END of ldap-container definition.


}
