/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : acl.yang
*
*/

submodule acl {

    belongs-to  ZebOS { prefix ZebOS; }


    import cml_data_types {
        prefix cml_data_types;
    }

    description
        "Access List Related Configurations";


    revision "2017-03-09" {
        description "Changing type of dscp,precedence and flowlabel.";
    }

    revision "2017-02-22" {
        description "Optimising the datamodel.";
    }

    revision "2016-11-17" {
        description "Initial version of datamodel.";
    }

    grouping accessListAttr {
                leaf remark  {
            type  cml_data_types:CML_STRING_T {
                length "0..255";
            }
        } // END of remark definition.


        list filterList {
             
            description
                "filterList";

            config true;
            key "accessNumFL";

            
            leaf accessNumFL  {
                type  cml_data_types:CML_UINT32_T {
                     range "1..268435453";
                }
            } // END of accessNumFL definition.

            leaf filterTypeFL  {
                type  cml_data_types:CML_ACL_FILTER_ACTION_T;  
            } // END of filterTypeFL definition.

            leaf logFL  {
                type  cml_data_types:CML_BOOL_T;  
                default false;
            } // END of logFL definition.

            leaf sampleFL  {
                type  cml_data_types:CML_BOOL_T;  
                default false;
            } // END of sampleFL definition.

            leaf enableOrDisableFL  {
                type  cml_data_types:CML_ENABLE_DISABLE_T;  
            } // END of enableOrDisableFL definition.

            leaf updtSeqNum  {
                type  cml_data_types:CML_INT32_T;  
            } // END of updtSeqNum definition.

            leaf packetFormatFM  {
                type  cml_data_types:CML_ACL_ETHER_TYPE_T;  
            } // END of packetFormatFM definition.

            leaf cosFM  {
                type  cml_data_types:CML_INT32_T {
                     range "0..7";
                }
            } // END of cosFM definition.

            leaf vlanFM  {
                type  cml_data_types:CML_INT32_T {
                     range "1..4094";
                }
            } // END of vlanFM definition.

            leaf sMacFM  {
                type  cml_data_types:CML_STRING_T {
                    pattern "[0-9a-fA-F]{4}\.[0-9a-fA-F]{4}\.[0-9a-fA-F]{4}|[0-9a-fA-F]{2}\-[0-9a-fA-F]{2}\-[0-9a-fA-F]{2}\-[0-9a-fA-F]{2}\-[0-9a-fA-F]{2}\-[0-9a-fA-F]{2}|[0-9a-fA-F]{2}:[0-9a-fA-F]{2}:[0-9a-fA-F]{2}:[0-9a-fA-F]{2}:[0-9a-fA-F]{2}:[0-9a-fA-F]{2}";
                    length "0..255";
                }
            } // END of sMacFM definition.

            leaf sMacMaskFM  {
                type  cml_data_types:CML_STRING_T {
                    pattern "[0-9a-fA-F]{4}\.[0-9a-fA-F]{4}\.[0-9a-fA-F]{4}|[0-9a-fA-F]{2}\-[0-9a-fA-F]{2}\-[0-9a-fA-F]{2}\-[0-9a-fA-F]{2}\-[0-9a-fA-F]{2}\-[0-9a-fA-F]{2}|[0-9a-fA-F]{2}:[0-9a-fA-F]{2}:[0-9a-fA-F]{2}:[0-9a-fA-F]{2}:[0-9a-fA-F]{2}:[0-9a-fA-F]{2}";
                    length "0..255";
                }
            } // END of sMacMaskFM definition.

            leaf dMacFM  {
                type  cml_data_types:CML_STRING_T {
                    pattern "[0-9a-fA-F]{4}\.[0-9a-fA-F]{4}\.[0-9a-fA-F]{4}|[0-9a-fA-F]{2}\-[0-9a-fA-F]{2}\-[0-9a-fA-F]{2}\-[0-9a-fA-F]{2}\-[0-9a-fA-F]{2}\-[0-9a-fA-F]{2}|[0-9a-fA-F]{2}:[0-9a-fA-F]{2}:[0-9a-fA-F]{2}:[0-9a-fA-F]{2}:[0-9a-fA-F]{2}:[0-9a-fA-F]{2}";
                    length "0..255";
                }
            } // END of dMacFM definition.

            leaf dMacMaskFM  {
                type  cml_data_types:CML_STRING_T {
                    pattern "[0-9a-fA-F]{4}\.[0-9a-fA-F]{4}\.[0-9a-fA-F]{4}|[0-9a-fA-F]{2}\-[0-9a-fA-F]{2}\-[0-9a-fA-F]{2}\-[0-9a-fA-F]{2}\-[0-9a-fA-F]{2}\-[0-9a-fA-F]{2}|[0-9a-fA-F]{2}:[0-9a-fA-F]{2}:[0-9a-fA-F]{2}:[0-9a-fA-F]{2}:[0-9a-fA-F]{2}:[0-9a-fA-F]{2}";
                    length "0..255";
                }
            } // END of dMacMaskFM definition.

            leaf sIpFC  {
                type  cml_data_types:CML_ACL_ANY_IPV4_ADDR_T;  
            } // END of sIpFC definition.

            leaf dIpFC  {
                type  cml_data_types:CML_ACL_ANY_IPV4_ADDR_T;  
            } // END of dIpFC definition.

            leaf srcAddrNotaFC  {
                type  cml_data_types:CML_UINT8_T;  
            } // END of srcAddrNotaFC definition.

            leaf dstAddrNotaFC  {
                type  cml_data_types:CML_UINT8_T;  
            } // END of dstAddrNotaFC definition.

            leaf protocolFC  {
                type  cml_data_types:CML_ACL_IP_PROTO_ENUM_T;  
            } // END of protocolFC definition.

            leaf srcPortMinFC  {
                type  cml_data_types:CML_UINT16_T {
                     range "0..65535";
                }
            } // END of srcPortMinFC definition.

            leaf srcPortMaxFC  {
                type  cml_data_types:CML_UINT16_T {
                     range "0..65535";
                }
            } // END of srcPortMaxFC definition.

            leaf srcPortUdpFC  {
                type  cml_data_types:CML_ACL_UDP_KEYWORD_T;  
            } // END of srcPortUdpFC definition.

            leaf srcPortTcpFC  {
                type  cml_data_types:CML_ACL_TCP_KEYWORD_T;  
            } // END of srcPortTcpFC definition.

            leaf srcPortOperFC  {
                type  cml_data_types:CML_ACL_PORT_OPERATIONS_T;  
            } // END of srcPortOperFC definition.

            leaf destPortMinFC  {
                type  cml_data_types:CML_UINT16_T {
                     range "0..65535";
                }
            } // END of destPortMinFC definition.

            leaf destPortMaxFC  {
                type  cml_data_types:CML_UINT16_T {
                     range "0..65535";
                }
            } // END of destPortMaxFC definition.

            leaf destPortUdpFC  {
                type  cml_data_types:CML_ACL_UDP_KEYWORD_T;  
            } // END of destPortUdpFC definition.

            leaf destPortTcpFC  {
                type  cml_data_types:CML_ACL_TCP_KEYWORD_T;  
            } // END of destPortTcpFC definition.

            leaf destPortOperFC  {
                type  cml_data_types:CML_ACL_PORT_OPERATIONS_T;  
            } // END of destPortOperFC definition.

            leaf dscpFC  {
                type  cml_data_types:CML_ACL_DSCP_ENUM_T;  
            } // END of dscpFC definition.

            leaf precedenceFC  {
                type  cml_data_types:CML_ACL_PRECEDENCE_ENUM_T;  
            } // END of precedenceFC definition.

            leaf fragmentsFC  {
                type  cml_data_types:CML_BOOL_T;  
                default true;
            } // END of fragmentsFC definition.

            leaf tcpFlagFC  {
                type  cml_data_types:CML_ACL_TCP_FLAGS_T;  
            } // END of tcpFlagFC definition.

            leaf icmpMsgFC  {
                type  cml_data_types:CML_ACL_ICMP_OPTIONS_T;  
            } // END of icmpMsgFC definition.

            leaf icmpTypeFC  {
                type  cml_data_types:CML_UINT8_T {
                     range "0..255";
                }
            } // END of icmpTypeFC definition.

            leaf icmpCodeFC  {
                type  cml_data_types:CML_UINT8_T {
                     range "0..255";
                }
            } // END of icmpCodeFC definition.

            leaf igmpMsgFC  {
                type  cml_data_types:CML_INT16_T;  
            } // END of igmpMsgFC definition.

            leaf protocolFZE  {
                type  cml_data_types:CML_ACL_IP_PROTO_ENUM_T;  
            } // END of protocolFZE definition.

            leaf srcAddrFZE  {
                type  cml_data_types:CML_ACL_ANY_IPV6_ADDR_T;  
            } // END of srcAddrFZE definition.

            leaf srcPortOperFZE  {
                type  cml_data_types:CML_ACL_PORT_OPERATIONS_T;  
            } // END of srcPortOperFZE definition.

            leaf srcPortMaxFZE  {
                type  cml_data_types:CML_UINT16_T {
                     range "0..65535";
                }
            } // END of srcPortMaxFZE definition.

            leaf srcPortMinFZE  {
                type  cml_data_types:CML_UINT16_T {
                     range "0..65535";
                }
            } // END of srcPortMinFZE definition.

            leaf srcPortUdpFZE  {
                type  cml_data_types:CML_ACL_UDP_KEYWORD_T;  
            } // END of srcPortUdpFZE definition.

            leaf srcPortTcpFZE  {
                type  cml_data_types:CML_ACL_TCP_KEYWORD_T;  
            } // END of srcPortTcpFZE definition.

            leaf destAddrFZE  {
                type  cml_data_types:CML_ACL_ANY_IPV6_ADDR_T;  
            } // END of destAddrFZE definition.

            leaf destPortOperFZE  {
                type  cml_data_types:CML_ACL_PORT_OPERATIONS_T;  
            } // END of destPortOperFZE definition.

            leaf destPortMaxFZE  {
                type  cml_data_types:CML_UINT16_T {
                     range "0..65535";
                }
            } // END of destPortMaxFZE definition.

            leaf destPortMinFZE  {
                type  cml_data_types:CML_UINT16_T {
                     range "0..65535";
                }
            } // END of destPortMinFZE definition.

            leaf destPortUdpFZE  {
                type  cml_data_types:CML_ACL_UDP_KEYWORD_T;  
            } // END of destPortUdpFZE definition.

            leaf destPortTcpFZE  {
                type  cml_data_types:CML_ACL_TCP_KEYWORD_T;  
            } // END of destPortTcpFZE definition.

            leaf flowLabelFZE  {
                type  cml_data_types:CML_INT32_T {
                     range "0..1048575";
                }
            } // END of flowLabelFZE definition.

            leaf fragmentsFZE  {
                type  cml_data_types:CML_BOOL_T;  
                default true;
            } // END of fragmentsFZE definition.

            leaf dscpFZE  {
                type  cml_data_types:CML_ACL_DSCP_ENUM_T;  
            } // END of dscpFZE definition.

            leaf tcpFlagFZE  {
                type  cml_data_types:CML_ACL_TCP_FLAGS_T;  
            } // END of tcpFlagFZE definition.

        } // End of filterList-list
        container defaultFilter {
                        config true;

            description
                "defaultFilter";

            leaf filterTypeDF  {
                type  cml_data_types:CML_ACL_FILTER_ACTION_T;  
            } // END of filterTypeDF definition.

            leaf enableOrDisableDF  {
                type  cml_data_types:CML_ENABLE_DISABLE_T;  
            } // END of enableOrDisableDF definition.

            leaf logDF  {
                type  cml_data_types:CML_BOOL_T;  
                default false;
            } // END of logDF definition.

            leaf sampleDF  {
                type  cml_data_types:CML_BOOL_T;  
                default false;
            } // END of sampleDF definition.

        } // END of defaultFilter-container definition.
    } // END of accessListAttr definition.

    grouping  accessMasterIPv4-grouping {
    container accessMasterIPv4 {
                config true;

        description
            "accessMasterIPv4";

        leaf vrId  {
            type  cml_data_types:CML_INT32_T;  
        } // END of vrId definition.

        leaf afiIPv4  {
            type  cml_data_types:CML_INT32_T;  
            default "1";
        } // END of afiIPv4 definition.


        list accessListIPv4 {
             
            description
                "accessListIPv4";

            config true;
            key "aclNameIPv4";

            
            leaf aclNameIPv4  {
                type  cml_data_types:CML_STRING_T {
                    length "1..64";
                }
            } // END of aclNameIPv4 definition.

            uses accessListAttr;
        } // End of accessListIPv4-list

        list accessListMac {
             
            description
                "accessListMac";

            config true;
            key "aclNameMAC";

            
            leaf aclNameMAC  {
                type  cml_data_types:CML_STRING_T {
                    length "1..64";
                }
            } // END of aclNameMAC definition.

            uses accessListAttr;
        } // End of accessListMac-list
    } // END of accessMasterIPv4-container definition.
    } // END of accessMasterIPv4-container definition.

    grouping  accessMasterIPv6-grouping {
    container accessMasterIPv6 {
                config true;

        description
            "accessMasterIPv6";

        leaf vrId  {
            type  cml_data_types:CML_INT32_T;  
        } // END of vrId definition.

        leaf afiIPv6  {
            type  cml_data_types:CML_INT32_T;  
            default "2";
        } // END of afiIPv6 definition.


        list accessListIPv6 {
             
            description
                "accessListIPv6";

            config true;
            key "aclNameIPv6";

            
            leaf aclNameIPv6  {
                type  cml_data_types:CML_STRING_T {
                    length "1..64";
                }
            } // END of aclNameIPv6 definition.

            uses accessListAttr;
        } // End of accessListIPv6-list
    } // END of accessMasterIPv6-container definition.
    } // END of accessMasterIPv6-container definition.


}
