/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-port-breakout-types.yang
*
*/

module ipi-port-breakout-types {

    yang-version 1.1;

    namespace   "http://www.ipinfusion.com/yang/ocnos/ipi-port-breakout-types";

    prefix "ipi-port-breakout-types";

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for Layer-2 Port Breakout types";


    revision "2022-06-01" {
        description "Updated the yang file with feature";
        reference " 0.2.0.";
    }

    revision "2021-11-29" {
        description "Restructured port-breakout module in accordance with OpenConfig style";
        reference " 0.1.0.";
    }



    typedef  port_breakout_mode_t {
        type enumeration {
            enum 4X10g {
                value 1;
                description "split to 4X10g";
            }
            enum 4X25g {
                value 2;
                description "split to 4X25g";
            }
            enum 2X50g {
                value 3;
                description "split to 2X50g";
            }
            enum 4X100g {
                value 8;
                if-feature feature-list:HAVE_TOMAHAWK3;
                description "split to 4X100g";
            }
            enum 8X50g {
                value 9;
                if-feature feature-list:HAVE_TOMAHAWK3;
                description "split to 8X50g";
            }
            enum 8X25g {
                value 10;
                if-feature feature-list:HAVE_TOMAHAWK3;
                description "split to 8X25g";
            }
            enum 8X10g {
                value 11;
                if-feature feature-list:HAVE_TOMAHAWK3;
                description "split to 8X10g";
            }
            enum 2X200g {
                value 12;
                if-feature feature-list:HAVE_TOMAHAWK3;
                description "split to 2X200g";
            }
        }
        description "type definition for PORT_BREAKOUT_MODE_T";
    }

    typedef  port_breakout_group_speed_t {
        type enumeration {
            enum 10g {
                value 0;
                description "10 gigabits";
            }
        }
        description "type definition for PORT_BREAKOUT_GROUP_SPEED_T";
    }

    typedef  port_breakout_if_mode_t {
        type enumeration {
            enum 4X10g {
                value 1;
                description "split to 4X10g";
            }
            enum 4X25g {
                value 2;
                description "split to 4X25g";
            }
            enum 2X50g {
                value 3;
                description "split to 2X50g";
            }
        }
        description "type definition for PORT_BREAKOUT_IF_MODE_T";
    }

}
