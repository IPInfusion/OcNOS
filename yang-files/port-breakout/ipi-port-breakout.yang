/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-port-breakout.yang
*
*/

module ipi-port-breakout {

    yang-version 1.1;

    namespace   "http://www.ipinfusion.com/yang/ocnos/ipi-port-breakout";

    prefix "ipi-port-breakout";

    import ipi-port-breakout-types {
        prefix ipi-port-breakout-types;
        revision-date 2022-06-01;
    }

    import feature-list {
        prefix feature-list;
        revision-date 2023-02-21;
    }

    include ipi-port-breakout-interface { revision-date 2022-06-01;}
    organization
        "IP Infusion Inc.";

    contact
        "Address: 3965 Freedom Circle, Suite 200, Santa Clara, CA 95054
         Phone: +1 408-400-1900
         E-mail: support@ipinfusion.com
         Web: http://www.ipinfusion.com/";

    description
        "Datamodel for Layer-2 Port Breakout";


    revision "2022-07-26" {
        description "Added vlan reservation as dependent object for breakout objectlist with flags";
        reference " 0.3.1.";
    }

    revision "2022-07-21" {
        description "Added vlan reservation as dependent object for breakout";
        reference " 0.3.0.";
    }

    revision "2022-06-01" {
        description "Updated the yang file with feature";
        reference " 0.2.0.";
    }

    revision "2021-11-29" {
        description "Restructured port-breakout module in accordance with OpenConfig style";
        reference " 0.1.0.";
    }

    revision "2018-09-17" {
        description "Initial Version";
        reference "Initial Version";
    }

    grouping port-breakout-breakout-state {
        description
            "Grouping for port-breakout operational state data";
        leaf block  {
            type  uint8;
            description "Use this attribute to get port-breakout block operational state data";
        } // END of block definition.

    } // END of port-breakout-breakout-state definition.
    grouping port-breakout-breakout-config {
        description
            "Grouping for port-breakout configuration data";
        leaf port-number  {
            type  uint8;
            description "Use this attribute to set the port number associated with this
                        instance";
        } // END of port-number definition.

        leaf mode  {
            type  ipi-port-breakout-types:port_breakout_mode_t;
            mandatory true;
            description "Use this attribute to set port breakout mode";
        } // END of mode definition.

    } // END of port-breakout-breakout-config definition.
    grouping port-breakout-breakout-top {
        description
            "Grouping for port-breakout entries";
        container breakouts {
            description
                "Container for port-breakout list configuration";

            list breakout {
            when " /ipi-port-breakout:port-breakout/ipi-port-breakout:breakouts/ipi-port-breakout:breakout/ipi-port-breakout:config/ipi-port-breakout:mode ";
                key "port-number";
                description
                    "List of port breakout";
                leaf port-number  {
                    type  leafref {
                        path  "../config/port-number";
                    }
                    description "Use this attribute to set the port number associated with this
                                instance";
                } // END of port-number definition.

                container config {
                    description
                        "Configuration data for port-breakout entry";
                    uses port-breakout-breakout-config;
                } // END of config-container definition.
                container state {
                    config false;
                    description
                        "Operational state data for port-breakout entry";
                    uses port-breakout-breakout-config;
                    uses port-breakout-breakout-state;
                } // END of state-container definition.
            } // End of breakout-list
        } // END of breakouts-container definition.
    } // END of port-breakout-breakout-top definition.
    grouping port-breakout-group-speed-state {
        description
            "Grouping for port-breakout group speed operational state data";
        leaf-list ports  {
            type  uint8;
            description "Use this attribute to get the list of ports within the group speed";
        } // END of ports definition.

    } // END of port-breakout-group-speed-state definition.
    grouping port-breakout-group-speed-config {
        description
            "Grouping for port-breakout group speed configuration data";
        leaf port-group  {
            type  uint8;
            description "Use this attribute to set the port group associated with this instance";
        } // END of port-group definition.

        leaf speed  {
            type  ipi-port-breakout-types:port_breakout_group_speed_t;
            mandatory true;
            description "Use this attribute to set the port group speed";
        } // END of speed definition.

    } // END of port-breakout-group-speed-config definition.
    grouping port-breakout-group-speed-top {
        description
            "Grouping for Port Breakout group speed";
        container groups-speed {
            description
                "Container for Port Breakout group speed list configuration";

            list group-speed {
            when " /ipi-port-breakout:port-breakout/ipi-port-breakout:groups-speed/ipi-port-breakout:group-speed/ipi-port-breakout:config/ipi-port-breakout:speed ";
                if-feature feature-list:NOT_HAVE_DUNE;
                key "port-group";
                description
                    "List of group speed";
                leaf port-group  {
                    type  leafref {
                        path  "../config/port-group";
                    }
                    description "Use this attribute to set the port group associated with this instance";
                } // END of port-group definition.

                container config {
                    description
                        "Configuration data for group speed entry";
                    uses port-breakout-group-speed-config;
                } // END of config-container definition.
                container state {
                    config false;
                    description
                        "Operational state data for group speed entry";
                    uses port-breakout-group-speed-config;
                    uses port-breakout-group-speed-state;
                } // END of state-container definition.
            } // End of group-speed-list
        } // END of groups-speed-container definition.
    } // END of port-breakout-group-speed-top definition.

    grouping  port-breakout-grouping {
    description
        "Port-breakout data model";
    container port-breakout {
        if-feature feature-list:HAVE_FLEXPORT;
        description
            "Port-breakout data model";
        uses port-breakout-breakout-top;
        uses port-breakout-group-speed-top;
        uses port-breakout-interface-top;
    } // END of port-breakout-container definition.
    } // END of port-breakout-grouping definition.

    uses port-breakout-grouping;

}
