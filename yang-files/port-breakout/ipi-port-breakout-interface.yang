/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-port-breakout-interface.yang
*
*/

submodule ipi-port-breakout-interface {

    yang-version 1.1;

    belongs-to  ipi-port-breakout { prefix ipi-port-breakout; }

    import ipi-port-breakout-types {
        prefix ipi-port-breakout-types;
        revision-date 2022-06-01;
    }

    import ipi-interface {
        prefix ipi-interface;
        revision-date 2022-08-24;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for Layer-2 Port Breakout Interface";


    revision "2022-06-01" {
        description "Updated the yang file with feature";
        reference " 0.2.0.";
    }

    revision "2021-11-29" {
        description "Restructured port-breakout module in accordance with OpenConfig style";
        reference " 0.1.0.";
    }

    revision "2018-09-17" {
        description "Initial Version";
        reference "Initial Version";
    }

    grouping port-breakout-interface-config {
        description
            "Grouping for Port-breakout Interface configuration data";
        leaf name  {
            type  leafref {
                path  "/ipi-interface:interfaces/ipi-interface:interface/ipi-interface:name";
            }
            description "Use this attribute to configure Port-breakout for an interface.";
        } // END of name definition.

        leaf mode  {
            type  ipi-port-breakout-types:port_breakout_if_mode_t;
            description "Use this attribute to configure Port-breakout mode for an interface";
        } // END of mode definition.

    } // END of port-breakout-interface-config definition.
    grouping port-breakout-interface-top {
        description
            "Grouping for Port-breakout Interface";
        container interfaces {
            description
                "Container for Port-breakout Interface configuration";

            list interface {
            when " /port-breakout/interfaces/interface/config/mode ";
                key "name";
                description
                    "List of interfaces on which port-breakout will be configured";
                leaf name  {
                    type  leafref {
                        path  "../config/name";
                    }
                    description "Use this attribute to configure Port-breakout for an interface.";
                } // END of name definition.

                container config {
                    description
                        "Configuration data for Port-breakout Interface";
                    uses port-breakout-interface-config;
                } // END of config-container definition.
                container state {
                    config false;
                    description
                        "Operational state data for Port-breakout Interface";
                    uses port-breakout-interface-config;
                } // END of state-container definition.
            } // End of interface-list
        } // END of interfaces-container definition.
    } // END of port-breakout-interface-top definition.


}
