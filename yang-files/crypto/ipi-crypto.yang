/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-crypto.yang
*
*/

module ipi-crypto {

    yang-version 1.1;

    namespace   "http://www.ipinfusion.com/yang/ocnos/ipi-crypto";

    prefix "ipi-crypto";

    import ietf-inet-types {
        prefix inet;
        revision-date 2013-07-15;
    }

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "This module defines configurations related to cryptographic
                certificate generation and management";


    revision "2022-06-01" {
        description "Updated the yang file with feature";
        reference " 0.2.0.";
    }

    revision "2021-07-30" {
        description "Initial Version";
        reference "Initial Version";
    }



    rpc crypto-rsa-key-gen {
        if-feature feature-list:HAVE_HOSTPD;
        description "Use this RPC to generate private key and certificate signing request";
        input  {
            leaf ipv4-addr  {
                type inet:ipv4-address;
                mandatory true;
                description "IP address for CSR common-name field";
            }
        }
    }

}
