/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-global-te.yang
*
*/

module ipi-global-te {

    yang-version 1.1;

    namespace   "http://www.ipinfusion.com/yang/ocnos/ipi-global-te";

    prefix "ipi-global-te";

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "Data model for Global Te";


    revision "2022-07-11" {
        description "Updated data model name";
        reference " 0.2.0.";
    }

    revision "2022-06-21" {
        description "Initial Version";
        reference " 0.1.0.";
    }

    grouping admin-group-config {
        description
            "Administrative Group Configurations";
        leaf name  {
            type  string {
                length "1..1965";
                pattern "[^?' =,>|]+";
            }
            description "Use this attribute to create a name-to-value binding for an
                        administrative group";
        } // END of name definition.

        leaf id  {
            type  uint8 {
                 range "0..31"  {
                    description "0..31: Supported range 0 - 31";
                 }
            }
            description "identifier value for the administrative group";
        } // END of id definition.

    } // END of admin-group-config definition.

    grouping  admin-groups-grouping {
    description
        "This defines a YANG data model for admin group config for  MPLS and TE
                configuration and operation.";
    container admin-groups {
        if-feature feature-list:HAVE_MPLS_OR_HAVE_SRV6;
        description
            "This defines a YANG data model for admin group config for  MPLS and TE
                    configuration and operation.";

        list admin-group {
            key "name id";
            description
                "Administrative Group Configurations";
            leaf name  {
                type  leafref {
                    path  "../config/name";
                }
                description "Use this attribute to create a name-to-value binding for an
                            administrative group";
            } // END of name definition.

            leaf id  {
                type  leafref {
                    path  "../config/id";
                }
                description "identifier value for the administrative group";
            } // END of id definition.

            container config {
                description
                    "Config Container for Administrative Groups";
                uses admin-group-config;
            } // END of config-container definition.
            container state {
                config false;
                description
                    "State Contatiner for Administrative Groups";
                uses admin-group-config;
            } // END of state-container definition.
        } // End of admin-group-list
    } // END of admin-groups-container definition.
    } // END of admin-groups-grouping definition.

    uses admin-groups-grouping;

}
