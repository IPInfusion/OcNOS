/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-vrrp-debug.yang
*
*/

submodule ipi-vrrp-debug {

    yang-version 1.1;

    belongs-to  ipi-vrrp { prefix ipi-vrrp; }

    import ipi-vrrp-types {
        prefix ipi-vrrp-types;
        revision-date 2022-06-01;
    }

    organization
        "IP Infusion Inc.";

    contact
        "Address: 3965 Freedom Circle, Suite 200, Santa Clara, CA 95054
         Phone: +1 408-400-1900
         E-mail: support@ipinfusion.com
         Web: http://www.ipinfusion.com/";

    description
        "Virtual Router Redundancy Protocol debug configuration";


    revision "2022-06-01" {
        description "Updated the yang file with feature";
        reference " 0.3.0.";
    }

    revision "2021-09-03" {
        description "Update descriptions of attribute";
        reference "Initial Version";
    }

    revision "2021-06-18" {
        description "Restructured module in accordance with OpenConfig style";
        reference "Initial Version";
    }

    grouping vrrp-debug-config {
        description
            "Grouping for VRRP Debug configuration";
        leaf debug-options  {
            type  ipi-vrrp-types:vrrp_debug_t;
            description "use this attribute to specify debugging options for VRRP";
        } // END of debug-options definition.

    } // END of vrrp-debug-config definition.
    grouping vrrp-debug-terminal-state {
        description
            "Grouping for VRRP Debug debug terminal state";
        container terminal {
            config false;
            description
                "Virtual Router Redundancy Protocol Debug terminal";
            container state {
                config false;
                description
                    "Virtual Router Redundancy Protocol Debug terminal state";
                uses vrrp-debug-config;
            } // END of state-container definition.
        } // END of terminal-container definition.
    } // END of vrrp-debug-terminal-state definition.
    grouping vrrp-debug-top {
        description
            "Grouping for VRRP Debug";
        container debug {
            description
                "Virtual Router Redundancy Protocol Debug";
            container config {
                description
                    "Virtual Router Redundancy Protocol Configuration";
                uses vrrp-debug-config;
            } // END of config-container definition.
            container state {
                config false;
                description
                    "Virtual Router Redundancy Protocol State";
                uses vrrp-debug-config;
            } // END of state-container definition.
            uses vrrp-debug-terminal-state;
        } // END of debug-container definition.
    } // END of vrrp-debug-top definition.


}
