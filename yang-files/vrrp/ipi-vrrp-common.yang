/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-vrrp-common.yang
*
*/

submodule ipi-vrrp-common {

    yang-version 1.1;

    belongs-to  ipi-vrrp { prefix ipi-vrrp; }

    import feature-list {
        prefix feature-list;
        revision-date 2023-02-21;
    }

    import cml-data-types {
        prefix cml-data-types;
        revision-date 2022-09-30;
    }

    import ietf-yang-types {
        prefix yang;
        revision-date 2013-07-15;
    }

    import ipi-interface {
        prefix ipi-interface;
        revision-date 2022-08-24;
    }

    import ipi-vrrp-types {
        prefix ipi-vrrp-types;
        revision-date 2022-06-01;
    }

    organization
        "IP Infusion Inc.";

    contact
        "Address: 3965 Freedom Circle, Suite 200, Santa Clara, CA 95054
         Phone: +1 408-400-1900
         E-mail: support@ipinfusion.com
         Web: http://www.ipinfusion.com/";

    description
        "Virtual Router Redundancy Protocol Common Groups";


    revision "2022-06-01" {
        description "Updated the yang file with feature";
        reference " 0.2.4.";
    }

    revision "2021-12-01" {
        description "Added support for object tracking";
        reference " 0.2.3.";
    }

    revision "2021-09-08" {
        description "Add attributes wrong-authentication-password and refresh-rate-interval";
        reference " 0.2.2.";
    }

    revision "2021-07-15" {
        description "Tracking interface priority as mandatoty leaf";
        reference " 0.2.1.";
    }

    revision "2021-05-07" {
        description "Restructured module in accordance with OpenConfig style";
        reference " 0.2.0.";
    }

    grouping vrrp-interface-errors-top {
        description
            "Grouping for VRRP Session Errors";
        container errors {
            config false;
            description
                "Virtual Router Redundancy Protocol Session Errors";
            container state {
                config false;
                description
                    "Virtual Router Redundancy Protocol Session Errors state";
                leaf wrong-interval-advertise-received  {
                    if-feature feature-list:NOT_HAVE_VRRP_V3;
                    type  yang:counter64;
                    description "Advertise received with wrong interval";
                } // END of wrong-interval-advertise-received definition.

                leaf ttl-error-packets  {
                    type  yang:counter64;
                    description "Number of packets received with ttl != 255";
                } // END of ttl-error-packets definition.

                leaf invalid-type-packets  {
                    type  yang:counter64;
                    description "Number of packets received with invalid type";
                } // END of invalid-type-packets definition.

                leaf address-list-errors  {
                    type  yang:counter64;
                    description "Number of packets received with address mismatch";
                } // END of address-list-errors definition.

                leaf invalid-authentication-type  {
                    type  yang:counter64;
                    description "Number of packets received with unknown auth type";
                } // END of invalid-authentication-type definition.

                leaf authentication-type-mismatch  {
                    type  yang:counter64;
                    description "Number of packets received with authentication type mismatch";
                } // END of authentication-type-mismatch definition.

                leaf wrong-authentication-password  {
                    type  yang:counter64;
                    description "Wrong Authentication";
                } // END of wrong-authentication-password definition.

                leaf address-mismatch-packets  {
                    type  yang:counter64;
                    description "Number of packets received with mismatch in Ip address count";
                } // END of address-mismatch-packets definition.

                leaf packet-length-errors  {
                    type  yang:counter64;
                    description "Total num of packets received with pkt length less than length of VRRP
                                header";
                } // END of packet-length-errors definition.

            } // END of state-container definition.
        } // END of errors-container definition.
    } // END of vrrp-interface-errors-top definition.
    grouping vrrp-interface-statistic-top {
        description
            "Grouping for VRRP Session Statistcs";
        container statistics {
            config false;
            description
                "Virtual Router Redundancy Protocol Session Statistcs";
            container state {
                config false;
                description
                    "Virtual Router Redundancy Protocol Session Statistcs state";
                leaf transitions-to-master  {
                    type  yang:counter64;
                    description "Times state transitioned to master";
                } // END of transitions-to-master definition.

                leaf advertise-received  {
                    type  yang:counter64;
                    description "Advertise received";
                } // END of advertise-received definition.

                leaf priority-zero-received-packets  {
                    type  yang:counter64;
                    description "Number of packets received with priority=0";
                } // END of priority-zero-received-packets definition.

                leaf priority-zero-sent-packets  {
                    type  yang:counter64;
                    description "Number of packets sent with priority=0";
                } // END of priority-zero-sent-packets definition.

                leaf disconnection-time  {
                    type  string {
                        length "1..1965";
                        pattern "((([0-1]?[0-9])|(2[0-3])):[0-5][0-9]:[0-5][0-9])|([0-9]+d(([0-1][0-9])|(2[0-3]))h[0-5][0-9]m)";
                    }
                    description "Discontinuity Time";
                } // END of disconnection-time definition.

                leaf monitored-circuit-up-events  {
                    type  yang:counter64;
                    description "Monitored circuit up event";
                } // END of monitored-circuit-up-events definition.

                leaf monitored-circuit-down-events  {
                    type  yang:counter64;
                    description "Monitored circuit down event";
                } // END of monitored-circuit-down-events definition.

            } // END of state-container definition.
        } // END of statistics-container definition.
    } // END of vrrp-interface-statistic-top definition.
    grouping vrrp-interface-state-timers-top {
        description
            "Grouping for VRRP Session Timers";
        container timers {
            config false;
            description
                "Virtual Router Redundancy Protocol Session Timers";
            container state {
                config false;
                description
                    "Virtual Router Redundancy Protocol Session Timers state";
                leaf switchback-delay-timer  {
                    type  uint32;
                    description "Countdown timer for switch back delay";
                } // END of switchback-delay-timer definition.

                leaf countdown-timer  {
                    type  uint32;
                    description "Countdown timer";
                } // END of countdown-timer definition.

                leaf skew-time  {
                    type  uint32;
                    description "Skew time";
                } // END of skew-time definition.

                leaf garp-packet-delay  {
                    type  uint32;
                    description "Garp packet delay";
                } // END of garp-packet-delay definition.

                leaf master-advertise-interval  {
                    type  uint32;
                    description "Advertise interval received from the master";
                } // END of master-advertise-interval definition.

                leaf refresh-rate-interval  {
                    type  uint32;
                    units "miliseconds";
                    description "Refresh Rate interval";
                } // END of refresh-rate-interval definition.

            } // END of state-container definition.
        } // END of timers-container definition.
    } // END of vrrp-interface-state-timers-top definition.
    grouping vrrp-interface-state-session-status-top {
        description
            "Grouping for VRRP Session Status";
        container session-status {
            config false;
            description
                "Virtual Router Redundancy Protocol Session Status";
            container state {
                config false;
                description
                    "Virtual Router Redundancy Protocol Session Status state";
                leaf vrrp-state  {
                    type  ipi-vrrp-types:vrrp_session_state_t;
                    description "vrrp state";
                } // END of vrrp-state definition.

                leaf virtual-address-status  {
                    type  ipi-vrrp-types:vrrp_ip_status_t;
                    description "Status of virtual-address";
                } // END of virtual-address-status definition.

            } // END of state-container definition.
        } // END of session-status-container definition.
    } // END of vrrp-interface-state-session-status-top definition.
    grouping vrrp-interface-state-session-info-top {
        description
            "Grouping for VRRP Session Information";
        container session-info {
            config false;
            description
                "Virtual Router Redundancy Protocol Session Information";
            container state {
                config false;
                description
                    "Virtual Router Redundancy Protocol Session Information state";
                leaf multicast-membership  {
                    type  ipi-vrrp-types:vrrp_member_state_t;
                    description "State of Multicast membership on interface";
                } // END of multicast-membership definition.

                leaf address-family  {
                    type  ipi-vrrp-types:vrrp_addr_family_t;
                    description "Address family";
                } // END of address-family definition.

                leaf running-priority  {
                    type  uint8;
                    description "Priority";
                } // END of running-priority definition.

                leaf virtual-mac-mbyte-word  {
                    type  cml-data-types:cml_mac_addr_t {
                        length "1..1965";
                    }
                    description "Virtual Mac";
                } // END of virtual-mac-mbyte-word definition.

                leaf administrative-state  {
                    type  ipi-vrrp-types:vrrp_admin_state_t;
                    description "Sadministrative state";
                } // END of administrative-state definition.

                leaf init-message-code  {
                    type  ipi-vrrp-types:vrrp_init_message_code_t;
                    description "Vrrp init message types";
                } // END of init-message-code definition.

            } // END of state-container definition.
        } // END of session-info-container definition.
    } // END of vrrp-interface-state-session-info-top definition.
    grouping vrrp-protocol-enable-config {
        description
            "Grouping for VRRP common protocol enable configuration";
        leaf enable  {
            type  empty;
            description "Use this attribute to enable a VRRP session on the router (to make it
                        participate in virtual routing). To make any changes to the VRRP
                        configuration, first disable the router from participating in virtual
                        routing using the disable command";
        } // END of enable definition.

    } // END of vrrp-protocol-enable-config definition.
    grouping vrrp-common-config {
        description
            "Grouping for VRRP common configuration";
        leaf interface-name  {
            // when " ipi-interface:interfaces/interface/config/enable-switchport != '1' ";
            type  leafref {
                path  "/ipi-interface:interfaces/ipi-interface:interface/ipi-interface:name";
            }
            description "Use this attribute to configure a VRRP routing process for an
                        interface.";
        } // END of interface-name definition.

        leaf disable-preempt-mode  {
            type  empty;
            description "Use this attribute to configure preempt mode. If set to true, the
                        highest priority backup is always the master when the default master
                        is unavailable. If set to false, a higher priority backup does not
                        preempt a lower priority backup which is acting as master";
        } // END of disable-preempt-mode definition.

        leaf priority  {
            type  uint8 {
                 range "1..254"  {
                    description "1..254: Supported range 1 - 254";
                 }
            }
            description "Use this attribute to configure the VRRP router priority within the
                        virtual router. Priority determines the role that each VRRP router
                        plays and what happens if the master virtual router fails. If a VRRP
                        router owns the IP address of the virtual router and the IP address of
                        the physical interface, this router functions as the master virtual
                        router";
        } // END of priority definition.

        leaf preempt-delay  {
            type  uint32 {
                 range "1..500000"  {
                    description "1..500000: Supported range 1 - 500000";
                 }
            }
            description "Use this attribute to set a switch-back delay timer for the master
                        VRRP router. This feature prevents the original master VRRP router
                        from transitioning back to the master state after coming back online
                        until the configured delay timer has expired.";
        } // END of preempt-delay definition.

        leaf advertisement-interval  {
            type  uint16 {
                 range "5..4095"  {
                    description "5..4095: Supported range 5 - 4095";
                 }
            }
            default "100";
            description "Use this attribute to configure the advertisement interval of a
                        virtual router. This is the length of time, in seconds, between each
                        advertisement sent from the master to its backup(s). The master
                        virtual router sends VRRP advertisements to other VRRP routers in the
                        same group. The advertisements communicate the priority and state of
                        the master virtual router. The VRRP advertisements are encapsulated in
                        IP packets and sent to the multicast address assigned to the VRRP
                        group (224.0.0.18). Advertisements are sent every second by default.";
        } // END of advertisement-interval definition.

        leaf disable-accept-mode  {
            type  empty;
            description "Use this attribute to enable accept mode for the session";
        } // END of disable-accept-mode definition.

    } // END of vrrp-common-config definition.
    grouping vrrp-ip-instance-config {
        description
            "Grouping for VRRP IPV4 instances configuration";
        leaf virtual-router-id  {
            type  uint8 {
                 range "1..255"  {
                    description "1..255: Supported range 1 - 255";
                 }
            }
            description "vrrp instance id";
        } // END of virtual-router-id definition.

    } // END of vrrp-ip-instance-config definition.
    grouping vrrp-interface-tracking-config {
        description
            "Grouping for interface tracking attributes";
        leaf interface-tracking-name  {
            type  leafref {
                path  "/ipi-interface:interfaces/ipi-interface:interface/ipi-interface:name";
            }
            description "Use this attribute to configure a VRRP routing process for an
                        interface.";
        } // END of interface-tracking-name definition.

        leaf priority-decrement  {
            type  uint8 {
                 range "1..253"  {
                    description "1..253: Supported range 1 - 253";
                 }
            }
            mandatory true;
            description "Use this attribute to configure the priority decrement for a VRRP
                        routing process for an interface.";
        } // END of priority-decrement definition.

    } // END of vrrp-interface-tracking-config definition.
    grouping vrrp-interface-tracking-state {
        description
            "Grouping for interface tracking attributes";
        leaf interface-status  {
            type  ipi-vrrp-types:vrrp_iface_status_t;
            description "Attribute to indicate the interface status.";
        } // END of interface-status definition.

        leaf interface-down-events  {
            type  uint32;
            description "Attribute to indicate the interface down event counter.";
        } // END of interface-down-events definition.

    } // END of vrrp-interface-tracking-state definition.
    grouping vrrp-interface-tracking-top {
        description
            "Grouping for VRRP interface tracking";
        container interfaces-tracking {
            description
                "VRRP Interface tracking container";

            list interface-tracking {
                key "interface-tracking-name";
                description
                    "VRRP Interface tracking List";
                leaf interface-tracking-name  {
                    type  leafref {
                        path  "../config/interface-tracking-name";
                    }
                    description "Use this command to enable the VRRP circuit failover feature.";
                } // END of interface-tracking-name definition.

                container config {
                    description
                        "Virtual Router Redundancy Protocol Interface tracking";
                    uses vrrp-interface-tracking-config;
                } // END of config-container definition.
                container state {
                    config false;
                    description
                        "Virtual Router Redundancy Protocol Interface tracking state";
                    uses vrrp-interface-tracking-config;
                    uses vrrp-interface-tracking-state;
                } // END of state-container definition.
            } // End of interface-tracking-list
        } // END of interfaces-tracking-container definition.
    } // END of vrrp-interface-tracking-top definition.
    grouping vrrp-interface-state-reasons-top {
        description
            "Grouping for interface state reasons";
        container reasons {
            config false;
            description
                "Container for interface state reasons";
            container state {
                config false;
                description
                    "State for interface state reasons";
                leaf new-master-reason  {
                    type  ipi-vrrp-types:vrrp_new_master_reason_t;
                    description "New master reason";
                } // END of new-master-reason definition.

            } // END of state-container definition.
        } // END of reasons-container definition.
    } // END of vrrp-interface-state-reasons-top definition.
    grouping vrrp-object-tracking-config {
        description
            "Grouping for object tracking attributes";
        leaf tracking-id  {
            type  uint16 {
                 range "1..500"  {
                    description "1..500: Supported range 1 - 500";
                 }
            }
            description "Use this attribute to configure a VRRP routing process for an object
                        tracking.";
        } // END of tracking-id definition.

        leaf decrement  {
            type  uint8 {
                 range "1..253"  {
                    description "1..253: Supported range 1 - 253";
                 }
            }
            mandatory true;
            description "Use this attribute to configure the priority decrement for a VRRP
                        routing process for an object.";
        } // END of decrement definition.

    } // END of vrrp-object-tracking-config definition.
    grouping vrrp-object-tracking-state {
        description
            "Grouping for object tracking attributes";
        leaf object-status  {
            type  ipi-vrrp-types:vrrp_iface_status_t;
            description "Attribute to indicate the object status.";
        } // END of object-status definition.

        leaf object-down-events  {
            type  uint32;
            description "Attribute to indicate the object down event counter.";
        } // END of object-down-events definition.

    } // END of vrrp-object-tracking-state definition.
    grouping vrrp-object-tracking-top {
        description
            "Grouping for VRRP object tracking";
        container objects-tracking {
            if-feature feature-list:HAVE_OBJ_TRACKING;
            description
                "VRRP object tracking container";

            list object-tracking {
                key "tracking-id";
                description
                    "VRRP object tracking List";
                leaf tracking-id  {
                    type  leafref {
                        path  "../config/tracking-id";
                    }
                    description "Use this command to enable the VRRP object tracking feature.";
                } // END of tracking-id definition.

                container config {
                    description
                        "Virtual Router Redundancy Protocol Object tracking";
                    uses vrrp-object-tracking-config;
                } // END of config-container definition.
                container state {
                    config false;
                    description
                        "Virtual Router Redundancy Protocol object tracking state";
                    uses vrrp-object-tracking-config;
                    uses vrrp-object-tracking-state;
                } // END of state-container definition.
            } // End of object-tracking-list
        } // END of objects-tracking-container definition.
    } // END of vrrp-object-tracking-top definition.


}
