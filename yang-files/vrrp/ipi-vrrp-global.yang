/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-vrrp-global.yang
*
*/

submodule ipi-vrrp-global {

    yang-version 1.1;

    belongs-to  ipi-vrrp { prefix ipi-vrrp; }

    import ietf-inet-types {
        prefix inet;
        revision-date 2013-07-15;
    }

    import ietf-yang-types {
        prefix yang;
        revision-date 2013-07-15;
    }

    import ipi-vrrp-types {
        prefix ipi-vrrp-types;
        revision-date 2022-06-01;
    }

    organization
        "IP Infusion Inc.";

    contact
        "Address: 3965 Freedom Circle, Suite 200, Santa Clara, CA 95054
         Phone: +1 408-400-1900
         E-mail: support@ipinfusion.com
         Web: http://www.ipinfusion.com/";

    description
        "Virtual Router Redundancy Protocol global configuration";


    revision "2022-06-01" {
        description "Updated the yang file with feature";
        reference " 0.2.5.";
    }

    revision "2021-09-23" {
        description "New grouping for vrrp packet error notification";
        reference " 0.2.4.";
    }

    revision "2021-09-03" {
        description "Update descriptions of attribute";
        reference " 0.2.3.";
    }

    revision "2021-08-26" {
        description "Change error-reason description";
        reference " 0.2.2.";
    }

    revision "2021-07-02" {
        description "Add global error status attributes";
        reference " 0.2.1.";
    }

    revision "2021-06-18" {
        description "Restructured module in accordance with OpenConfig style";
        reference " 0.2.0.";
    }

    revision "2018-06-16" {
        description "Initial Version";
        reference " 0.1.0.";
    }

    grouping vrrp-global-error-top {
        description
            "Grouping for VRRP Global Error State";
        container errors {
            config false;
            description
                "Virtual Router Global Errors";
            container state {
                config false;
                description
                    "Virtual Router Global Errors state";
                leaf checksum-error  {
                    type  yang:counter64;
                    description "Number of VRRP packets received with checksum error";
                } // END of checksum-error definition.

                leaf version-error  {
                    type  yang:counter64;
                    description "Number of VRRP packets received with version error";
                } // END of version-error definition.

                leaf invalid-virtual-router-id  {
                    type  yang:counter64;
                    description "Number of VRRP packets received with invalid virtual router id";
                } // END of invalid-virtual-router-id definition.

            } // END of state-container definition.
        } // END of errors-container definition.
    } // END of vrrp-global-error-top definition.
    grouping vrrp-global-config {
        description
            "Grouping for VRRP Global configuration";
        leaf disable-virtual-router-mac-address  {
            type  empty;
            description "Use this attribute to enable or disable Virtual MAC (VMAC). This
                        affects all VRRP groups in a router. On a single network segment,
                        multiple VRRP groups can be configured, each using a different VMAC.
                        The use of VMAC addressing allows for faster switchover when a backup
                        router assumes the master role. When this attribute is used to enable
                        a VMAC, the virtual router forwards packets with a special-purpose
                        multicast VMAC address (0:0:5e:0:01:VR_ID). Otherwise, it forwards
                        with interface physical address.The VMAC address is assigned to a
                        router interface at the time the VRRP group is enabled in the router.";
        } // END of disable-virtual-router-mac-address definition.

        leaf vrrp-v2-compatible  {
            type  empty;
            description "Use this attribute to enable or disable backward-compatibility
                        feature. When enabled, both VRRPv3 and VRRPv2 interoperation are
                        supported.";
        } // END of vrrp-v2-compatible definition.

        leaf ipv4-exclude-pseudo-header  {
            type  empty;
            description "This command excludes the pseudo-header in IPv4 VRRPv3 checksum
                        calculation on the VRRP group";
        } // END of ipv4-exclude-pseudo-header definition.

    } // END of vrrp-global-config definition.
    grouping vrrp-global-session-state-top {
        description
            "Grouping for VRRP Global Session State";
        container session {
            config false;
            description
                "Virtual Router Redundancy Protocol Session";
            container state {
                config false;
                description
                    "Virtual Router Redundancy Protocol Session State";
                leaf session-table-maximum  {
                    type  uint32;
                    description "Instance table max value";
                } // END of session-table-maximum definition.

                leaf session-table-size  {
                    type  uint32;
                    description "Instance table count value";
                } // END of session-table-size definition.

                leaf ipv4-session-count  {
                    type  uint32;
                    description "IPv4 Session count";
                } // END of ipv4-session-count definition.

                leaf ipv6-session-count  {
                    type  uint32;
                    description "IPv6 Session count";
                } // END of ipv6-session-count definition.

            } // END of state-container definition.
        } // END of session-container definition.
    } // END of vrrp-global-session-state-top definition.
    grouping vrrp-global-state {
        description
            "Grouping for VRRP Global State";
        leaf notification-control  {
            type  empty;
            description "Flag For Trap Generation";
        } // END of notification-control definition.

    } // END of vrrp-global-state definition.
    grouping vrrp-new-master-top {
        description
            "Grouping for VRRP new master";
        container new-master {
            config false;
            description
                "Virtual Router Redundancy New Master Notification";
            leaf operational-master-address  {
                type  inet:ip-address;
                description "Operational Master address";
            } // END of operational-master-address definition.

            leaf virtual-router-id  {
                type  uint8;
                description "Virtual router id";
            } // END of virtual-router-id definition.

            leaf new-master-reason  {
                type  ipi-vrrp-types:vrrp_new_master_reason_t;
                description "New Master reason";
            } // END of new-master-reason definition.

            leaf uptime  {
                type  string {
                    length "1..1965";
                    pattern "((([0-1]?[0-9])|(2[0-3])):[0-5][0-9]:[0-5][0-9])|([0-9]+d(([0-1][0-9])|(2[0-3]))h[0-5][0-9]m)";
                }
                description "This attribute provides session uptime";
            } // END of uptime definition.

        } // END of new-master-container definition.
    } // END of vrrp-new-master-top definition.
    grouping vrrp-protocol-error-top {
        description
            "Grouping for VRRP protocol error";
        container protocol-error {
            config false;
            description
                "Virtual Router Redundancy Protocol Error Notification";
            leaf operational-master-address  {
                type  inet:ip-address;
                description "Operational Master address";
            } // END of operational-master-address definition.

            leaf virtual-router-id  {
                type  uint8;
                description "Virtual router id";
            } // END of virtual-router-id definition.

            leaf error-reason  {
                type  ipi-vrrp-types:vrrp_error_reason_t;
                description "Protocol error reason";
            } // END of error-reason definition.

            leaf uptime  {
                type  string {
                    length "1..1965";
                    pattern "((([0-1]?[0-9])|(2[0-3])):[0-5][0-9]:[0-5][0-9])|([0-9]+d(([0-1][0-9])|(2[0-3]))h[0-5][0-9]m)";
                }
                description "This attribute provides session uptime";
            } // END of uptime definition.

        } // END of protocol-error-container definition.
    } // END of vrrp-protocol-error-top definition.
    grouping vrrp-packet-error-top {
        description
            "Grouping for VRRP packet error";
        container packet-error {
            config false;
            description
                "Virtual Router Redundancy Packet Error Notification";
            leaf error-reason  {
                type  ipi-vrrp-types:vrrp_error_reason_t;
                description "Protocol error reason";
            } // END of error-reason definition.

        } // END of packet-error-container definition.
    } // END of vrrp-packet-error-top definition.
    grouping vrrp-global-top {
        description
            "Grouping for VRRP Global";
        container global {
            description
                "Virtual Router Redundancy Protocol Global";
            container config {
                description
                    "Virtual Router Redundancy Protocol Global Configurations";
                uses vrrp-global-config;
            } // END of config-container definition.
            container state {
                config false;
                description
                    "Virtual Router Redundancy Protocol Global State";
                uses vrrp-global-config;
                uses vrrp-global-state;
            } // END of state-container definition.
            uses vrrp-global-session-state-top;
            uses vrrp-new-master-top;
            uses vrrp-protocol-error-top;
            uses vrrp-packet-error-top;
            uses vrrp-global-error-top;
        } // END of global-container definition.
    } // END of vrrp-global-top definition.


}
