/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : vr.yang
*
*/

submodule vr {

    belongs-to  ZebOS { prefix ZebOS; }
            include bridge;
            include pim;
            include mstp;
            include rip;
            include lacp;
            include dhcpc;
            include radius;
            include auth;
            include rib;
            include igmp;
            include pim4;
            include oambfd;
            include hqos;
            include mrib4;
            include vrrp;
            include vxlan;
            include switchportinterface;
            include vlan;
            include lag;
            include vrf;
            include interface;
            include keychain;
            include aclinterface;
            include cmm;
            include routemap;
            include ospf;
            include acl;
            include bgp;
            include pbb;
            include igmpsnooping;


    import cml_data_types {
        prefix cml_data_types;
    }

    description
        "Virtual router";


    revision "2016-10-29" {
        description "Added configurable attributes and operations.";
    }

    revision "2015-10-08" {
        description "Revisied on 2015-10-08.";
    }



    grouping vr-grouping {
        list vr {
             
            description
                "Virtual router object";

            config true;
            key "vrId";

            
            leaf vrId  {
                type  cml_data_types:CML_UINT32_T {
                     range "0..255";
                }
            } // END of vrId definition.

            leaf name  {
                type  cml_data_types:CML_STRING_T {
                    length "0..255";
                }
            } // END of name definition.


            list vrInstances {
                 
                description
                    "object for virtual router configurations";

                config true;
                key "vrName";

                
                leaf vrName  {
                    type  cml_data_types:CML_STRING_T {
                        length "1..12";
                    }
                } // END of vrName definition.

                leaf description  {
                    type  cml_data_types:CML_STRING_T {
                        length "0..255";
                    }
                } // END of description definition.

                leaf protocol  {
                    type  cml_data_types:CML_VR_PROTOCOL_T;  
                } // END of protocol definition.

            } // End of vrInstances-list
            uses bridge-grouping;
            uses spanningTree-grouping;
            uses pimDebug-grouping;
            uses pimTermDebug-grouping;
            uses mstpSpanningTree-grouping;
            uses mstpbridge-grouping;
            uses spanningPort-grouping;
            uses bridgePort-grouping;
            uses backboneBridge-grouping;
            uses backboneBridgeInstance-grouping;
            uses customerSpanningtree-grouping;
            uses ripConfiguration-grouping;
            uses nsmlacpInterface-grouping;
            uses nsmportInterface-grouping;
            uses DHCPClientInterface-grouping;
            uses Hostpdradius-grouping;
            uses radius-grouping;
            uses authPort-grouping;
            uses authmac-grouping;
            uses ribInterface-grouping;
            uses rib-grouping;
            uses mrib4Igmp-grouping;
            uses mrib4IgmpInterface-grouping;
            uses pim4Vrf-grouping;
            uses pim4Interface-grouping;
            uses pim4Debug-grouping;
            uses bfd-grouping;
            uses bfdInterface-grouping;
            uses qos-grouping;
            uses mrib4Vrf-grouping;
            uses mrib4Interface-grouping;
            uses Vrrp4Instance-grouping;
            uses Vrrp6Instance-grouping;
            uses vrrp-grouping;
            uses nsmnvo-grouping;
            uses switchportInterface-grouping;
            uses macAddressTable-grouping;
            uses vlanStacking-grouping;
            uses l2protocol-grouping;
            uses pvlan-grouping;
            uses vlanAccessMap-grouping;
            uses lacpInterface-grouping;
            uses vrf-grouping;
            uses interface-grouping;
            uses keychain-grouping;
            uses aclInterface-grouping;
            uses dmmMonitorPort-grouping;
            uses pbrConfig-grouping;
            uses ospf-grouping;
            uses ospfInterface-grouping;
            uses teLinkOspf-grouping;
            uses accessMasterIPv4-grouping;
            uses accessMasterIPv6-grouping;
            uses bgp-grouping;
            uses vrfTable-grouping;
            uses pbbInterface-grouping;
            uses igmpSnoopInterface-grouping;
        } // End of vr-list
    } // END of vr-grouping definition.


}
