/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-dhcp-relay-types.yang
*
*/

module ipi-dhcp-relay-types {

    yang-version 1.1;

    namespace   "http://www.ipinfusion.com/yang/ocnos/ipi-dhcp-relay-types";

    prefix "ipi-dhcp-relay-types";

    organization
        "IP Infusion Inc.";

    contact
        "Address: 3965 Freedom Circle, Suite 200, Santa Clara, CA 95054
         Phone: +1 408-400-1900
         E-mail: support@ipinfusion.com
         Web: http://www.ip        infusion.com/";

    description
        "YANG version of the ipi-dhcp-relay-types";


    revision "2021-09-03" {
        description "Update descriptions of attribute";
        reference " 0.4.0.";
    }

    revision "2021-06-11" {
        description "Changes to support DHCP L3VPN feature";
        reference " 0.3.0.";
    }

    revision "2020-12-15" {
        description "Change to have data-types in lower case instead of camel case";
        reference " 0.2.0.";
    }

    revision "2020-08-11" {
        description "Initial Version";
        reference " 0.1.0.";
    }



    typedef  dhcp_remote_id_enum_t {
        type enumeration {
            enum hostname {
                value 0;
                description "Use hostname as remote-id";
            }
        }
        description "type definition for DHCP_REMOTE_ID_ENUM_T";
    }

    typedef  dhcp_remote_id_t {
        type union {
            type dhcp_remote_id_enum_t {

            }
            type string {

            }
        }
        description "type definition for DHCP_REMOTE_ID_T";
    }

    typedef  dhcp6_pd_route_state_t {
        type enumeration {
            enum add {
                value 0;
                description "Addition of PD injected route";
            }
            enum delete {
                value 1;
                description "Deletion of PD injected route";
            }
        }
        description "type definition for DHCP6_PD_ROUTE_STATE_T";
    }

    typedef  dhcp_vpn_interface_direction_t {
        type enumeration {
            enum uplink {
                value 1;
                description "DHCP Relay uplink interface";
            }
            enum downlink {
                value 2;
                description "DHCP Relay downlink interface";
            }
        }
        description "type definition for DHCP_VPN_INTERFACE_DIRECTION_T";
    }

    typedef  dhcp_vpn_interface_type_t {
        type enumeration {
            enum l3vpn {
                value 1;
                description "L3VPN interface";
            }
            enum evpn {
                value 2;
                description "IP VRF IRB interface";
            }
        }
        description "type definition for DHCP_VPN_INTERFACE_TYPE_T";
    }

}
