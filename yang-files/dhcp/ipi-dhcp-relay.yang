/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-dhcp-relay.yang
*
*/

submodule ipi-dhcp-relay {

    yang-version 1.1;

    belongs-to  ipi-dhcp { prefix ipi-dhcp; }

    import feature-list {
        prefix feature-list;
        revision-date 2023-02-21;
    }

    import ipi-dhcp-relay-types {
        prefix ipi-dhcp-relay-types;
        revision-date 2021-09-03;
    }

    import ietf-inet-types {
        prefix inet;
        revision-date 2013-07-15;
    }

    import ietf-yang-types {
        prefix yang;
        revision-date 2013-07-15;
    }

    import ipi-interface {
        prefix ipi-interface;
        revision-date 2022-08-24;
    }

    import ipi-network-instance {
        prefix ipi-network-instance;
        revision-date 2022-06-01;
    }

    import ipi-vrf {
        prefix ipi-vrf;
        revision-date 2022-07-13;
    }

    organization
        "IP Infusion Inc.";

    contact
        "Address: 3965 Freedom Circle, Suite 200, Santa Clara, CA 95054
         Phone: +1 408-400-1900
         E-mail: support@ipinfusion.com
         Web: http://www.ipinfusion.com/";

    description
        "dhcp_relay_configuration";


    revision "2022-07-15" {
        description "Added autoPopulate tags in datamodel";
        reference " 0.6.2.";
    }

    revision "2022-07-04" {
        description "Added implicit_delete tags in datamodel";
        reference " 0.6.1.";
    }

    revision "2022-06-01" {
        description "Updated the yang file with feature";
        reference " 0.6.0.";
    }

    revision "2021-11-30" {
        description "Changes to support DHCP Relay across VRF feature";
        reference " 0.5.0.";
    }

    revision "2021-09-03" {
        description "Update descriptions of attribute";
        reference " 0.4.0.";
    }

    revision "2021-06-11" {
        description "Changes to support DHCP L3VPN feature";
        reference " 0.3.0.";
    }

    revision "2020-12-15" {
        description "Change to have data-types in lower case instead of camel case";
        reference " 0.2.0.";
    }

    revision "2020-08-11" {
        description "Initial Version";
        reference " 0.1.0.";
    }

    grouping relay-global-config {
        description
            "DHCP relay global configuration data attributes group";
        leaf disable-dhcpv4-relay  {
            type  empty;
            description "Use this attribute to disable the DHCP relay global config";
        } // END of disable-dhcpv4-relay definition.

        leaf disable-dhcpv6-relay  {
            type  empty;
            description "Use this attribute to disable the DHCP relay global config";
        } // END of disable-dhcpv6-relay definition.

    } // END of relay-global-config definition.
    grouping relay-ipv4-vpn-vrf-top {
        description
            "DHCPv4 relay VPN information grouping";
        container ipv4-vpn-links {
            description
                "Top level container for IPv4 DHCP Relay VPN config";

            list ipv4-vpn-link {
            when " /dhcp/relay/relay-agent/ipv4-vpn-links/ipv4-vpn-link/config/interface-direction ";
                key "interface-type";
                description
                    "DHCPv4 relay vpn configs";
                leaf interface-type  {
                    type  leafref {
                        path  "../config/interface-type";
                    }
                    description "DHCP relay vpn interface type";
                } // END of interface-type definition.

                container config {
                    description
                        "Configuration data for DHCP-relay on each vpn";
                    uses ipv4-vpn-link-attrs-config;
                } // END of config-container definition.
                container state {
                    config false;
                    description
                        "Operational data for DHCP-relay on each vpn";
                    uses ipv4-vpn-link-attrs-config;
                } // END of state-container definition.
            } // End of ipv4-vpn-link-list
        } // END of ipv4-vpn-links-container definition.
    } // END of relay-ipv4-vpn-vrf-top definition.
    grouping ipv4-vpn-link-attrs-config {
        description
            "Attrs for DHCPv4-relay vpn";
        leaf interface-type  {
            type  ipi-dhcp-relay-types:dhcp_vpn_interface_type_t;
            description "DHCP relay vpn interface type";
        } // END of interface-type definition.

        leaf interface-direction  {
            type  ipi-dhcp-relay-types:dhcp_vpn_interface_direction_t;
            mandatory true;
            description "DHCP relay vpn interface direction";
        } // END of interface-direction definition.

    } // END of ipv4-vpn-link-attrs-config definition.
    grouping relay-ipv6-vpn-vrf-top {
        description
            "DHCPv6 relay VPN information grouping";
        container ipv6-vpn-links {
            description
                "Top level container for IPv6 DHCP Relay VPN config";

            list ipv6-vpn-link {
            when " /dhcp/relay/relay-agent/ipv6-vpn-links/ipv6-vpn-link/config/interface-direction-v6 ";
                if-feature feature-list:HAVE_IPV6;
                key "interface-type-v6";
                description
                    "DHCPv6 relay vpn configs";
                leaf interface-type-v6  {
                    type  leafref {
                        path  "../config/interface-type-v6";
                    }
                    description "DHCPv6 relay vpn interface type";
                } // END of interface-type-v6 definition.

                container config {
                    description
                        "Configuration data for DHCP-relay on each vpn";
                    uses ipv6-vpn-link-attrs-config;
                } // END of config-container definition.
                container state {
                    config false;
                    description
                        "Operational data for DHCP-relay on each vpn";
                    uses ipv6-vpn-link-attrs-config;
                } // END of state-container definition.
            } // End of ipv6-vpn-link-list
        } // END of ipv6-vpn-links-container definition.
    } // END of relay-ipv6-vpn-vrf-top definition.
    grouping ipv6-vpn-link-attrs-config {
        description
            "Attrs for DHCPv6-relay vpn";
        leaf interface-type-v6  {
            type  ipi-dhcp-relay-types:dhcp_vpn_interface_type_t;
            description "DHCPv6 relay vpn interface type";
        } // END of interface-type-v6 definition.

        leaf interface-direction-v6  {
            type  ipi-dhcp-relay-types:dhcp_vpn_interface_direction_t;
            mandatory true;
            description "DHCPv6 relay vpn interface direction";
        } // END of interface-direction-v6 definition.

    } // END of ipv6-vpn-link-attrs-config definition.
    grouping relay-ipv4-dhcp-server-top {
        description
            "DHCPv4 relay Server address grouping";
        container ipv4-dhcp-servers {
            description
                "Top level container for IPv4 DHCP Relay Server address config";

            list ipv4-dhcp-server {
                key "ip-address";
                description
                    "DHCPv4 relay server address configs";
                leaf ip-address  {
                    type  leafref {
                        path  "../config/ip-address";
                    }
                    description "IPv4 address of the DHCP server";
                } // END of ip-address definition.

                container config {
                    description
                        "Configuration data for DHCP-relay server addr";
                    uses ipv4-server-addr-attrs-config;
                } // END of config-container definition.
                container state {
                    config false;
                    description
                        "Operational data for DHCP-relay server address";
                    uses ipv4-server-addr-attrs-config;
                } // END of state-container definition.
            } // End of ipv4-dhcp-server-list
        } // END of ipv4-dhcp-servers-container definition.
    } // END of relay-ipv4-dhcp-server-top definition.
    grouping ipv4-server-addr-attrs-config {
        description
            "Attrs for DHCPv4-relay server address";
        leaf ip-address  {
            type  inet:ipv4-address;
            description "IPv4 address of the DHCP server";
        } // END of ip-address definition.

        leaf dhcpv4-server-global-vrf  {
            type  leafref {
                path  "/ipi-network-instance:network-instances/ipi-network-instance:network-instance/ipi-vrf:vrf/ipi-vrf:config/ipi-vrf:vrf-name";
            }
            description "This attributes defines the VRF in which the DHCPv4 relay server is
                        present";
        } // END of dhcpv4-server-global-vrf definition.

    } // END of ipv4-server-addr-attrs-config definition.
    grouping relay-ipv6-dhcp-server-top {
        description
            "DHCPv6 relay Server address grouping";
        container ipv6-dhcp-servers {
            if-feature feature-list:HAVE_IPV6;
            description
                "Top level container for IPv6 DHCP Relay Server address config";

            list ipv6-dhcp-server {
                key "ipv6-address";
                description
                    "DHCPv6 relay server address configs";
                leaf ipv6-address  {
                    type  leafref {
                        path  "../config/ipv6-address";
                    }
                    description "IPv6 address of the DHCP server";
                } // END of ipv6-address definition.

                container config {
                    description
                        "Configuration data for DHCP-relay server addr";
                    uses ipv6-server-addr-attrs-config;
                } // END of config-container definition.
                container state {
                    config false;
                    description
                        "Operational data for DHCP-relay server addr";
                    uses ipv6-server-addr-attrs-config;
                } // END of state-container definition.
            } // End of ipv6-dhcp-server-list
        } // END of ipv6-dhcp-servers-container definition.
    } // END of relay-ipv6-dhcp-server-top definition.
    grouping ipv6-server-addr-attrs-config {
        description
            "Attrs for DHCPv6-relay server address";
        leaf ipv6-address  {
            if-feature feature-list:HAVE_IPV6;
            type  inet:ipv6-address;
            description "IPv6 address of the DHCP server";
        } // END of ipv6-address definition.

        leaf dhcpv6-server-global-vrf  {
            type  leafref {
                path  "/ipi-network-instance:network-instances/ipi-network-instance:network-instance/ipi-vrf:vrf/ipi-vrf:config/ipi-vrf:vrf-name";
            }
            description "This attributes defines the VRF in which the DHCPv6 relay server is
                        present";
        } // END of dhcpv6-server-global-vrf definition.

    } // END of ipv6-server-addr-attrs-config definition.
    grouping relay-global-vrf-config {
        description
            "DHCP relay VRF level information grouping";
        leaf link-selection-source-ip  {
            type  inet:ipv4-address;
            description "Enable link selection sub-option (5) in the option-82 in DHCP packet";
        } // END of link-selection-source-ip definition.

        leaf enable-option82  {
            type  empty;
            description "Enable the device to insert and remove option-82 information on DHCP
                        packets forwarded by the DHCP relay agent.";
        } // END of enable-option82 definition.

        leaf enable-dhcpv6-pd-route-injection  {
            if-feature feature-list:HAVE_IPV6;
            type  empty;
            description "Enable the route installation from the prefixes learned through prefix
                        delegation.";
        } // END of enable-dhcpv6-pd-route-injection definition.

        leaf remote-id  {
            when " /dhcp/relay/relay-agent/config/enable-option82 ";
            type  ipi-dhcp-relay-types:dhcp_remote_id_t;
            description "Remote host identifier. Use option 82 to provide the DHCP server
                        information about the DHCP client";
        } // END of remote-id definition.

        leaf subscriber-id  {
            type  string {
                length "1..1965";
                pattern "[^?' =,>|]+";
            }
            description "Subscriber identifier. Use this option to allows the service provider
                        to assign/activate subscriber-specific actions";
        } // END of subscriber-id definition.

    } // END of relay-global-vrf-config definition.
    grouping relay-interface-config {
        description
            "Configuration data for DHCP-relay on each interface";
        leaf ipv4-relay-interface  {
            when " not(/dhcp/relay/interfaces/interface/config/ipv4-uplink-interface) ";
            type  empty;
            description "Enable relay on Client facing interface";
        } // END of ipv4-relay-interface definition.

        leaf ipv4-uplink-interface  {
            when " not(/dhcp/relay/interfaces/interface/config/ipv4-relay-interface) ";
            type  empty;
            description "Specify the interface as an uplink interface(Server facing)";
        } // END of ipv4-uplink-interface definition.

        leaf ipv6-relay-interface  {
            when " not(/dhcp/relay/interfaces/interface/config/ipv6-uplink-interface) ";
            if-feature feature-list:HAVE_IPV6;
            type  empty;
            description "Enable IPv6 relay on Client facing interface";
        } // END of ipv6-relay-interface definition.

        leaf ipv6-uplink-interface  {
            when " not(/dhcp/relay/interfaces/interface/config/ipv6-relay-interface) ";
            if-feature feature-list:HAVE_IPV6;
            type  empty;
            description "Specify the interface as an uplink interface(Server facing)";
        } // END of ipv6-uplink-interface definition.

    } // END of relay-interface-config definition.
    grouping relay-stats {
        description
            "DHCP Relay statistics";
        leaf bogus-giaddr-drops  {
            type  uint32;
            description "Packets sent to us to relay back to a client, but with a bogus giaddr";
        } // END of bogus-giaddr-drops definition.

        leaf client-packets-relayed  {
            type  uint32;
            description "Packets relayed from client to server";
        } // END of client-packets-relayed definition.

        leaf server-packet-errors  {
            type  uint32;
            description "Errors sending packets to servers";
        } // END of server-packet-errors definition.

        leaf server-packets-relayed  {
            type  uint32;
            description "Packets relayed from server to client";
        } // END of server-packets-relayed definition.

        leaf client-packet-errors  {
            type  uint32;
            description "Errors sending packets to clients";
        } // END of client-packet-errors definition.

        leaf agent-option-errors  {
            type  uint32;
            description "Number of packets forwarded without agent options because there was no
                        room";
        } // END of agent-option-errors definition.

        leaf corrupt-agent-options  {
            type  uint32;
            description "Number of packets dropped because relay agent information option was
                        bad";
        } // END of corrupt-agent-options definition.

        leaf missing-agent-option  {
            type  uint32;
            description "Number of packets dropped because no RAI option matching our ID was
                        found";
        } // END of missing-agent-option definition.

        leaf bad-circuit-id  {
            type  uint32;
            description "Circuit ID option in matching RAI option did not match any known
                        circuit ID";
        } // END of bad-circuit-id definition.

        leaf missing-circuit-id  {
            type  uint32;
            description "Circuit ID option in matching RAI option was missing";
        } // END of missing-circuit-id definition.

        leaf circuit-id  {
            type  string {
                length "0..1965";
                pattern "[^?' =,>|]*";
            }
            description "Circuit ID";
        } // END of circuit-id definition.

    } // END of relay-stats definition.
    grouping relay-delegated-prefixes {
        description
            "DHCPv6 Prefix Delegation learnt prefix details";

        list dhcpv6-delegated-prefixes {
            if-feature feature-list:HAVE_IPV6;
            key "interface-name";
            config false;
            description
                "Delegated prefix list";
            leaf interface-name  {
                type  leafref {
                    path  "../state/interface-name";
                }
                description "DHCP client facing interface, which is part of the LAN network";
            } // END of interface-name definition.

            container state {
                config false;
                description
                    "Operational state data";
                uses dhcpv6-delegated-prefixes-attrs;
            } // END of state-container definition.
        } // End of dhcpv6-delegated-prefixes-list
    } // END of relay-delegated-prefixes definition.
    grouping dhcpv6-delegated-prefixes-attrs {
        description
            "DHCPv6 Prefix Delegation learnt prefix attrs";
        leaf interface-name  {
            type  string {
                length "1..1965";
                pattern "[^?' =,>|]+";
            }
            description "DHCP client facing interface, which is part of the LAN network";
        } // END of interface-name definition.

        leaf next-hop  {
            type  inet:ipv6-address;
            description "DHCP client interface linklocal adddress";
        } // END of next-hop definition.

        leaf prefix  {
            type  inet:ipv6-prefix;
            description "Delegated prefix";
        } // END of prefix definition.

        leaf preferred-lifetime  {
            type  uint32;
            units "seconds";
            description "Specifies how long the prefix remains preferred in seconds";
        } // END of preferred-lifetime definition.

        leaf maximum-lifetime  {
            type  uint32;
            units "seconds";
            description "Specifies how long the prefix remains validin seconds";
        } // END of maximum-lifetime definition.

        leaf prefix-start-time  {
            type  yang:date-and-time {
                pattern "\\d{4}-\\d{2}-\\d{2}T\\d{2}:\\d{2}:\\d{2}(\\.\\d+)?(Z|[\\+\\-]\\d{2}:\\d{2})";
                }
                description "The time when the prefix was learned";
            } // END of prefix-start-time definition.

            leaf prefix-expiry-time  {
                type  yang:date-and-time {
                    pattern "\\d{4}-\\d{2}-\\d{2}T\\d{2}:\\d{2}:\\d{2}(\\.\\d+)?(Z|[\\+\\-]\\d{2}:\\d{2})";
                    }
                    description "The time when the prefix would expire";
                } // END of prefix-expiry-time definition.

                leaf state  {
                    type  ipi-dhcp-relay-types:dhcp6_pd_route_state_t;
                    description "Notification route add/delete input";
                } // END of state definition.

    } // END of dhcpv6-delegated-prefixes-attrs definition.
    grouping relay-interface-top {
        description
            "DHCP relay interface level information grouping";
        container interfaces {
            description
                "Top level container for DHCP relay on each interface";

            list interface {
            // when " !ipi-interface:interfaces/interface/config/enable-switchport ";
                key "name";
                description
                    "List of interfaces mapped with DHCP relay";
                leaf name  {
                    type  leafref {
                        path  "/ipi-interface:interfaces/ipi-interface:interface/ipi-interface:name";
                    }
                    description "The textual name of the interface. The value of this object should be
                                the name of the interface as assigned by the local device and should
                                be suitable for use in commands entered at the device's `console'.
                                This might be a text name, such as `le0' or a simple port number, such
                                as `1', depending on the interface naming syntax of the device. If
                                several entries in the ifTable together represent a single interface
                                as named by the device, then each will have the same value of name.
                                Note that for an agent which responds to SNMP queries concerning an
                                interface on some other (proxied) device, then the value of name for
                                such an interface is the proxied device's local name for it. If there
                                is no local name, or this object is otherwise not applicable, then
                                this object contains a zero-length string.";
                } // END of name definition.

                container config {
                    description
                        "Configuration data for DHCP relay on each interface";
                    uses relay-interface-config;
                } // END of config-container definition.
                container state {
                    config false;
                    description
                        "Operational state data";
                    uses relay-interface-config;
                } // END of state-container definition.
            } // End of interface-list
        } // END of interfaces-container definition.
    } // END of relay-interface-top definition.
    grouping relay-global-top {
        description
            "DHCP relay global level information grouping";

        list relay-agent {
            key "vrf-name";
            description
                "List of Virtual Routing and Forwarding instances on the router";
            leaf vrf-name  {
                type  leafref {
                    path  "/ipi-network-instance:network-instances/ipi-network-instance:network-instance/ipi-vrf:vrf/ipi-vrf:config/ipi-vrf:vrf-name";
                }
                description "VPN routing/forwarding Instance name";
            } // END of vrf-name definition.

            container config {
                description
                    "Configuration parameters relating to a VRF instance";
                uses relay-global-vrf-config;
            } // END of config-container definition.
            container state {
                config false;
                description
                    "Operational state data";
                uses relay-global-vrf-config;
                uses relay-stats;
            } // END of state-container definition.
            uses relay-ipv4-vpn-vrf-top;
            uses relay-ipv6-vpn-vrf-top;
            uses relay-delegated-prefixes;
            uses relay-ipv4-dhcp-server-top;
            uses relay-ipv6-dhcp-server-top;
        } // End of relay-agent-list
        container global {
            description
                "DHCP relay global level information";
            container config {
                description
                    "Configuration data for DHCP relay global level";
                uses relay-global-config;
            } // END of config-container definition.
            container state {
                config false;
                description
                    "Operational state data";
                uses relay-global-config;
            } // END of state-container definition.
        } // END of global-container definition.
    } // END of relay-global-top definition.

    grouping  relay-grouping {
    description
        "DHCP relay related operations";
    container relay {
        when " not(/dhcp/global/config/disable-dhcp-feature) ";
        if-feature feature-list:HAVE_HOSTPD;
        if-feature feature-list:HAVE_DHCP_CLIENT;
        if-feature feature-list:HAVE_DHCP_SERVER_OR_HAVE_DHCP_SNOOP_OR_HAVE_DHCP_UPDATE_STYLE;
        description
            "DHCP relay related operations";
        uses relay-global-top;
        uses relay-interface-top;
    } // END of relay-container definition.
    } // END of relay-grouping definition.


}
