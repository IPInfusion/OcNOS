/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-dhcp-client.yang
*
*/

submodule ipi-dhcp-client {

    yang-version 1.1;

    belongs-to  ipi-dhcp { prefix ipi-dhcp; }

    import feature-list {
        prefix feature-list;
        revision-date 2023-02-21;
    }

    import ipi-interface {
        prefix ipi-interface;
        revision-date 2022-08-24;
    }

    import ietf-inet-types {
        prefix inet;
        revision-date 2013-07-15;
    }

    import cml-data-types {
        prefix cml-data-types;
        revision-date 2022-09-30;
    }

    organization
        "IP Infusion Inc.";

    contact
        "Address: 3965 Freedom Circle, Suite 200, Santa Clara, CA 95054
         Phone: +1 408-400-1900
         E-mail: support@ipinfusion.com
         Web: http://www.ipinfusion.com/";

    description
        "dhcp_client_configuration";


    revision "2022-06-01" {
        description "Updated the yang file with feature";
        reference " 0.5.0.";
    }

    revision "2021-11-16" {
        description "Added some if-feature to fix customer SKU compilation";
        reference " 0.4.0.";
    }

    revision "2021-09-03" {
        description "Update descriptions of attribute";
        reference " 0.3.0.";
    }

    revision "2020-12-15" {
        description "Change to have data-types in lower case instead of camel case";
        reference " 0.2.0.";
    }

    revision "2020-08-11" {
        description "Initial Version";
        reference " 0.1.0.";
    }

    grouping client-interface-config {
        description
            "Configuration data for dhcp-client on each interface";
        leaf request-ipv4-dns  {
            type  empty;
            description "Use this attribute to to add an option to a DHCP request.";
        } // END of request-ipv4-dns definition.

        leaf request-log-server  {
            if-feature feature-list:HAVE_SYSLOG;
            type  empty;
            description "Use this attribute to to add an option to a DHCP request.";
        } // END of request-log-server definition.

        leaf request-host-name  {
            type  empty;
            description "Use this attribute to to add an option to a DHCP request.";
        } // END of request-host-name definition.

        leaf request-ntp-server  {
            if-feature feature-list:HAVE_HOSTP_NTP;
            type  empty;
            description "Use this attribute to to add an option to a DHCP request.";
        } // END of request-ntp-server definition.

        leaf request-ipv6-dns  {
            if-feature feature-list:HAVE_IPV6;
            type  empty;
            description "Use this attribute to to add an option to a DHCP request.";
        } // END of request-ipv6-dns definition.

        leaf request-ipv6-domain-list  {
            if-feature feature-list:HAVE_IPV6;
            type  empty;
            description "Use this attribute to specifies a search list of Domain Names to be
                        used by the client to locate not-fully-qualified domain names.";
        } // END of request-ipv6-domain-list definition.

        leaf request-ipv6-ntp-server  {
            if-feature feature-list:HAVE_IPV6;
            type  empty;
            description "Use this attribute to specifies a list of local NTP servers available
                        for the client to synchronize their clocks.";
        } // END of request-ipv6-ntp-server definition.

        leaf request-ipv6-rapid-commit  {
            if-feature feature-list:HAVE_IPV6;
            type  empty;
            description "Use this attribute to indicate the clients to enter into rapid-commit
                        with the server.";
        } // END of request-ipv6-rapid-commit definition.

        leaf request-ipv6-vendor-opts  {
            if-feature feature-list:HAVE_IPV6;
            type  empty;
            description "Use this attribute to specify a 32-bit Enterprise-ID number.";
        } // END of request-ipv6-vendor-opts definition.

        leaf ipv6-information-request  {
            if-feature feature-list:HAVE_IPV6;
            type  empty;
            description "Use this attribute to get only stateless configuration parameters
                        (i.e., without address).";
        } // END of ipv6-information-request definition.

        leaf ipv6-dad-wait-time  {
            if-feature feature-list:HAVE_IPV6;
            type  uint16 {
                 range "1..600"  {
                    description "1..600: Supported range 1 - 600";
                 }
            }
            description "Use this attribute to Specify maximum time (in seconds) that the
                        client should wait for the duplicate address detection (DAD) to
                        complete on an interface.";
        } // END of ipv6-dad-wait-time definition.

        leaf ipv6-client-duid-type  {
            if-feature feature-list:HAVE_IPV6;
            type  cml-data-types:dhcp6_duid_type_t;
            description "Use this attribute to configure duid type(ll or llt).";
        } // END of ipv6-client-duid-type definition.

        leaf request-ipv6-prefix  {
            if-feature feature-list:HAVE_IPV6;
            type  string {
                length "1..1965";
                pattern "[^?' =,>|]+";
            }
            description "Use this attribute to add an option to a DHCP request.";
        } // END of request-ipv6-prefix definition.

    } // END of client-interface-config definition.
    grouping learned-prefix-state {
        description
            "Learnt prefix parameters";
        leaf learnt-prefix  {
            type  inet:ipv6-prefix;
            config false;
            description "Learnt prefix addr from DHCP server";
        } // END of learnt-prefix definition.

        leaf max-lifetime  {
            type  uint32;
            config false;
            description "Learnt Prefix Max lifetime in secs";
        } // END of max-lifetime definition.

        leaf preferred-lifetime  {
            type  uint32;
            config false;
            description "Learnt Prefix Preffered life time in secs";
        } // END of preferred-lifetime definition.

    } // END of learned-prefix-state definition.
    grouping prefix-ipv6-addr-config {
        description
            "IPv6 address configured using learnt Prefix from DHCP Server";
        leaf prefix-name  {
            type  string {
                length "1..1965";
                pattern "[^?' =,>|]+";
            }
            description "";
        } // END of prefix-name definition.

        leaf suffix-ipv6-addr  {
            type  string {
                length "1..1965";
                pattern "[^?' =,>|]+";
            }
            description "";
        } // END of suffix-ipv6-addr definition.

    } // END of prefix-ipv6-addr-config definition.
    grouping prefix-ipv6-addr-list-entry {
        description
            "Configure the IPv6 address using the Prefix learned from DHCP Server";
        container prefix-ipv6-addresses {
            if-feature feature-list:HAVE_IPV6;
            description
                "IPv6 address configured using learnt Prefix from DHCP Server";

            list prefix-ipv6-address-entry {
                key "prefix-name suffix-ipv6-addr";
                description
                    "IPv6 address configured using learnt Prefix from DHCP Server";
                leaf prefix-name  {
                    type  leafref {
                        path  "../config/prefix-name";
                    }
                    description "";
                } // END of prefix-name definition.

                leaf suffix-ipv6-addr  {
                    type  leafref {
                        path  "../config/suffix-ipv6-addr";
                    }
                    description "";
                } // END of suffix-ipv6-addr definition.

                container config {
                    description
                        "IPv6 address configured using learnt Prefix from DHCP Server";
                    uses prefix-ipv6-addr-config;
                } // END of config-container definition.
                container state {
                    config false;
                    description
                        "Prefix addr Operational state data";
                    uses prefix-ipv6-addr-config;
                } // END of state-container definition.
            } // End of prefix-ipv6-address-entry-list
        } // END of prefix-ipv6-addresses-container definition.
    } // END of prefix-ipv6-addr-list-entry definition.
    grouping dhcp-interface-top {
        description
            "DHCP interface related operations";
        container interfaces {
            description
                "Top level container for dhcp-client on each interface";

            list interface {
            // when " !ipi-interface:interfaces/interface/config/enable-switchport ";
                key "name";
                description
                    "List of interfaces mapped with dhcp-client";
                leaf name  {
                    type  leafref {
                        path  "/ipi-interface:interfaces/ipi-interface:interface/ipi-interface:name";
                    }
                    description "The textual name of the interface. The value of this object should be
                                the name of the interface as assigned by the local device and should
                                be suitable for use in commands entered at the device's `console'.
                                This might be a text name, such as `le0' or a simple port number, such
                                as `1', depending on the interface naming syntax of the device. If
                                several entries in the ifTable together represent a single interface
                                as named by the device, then each will have the same value of name.
                                Note that for an agent which responds to SNMP queries concerning an
                                interface on some other (proxied) device, then the value of name for
                                such an interface is the proxied device's local name for it. If there
                                is no local name, or this object is otherwise not applicable, then
                                this object contains a zero-length string.";
                } // END of name definition.

                container config {
                    description
                        "Configuration data for dhcp-client on each interface";
                    uses client-interface-config;
                } // END of config-container definition.
                container state {
                    config false;
                    description
                        "Operational state data";
                    uses client-interface-config;
                } // END of state-container definition.
                container learned-prefix {
                    config false;
                    description
                        "Learnt prefix parameters";
                    container state {
                        config false;
                        description
                            "Operational state data";
                        uses learned-prefix-state;
                    } // END of state-container definition.
                } // END of learned-prefix-container definition.
                uses prefix-ipv6-addr-list-entry;
            } // End of interface-list
        } // END of interfaces-container definition.
    } // END of dhcp-interface-top definition.

    grouping  client-grouping {
    description
        "DHCP client related operations";
    container client {
        when " not(/dhcp/global/config/disable-dhcp-feature) ";
        if-feature feature-list:HAVE_DHCP_CLIENT;
        if-feature feature-list:HAVE_DHCP_SERVER_OR_HAVE_DHCP_SNOOP_OR_HAVE_DHCP_UPDATE_STYLE;
        description
            "DHCP client related operations";
        uses dhcp-interface-top;
    } // END of client-container definition.
    } // END of client-grouping definition.


}
