/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-time-range.yang
*
*/

module ipi-time-range {

    yang-version 1.1;

    namespace   "http://www.ipinfusion.com/yang/ocnos/ipi-time-range";

    prefix "ipi-time-range";

    organization
        "IP Infusion Inc.";

    contact
        "Address: 3965 Freedom Circle, Suite 200, Santa Clara, CA 95054
         Phone: +1 408-400-1900
         E-mail: support@ipinfusion.com
         Web: http://www.ipinfusion.com/";

    description
        "Datamodel for Time Range definitions";


    revision "2022-06-01" {
        description "Updated the yang file with feature";
        reference " 0.3.0.";
    }

    revision "2021-08-19" {
        description "Corrected time-range datamodel as per Open Config style";
        reference "Initial Version";
    }

    revision "2021-02-12" {
        description "Initial Version";
        reference "Initial Version";
    }



    typedef  time_range_date_time_t {
        type string {
            pattern "([0-9]|[01][0-9]|2[0123]):([0-9]|[012345][0-9]) (([12][0-9])|(3[01])|([0][1-9])) ((([a-z])|([A-Z])){2,8}) ((199[5-9])|(20[012][0-9])|(203[0-5]))";
        }
        description "type definition for TIME_RANGE_DATE_TIME_T";
    }

    typedef  time_range_frequency_flag_t {
        type enumeration {
            enum daily {
                value 127;
                description "Daily frequency";
            }
            enum hourly {
                value 256;
                description "Hourly frequency";
            }
            enum weekly {
                value 512;
                description "Weekly frequency";
            }
        }
        description "type definition for TIME_RANGE_FREQUENCY_FLAG_T";
    }

    typedef  time_range_frequency_day_t {
        type string;
        description "type definition for TIME_RANGE_FREQUENCY_DAY_T";
    }

    typedef  time_range_frequency_t {
        type union {
            type time_range_frequency_flag_t {

            }
            type time_range_frequency_day_t {

            }
        }
        description "type definition for TIME_RANGE_FREQUENCY_T";
    }

    typedef  time_range_after_t {
        type uint32 {
             range 0..4294967295;
        }
        description "type definition for TIME_RANGE_AFTER_T";
    }

    typedef  time_range_now_t {
        type string;
        description "type definition for TIME_RANGE_NOW_T";
    }

    typedef  time_range_relative_time_t {
        type union {
            type time_range_after_t {

            }
            type time_range_now_t {

            }
        }
        description "type definition for TIME_RANGE_RELATIVE_TIME_T";
    }    grouping tr-range-config {
        description
            "Grouping for time range configuration";
        leaf name  {
            type  string {
                length "1..1965";
                pattern "[^?' =,>|]+";
            }
            description "";
        } // END of name definition.

    } // END of tr-range-config definition.
    grouping frequency-option-config {
        description
            "frequency configs";
        leaf frequency  {
            when " /ipi-time-range:time-ranges/ipi-time-range:time-range/ipi-time-range:start-time-options/ipi-time-range:config/ipi-time-range:absolute-start-time and /ipi-time-range:time-ranges/ipi-time-range:time-range/ipi-time-range:end-time-options/ipi-time-range:config/ipi-time-range:absolute-end-time ";
            type  time_range_frequency_t;
            description "Frequency (hourly, daily, weekly)";
        } // END of frequency definition.

    } // END of frequency-option-config definition.
    grouping start-time-option-config {
        description
            "Definition of parameters inside the created time range";
        choice start-time {
            description
                "Use this attribute to choose between absolute and relative start-time.";
            case absolute-start-time {

                description
                    "Use this attribute to choose absolute start-time.";

                leaf absolute-start-time  {
                    type  time_range_date_time_t {
                        length "1..1965";
                    }
                    description "Start time hour and minute";
                } // END of absolute-start-time definition.

            }
            case relative-start-time {

                description
                    "Use this attribute to choose relative start-time.";

                leaf relative-start-time  {
                    type  time_range_relative_time_t;
                    description "Configure the start-time of the time-range to be now or after sometime";
                } // END of relative-start-time definition.

            }
        } // END of start-time-choice definition.
    } // END of start-time-option-config definition.
    grouping end-time-option-config {
        description
            "Definition of parameters inside the created time range";
        choice end-time {
            description
                "Use this attribute to choose between absolute and relative end-time.";
            case absolute-end-time {

                description
                    "Use this attribute to choose absolute end-time.";

                leaf absolute-end-time  {
                    type  time_range_date_time_t {
                        length "1..1965";
                    }
                    description "End time hour and minute";
                } // END of absolute-end-time definition.

            }
            case relative-end-time {

                description
                    "Use this attribute to choose relative end-time.";

                leaf relative-end-time  {
                    type  string {
                        length "1..1965";
                        pattern "([0-9]+)";
                    }
                    description "Relative time in minutes";
                } // END of relative-end-time definition.

            }
        } // END of end-time-choice definition.
    } // END of end-time-option-config definition.
    grouping start-time-option-top {
        description
            "Start time option configuration";
        container start-time-options {
            description
                "Definition of parameters inside the created time range";
            container config {
                description
                    "Configuration data";
                uses start-time-option-config;
            } // END of config-container definition.
            container state {
                config false;
                description
                    "Operational state data";
                uses start-time-option-config;
            } // END of state-container definition.
        } // END of start-time-options-container definition.
    } // END of start-time-option-top definition.
    grouping end-time-option-top {
        description
            "Start time option configuration";
        container end-time-options {
            description
                "Definition of parameters inside the created time range";
            container config {
                description
                    "Configuration data";
                uses end-time-option-config;
            } // END of config-container definition.
            container state {
                config false;
                description
                    "Operational state data";
                uses end-time-option-config;
            } // END of state-container definition.
        } // END of end-time-options-container definition.
    } // END of end-time-option-top definition.
    grouping frequency-option-top {
        description
            "Start time option configuration";
        container frequency-options {
            description
                "Definition of parameters inside the created time range";
            container config {
                description
                    "Configuration data";
                uses frequency-option-config;
            } // END of config-container definition.
            container state {
                config false;
                description
                    "Operational state data";
                uses frequency-option-config;
            } // END of state-container definition.
        } // END of frequency-options-container definition.
    } // END of frequency-option-top definition.

    grouping  time-ranges-grouping {
    description
        "All configured time ranges on the device";
    container time-ranges {
        description
            "All configured time ranges on the device";

        list time-range {
            key "name";
            description
                "This defines a YANG data model for creating Time Ranges";
            leaf name  {
                type  leafref {
                    path  "../config/name";
                }
                description "";
            } // END of name definition.

            container config {
                description
                    "time-range configuration container";
                uses tr-range-config;
            } // END of config-container definition.
            container state {
                config false;
                description
                    "time-range state container";
                uses tr-range-config;
            } // END of state-container definition.
            uses start-time-option-top;
            uses end-time-option-top;
            uses frequency-option-top;
        } // End of time-range-list
    } // END of time-ranges-container definition.
    } // END of time-ranges-grouping definition.

    uses time-ranges-grouping;

}
