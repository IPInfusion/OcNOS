/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : aaa.yang
*
*/

submodule aaa {

    belongs-to  ZebOS { prefix ZebOS; }
    include vrf;
    include tacacs;
    include radius;


    import cml_data_types {
        prefix cml_data_types;
    }

    description
        "Layer-3 aaa configurations";


    revision "2016-12-27" {
        description "Added snmp oid and documentation tag.";
    }

    revision "2016-10-28" {
        description "Initial version of AAA datamodel.";
    }


    grouping  aaa-grouping {
    container aaa {
                config true;

        description
            "aaa related commands";

        leaf vrfName  {
            type  cml_data_types:CML_STRING_T {
                length "0..255";
            }
            default "default";
        } // END of vrfName definition.

        leaf defaultAccounting  {
            type  cml_data_types:CML_BOOL_T;  
        } // END of defaultAccounting definition.

        leaf acctGroup  {
            type  cml_data_types:CML_STRING_T {
                length "0..255";
            }
            description "aaa accounting details group";
        } // END of acctGroup definition.

        leaf acctLocal  {
            type  cml_data_types:CML_BOOL_T;  
            description "aaa accounting details local";
        } // END of acctLocal definition.

        leaf errorEnable  {
            type  cml_data_types:CML_BOOL_T;  
            description "aaa authentication login";
        } // END of errorEnable definition.

        leaf authDefault  {
            type  cml_data_types:CML_BOOL_T;  
        } // END of authDefault definition.

        leaf authDefaultGroup  {
            type  cml_data_types:CML_STRING_T {
                length "0..255";
            }
            description "aaa authentication login default group";
        } // END of authDefaultGroup definition.

        leaf authMaxfail  {
            type  cml_data_types:CML_UINT8_T {
                 range "1..25";
            }
            default "3";
            description "aaa local authentication attempts max-fail";
        } // END of authMaxfail definition.

        leaf authDefaultFallback  {
            type  cml_data_types:CML_BOOL_T;  
            description "aaa authentication login default fallback error";
        } // END of authDefaultFallback definition.

        leaf authLocalDefault  {
            type  cml_data_types:CML_BOOL_T;  
            description "aaa authentication login default local";
        } // END of authLocalDefault definition.

        leaf authNoneDefault  {
            type  cml_data_types:CML_BOOL_T;  
            description "aaa authentication login default none";
        } // END of authNoneDefault definition.

        leaf debugaaa  {
            type  cml_data_types:CML_BOOL_T;  
            description "debug aaa";
        } // END of debugaaa definition.

        leaf debugaaaConfig  {
            type  cml_data_types:CML_BOOL_T;  
        } // END of debugaaaConfig definition.


        list aaaGroupServerNameRadius {
             
            description
                "aaaGroupServerNameRadius";

            config true;
            key "groupWordRadius";

            
            leaf groupWordRadius  {
                type  cml_data_types:CML_STRING_T {
                    length "1..127";
                }
            } // END of groupWordRadius definition.


            list aaaRadiusServer {
                 
                description
                    "aaaRadiusServer";

                config true;
                key "hostAddr";

                
                leaf vrfName  {
                    type  cml_data_types:CML_STRING_T {
                        length "0..255";
                    }
                    default "default";
                } // END of vrfName definition.

                leaf hostAddr  {
                    type  cml_data_types:CML_HOSTPNAME_T;  
                } // END of hostAddr definition.

            } // End of aaaRadiusServer-list
        } // End of aaaGroupServerNameRadius-list

        list aaaGroupServerNameTacacs {
             
            description
                "aaaGroupServerNameTacacs";

            config true;
            key "groupWordTacacs";

            
            leaf groupWordTacacs  {
                type  cml_data_types:CML_STRING_T {
                    length "1..127";
                }
            } // END of groupWordTacacs definition.


            list aaaTacacsServer {
                 
                description
                    "aaaTacacsServer";

                config true;
                key "hostAddr";

                
                leaf vrfName  {
                    type  cml_data_types:CML_STRING_T {
                        length "0..255";
                    }
                    default "default";
                } // END of vrfName definition.

                leaf hostAddr  {
                    type  cml_data_types:CML_HOSTNAME_T;  
                } // END of hostAddr definition.

            } // End of aaaTacacsServer-list
        } // End of aaaGroupServerNameTacacs-list
        container console {
                        config true;

            description
                "console";

            leaf authConsoleGroup  {
                type  cml_data_types:CML_STRING_T {
                    length "0..255";
                }
                description "aaa authentication login console";
            } // END of authConsoleGroup definition.

            leaf authConsoleFallback  {
                type  cml_data_types:CML_BOOL_T;  
                description "aaa authentication login console fallback error";
            } // END of authConsoleFallback definition.

            leaf authLocal  {
                type  cml_data_types:CML_BOOL_T;  
                description "aaa authentication login console";
            } // END of authLocal definition.

            leaf authNone  {
                type  cml_data_types:CML_BOOL_T;  
            } // END of authNone definition.

        } // END of console-container definition.
    } // END of aaa-container definition.
    } // END of aaa-container definition.


}
