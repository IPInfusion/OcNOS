/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-authentication-radius.yang
*
*/

module ipi-authentication-radius {

    yang-version 1.1;

    namespace   "http://www.ipinfusion.com/yang/ocnos/ipi-authentication-radius";

    prefix "ipi-authentication-radius";

    import ietf-inet-types {
        prefix inet;
        revision-date 2013-07-15;
    }

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "Layer-3 authentication radius configurations";


    revision "2022-06-01" {
        description "Updated the yang file with feature";
        reference " 0.6.0.";
    }

    revision "2022-04-07" {
        description "Using new type of key cipher";
        reference " 0.5.0.";
    }

    revision "2022-04-01" {
        description "Added some state attributes";
        reference " 0.4.0.";
    }

    revision "2022-03-18" {
        description "Changed length for key-string attributes";
        reference " 0.3.0.";
    }

    revision "2022-01-28" {
        description "Restructured module in accordance with OpenConfig style";
        reference " 0.2.0.";
    }

    revision "2018-06-21" {
        description "Initial Version";
        reference " 0.1.0.";
    }

    grouping auth-radius-host-state-top {
        description
            "Grouping for Authentication Radius Host state data";
        leaf next-radius-message-id  {
            type  uint8;
            description "Next radius message id for radius host.";
        } // END of next-radius-message-id definition.

        leaf encryption-key-operational  {
            type  string {
                length "1..1965";
                pattern "[^?' =,>|]+";
            }
            description "Key shared between the device and RADIUS servers for radius host.";
        } // END of encryption-key-operational definition.

        leaf host-port-operational  {
            type  uint16;
            description "Radius client port number for radius host.";
        } // END of host-port-operational definition.

        leaf host-timeout-operational  {
            type  uint8;
            description "How long the device waits for a response from a RADIUS server before
                        declaring a timeout failure for radius host.";
        } // END of host-timeout-operational definition.

        leaf host-retransmit-max-retries-operational  {
            type  uint8;
            description "Times the router transmits each radius request to the server before
                        giving up for radius host.";
        } // END of host-retransmit-max-retries-operational definition.

    } // END of auth-radius-host-state-top definition.
    grouping auth-radius-host-config {
        description
            "Grouping for Authentication Radius Host configuration data";
        leaf host-address  {
            type  inet:ipv4-address;
            description "The host-address to configure the radius host.";
        } // END of host-address definition.

        leaf host-port  {
            type  uint16 {
                 range "0..65535"  {
                    description "0..65535: Supported range 0 - 65535";
                 }
            }
            description "Specify the radius client port number. The default port number is
                        1812.";
        } // END of host-port definition.

        leaf host-timeout  {
            type  uint8 {
                 range "0..60"  {
                    description "0..60: Supported range 0 - 60";
                 }
            }
            units "seconds";
            description "Use this attribute to set the timeout which is how long the device
                        waits for a response from a RADIUS server before declaring a timeout
                        failure.";
        } // END of host-timeout definition.

        leaf host-retransmit-max-retries  {
            type  uint8 {
                 range "0..100"  {
                    description "0..100: Supported range 0 - 100";
                 }
            }
            description "Use this attribute to specify the number of times the router transmits
                        each radius request to the server before giving up.";
        } // END of host-retransmit-max-retries definition.

        choice host-key-type {
            description
                "Key string types";
            case key-string {

                description
                    "Supply key string in clear text format";

                leaf key-string  {
                    type  string {
                        length "1..64";
                        pattern "[^?' =,>|]+";
                    }
                    description "Use this attribute to set a key (shared secret) which is a text string
                                shared between the device and RADIUS servers";
                } // END of key-string definition.

            }
            case encrypted {

                description
                    "Supply key string in encrypted form";

                leaf encryption-key  {
                    type  string {
                        length "18..130";
                        pattern "[^?' =,>|]+";
                    }
                    description "Use this attribute to set a key (shared secret) which is a text string
                                shared between the device and RADIUS servers";
                } // END of encryption-key definition.

            }
        } // END of host-key-type-choice definition.
    } // END of auth-radius-host-config definition.
    grouping auth-radius-host-top {
        description
            "Grouping for Authentication Radius Host";
        container hosts {
            description
                "Authentication Radius Host";

            list host {
                key "host-address";
                description
                    "List of Authentication Radius Hosts";
                leaf host-address  {
                    type  leafref {
                        path  "../config/host-address";
                    }
                    description "The host-address to configure the radius host.";
                } // END of host-address definition.

                container config {
                    description
                        "Configuration data Authentication Radius Host";
                    uses auth-radius-host-config;
                } // END of config-container definition.
                container state {
                    config false;
                    description
                        "Operational state data for Authentication Radius Host";
                    uses auth-radius-host-config;
                    uses auth-radius-host-state-top;
                } // END of state-container definition.
            } // End of host-list
        } // END of hosts-container definition.
    } // END of auth-radius-host-top definition.
    grouping auth-radius-global-config {
        description
            "Grouping for Authentication Radius global configuration data";
        leaf source-address  {
            when " /ipi-authentication-radius:authentication-radius/ipi-authentication-radius:global/ipi-authentication-radius:config/ipi-authentication-radius:port ";
            type  inet:ipv4-address;
            description "Use this command to set the local address sent in packets to the
                        radius server.";
        } // END of source-address definition.

        leaf port  {
            when " /ipi-authentication-radius:authentication-radius/ipi-authentication-radius:global/ipi-authentication-radius:config/ipi-authentication-radius:source-address ";
            type  uint16 {
                 range "0..65535"  {
                    description "0..65535: Supported range 0 - 65535";
                 }
            }
            description "Specify the radius client port number. The default port number is
                        1812.";
        } // END of port definition.

        leaf timeout  {
            type  uint8 {
                 range "1..60"  {
                    description "1..60: Supported range 1 - 60";
                 }
            }
            units "seconds";
            description "Use this attribute to set the global timeout which is how long the
                        device waits for a response from a RADIUS server before declaring a
                        timeout failure.";
        } // END of timeout definition.

        leaf retransmit-max-retries  {
            type  uint8 {
                 range "1..100"  {
                    description "1..100: Supported range 1 - 100";
                 }
            }
            description "Use this attribute to specify the number of times the router transmits
                        each radius request to the server before giving up";
        } // END of retransmit-max-retries definition.

        choice key-type {
            description
                "Key string types";
            case key-string {

                description
                    "Supply key string in clear text format";

                leaf key-string  {
                    type  string {
                        length "1..64";
                        pattern "[^?' =,>|]+";
                    }
                    description "Use this attribute to set a global preshared key (shared secret) which
                                is a text string shared between the device and RADIUS servers";
                } // END of key-string definition.

            }
            case encrypted {

                description
                    "Supply key string in encrypted format";

                leaf encryption-key  {
                    type  string {
                        length "18..130";
                        pattern "[^?' =,>|]+";
                    }
                    description "Use this attribute to set a global preshared key (shared secret) which
                                is a text string shared between the device and RADIUS servers";
                } // END of encryption-key definition.

            }
        } // END of key-type-choice definition.
    } // END of auth-radius-global-config definition.
    grouping auth-radius-global-top {
        description
            "Grouping for Authentication Radius global configuration";
        container global {
            description
                "Authentication Radius global configuration";
            container config {
                description
                    "Configuration data for Authentication Radius global";
                uses auth-radius-global-config;
            } // END of config-container definition.
            container state {
                config false;
                description
                    "Operational state data for Authentication Radius global";
                uses auth-radius-global-config;
            } // END of state-container definition.
        } // END of global-container definition.
    } // END of auth-radius-global-top definition.

    grouping  authentication-radius-grouping {
    description
        "Grouping for Authentication Radius";
    container authentication-radius {
        if-feature feature-list:HAVE_ENCRYPT_CLEARTEXT;
        if-feature feature-list:HAVE_AUTHD;
        description
            "Grouping for Authentication Radius";
        uses auth-radius-global-top;
        uses auth-radius-host-top;
    } // END of authentication-radius-container definition.
    } // END of authentication-radius-grouping definition.

    uses authentication-radius-grouping;

}
