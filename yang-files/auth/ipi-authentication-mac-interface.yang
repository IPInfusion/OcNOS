/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-authentication-mac-interface.yang
*
*/

submodule ipi-authentication-mac-interface {

    yang-version 1.1;

    belongs-to  ipi-authentication { prefix ipi-authentication; }

    import feature-list {
        prefix feature-list;
        revision-date 2023-02-21;
    }

    import ipi-interface {
        prefix ipi-interface;
        revision-date 2022-08-24;
    }

    import ipi-authentication-types {
        prefix ipi-authentication-types;
        revision-date 2022-06-01;
    }

    organization
        "IP Infusion Inc.";

    contact
        "Address: 3965 Freedom Circle, Suite 200, Santa Clara, CA 95054
         Phone: +1 408-400-1900
         E-mail: support@ipinfusion.com
         Web: http://www.ipinfusion.com/";

    description
        "MAC Interface Authentication";


    revision "2022-06-01" {
        description "Updated the yang file with feature";
        reference " 0.4.0.";
    }

    revision "2022-03-18" {
        description "Removed mac interface state grouping";
        reference " 0.3.0.";
    }

    revision "2022-02-16" {
        description "Fix when tag for switchport";
        reference " 0.2.0.";
    }

    revision "2022-01-28" {
        description "Initial Version";
        reference " 0.1.0.";
    }

    grouping auth-mac-interface-config {
        description
            "Grouping for MAC Authentication Interface configuration data";
        leaf name  {
            type  leafref {
                path  "/ipi-interface:interfaces/ipi-interface:interface/ipi-interface:name";
            }
            description "The interface name to configure the MAC Authentication.";
        } // END of name definition.

        leaf mac-control  {
            type  empty;
            mandatory true;
            description "Use this attribute to enable or disable the MAC authentication control
                        on an interface.";
        } // END of mac-control definition.

        leaf mac-mode  {
            type  ipi-authentication-types:auth_mac_mode_t;
            description "Use this attribute to enable or disable the MAC authentication mode on
                        an interface.";
        } // END of mac-mode definition.

        leaf dynamic-vlan-creation  {
            type  empty;
            description "Use this attribute to enable or disable dynamic VLAN creation after
                        successful MAC authentication.";
        } // END of dynamic-vlan-creation definition.

        leaf mac-address-aging  {
            type  empty;
            description "Use this attribute to either enable or disable MAC aging. When
                        enabled, a MAC entry is added to the forwarding database, with aging
                        time equal to the bridge aging time. Otherwise, the MAC entry will not
                        be aged out. If MAC aging is disabled, the MAC entry will not be aged
                        out";
        } // END of mac-address-aging definition.

    } // END of auth-mac-interface-config definition.
    grouping auth-mac-interface-top {
        description
            "Grouping for MAC Authentication Interface";
        container mac-interfaces {
            when " /authentication/global/config/mac-authentication ";
            if-feature feature-list:HAVE_MAC_AUTH;
            description
                "MAC Authentication Interface";

            list mac-interface {
            when " /authentication/mac-interfaces/mac-interface/config/mac-control ";
                key "name";
                description
                    "List of MAC Authentication Interfaces";
                leaf name  {
                    type  leafref {
                        path  "../config/name";
                    }
                    description "The interface name to configure the MAC Authentication.";
                } // END of name definition.

                container config {
                    description
                        "Configuration data for MAC Authentication Interface";
                    uses auth-mac-interface-config;
                } // END of config-container definition.
                container state {
                    config false;
                    description
                        "Operational state data for MAC Authentication Interface";
                    uses auth-mac-interface-config;
                } // END of state-container definition.
            } // End of mac-interface-list
        } // END of mac-interfaces-container definition.
    } // END of auth-mac-interface-top definition.


}
