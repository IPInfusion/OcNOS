/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-authentication-dot1x-interface.yang
*
*/

submodule ipi-authentication-dot1x-interface {

    yang-version 1.1;

    belongs-to  ipi-authentication { prefix ipi-authentication; }

    import feature-list {
        prefix feature-list;
        revision-date 2023-02-21;
    }

    import ipi-interface {
        prefix ipi-interface;
        revision-date 2022-08-24;
    }

    import ipi-authentication-types {
        prefix ipi-authentication-types;
        revision-date 2022-06-01;
    }

    organization
        "IP Infusion Inc.";

    contact
        "Address: 3965 Freedom Circle, Suite 200, Santa Clara, CA 95054
         Phone: +1 408-400-1900
         E-mail: support@ipinfusion.com
         Web: http://www.ipinfusion.com/";

    description
        "802.1X Interface Authentication";


    revision "2022-07-04" {
        description "No need to check switchport status for enable-mac-auth-bypass parameter";
        reference " 0.6.0.";
    }

    revision "2022-06-01" {
        description "Updated the yang file with feature";
        reference " 0.5.0.";
    }

    revision "2022-04-05" {
        description "Added groupings for operational values";
        reference " 0.4.0.";
    }

    revision "2022-03-18" {
        description "Added authenticator BE state grouping";
        reference " 0.3.0.";
    }

    revision "2022-02-16" {
        description "Fix when tag for switchport";
        reference " 0.2.0.";
    }

    revision "2022-01-28" {
        description "Initial Version";
        reference " 0.1.0.";
    }

    grouping auth-authenticator-be-operational-top {
        description
            "Grouping for 802.1X 802.1X Authentication Interface authenticator
                        Backend operational data";
        container authenticator-be-operational {
            config false;
            description
                "802.1X Authentication Interface authenticator BE operational state";
            container state {
                config false;
                description
                    "Operational state data for 802.1X Authentication Interface
                            authenticator BE";
                leaf supplicant-timeout-operational  {
                    type  uint16;
                    description "Operational interval for a supplicant to respond for 802.1X
                                authentication on an interface.";
                } // END of supplicant-timeout-operational definition.

                leaf server-timeout-operational  {
                    type  uint16;
                    description "Operational authentication server response timeout for 802.1X
                                authentication on an interface.";
                } // END of server-timeout-operational definition.

                leaf current-id  {
                    type  uint8;
                    description "Current id for 802.1X authentication on an interface.";
                } // END of current-id definition.

                leaf be-state  {
                    type  ipi-authentication-types:auth_be_state_t;
                    description "Backend state for 802.1X authentication on an interface.";
                } // END of be-state definition.

                leaf req-count  {
                    type  uint8;
                    description "Backend requisition count for 802.1X authentication on an interface.";
                } // END of req-count definition.

                leaf id-from-server  {
                    type  uint8;
                    description "Backend id from server for 802.1X authentication on an interface.";
                } // END of id-from-server definition.

            } // END of state-container definition.
        } // END of authenticator-be-operational-container definition.
    } // END of auth-authenticator-be-operational-top definition.
    grouping auth-authenticator-be-config {
        description
            "Grouping for 802.1X 802.1X Authentication Interface authenticator
                        Backend configuration data";
        leaf supplicant-timeout  {
            type  uint16 {
                 range "1..65535"  {
                    description "1..65535: Supported range 1 - 65535";
                 }
            }
            units "seconds";
            description "Use this attribute to set the interval for a supplicant to respond.";
        } // END of supplicant-timeout definition.

        leaf server-timeout  {
            type  uint16 {
                 range "1..65535"  {
                    description "1..65535: Supported range 1 - 65535";
                 }
            }
            units "seconds";
            description "Use this attribute to set the authentication server response timeout.";
        } // END of server-timeout definition.

    } // END of auth-authenticator-be-config definition.
    grouping auth-authenticator-be-top {
        description
            "Grouping for 802.1X Authentication Interface authenticator BE";
        container authenticator-be {
            description
                "802.1X Authentication Interface authenticator BE";
            container config {
                description
                    "Configuration data for 802.1X Authentication Interface authenticator
                            BE";
                uses auth-authenticator-be-config;
            } // END of config-container definition.
            container state {
                config false;
                description
                    "Operational state data for 802.1X Authentication Interface
                            authenticator BE";
                uses auth-authenticator-be-config;
            } // END of state-container definition.
        } // END of authenticator-be-container definition.
    } // END of auth-authenticator-be-top definition.
    grouping auth-reauthentication-timer-operational-top {
        description
            "Grouping for 802.1X Authentication Interface reauthentication timer
                        operational data";
        container reauthentication-timer-operational {
            config false;
            description
                "802.1X Authentication Interface reauthentication timer operational
                        state";
            container state {
                config false;
                description
                    "Operational state data for 802.1X Authentication Interface
                            reauthentication timer";
                leaf reauthentication-period-operational  {
                    type  uint32;
                    description "Operational interval between reauthorization attempts for 802.1X
                                Authentication Interface reauthentication timer.";
                } // END of reauthentication-period-operational definition.

                leaf enable-reauthentication-operational  {
                    type  empty;
                    description "Operational reauthentication status on a port for 802.1X
                                Authentication Interface reauthentication timer.";
                } // END of enable-reauthentication-operational definition.

                leaf dot1x-timer  {
                    if-feature feature-list:HAVE_MAC_AUTH;
                    type  ipi-authentication-types:auth_mac_dot1x_timer_status_t;
                    description "802.1X timer status for 802.1X Authentication Interface
                                reauthentication timer.";
                } // END of dot1x-timer definition.

                leaf mac-status  {
                    if-feature feature-list:HAVE_MAC_AUTH;
                    type  ipi-authentication-types:auth_mac_status_t;
                    description "MAC status for 802.1X Authentication Interface reauthentication timer.";
                } // END of mac-status definition.

                leaf last-rejected-mac  {
                    if-feature feature-list:HAVE_MAC_AUTH;
                    type  ipi-authentication-types:auth_dot1x_mac_address_t {
                        length "1..1965";
                    }
                    description "Last rejected MAC for 802.1X Authentication Interface reauthentication
                                timer.";
                } // END of last-rejected-mac definition.

            } // END of state-container definition.
        } // END of reauthentication-timer-operational-container definition.
    } // END of auth-reauthentication-timer-operational-top definition.
    grouping auth-reauthentication-timer-config {
        description
            "Grouping for 802.1X Authentication Interface reauthentication timer
                        configuration data";
        leaf reauthentication-period  {
            type  uint32 {
                 range "1..4294967295"  {
                    description "1..4294967295: Supported range 1 - 4294967295";
                 }
            }
            units "seconds";
            description "Use this attribute to set the interval between reauthorization
                        attempts.";
        } // END of reauthentication-period definition.

        leaf enable-reauthentication  {
            type  empty;
            description "Use this attribute to enable reauthentication on a port.";
        } // END of enable-reauthentication definition.

        leaf enable-mac-auth-bypass  {
            if-feature feature-list:HAVE_MAC_AUTH;
            type  ipi-authentication-types:auth_dot1x_mac_auth_bypass_t;
            description "Use this attribute to enable/disable mac-auth-bypass on a port.";
        } // END of enable-mac-auth-bypass definition.

    } // END of auth-reauthentication-timer-config definition.
    grouping auth-reauthentication-timer-top {
        description
            "Grouping for 802.1X Authentication Interface reauthentication timer";
        container reauthentication-timer {
            description
                "802.1X Authentication Interface reauthentication timer";
            container config {
                description
                    "Configuration data for 802.1X Authentication Interface
                            reauthentication timer";
                uses auth-reauthentication-timer-config;
            } // END of config-container definition.
            container state {
                config false;
                description
                    "Operational state data for 802.1X Authentication Interface
                            reauthentication timer";
                uses auth-reauthentication-timer-config;
            } // END of state-container definition.
        } // END of reauthentication-timer-container definition.
    } // END of auth-reauthentication-timer-top definition.
    grouping auth-authenticator-pae-operational-top {
        description
            "Grouping for 802.1X 802.1X Authentication Interface authenticator PAE
                        operational data";
        container auth-authenticator-pae-operational {
            config false;
            description
                "802.1X Authentication Interface authenticator PAE operational state";
            container state {
                config false;
                description
                    "Operational state data for 802.1X Authentication Interface
                            authenticator PAE";
                leaf quiet-period-operational  {
                    type  uint16;
                    description "Operational PAE quiet-period time interval for 802.1X authentication
                                on an interface.";
                } // END of quiet-period-operational definition.

                leaf max-reauth-value-operational  {
                    type  uint8;
                    description "Operational PAE maximum reauthentication value for 802.1X
                                authentication on an interface.";
                } // END of max-reauth-value-operational definition.

                leaf interval-period-operational  {
                    type  uint16;
                    description "Operational PAE interval between successive attempts to request an ID
                                for 802.1X authentication on an interface.";
                } // END of interval-period-operational definition.

                leaf port-status  {
                    type  ipi-authentication-types:auth_dot1x_port_status_t;
                    description "PAE port status for 802.1X authentication on an interface.";
                } // END of port-status definition.

                leaf pae-state  {
                    type  ipi-authentication-types:auth_dot1x_pae_state_t;
                    description "PAE state for 802.1X authentication on an interface.";
                } // END of pae-state definition.

                leaf port-mode  {
                    type  ipi-authentication-types:auth_dot1x_port_ctrl_t;
                    description "PAE port mode for 802.1X authentication on an interface.";
                } // END of port-mode definition.

                leaf reauth-count  {
                    type  uint32;
                    description "PAE reauthentication count for 802.1X authentication on an interface.";
                } // END of reauth-count definition.

                leaf rx-response-id  {
                    type  uint32;
                    description "PAE received response id for 802.1X authentication on an interface.";
                } // END of rx-response-id definition.

            } // END of state-container definition.
        } // END of auth-authenticator-pae-operational-container definition.
    } // END of auth-authenticator-pae-operational-top definition.
    grouping auth-authenticator-pae-config {
        description
            "Grouping for 802.1X 802.1X Authentication Interface authenticator PAE
                        configuration data";
        leaf quiet-period  {
            type  uint16 {
                 range "1..65535"  {
                    description "1..65535: Supported range 1 - 65535";
                 }
            }
            units "seconds";
            description "Use this attribute to set the quiet-period time interval.When a switch
                        cannot authenticate a client, the switch remains idle for a
                        quiet-period interval of time, then tries again. By administratively
                        changing the quiet-period interval, by entering a lower number than
                        the default, a faster response time can be provided";
        } // END of quiet-period definition.

        leaf max-reauth-value  {
            type  uint8 {
                 range "1..10"  {
                    description "1..10: Supported range 1 - 10";
                 }
            }
            description "Use this attribute to set the maximum reauthentication value, which
                        sets the maximum number of reauthentication attempts after which the
                        port will be unauthorized.";
        } // END of max-reauth-value definition.

        leaf interval-period  {
            type  uint16 {
                 range "1..65535"  {
                    description "1..65535: Supported range 1 - 65535";
                 }
            }
            units "seconds";
            description "Use this attribute to set the interval between successive attempts to
                        request an ID.";
        } // END of interval-period definition.

    } // END of auth-authenticator-pae-config definition.
    grouping auth-authenticator-pae-top {
        description
            "Grouping for 802.1X Authentication Interface authenticator PAE";
        container authenticator-pae {
            description
                "802.1X Authentication Interface authenticator PAE";
            container config {
                description
                    "Configuration data for 802.1X Authentication Interface authenticator
                            PAE";
                uses auth-authenticator-pae-config;
            } // END of config-container definition.
            container state {
                config false;
                description
                    "Operational state data for 802.1X Authentication Interface
                            authenticator PAE";
                uses auth-authenticator-pae-config;
            } // END of state-container definition.
        } // END of authenticator-pae-container definition.
    } // END of auth-authenticator-pae-top definition.
    grouping auth-authentication-key-received-operational-top {
        description
            "Grouping for 802.1X Authentication Interface key received operational
                        data";
        container authentication-key-received-operational {
            config false;
            description
                "802.1X Authentication Interface key received operational state";
            container state {
                config false;
                description
                    "Operational state data for 802.1X Authentication Interface key
                            received";
                leaf rx-key  {
                    type  boolean;
                    description "Received key for 802.1X authentication on an interface.";
                } // END of rx-key definition.

            } // END of state-container definition.
        } // END of authentication-key-received-operational-container definition.
    } // END of auth-authentication-key-received-operational-top definition.
    grouping auth-authentication-control-dir-operational-top {
        description
            "Grouping for 802.1X Authentication Interface control dir operational
                        data";
        container authentication-control-dir-operational {
            config false;
            description
                "802.1X Authentication Interface control dir operational state";
            container state {
                config false;
                description
                    "Operational state data for 802.1X Authentication Interface control dir";
                leaf admin-controlled-directions  {
                    type  ipi-authentication-types:auth_dot1x_control_dir_t;
                    description "Administrative controlled directions for 802.1X authentication on an
                                interface.";
                } // END of admin-controlled-directions definition.

                leaf oper-controlled-directions  {
                    type  ipi-authentication-types:auth_dot1x_control_dir_t;
                    description "Operational controlled directions for 802.1X authentication on an
                                interface.";
                } // END of oper-controlled-directions definition.

                leaf bridge-detected  {
                    type  boolean;
                    description "Bridge detected for 802.1X authentication on an interface.";
                } // END of bridge-detected definition.

            } // END of state-container definition.
        } // END of authentication-control-dir-operational-container definition.
    } // END of auth-authentication-control-dir-operational-top definition.
    grouping auth-dot1x-interface-operational-top {
        description
            "Grouping for 802.1X Authentication Interface operational data";
        container auth-dot1x-interface-operational {
            config false;
            description
                "802.1X Authentication Interface operational state";
            container state {
                config false;
                description
                    "Operational state data for 802.1X Authentication Interface";
                leaf dot1x-control-operational  {
                    type  ipi-authentication-types:auth_dot1x_control_t;
                    description "Operational 802.1X authentication control status for 802.1X
                                authentication on an interface.";
                } // END of dot1x-control-operational definition.

                leaf supplicant-name  {
                    type  string {
                        length "1..1965";
                        pattern "[^?' =,>|]+";
                    }
                    description "Supplicant name for 802.1X authentication on an interface.";
                } // END of supplicant-name definition.

                leaf supplicant-mac-address  {
                    type  ipi-authentication-types:auth_dot1x_mac_address_t {
                        length "1..1965";
                    }
                    description "Supplicant MAC address for 802.1X authentication on an interface.";
                } // END of supplicant-mac-address definition.

                leaf port-enabled  {
                    type  boolean;
                    description "Port enabled for 802.1X authentication on an interface.";
                } // END of port-enabled definition.

                leaf authentication-abort  {
                    type  boolean;
                    description "Authentication abort for 802.1X authentication on an interface.";
                } // END of authentication-abort definition.

                leaf authentication-fail  {
                    type  boolean;
                    description "Authentication fail for 802.1X authentication on an interface.";
                } // END of authentication-fail definition.

                leaf authentication-start  {
                    type  boolean;
                    description "Authentication start for 802.1X authentication on an interface.";
                } // END of authentication-start definition.

                leaf authentication-timeout  {
                    type  boolean;
                    description "Authentication timeout for 802.1X authentication on an interface.";
                } // END of authentication-timeout definition.

                leaf authentication-success  {
                    type  boolean;
                    description "Authentication success for 802.1X authentication on an interface.";
                } // END of authentication-success definition.

                leaf key-available  {
                    type  boolean;
                    description "Key available for 802.1X authentication on an interface.";
                } // END of key-available definition.

                leaf key-tx-enabled  {
                    type  boolean;
                    description "Key transmission enabled for 802.1X authentication on an interface.";
                } // END of key-tx-enabled definition.

            } // END of state-container definition.
        } // END of auth-dot1x-interface-operational-container definition.
    } // END of auth-dot1x-interface-operational-top definition.
    grouping auth-dot1x-interface-config {
        description
            "Grouping for 802.1X Authentication Interface configuration data";
        leaf name  {
            type  leafref {
                path  "/ipi-interface:interfaces/ipi-interface:interface/ipi-interface:name";
            }
            description "The interface name to configure the 802.1X Authentication.";
        } // END of name definition.

        leaf dot1x-control  {
            type  ipi-authentication-types:auth_dot1x_control_t;
            mandatory true;
            description "Use this attribute to enable or disable the 802.1X authentication
                        control on an interface.";
        } // END of dot1x-control definition.

        leaf protocol-version  {
            type  ipi-authentication-types:auth_dot1x_eapol_version_t;
            description "Use this attribute to set the protocol version of dot1x to 1 or 2. The
                        protocol version must be synchronized with the Xsupplicant being used
                        in that interface.";
        } // END of protocol-version definition.

    } // END of auth-dot1x-interface-config definition.
    grouping auth-dot1x-interface-top {
        description
            "Grouping for 802.1X Authentication Interface";
        container dot1x-interfaces {
            when " /authentication/global/config/dot1x-authentication ";
            description
                "802.1X Authentication Interface";

            list dot1x-interface {
            when " /authentication/dot1x-interfaces/dot1x-interface/config/dot1x-control ";
                key "name";
                description
                    "List of 802.1X Authentication Interfaces";
                leaf name  {
                    type  leafref {
                        path  "../config/name";
                    }
                    description "The interface name to configure the 802.1X Authentication.";
                } // END of name definition.

                container config {
                    description
                        "Configuration data for 802.1X Authentication Interface";
                    uses auth-dot1x-interface-config;
                } // END of config-container definition.
                container state {
                    config false;
                    description
                        "Operational state data for 802.1X Authentication Interface";
                    uses auth-dot1x-interface-config;
                } // END of state-container definition.
                uses auth-dot1x-interface-operational-top;
                uses auth-authentication-control-dir-operational-top;
                uses auth-authentication-key-received-operational-top;
                uses auth-authenticator-pae-top;
                uses auth-authenticator-pae-operational-top;
                uses auth-reauthentication-timer-top;
                uses auth-reauthentication-timer-operational-top;
                uses auth-authenticator-be-top;
                uses auth-authenticator-be-operational-top;
            } // End of dot1x-interface-list
        } // END of dot1x-interfaces-container definition.
    } // END of auth-dot1x-interface-top definition.


}
