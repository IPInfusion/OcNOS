/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-service-map.yang
*
*/

module ipi-service-map {

    yang-version 1.1;

    namespace   "http://www.ipinfusion.com/yang/ocnos/ipi-service-map";

    prefix "ipi-service-map";

    import ipi-service-map-types {
        prefix ipi-service-map-types;
        revision-date 2022-06-01;
    }

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "Data model for Service Mapping";


    revision "2022-06-01" {
        description "Updated the yang file with feature";
        reference " 2.0.0.";
    }

    revision "2022-03-21" {
        description "Added selection mode and tunnel-type attributes to accomodate both srv6 and mpls tunnel-policy";
        reference " 1.0.0.";
    }

    revision "2020-11-03" {
        description "Initial Version";
        reference " 0.1.0.";
    }

    grouping tunnel-policies-config {
        description
            "configuration parameters for tunnel policy";
        leaf name  {
            type  string {
                length "1..1965";
                pattern "[^?' =,>|]+";
            }
            description "Name for the tunnel policy";
        } // END of name definition.

        leaf-list color-code  {
            type  uint32 {
                 range "1..4294967295"  {
                    description "1..4294967295: Supported range 1 - 4294967295";
                 }
            }
            description "Use this attribute to configure color for tunnel policy";
        } // END of color-code definition.

        leaf selection-mode  {
            type  ipi-service-map-types:tunnel_selection_mode_t;
            default "dedicated";
            description "Use this attribute to configure selection mode as dedicated or
                        best-effort for tunnel policy";
        } // END of selection-mode definition.

        leaf tunnel-type  {
            if-feature feature-list:HAVE_SRV6_OR_HAVE_SR_MPLS_OR_HAVE_MPLS;
            type  ipi-service-map-types:tunnel_selection_type_t;
            description "Use this attribute to configure selection mode as sr or srv6 or rsvp
                        for tunnel policy";
        } // END of tunnel-type definition.

    } // END of tunnel-policies-config definition.

    grouping  service-map-grouping {
    description
        "Top level container for MPLS, including configuration and state data";
    container service-map {
        if-feature feature-list:HAVE_SERVICE_MAPPING;
        description
            "Top level container for MPLS, including configuration and state data";
        container tunnel-policies {
            description
                "tunnel policy configuration and state data";

            list tunnel-policy {
                key "name";
                description
                    "List of tunnel policies";
                leaf name  {
                    type  leafref {
                        path  "../config/name";
                    }
                    description "Name for the tunnel policy";
                } // END of name definition.

                container config {
                    description
                        "configuration for tunnel-policy";
                    uses tunnel-policies-config;
                } // END of config-container definition.
                container state {
                    config false;
                    description
                        "state data for tunnel policy";
                    uses tunnel-policies-config;
                } // END of state-container definition.
            } // End of tunnel-policy-list
        } // END of tunnel-policies-container definition.
    } // END of service-map-container definition.
    } // END of service-map-grouping definition.

    uses service-map-grouping;

}
