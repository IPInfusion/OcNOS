/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-tacacs.yang
*
*/

submodule zebos-tacacs {

    belongs-to  zebos { prefix zebos; }

    import cml_data_types {
        prefix cml_data_types;
    }

    import feature_list {
        prefix feature_list;
    }

    include zebos-vrf;
    organization
        "IP Infusion Inc.";

    contact
        "Address: 3965 Freedom Circle, Suite 200, Santa Clara, CA 95054
        Phone: +1 408-400-1900
        E-mail: support@ipinfusion.com
        Web: http://www.ipinfusion.com/";

    description
        "Layer-3 tacacs configurations";


    revision "2018-06-21" {
        description " Initial Version.";
        reference "";
    }



    grouping tacacs-grouping {
    description
        "tacacs related operations";
        list tacacs {
            key "vrfName";
            description
                "tacacs related operations";
            leaf vrfName  {
                type  cml_data_types:CML_STRING_T {
                    length "0..255";
                }
                description "";
            } // END of vrfName definition.

            leaf featureTacacs  {
                type  cml_data_types:CML_HOSTP_TACACS_T;
                description "";
            } // END of featureTacacs definition.

            leaf tacacsKeyEnable  {
                if-feature feature_list:HAVE_HOSTPD;
                if-feature feature_list:HAVE_AAA;
                if-feature feature_list:HAVE_TACACS_CLIENT;
                type  cml_data_types:CML_HOSTP_KEY_TYPE_T;
                description "";
            } // END of tacacsKeyEnable definition.

            leaf tacacsKeyWord  {
                if-feature feature_list:HAVE_HOSTPD;
                if-feature feature_list:HAVE_AAA;
                if-feature feature_list:HAVE_TACACS_CLIENT;
                type  cml_data_types:CML_STRING_T {
                    length "1..63";
                }
                description "";
            } // END of tacacsKeyWord definition.


            list tacacshost {
                key "hostAddr";
                description
                    "tacacshost";
                leaf hostAddr  {
                    type  cml_data_types:CML_STRING_T {
                        length "1..63";
                    }
                    description "";
                } // END of hostAddr definition.

                leaf seqNum  {
                    if-feature feature_list:HAVE_HOSTPD;
                    if-feature feature_list:HAVE_AAA;
                    if-feature feature_list:HAVE_TACACS_CLIENT;
                    type  cml_data_types:CML_UINT8_T {
                         range "1..8";
                    }
                    mandatory true;
                    description "";
                } // END of seqNum definition.

                leaf keyEnable  {
                    if-feature feature_list:HAVE_HOSTPD;
                    if-feature feature_list:HAVE_AAA;
                    if-feature feature_list:HAVE_TACACS_CLIENT;
                    type  cml_data_types:CML_HOSTP_KEY_TYPE_T;
                    description "";
                } // END of keyEnable definition.

                leaf keyWord  {
                    if-feature feature_list:HAVE_HOSTPD;
                    if-feature feature_list:HAVE_AAA;
                    if-feature feature_list:HAVE_TACACS_CLIENT;
                    type  cml_data_types:CML_STRING_T {
                        length "0..255";
                    }
                    description "";
                } // END of keyWord definition.

                leaf port  {
                    if-feature feature_list:HAVE_HOSTPD;
                    if-feature feature_list:HAVE_AAA;
                    if-feature feature_list:HAVE_TACACS_CLIENT;
                    type  cml_data_types:CML_UINT32_T {
                         range "1025..65535";
                    }
                    description "";
                } // END of port definition.

            } // End of tacacshost-list
        } // End of tacacs-list
    } // END of tacacs-grouping definition.

    grouping  debugTacacs-grouping {
    description
        "tacacs debug commands";
    container debugTacacs {
        description
            "tacacs debug commands";
        leaf debugtacacs  {
            if-feature feature_list:HAVE_HOSTPD;
            if-feature feature_list:HAVE_AAA;
            if-feature feature_list:HAVE_TACACS_CLIENT;
            type  cml_data_types:CML_BOOL_T;
            description "";
        } // END of debugtacacs definition.

        leaf debugtacacsConfig  {
            if-feature feature_list:HAVE_HOSTPD;
            if-feature feature_list:HAVE_AAA;
            if-feature feature_list:HAVE_TACACS_CLIENT;
            type  cml_data_types:CML_BOOL_T;
            description "";
        } // END of debugtacacsConfig definition.

    } // END of debugTacacs-container definition.
    } // END of debugTacacs-container definition.


}
