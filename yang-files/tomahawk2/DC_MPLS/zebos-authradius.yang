/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-authradius.yang
*
*/

submodule zebos-authradius {

    belongs-to  zebos { prefix zebos; }

    import cml_data_types {
        prefix cml_data_types;
    }

    include zebos-vrf;
    organization
        "IP Infusion Inc.";

    contact
        "Address: 3965 Freedom Circle, Suite 200, Santa Clara, CA 95054
        Phone: +1 408-400-1900
        E-mail: support@ipinfusion.com
        Web: http://www.ipinfusion.com/";

    description
        "Layer-3 radius configurations";


    revision "2018-06-21" {
        description " Initial Version.";
        reference "";
    }



    grouping Hostradius-grouping {
    description
        "hostaddr structure";
        list Hostradius {
            key "hostAddr";
            description
                "hostaddr structure";
            leaf hostAddr  {
                type  cml_data_types:CML_HOSTPNAME_T {
                    length "0..255";
                }
                description "";
            } // END of hostAddr definition.

            leaf key  {
                type  cml_data_types:CML_BOOL_T;
                description "";
            } // END of key definition.

            leaf keyType  {
                type  cml_data_types:CML_HOSTP_KEY_TYPE_T;
                default "0";
                description "";
            } // END of keyType definition.

            leaf keyWord  {
                type  cml_data_types:CML_STRING_T {
                    length "0..255";
                }
                description "";
            } // END of keyWord definition.

            leaf authPort  {
                type  cml_data_types:CML_UINT32_T {
                     range "0..65535";
                }
                description "";
            } // END of authPort definition.

            leaf timeout  {
                type  cml_data_types:CML_UINT32_T {
                     range "1..60";
                }
                default "5";
                description "";
            } // END of timeout definition.

            leaf hostRetransmit  {
                type  cml_data_types:CML_UINT32_T {
                     range "1..100";
                }
                description "";
            } // END of hostRetransmit definition.

        } // End of Hostradius-list
    } // END of Hostradius-grouping definition.

    grouping  authradius-grouping {
    description
        "radius related commands";
    container authradius {
        description
            "radius related commands";
        leaf sourceInterface  {
            type  cml_data_types:CML_STRING_T {
                length "0..255";
            }
            description "";
        } // END of sourceInterface definition.

        leaf port  {
            type  cml_data_types:CML_UINT32_T;
            description "";
        } // END of port definition.

        leaf globalTimeout  {
            type  cml_data_types:CML_UINT32_T {
                 range "1..60";
            }
            default "5";
            description "";
        } // END of globalTimeout definition.

        leaf key  {
            type  cml_data_types:CML_BOOL_T;
            description "";
        } // END of key definition.

        leaf globalKeytype  {
            type  cml_data_types:CML_HOSTP_KEY_TYPE_T;
            default "0";
            description "";
        } // END of globalKeytype definition.

        leaf globalKeyword  {
            type  cml_data_types:CML_STRING_T {
                length "0..255";
            }
            description "";
        } // END of globalKeyword definition.

        leaf deadtime  {
            type  cml_data_types:CML_UINT32_T;
            description "";
        } // END of deadtime definition.

        leaf retransmit  {
            type  cml_data_types:CML_UINT32_T;
            description "";
        } // END of retransmit definition.

    } // END of authradius-container definition.
    } // END of authradius-container definition.


}
