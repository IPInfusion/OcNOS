/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-rpf.yang
*
*/

submodule zebos-rpf {

    belongs-to  zebos { prefix zebos; }

    import cml_data_types {
        prefix cml_data_types;
    }

    import feature_list {
        prefix feature_list;
    }

    organization
        "IP Infusion Inc.";

    contact
        "Address: 3965 Freedom Circle, Suite 200, Santa Clara, CA 95054
        Phone: +1 408-400-1900
        E-mail: support@ipinfusion.com
        Web: http://www.ipinfusion.com/";

    description
        "Datamodel for Unicast Reverse Path Forwarding";


    revision "2018-06-21" {
        description " Initial Version.";
        reference "";
    }


    grouping  rpf-grouping {
    description
        "rpf";
    container rpf {
        description
            "rpf";
        leaf urpfEnable  {
            type  cml_data_types:CML_BOOL_T;
            description "";
        } // END of urpfEnable definition.

        leaf urpfEnableAllowDefault  {
            if-feature feature_list:HAVE_DUNE;
            type  cml_data_types:CML_BOOL_T;
            description "";
        } // END of urpfEnableAllowDefault definition.

    } // END of rpf-container definition.
    } // END of rpf-container definition.

    grouping  rpfInfo-grouping {
    description
        "Unicast Reverse Path Forwarding Info";
    container rpfInfo {
        description
            "Unicast Reverse Path Forwarding Info";
        leaf nsmUrpfMode  {
            type  cml_data_types:CML_URPF_MODE_T;
            description "";
        } // END of nsmUrpfMode definition.

    } // END of rpfInfo-container definition.
    } // END of rpfInfo-container definition.


}
