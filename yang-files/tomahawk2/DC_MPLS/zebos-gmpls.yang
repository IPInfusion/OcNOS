/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-gmpls.yang
*
*/

submodule zebos-gmpls {

    belongs-to  zebos { prefix zebos; }

    import cml_data_types {
        prefix cml_data_types;
    }

    organization
        "IP Infusion Inc.";

    contact
        "Address: 3965 Freedom Circle, Suite 200, Santa Clara, CA 95054
        Phone: +1 408-400-1900
        E-mail: support@ipinfusion.com
        Web: http://www.ipinfusion.com/";

    description
        "Generalized Multiprotocol Label Switching";


    revision "2018-06-21" {
        description " Initial Version.";
        reference "";
    }



    grouping telink-grouping {
    description
        "telink";
        list telink {
            key "teName";
            description
                "telink";
            leaf teName  {
                type  cml_data_types:CML_STRING_T {
                    length "0..255";
                }
                description "";
            } // END of teName definition.

            leaf telinkDesc  {
                type  cml_data_types:CML_STRING_T {
                    length "0..255";
                }
                description "";
            } // END of telinkDesc definition.

            leaf labelSwitchingFlags  {
                type  cml_data_types:CML_BOOL_T;
                description "";
            } // END of labelSwitchingFlags definition.

            leaf adminStatusFlags  {
                type  cml_data_types:CML_BOOL_T;
                description "";
            } // END of adminStatusFlags definition.

            leaf ifaceBoundDl  {
                type  cml_data_types:CML_UINT16_T;
                config false;
                description "";
            } // END of ifaceBoundDl definition.

            leaf totalDl  {
                type  cml_data_types:CML_UINT16_T;
                config false;
                description "";
            } // END of totalDl definition.

            leaf gifindex  {
                type  cml_data_types:CML_UINT32_T;
                config false;
                description "";
            } // END of gifindex definition.

            leaf lLinkIdType  {
                type  cml_data_types:CML_UINT8_T;
                config false;
                description "";
            } // END of lLinkIdType definition.

            leaf teLocalLinkId  {
                type  cml_data_types:CML_IPV4_ADDR_T;
                mandatory true;
                description "";
            } // END of teLocalLinkId definition.

            leaf isNumbered  {
                type  cml_data_types:CML_BOOL_T;
                description "";
            } // END of isNumbered definition.

            leaf rLinkIdType  {
                type  cml_data_types:CML_UINT8_T;
                config false;
                description "";
            } // END of rLinkIdType definition.

            leaf teRemoteLinkId  {
                type  cml_data_types:CML_IPV4_ADDR_T;
                description "";
            } // END of teRemoteLinkId definition.

            leaf ifName  {
                type  cml_data_types:CML_STRING_T {
                    length "0..255";
                }
                description "";
            } // END of ifName definition.

            container telink_properties {
                description
                    "telinkCMLSEPproperties";
                leaf adminGroup  {
                    type  cml_data_types:CML_UINT32_T;
                    config false;
                    description "";
                } // END of adminGroup definition.

                leaf-list srlg  {
                    type  cml_data_types:CML_UINT32_T {
                         range "0..4294967295";
                    }
                    description "";
                } // END of srlg definition.

                leaf linkid  {
                    type  cml_data_types:CML_STRING_T {
                        length "0..255";
                    }
                    config false;
                    description "";
                } // END of linkid definition.

                leaf mtu  {
                    type  cml_data_types:CML_UINT32_T;
                    config false;
                    description "";
                } // END of mtu definition.

            } // END of telink_properties-container definition.
        } // End of telink-list
    } // END of telink-grouping definition.


    grouping controlChannel-grouping {
    description
        "controlChannel";
        list controlChannel {
            key "ccName";
            description
                "controlChannel";
            leaf ccName  {
                type  cml_data_types:CML_STRING_T {
                    length "0..255";
                }
                description "";
            } // END of ccName definition.

            leaf ccNameDesc  {
                type  cml_data_types:CML_STRING_T {
                    length "0..255";
                }
                description "";
            } // END of ccNameDesc definition.

            leaf shutdownFlags  {
                type  cml_data_types:CML_BOOL_T;
                description "";
            } // END of shutdownFlags definition.

            leaf gifindex  {
                type  cml_data_types:CML_UINT32_T;
                config false;
                description "";
            } // END of gifindex definition.

            leaf bifindex  {
                type  cml_data_types:CML_UINT32_T;
                config false;
                description "";
            } // END of bifindex definition.

            leaf ccid  {
                type  cml_data_types:CML_UINT32_T {
                     range "1..4294967295";
                }
                description "";
            } // END of ccid definition.

            leaf lAddr  {
                type  cml_data_types:CML_IPV4_ADDR_T;
                description "";
            } // END of lAddr definition.

            leaf rAddr  {
                type  cml_data_types:CML_IPV4_ADDR_T;
                description "";
            } // END of rAddr definition.

            leaf ccNameStatus  {
                type  cml_data_types:CML_UINT16_T;
                config false;
                description "";
            } // END of ccNameStatus definition.

            leaf upcntrs  {
                type  cml_data_types:CML_UINT32_T;
                config false;
                description "";
            } // END of upcntrs definition.

            leaf lastUpTime  {
                type  cml_data_types:CML_STRING_T {
                    length "0..255";
                }
                config false;
                description "";
            } // END of lastUpTime definition.

            leaf lastDownTime  {
                type  cml_data_types:CML_STRING_T {
                    length "0..255";
                }
                config false;
                description "";
            } // END of lastDownTime definition.

            leaf primary  {
                type  cml_data_types:CML_UINT8_T;
                config false;
                description "";
            } // END of primary definition.

        } // End of controlChannel-list
    } // END of controlChannel-grouping definition.


    grouping controlAdjacency-grouping {
    description
        "controlAdjacency";
        list controlAdjacency {
            key "caName";
            description
                "controlAdjacency";
            leaf caName  {
                type  cml_data_types:CML_STRING_T {
                    length "0..255";
                }
                description "";
            } // END of caName definition.

            leaf caNameDesc  {
                type  cml_data_types:CML_STRING_T {
                    length "0..255";
                }
                description "";
            } // END of caNameDesc definition.

            leaf gifindex  {
                type  cml_data_types:CML_UINT32_T;
                config false;
                description "";
            } // END of gifindex definition.

            leaf rNodeid  {
                type  cml_data_types:CML_IPV4_ADDR_T;
                description "";
            } // END of rNodeid definition.

            leaf lmpType  {
                type  cml_data_types:CML_GMPLS_LMPTYPE_T;
                default "using-lmp";
                description "";
            } // END of lmpType definition.

            leaf flags  {
                type  cml_data_types:CML_UINT8_T;
                config false;
                description "";
            } // END of flags definition.

            leaf ccupcntrs  {
                type  cml_data_types:CML_UINT32_T;
                config false;
                description "";
            } // END of ccupcntrs definition.

            leaf ccgifindex  {
                type  cml_data_types:CML_UINT32_T;
                config false;
                description "";
            } // END of ccgifindex definition.

            leaf lmpInuse  {
                type  cml_data_types:CML_UINT8_T;
                config false;
                description "";
            } // END of lmpInuse definition.


            list cclist {
                key "ccName";
                description
                    "cclist";
                leaf ccName  {
                    type  cml_data_types:CML_STRING_T {
                        length "0..255";
                    }
                    description "";
                } // END of ccName definition.

                leaf isPrimary  {
                    type  cml_data_types:CML_BOOL_T;
                    description "";
                } // END of isPrimary definition.

            } // End of cclist-list

            list telist {
                key "tlName";
                description
                    "telist";
                leaf tlName  {
                    type  cml_data_types:CML_STRING_T {
                        length "0..255";
                    }
                    description "";
                } // END of tlName definition.

            } // End of telist-list
        } // End of controlAdjacency-list
    } // END of controlAdjacency-grouping definition.


    grouping bidirectionalFtnEntry-grouping {
    description
        "bidirectionalFtnEntry";
        list bidirectionalFtnEntry {
            key "ftnBName";
            description
                "bidirectionalFtnEntry";
            leaf ftnBName  {
                type  cml_data_types:CML_STRING_T {
                    length "0..255";
                }
                description "";
            } // END of ftnBName definition.

            leaf flags  {
                type  cml_data_types:CML_GMPLS_BIDIRECTIONAL_FLAG_T;
                config false;
                description "";
            } // END of flags definition.


            list ftn {
                key "ftnTunId";
                description
                    "ftn";
                leaf ftnTunId  {
                    type  cml_data_types:CML_UINT32_T {
                         range "1..100";
                    }
                    description "";
                } // END of ftnTunId definition.

                leaf fec  {
                    type  cml_data_types:CML_IPV4_ADDR_PREFIX_T;
                    mandatory true;
                    description "";
                } // END of fec definition.

                leaf outLabel  {
                    type  cml_data_types:CML_STRING_T {
                        length "0..255";
                    }
                    mandatory true;
                    description "";
                } // END of outLabel definition.

                leaf nhAddr  {
                    type  cml_data_types:CML_IPV4_ADDR_T;
                    default "255.255.255.255";
                    description "";
                } // END of nhAddr definition.

                leaf ifName  {
                    type  cml_data_types:CML_STRING_T {
                        length "0..255";
                    }
                    mandatory true;
                    description "";
                } // END of ifName definition.

            } // End of ftn-list
        } // End of bidirectionalFtnEntry-list
    } // END of bidirectionalFtnEntry-grouping definition.


    grouping ftnTable-grouping {
    description
        "ftnTable";
        list ftnTable {
            key "tunId";
            description
                "ftnTable";
            leaf tunId  {
                type  cml_data_types:CML_UINT32_T {
                     range "1..100";
                }
                description "";
            } // END of tunId definition.

            leaf fec  {
                type  cml_data_types:CML_IPV4_ADDR_PREFIX_T;
                mandatory true;
                description "";
            } // END of fec definition.

            leaf outLabel  {
                type  cml_data_types:CML_STRING_T {
                    length "0..255";
                }
                mandatory true;
                description "";
            } // END of outLabel definition.

            leaf nhAddr  {
                type  cml_data_types:CML_IPV4_ADDR_T;
                default "255.255.255.255";
                description "";
            } // END of nhAddr definition.

            leaf ifName  {
                type  cml_data_types:CML_STRING_T {
                    length "0..255";
                }
                mandatory true;
                description "";
            } // END of ifName definition.

        } // End of ftnTable-list
    } // END of ftnTable-grouping definition.


    grouping bidirectionalIlmEntry-grouping {
    description
        "bidirectionalIlmEntry";
        list bidirectionalIlmEntry {
            key "bName";
            description
                "bidirectionalIlmEntry";
            leaf bName  {
                type  cml_data_types:CML_STRING_T {
                    length "0..255";
                }
                description "";
            } // END of bName definition.

            leaf flags  {
                type  cml_data_types:CML_GMPLS_BIDIRECTIONAL_FLAG_T;
                config false;
                description "";
            } // END of flags definition.


            list ilm {
                key "ilmInLabel";
                description
                    "ilm";
                leaf ilmInLabel  {
                    type  cml_data_types:CML_STRING_T {
                        length "0..255";
                    }
                    description "";
                } // END of ilmInLabel definition.


                list ilmData {
                    key "inIfName";
                    description
                        "ilmData";
                    leaf inIfName  {
                        type  cml_data_types:CML_STRING_T {
                            length "0..255";
                        }
                        description "";
                    } // END of inIfName definition.

                    leaf opCode  {
                        type  cml_data_types:CML_MPLS_VPLS_OPCODE_T;
                        description "";
                    } // END of opCode definition.

                    leaf popOpCode  {
                        type  cml_data_types:CML_MPLS_VPLS_POPOPCODE_T;
                        description "";
                    } // END of popOpCode definition.

                    leaf outLabel  {
                        type  cml_data_types:CML_STRING_T {
                            length "0..255";
                        }
                        description "";
                    } // END of outLabel definition.

                    leaf outIfName  {
                        type  cml_data_types:CML_STRING_T {
                            length "0..255";
                        }
                        description "";
                    } // END of outIfName definition.

                    leaf ilmNexthopIpAddr  {
                        type  cml_data_types:CML_IPV4_ADDR_T;
                        default "255.255.255.255";
                        description "";
                    } // END of ilmNexthopIpAddr definition.

                    leaf ilmFecAddr  {
                        type  cml_data_types:CML_IPV4_PREFIX_T;
                        description "";
                    } // END of ilmFecAddr definition.

                    leaf ilmIndex  {
                        type  cml_data_types:CML_UINT32_T {
                             range "1..4294967295";
                        }
                        description "";
                    } // END of ilmIndex definition.

                } // End of ilmData-list
            } // End of ilm-list
        } // End of bidirectionalIlmEntry-list
    } // END of bidirectionalIlmEntry-grouping definition.


    grouping unidirectionalIlm-grouping {
    description
        "unidirectionalIlm";
        list unidirectionalIlm {
            key "inLabel";
            description
                "unidirectionalIlm";
            leaf inLabel  {
                type  cml_data_types:CML_STRING_T {
                    length "0..255";
                }
                description "";
            } // END of inLabel definition.


            list ilmData {
                key "inIfName";
                description
                    "ilmData";
                leaf inIfName  {
                    type  cml_data_types:CML_STRING_T {
                        length "0..255";
                    }
                    description "";
                } // END of inIfName definition.

                leaf opCode  {
                    type  cml_data_types:CML_MPLS_IPV6OPCODE_T;
                    description "";
                } // END of opCode definition.

                leaf popOpCode  {
                    type  cml_data_types:CML_MPLS_VPLS_POPOPCODE_T;
                    description "";
                } // END of popOpCode definition.

                leaf outLabel  {
                    type  cml_data_types:CML_STRING_T {
                        length "0..255";
                    }
                    description "";
                } // END of outLabel definition.

                leaf outIfName  {
                    type  cml_data_types:CML_STRING_T {
                        length "0..255";
                    }
                    description "";
                } // END of outIfName definition.

                leaf ilmNexthopIpAddr  {
                    type  cml_data_types:CML_IPV4_ADDR_T;
                    default "255.255.255.255";
                    description "";
                } // END of ilmNexthopIpAddr definition.

                leaf ilmFecAddr  {
                    type  cml_data_types:CML_IPV4_PREFIX_T;
                    description "";
                } // END of ilmFecAddr definition.

                leaf ilmIndex  {
                    type  cml_data_types:CML_UINT32_T {
                         range "1..4294967295";
                    }
                    description "";
                } // END of ilmIndex definition.

            } // End of ilmData-list
        } // End of unidirectionalIlm-list
    } // END of unidirectionalIlm-grouping definition.

    grouping  datalinkTree-grouping {
    description
        "datalinkTree";
    container datalinkTree {
        presence "yes";
        description
            "datalinkTree";
        leaf gmplsType  {
            type  cml_data_types:CML_GMPLS_TYPE_T;
            mandatory true;
            description "";
        } // END of gmplsType definition.

        leaf switchingCap  {
            type  cml_data_types:CML_GMPLS_CAPABILITY_TYPE_T;
            description "";
        } // END of switchingCap definition.

        leaf desc  {
            type  cml_data_types:CML_STRING_T {
                length "0..255";
            }
            config false;
            description "";
        } // END of desc definition.

        leaf flags  {
            type  cml_data_types:CML_UINT16_T;
            config false;
            description "";
        } // END of flags definition.

        leaf gifindex  {
            type  cml_data_types:CML_UINT32_T;
            config false;
            description "";
        } // END of gifindex definition.

        leaf lLinkIdType  {
            type  cml_data_types:CML_UINT8_T;
            config false;
            description "";
        } // END of lLinkIdType definition.

        leaf lLinkId  {
            type  cml_data_types:CML_IPV4_ADDR_T;
            description "";
        } // END of lLinkId definition.

        leaf rLinkIdType  {
            type  cml_data_types:CML_UINT8_T;
            config false;
            description "";
        } // END of rLinkIdType definition.

        leaf rLinkId  {
            type  cml_data_types:CML_IPV4_ADDR_T;
            description "";
        } // END of rLinkId definition.

        container linkProperties {
            description
                "linkProperties";
            leaf maxLspSize  {
                type  cml_data_types:CML_STRING_T {
                    length "0..255";
                }
                default "NULL";
                description "";
            } // END of maxLspSize definition.

            leaf maxLspBw  {
                type  cml_data_types:CML_STRING_T {
                    length "0..255";
                }
                config false;
                description "";
            } // END of maxLspBw definition.

            leaf bandwidth  {
                type  cml_data_types:CML_STRING_T {
                    length "0..255";
                }
                config false;
                description "";
            } // END of bandwidth definition.

            leaf maxResvBw  {
                type  cml_data_types:CML_STRING_T {
                    length "0..255";
                }
                config false;
                description "";
            } // END of maxResvBw definition.

            leaf teclPriorityBw  {
                type  cml_data_types:CML_STRING_T {
                    length "0..255";
                }
                config false;
                description "";
            } // END of teclPriorityBw definition.

            leaf aggrRsvdBw  {
                type  cml_data_types:CML_STRING_T {
                    length "0..255";
                }
                config false;
                description "";
            } // END of aggrRsvdBw definition.

            leaf bwConstraint  {
                type  cml_data_types:CML_STRING_T {
                    length "0..255";
                }
                config false;
                description "";
            } // END of bwConstraint definition.

            leaf ctAggrRsvdBw  {
                type  cml_data_types:CML_STRING_T {
                    length "0..255";
                }
                config false;
                description "";
            } // END of ctAggrRsvdBw definition.

        } // END of linkProperties-container definition.
    } // END of datalinkTree-container definition.
    } // END of datalinkTree-container definition.


}
