/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-dhcpr.yang
*
*/

submodule zebos-dhcpr {

    belongs-to  zebos { prefix zebos; }

    import cml_data_types {
        prefix cml_data_types;
    }

    include zebos-interface;
    organization
        "IP Infusion Inc.";

    contact
        "Address: 3965 Freedom Circle, Suite 200, Santa Clara, CA 95054
        Phone: +1 408-400-1900
        E-mail: support@ipinfusion.com
        Web: http://www.ipinfusion.com/";

    description
        "dhcp_relay_configuration";


    revision "2018-06-21" {
        description " Initial Version.";
        reference "";
    }



    grouping dhcprelayinterface-grouping {
    description
        "DHCP interface related operations";
        list dhcprelayinterface {
            key "ifName";
            description
                "DHCP interface related operations";
            leaf ifName  {
                type  cml_data_types:CML_STRING_T {
                    length "0..255";
                }
                description "";
            } // END of ifName definition.

            leaf-list address  {
                type  cml_data_types:CML_IPV4_ADDR_T;
                description "";
            } // END of address definition.

        } // End of dhcprelayinterface-list
    } // END of dhcprelayinterface-grouping definition.


    grouping dhcp6nterface-grouping {
    description
        "DHCP interface related operations";
        list dhcp6nterface {
            key "ifName";
            description
                "DHCP interface related operations";
            leaf ifName  {
                type  cml_data_types:CML_STRING_T {
                    length "0..255";
                }
                description "";
            } // END of ifName definition.


            list dhcprelayaddress6 {
                key "ipv6address";
                description
                    "dhcprelayaddress6";
                leaf ipv6address  {
                    type  cml_data_types:CML_IPV6_ADDR_T;
                    description "";
                } // END of ipv6address definition.

                leaf interface  {
                    type  cml_data_types:CML_STRING_T {
                        length "0..255";
                    }
                    description "";
                } // END of interface definition.

            } // End of dhcprelayaddress6-list
        } // End of dhcp6nterface-list
    } // END of dhcp6nterface-grouping definition.

    grouping  dhcprelay-grouping {
    description
        "dhcprelay";
    container dhcprelay {
        description
            "dhcprelay";
        leaf relay  {
            type  cml_data_types:CML_BOOL_T;
            description "";
        } // END of relay definition.

        leaf option  {
            type  cml_data_types:CML_BOOL_T;
            description "";
        } // END of option definition.

    } // END of dhcprelay-container definition.
    } // END of dhcprelay-container definition.

    grouping  dhcprelay6-grouping {
    description
        "DHCP";
    container dhcprelay6 {
        description
            "DHCP";
        leaf relay6  {
            type  cml_data_types:CML_BOOL_T;
            description "";
        } // END of relay6 definition.

    } // END of dhcprelay6-container definition.
    } // END of dhcprelay6-container definition.


}
