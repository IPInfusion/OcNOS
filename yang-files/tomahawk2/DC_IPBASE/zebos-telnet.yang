/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-telnet.yang
*
*/

submodule zebos-telnet {

    belongs-to  zebos { prefix zebos; }

    import cml_data_types {
        prefix cml_data_types;
    }

    import feature_list {
        prefix feature_list;
    }

    include zebos-vrf;
    organization
        "IP Infusion Inc.";

    contact
        "Address: 3965 Freedom Circle, Suite 200, Santa Clara, CA 95054
        Phone: +1 408-400-1900
        E-mail: support@ipinfusion.com
        Web: http://www.ipinfusion.com/";

    description
        "Telnet configurations";


    revision "2018-06-21" {
        description " Initial Version.";
        reference "";
    }



    grouping telnetVrfInstance-grouping {
    description
        "telnet vrf instance";
        list telnetVrfInstance {
            key "vrfName";
            description
                "telnet vrf instance";
            leaf vrfName  {
                type  cml_data_types:CML_STRING_T;
                description "";
            } // END of vrfName definition.

            leaf featureTelnet  {
                type  cml_data_types:CML_BOOL_T;
                description "";
            } // END of featureTelnet definition.

            leaf port  {
                if-feature feature_list:HAVE_TELNET_SERVER;
                type  cml_data_types:CML_INT32_T {
                     range "1024..65535";
                }
                description "";
            } // END of port definition.

        } // End of telnetVrfInstance-list
    } // END of telnetVrfInstance-grouping definition.

    grouping  debugTELNETconfig-grouping {
    description
        "telnet related operations";
    container debugTELNETconfig {
        description
            "telnet related operations";
        leaf debugtelnet  {
            if-feature feature_list:HAVE_TELNET_SERVER;
            type  cml_data_types:CML_BOOL_T;
            default false;
            description "";
        } // END of debugtelnet definition.

    } // END of debugTELNETconfig-container definition.
    } // END of debugTELNETconfig-container definition.


}
