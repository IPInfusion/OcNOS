/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-nsmsnmp.yang
*
*/

submodule zebos-nsmsnmp {

    belongs-to  zebos { prefix zebos; }

    import cml_data_types {
        prefix cml_data_types;
    }

    import feature_list {
        prefix feature_list;
    }

    include zebos-vrf;
    organization
        "IP Infusion Inc.";

    contact
        "Address: 3965 Freedom Circle, Suite 200, Santa Clara, CA 95054
        Phone: +1 408-400-1900
        E-mail: support@ipinfusion.com
        Web: http://www.ipinfusion.com/";

    description
        "Simple Network Management Protocol";


    revision "2018-06-21" {
        description " Initial Version.";
        reference "";
    }



    grouping nsmsnmp-grouping {
    description
        "snmp  related operations";
        list nsmsnmp {
            key "vrfName";
            description
                "snmp  related operations";
            leaf vrfName  {
                type  cml_data_types:CML_STRING_T;
                description "";
            } // END of vrfName definition.

            leaf enabled  {
                type  cml_data_types:CML_SNMP_ENABLE_T;
                description "";
            } // END of enabled definition.

            leaf syscontact  {
                if-feature feature_list:HAVE_SNMP_AGENT;
                type  cml_data_types:CML_LINE_T;
                description "";
            } // END of syscontact definition.

            leaf syslocation  {
                if-feature feature_list:HAVE_SNMP_AGENT;
                type  cml_data_types:CML_LINE_T;
                description "";
            } // END of syslocation definition.

        } // End of nsmsnmp-list
    } // END of nsmsnmp-grouping definition.


}
