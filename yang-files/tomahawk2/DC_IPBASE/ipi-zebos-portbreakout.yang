/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-zebos-portbreakout.yang
*
*/

submodule ipi-zebos-portbreakout {

    belongs-to  ipi-zebos { prefix ipi-zebos; }

    import cml-data-types {
        prefix cml-data-types;
    }

    organization
        "IP Infusion Inc.";

    contact
        "Address: 3965 Freedom Circle, Suite 200, Santa Clara, CA 95054
        Phone: +1 408-400-1900
        E-mail: support@ipinfusion.com
        Web: http://www.ipinfusion.com/";

    description
        "Datamodel for port breakout object";


    revision "2018-09-17" {
        description " Initial Version.";
        reference "";
    }



    grouping portBreakout-grouping {
    description
        "port breakout object";
        list portBreakout {
            key "portNum";
            description
                "port breakout object";
            leaf portNum  {
                type  cml-data-types:CML_UINT8_T {
                     range "1..125";
                }
                description "The port number";
            } // END of portNum definition.

            leaf breakout  {
                type  cml-data-types:CML_NSM_BREAKOUT_TYPE_T;
                mandatory true;
                description "The breakout mode of the port.";
            } // END of breakout definition.

        } // End of portBreakout-list
    } // END of portBreakout-grouping definition.


    grouping portGroupSpeed-grouping {
    description
        "port group speed object";
        list portGroupSpeed {
            key "portGroup";
            description
                "port group speed object";
            leaf portGroup  {
                type  cml-data-types:CML_UINT8_T {
                     range "1..64";
                }
                description "The port group number";
            } // END of portGroup definition.

            leaf speed  {
                type  cml-data-types:CML_NSM_PORT_GROUP_SPEED_T;
                mandatory true;
                description "The speed mode of the port.";
            } // END of speed definition.

        } // End of portGroupSpeed-list
    } // END of portGroupSpeed-grouping definition.


}
