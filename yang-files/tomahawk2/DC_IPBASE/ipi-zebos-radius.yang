/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-zebos-radius.yang
*
*/

submodule ipi-zebos-radius {

    belongs-to  ipi-zebos { prefix ipi-zebos; }

    import cml-data-types {
        prefix cml-data-types;
    }

    import feature-list {
        prefix feature-list;
    }

    include ipi-zebos-vrf;
    organization
        "IP Infusion Inc.";

    contact
        "Address: 3965 Freedom Circle, Suite 200, Santa Clara, CA 95054
        Phone: +1 408-400-1900
        E-mail: support@ipinfusion.com
        Web: http://www.ipinfusion.com/";

    description
        "Layer-3 radius configurations";


    revision "2018-06-21" {
        description " Initial Version.";
        reference "";
    }



    grouping radius-grouping {
    description
        "radius related commands";
        list radius {
            if-feature feature-list:HAVE_AAA;
            key "vrfName";
            description
                "radius related commands";
            leaf vrfName  {
                type  cml-data-types:CML_STRING_T;
                description "";
            } // END of vrfName definition.

            leaf globalTimeout  {
                type  cml-data-types:CML_UINT32_T {
                     range "1..60";
                }
                default "5";
                description "";
            } // END of globalTimeout definition.

            leaf key  {
                type  cml-data-types:CML_BOOL_T;
                description "";
            } // END of key definition.

            leaf globalKeytype  {
                type  cml-data-types:CML_HOSTP_KEY_TYPE_T;
                default "0";
                description "";
            } // END of globalKeytype definition.

            leaf globalKeyword  {
                type  cml-data-types:CML_STRING_T {
                    length "1..63";
                }
                description "";
            } // END of globalKeyword definition.


            list Hostpdradius {
                key "hostAddr";
                description
                    "hostaddr structure";
                leaf hostAddr  {
                    type  cml-data-types:CML_STRING_T {
                        length "1..63";
                    }
                    description "";
                } // END of hostAddr definition.

                leaf seqNum  {
                    type  cml-data-types:CML_UINT8_T {
                         range "1..8";
                    }
                    mandatory true;
                    description "";
                } // END of seqNum definition.

                leaf key  {
                    type  cml-data-types:CML_BOOL_T;
                    description "";
                } // END of key definition.

                leaf keyType  {
                    type  cml-data-types:CML_HOSTP_KEY_TYPE_T;
                    default "0";
                    description "";
                } // END of keyType definition.

                leaf keyWord  {
                    type  cml-data-types:CML_STRING_T {
                        length "1..63";
                    }
                    description "";
                } // END of keyWord definition.

                leaf authPort  {
                    type  cml-data-types:CML_UINT32_T {
                         range "0..65535";
                    }
                    default "1812";
                    description "";
                } // END of authPort definition.

                leaf acctPort  {
                    type  cml-data-types:CML_UINT32_T {
                         range "0..65535";
                    }
                    default "1813";
                    description "";
                } // END of acctPort definition.

                leaf timeout  {
                    type  cml-data-types:CML_UINT32_T {
                         range "1..60";
                    }
                    default "5";
                    description "";
                } // END of timeout definition.

            } // End of Hostpdradius-list
        } // End of radius-list
    } // END of radius-grouping definition.

    grouping  radiusDebug-grouping {
    description
        "debug radius commands";
    container radiusDebug {
        description
            "debug radius commands";
        leaf debugradius  {
            type  cml-data-types:CML_BOOL_T;
            description "";
        } // END of debugradius definition.

        leaf debugradiusconfig  {
            type  cml-data-types:CML_BOOL_T;
            description "";
        } // END of debugradiusconfig definition.

    } // END of radiusDebug-container definition.
    } // END of radiusDebug-container definition.


}
