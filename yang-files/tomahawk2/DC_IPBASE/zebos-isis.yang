/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-isis.yang
*
*/

submodule zebos-isis {

    belongs-to  zebos { prefix zebos; }

    import cml_data_types {
        prefix cml_data_types;
    }

    import feature_list {
        prefix feature_list;
    }

    include zebos-interface;
    include zebos-vrf;
    organization
        "IP Infusion Inc.";

    contact
        "Address: 3965 Freedom Circle, Suite 200, Santa Clara, CA 95054
        Phone: +1 408-400-1900
        E-mail: support@ipinfusion.com
        Web: http://www.ipinfusion.com/";

    description
        "Intermediate System - Intermediate System (IS-IS)";


    revision "2018-06-21" {
        description " Initial Version.";
        reference "";
    }

    grouping redistgrp {
        description
            "redistgrp";
        leaf redistlevel  {
            type  cml_data_types:CML_IS_TYPE3_T;
            default "level-2";
            description "";
        } // END of redistlevel definition.

        leaf redistmetric  {
            type  cml_data_types:CML_UINT32_T {
                 range "0..4261412864";
            }
            default "0";
            description "IS-IS metric";
        } // END of redistmetric definition.

        leaf redistmetrictype  {
            type  cml_data_types:CML_ISIS_METRIC_T;
            default "internal";
            description "External metric type, (Internal|External)";
        } // END of redistmetrictype definition.

        leaf redistroute  {
            type  cml_data_types:CML_STRING_T;
            default "";
            description "Name of route-map";
        } // END of redistroute definition.

    } // END of redistgrp definition.
    grouping neighborattributes {
        description
            "neighborattributes";
        leaf nbrAdjflags  {
            type  cml_data_types:CML_ISIS_NBR_ADJ_T;
            config false;
            description "isis_neighbor - Flags";
        } // END of nbrAdjflags definition.

        leaf nbr_mac  {
            type  cml_data_types:CML_STRING_T;
            config false;
            description "MAC address";
        } // END of nbr_mac definition.

        leaf nbr_topology_type  {
            type  cml_data_types:CML_STRING_T;
            config false;
            description "Multi topology type";
        } // END of nbr_topology_type definition.

        leaf nbr_uptime  {
            type  cml_data_types:CML_STRING_T;
            config false;
            description "Uptime";
        } // END of nbr_uptime definition.

        leaf nbr_proto  {
            type  cml_data_types:CML_STRING_T;
            config false;
            description "Protocol";
        } // END of nbr_proto definition.


        list AreaAddressCount {
            key "nbrAreaCount";
            config false;
            description
                "Area Address(es) counter";
            leaf nbrAreaCount  {
                type  cml_data_types:CML_INT8_T;
                description "Neighbor Area Addresses count";
            } // END of nbrAreaCount definition.

            container AreaAddress {
                config false;
                description
                    "Area Address(es)";
                leaf nbr_area_vec  {
                    type  cml_data_types:CML_STRING_T;
                    description "Area addresses";
                } // END of nbr_area_vec definition.

            } // END of AreaAddress-container definition.
        } // End of AreaAddressCount-list

        list IpAddressCount {
            key "nbrIpCount";
            config false;
            description
                "IP Address(es) counter";
            leaf nbrIpCount  {
                type  cml_data_types:CML_INT8_T;
                description "Neighbor IP Addresses count";
            } // END of nbrIpCount definition.

            container IpAddress {
                config false;
                description
                    "IP Address(es)";
                leaf nbr_ip_vec  {
                    type  cml_data_types:CML_IPV4_ADDR_T;
                    description "Neighbor IP Addresses";
                } // END of nbr_ip_vec definition.

            } // END of IpAddress-container definition.
        } // End of IpAddressCount-list

        list Ipv6AddressCount {
            key "nbrIpv6Count";
            config false;
            description
                "IPv6 Address(es) counter";
            leaf nbrIpv6Count  {
                type  cml_data_types:CML_INT8_T;
                description "Neighbor IPv6 Addresses count";
            } // END of nbrIpv6Count definition.

            container Ipv6Address {
                config false;
                description
                    "IPv6 Address(es)";
                leaf nbr_ipv6_vec  {
                    type  cml_data_types:CML_IPV4_ADDR_T;
                    description "Neighbor IPv6 Addresses";
                } // END of nbr_ipv6_vec definition.

            } // END of Ipv6Address-container definition.
        } // End of Ipv6AddressCount-list
    } // END of neighborattributes definition.
    grouping isisPath {
        description
            "isisPath";
        container pathattrs {
            config false;
            description
                "pathattrs";
            leaf path_flags  {
                type  cml_data_types:CML_UINT8_T;
                description "Path type flags";
            } // END of path_flags definition.

            leaf path_redist  {
                type  cml_data_types:CML_UINT8_T;
                description "Redistribute Path Flag";
            } // END of path_redist definition.

            leaf path_lock  {
                type  cml_data_types:CML_UINT16_T;
                description "Path Lock";
            } // END of path_lock definition.

            leaf path_metric  {
                type  cml_data_types:CML_UINT32_T;
                description "Path Metric";
            } // END of path_metric definition.

            leaf path_tag  {
                type  cml_data_types:CML_UINT32_T;
                description "Path admin tag value";
            } // END of path_tag definition.

            leaf tag_present  {
                type  cml_data_types:CML_BOOL_T;
                description "set if admin tag is present";
            } // END of tag_present definition.

            leaf path_t_metric  {
                if-feature feature_list:HAVE_MPLS;
                type  cml_data_types:CML_BOOL_T;
                description "Tunnel Nexthop vector-metric";
            } // END of path_t_metric definition.


            list nexthop {
                key "nexthop_source_id";
                config false;
                description
                    "IS-IS IP netxthop";
                leaf nexthop_flags  {
                    type  cml_data_types:CML_UINT8_T;
                    description "Nexthop flags";
                } // END of nexthop_flags definition.

                leaf nexthop_ifindex  {
                    type  cml_data_types:CML_UINT32_T;
                    description "Nexthop interface index";
                } // END of nexthop_ifindex definition.

                leaf nexthop_source_id  {
                    type  cml_data_types:CML_STRING_T;
                    description "Nexthop neighbor source ID";
                } // END of nexthop_source_id definition.

                leaf nexthop_lock  {
                    type  cml_data_types:CML_UINT32_T;
                    description "Nexthop neighbor Lock";
                } // END of nexthop_lock definition.

                leaf ip_addr  {
                    type  cml_data_types:CML_STRING_T;
                    description "Selected nexthops IP interface address";
                } // END of ip_addr definition.

                leaf ipv6_addr  {
                    if-feature feature_list:HAVE_IPV6;
                    type  cml_data_types:CML_STRING_T;
                    description "Selected nexthop's IPv6 interface linklocal address";
                } // END of ipv6_addr definition.

            } // End of nexthop-list
            uses tlv;
        } // END of pathattrs-container definition.
    } // END of isisPath definition.
    grouping tlv {
        description
            "IS-IS tlv";

        list tlv_elements {
            key "tlvtype";
            config false;
            description
                "tlvCMLSEPelements";
            leaf tlvtype  {
                type  cml_data_types:CML_UINT8_T;
                description "TLV type";
            } // END of tlvtype definition.

            leaf tlvlength  {
                type  cml_data_types:CML_UINT8_T;
                description "TLV length";
            } // END of tlvlength definition.

            leaf tlvlentmp  {
                type  cml_data_types:CML_UINT8_T;
                description "TLV length not committed";
            } // END of tlvlentmp definition.

            leaf tlvflags  {
                type  cml_data_types:CML_UINT8_T;
                description "TLV flags";
            } // END of tlvflags definition.

            leaf tlvslot  {
                type  cml_data_types:CML_UINT8_T;
                description "Allocated slot";
            } // END of tlvslot definition.

            leaf tlvbody  {
                type  cml_data_types:CML_STRING_T;
                description "TLV body";
            } // END of tlvbody definition.

        } // End of tlv_elements-list
    } // END of tlv definition.
    grouping igpshortcutlsp {
        description
            "igpshortcutlsp";

        list igpshortcutlsp {
            key "igpmetric";
            config false;
            description
                "igpshortcutlsp";
            leaf igpmetric  {
                type  cml_data_types:CML_UINT16_T;
                description "";
            } // END of igpmetric definition.

            leaf igptunnel_id  {
                type  cml_data_types:CML_UINT32_T;
                description "";
            } // END of igptunnel_id definition.

            leaf igpt_endp  {
                type  cml_data_types:CML_STRING_T;
                description "";
            } // END of igpt_endp definition.

            leaf igplock  {
                type  cml_data_types:CML_UINT16_T;
                description "";
            } // END of igplock definition.

            leaf igp_flags  {
                type  cml_data_types:CML_UINT8_T;
                description "";
            } // END of igp_flags definition.

        } // End of igpshortcutlsp-list
    } // END of igpshortcutlsp definition.

    grouping  isismaster-grouping {
    description
        "IS-IS master for instance wide configurations";
    container isismaster {
        description
            "IS-IS master for instance wide configurations";
        leaf reach_map_delay  {
            type  cml_data_types:CML_STRING_T;
            config false;
            description "IS-IS reachability timer delay";
        } // END of reach_map_delay definition.

        leaf lsp_refresh_delay  {
            type  cml_data_types:CML_STRING_T;
            config false;
            description "IS-IS LSP refresh timer delay";
        } // END of lsp_refresh_delay definition.


        list hostentry {
            key "hostnameisis";
            config false;
            description
                "IS-IS dynamic hostname table";
            leaf mtime  {
                type  cml_data_types:CML_STRING_T;
                description "Timeatamp";
            } // END of mtime definition.

            leaf hostnameisis  {
                type  cml_data_types:CML_STRING_T;
                description "Hostname";
            } // END of hostnameisis definition.

        } // End of hostentry-list

        list isistop {
            key "isisInstanceTag";
            description
                "IS-IS structure";
            leaf isisInstanceTag  {
                type  cml_data_types:CML_STRING_T;
                description "";
            } // END of isisInstanceTag definition.

            leaf vrfName  {
                if-feature feature_list:HAVE_VRF_ISIS;
                type  cml_data_types:CML_STRING_T;
                description "VRF Name to associate with this instance";
            } // END of vrfName definition.

            leaf instance_id  {
                type  cml_data_types:CML_UINT32_T;
                config false;
                description "Instance ID";
            } // END of instance_id definition.

            leaf dynamicHostname  {
                type  cml_data_types:CML_ISIS_DYNAMIC_HOSTANME_T;
                default "dynamic-hostname";
                description "flag Method for dynamic-hostname";
            } // END of dynamicHostname definition.

            leaf adjacencyCheck  {
                type  cml_data_types:CML_BOOL_T;
                description "";
            } // END of adjacencyCheck definition.

            leaf ignore-lsp-errors  {
                type  cml_data_types:CML_BOOL_T;
                description "ignore-lsp-errors";
            } // END of ignore-lsp-errors definition.

            leaf lfaHoldTimer  {
                if-feature feature_list:HAVE_ISIS_LFA;
                type  cml_data_types:CML_INT32_T {
                     range "100..100000";
                }
                default "1000";
                description "";
            } // END of lfaHoldTimer definition.

            leaf starttime  {
                type  cml_data_types:CML_UINT32_T;
                config false;
                description "IS-IS start time";
            } // END of starttime definition.

            leaf prcmindelay  {
                type  cml_data_types:CML_UINT32_T {
                     range "0..2147483647";
                }
                default "500";
                description "Minimum delay between receiving a change to SPF calculation in milliseconds 0-2147483647";
            } // END of prcmindelay definition.

            leaf prcmaxdelay  {
                type  cml_data_types:CML_UINT32_T {
                     range "0..2147483647";
                }
                default "50000";
                description "Maximum delay between receiving a change to SPF calculation in milliseconds 0-2147483647";
            } // END of prcmaxdelay definition.

            leaf areaPassword  {
                type  cml_data_types:CML_STRING_T;
                description "Authentication key";
            } // END of areaPassword definition.

            leaf area-snp  {
                type  cml_data_types:CML_ISIS_SNP_T;
                description "authenticate snp  (send-only|validate)";
            } // END of area-snp definition.

            leaf domainPassword  {
                type  cml_data_types:CML_STRING_T;
                description "Authentication key";
            } // END of domainPassword definition.

            leaf domain-snp  {
                type  cml_data_types:CML_ISIS_SNP_T;
                description "authenticate snp  (send-only|validate)";
            } // END of domain-snp definition.

            leaf metricStyle  {
                if-feature feature_list:HAVE_WIDE_METRIC;
                type  cml_data_types:CML_METRIC_STYLE_T;
                description "metric-style value";
            } // END of metricStyle definition.

            leaf metricLevel  {
                if-feature feature_list:HAVE_WIDE_METRIC;
                type  cml_data_types:CML_ISIS_LEVEL3_T;
                description "metric-style value";
            } // END of metricLevel definition.

            leaf protocoltopology  {
                if-feature feature_list:HAVE_PROTOCOL_TOPOLOGY;
                type  cml_data_types:CML_BOOL_T;
                description "Protocol Topology";
            } // END of protocoltopology definition.

            leaf-list net  {
                type  cml_data_types:CML_STRING_T;
                description "Network entity title in string";
            } // END of net definition.

            leaf is-type  {
                type  cml_data_types:CML_IS_TYPE_T;
                default "level-1-2";
                description "IS-IS instance level type (1|2|3)";
            } // END of is-type definition.

            leaf ispflevels  {
                type  cml_data_types:CML_IS_TYPE_T;
                default "level-1-2";
                description "The iSPF level";
            } // END of ispflevels definition.

            leaf topprototype  {
                type  cml_data_types:CML_UINT8_T;
                config false;
                description "IS-IS protocols supported";
            } // END of topprototype definition.

            leaf priorityTag  {
                if-feature feature_list:HAVE_WIDE_METRIC;
                type  cml_data_types:CML_UINT32_T {
                     range "1..4294967295";
                }
                description "IS-IS priority tag";
            } // END of priorityTag definition.

            leaf addfamily  {
                type  cml_data_types:CML_UINT8_T;
                config false;
                description "RIP Address Family";
            } // END of addfamily definition.

            leaf adminflags  {
                type  cml_data_types:CML_UINT8_T;
                config false;
                description "IS-IS administrative flags";
            } // END of adminflags definition.

            leaf cspf_flag  {
                if-feature feature_list:HAVE_ISIS_CSPF;
                type  cml_data_types:CML_BOOL_T;
                description "";
            } // END of cspf_flag definition.

            leaf bfdall  {
                type  cml_data_types:CML_BOOL_T;
                description "isis bfd config flag";
            } // END of bfdall definition.

            leaf max-area-address  {
                type  cml_data_types:CML_UINT8_T {
                     range "3..254";
                }
                default "3";
                description "limit The maximum number of areas in the network <3-254>";
            } // END of max-area-address definition.

            leaf lsp-refresh-interval  {
                type  cml_data_types:CML_UINT16_T {
                     range "1..65535";
                }
                default "900";
                description "Interval in seconds";
            } // END of lsp-refresh-interval definition.

            leaf max-lsp-lifetime  {
                type  cml_data_types:CML_UINT16_T {
                     range "350..65535";
                }
                default "1200";
                description "Maximum LSP lifetime in seconds";
            } // END of max-lsp-lifetime definition.

            leaf router-id  {
                if-feature feature_list:HAVE_ISIS_TE;
                type  cml_data_types:CML_IPV4_ADDR_T;
                description "Router ID to be set";
            } // END of router-id definition.

            leaf overloadtimerflags  {
                type  cml_data_types:CML_UINT8_T;
                config false;
                description "Overload timer flags to capture the overload state of the system";
            } // END of overloadtimerflags definition.

            leaf overloadstartedval  {
                type  cml_data_types:CML_UINT32_T;
                config false;
                description "Overload interval the timer is started with";
            } // END of overloadstartedval definition.

            leaf tvoverload  {
                type  cml_data_types:CML_STRING_T;
                config false;
                description "Overload interval start time";
            } // END of tvoverload definition.


            list areaaddr {
                key "addressarea";
                config false;
                description
                    "Manual Area Addresses";
                leaf addressarea  {
                    type  cml_data_types:CML_STRING_T;
                    description "Manual Area Addresses";
                } // END of addressarea definition.

            } // End of areaaddr-list

            list recvaddr {
                key "addressrecvarea";
                config false;
                description
                    "Manual Area Addresses";
                leaf addressrecvarea  {
                    type  cml_data_types:CML_STRING_T;
                    description "Rcv Area Addresses - other than already in Manual area addr list";
                } // END of addressrecvarea definition.

            } // End of recvaddr-list

            list passive {
                key "passiveifName";
                description
                    "Suppress routing updates";
                leaf passiveifName  {
                    type  cml_data_types:CML_STRING_T;
                    description "Interface name";
                } // END of passiveifName definition.

            } // End of passive-list

            list protoipv6 {
                key "isAddrFamily";
                description
                    "IS-IS protocol IPV6";
                leaf isAddrFamily  {
                    type  cml_data_types:CML_ISIS_ADDRESS_IPV6_T;
                    description "address-family";
                } // END of isAddrFamily definition.

                leaf pindex6  {
                    type  cml_data_types:CML_UINT8_T;
                    config false;
                    description "Index of protocol";
                } // END of pindex6 definition.

                leaf ipv6redistribute1to2  {
                    type  cml_data_types:CML_BOOL_T;
                    description "";
                } // END of ipv6redistribute1to2 definition.

                leaf ipv6redistribute2to1  {
                    type  cml_data_types:CML_BOOL_T;
                    description "";
                } // END of ipv6redistribute2to1 definition.

                leaf ipv6redistributelist1to2  {
                    type  cml_data_types:CML_STRING_T;
                    description "";
                } // END of ipv6redistributelist1to2 definition.

                leaf ipv6redistributelist2to1  {
                    type  cml_data_types:CML_STRING_T;
                    description "";
                } // END of ipv6redistributelist2to1 definition.

                leaf originate6  {
                    type  cml_data_types:CML_ISIS_ORIGIN_TYPE_T;
                    description "";
                } // END of originate6 definition.

                leaf rmapName6  {
                    type  cml_data_types:CML_STRING_T;
                    default "";
                    description "";
                } // END of rmapName6 definition.

                leaf AddrDistance  {
                    type  cml_data_types:CML_UINT8_T {
                         range "1..255";
                    }
                    default "115";
                    description "Administrative distance";
                } // END of AddrDistance definition.

                leaf adjacency-check6  {
                    type  cml_data_types:CML_BOOL_T;
                    description "adjacency-check";
                } // END of adjacency-check6 definition.

                leaf ipv6redistupdate  {
                    type  cml_data_types:CML_INT32_T;
                    config false;
                    description "Redistrubution timer argument";
                } // END of ipv6redistupdate definition.

                leaf ipv6tvredist  {
                    type  cml_data_types:CML_STRING_T;
                    config false;
                    description "Redistribution last performed";
                } // END of ipv6tvredist definition.


                list ipv6redistribute {
                    key "Ipv6redistribute";
                    description
                        "ipv6redistribute";
                    leaf Ipv6redistribute  {
                        type  cml_data_types:CML_ISIS_REDISTRIBUTE_T;
                        description "";
                    } // END of Ipv6redistribute definition.

                    container redistconf6 {
                        description
                            "redistconf6";
                        leaf redistflags  {
                            type  cml_data_types:CML_UINT8_T;
                            config false;
                            description "isis_redist_conf - flags";
                        } // END of redistflags definition.

                        leaf ipv6redistmetric  {
                            type  cml_data_types:CML_UINT32_T {
                                 range "0..4261412864";
                            }
                            default "0";
                            description "";
                        } // END of ipv6redistmetric definition.

                        leaf ipv6redistmetrictype  {
                            type  cml_data_types:CML_ISIS_METRIC_T;
                            default "internal";
                            description "";
                        } // END of ipv6redistmetrictype definition.

                        leaf ipv6redistroute  {
                            type  cml_data_types:CML_STRING_T;
                            default "";
                            description "";
                        } // END of ipv6redistroute definition.

                        leaf ipv6redistlevel  {
                            type  cml_data_types:CML_IS_TYPE3_T;
                            default "level-2";
                            description "";
                        } // END of ipv6redistlevel definition.

                    } // END of redistconf6-container definition.
                } // End of ipv6redistribute-list

                list summaryprefix {
                    key "summaryprefix";
                    description
                        "summaryprefix";
                    leaf summaryprefix  {
                        type  cml_data_types:CML_IPV6_PREFIX_T;
                        description "IPv6 network address";
                    } // END of summaryprefix definition.

                    leaf level-summary  {
                        type  cml_data_types:CML_ISIS_SUMMARY_LEVEL_T;
                        description "IS-IS instance level,(1|2|3)";
                    } // END of level-summary definition.

                    leaf summarymetric  {
                        type  cml_data_types:CML_UINT8_T {
                             range "1..63";
                        }
                        description "Metric value";
                    } // END of summarymetric definition.

                } // End of summaryprefix-list

                list multitopology {
                    if-feature feature_list:HAVE_MULTI_TOPOLOGY;
                    key "multitopologylevel";
                    description
                        "multitopology";
                    leaf multitopologylevel  {
                        type  cml_data_types:CML_ISIS_LEVEL3_T;
                        description "IS-IS instance level,(1|2|3)";
                    } // END of multitopologylevel definition.

                    leaf multitransition  {
                        type  cml_data_types:CML_BOOL_T;
                        description "";
                    } // END of multitransition definition.

                } // End of multitopology-list

                list route6 {
                    key "routedistance6";
                    config false;
                    description
                        "IS-IS routing table entry";
                    leaf irflags6  {
                        type  cml_data_types:CML_UINT8_T;
                        description "Flag used by iSPF and PRC";
                    } // END of irflags6 definition.

                    leaf routedistance6  {
                        type  cml_data_types:CML_UINT8_T;
                        description "Route distance";
                    } // END of routedistance6 definition.

                    uses isisPath;
                } // End of route6-list
                uses isisPath;
            } // End of protoipv6-list

            list levelOptional {
                key "level3types";
                description
                    "Level context with 3 options";
                leaf level3types  {
                    type  cml_data_types:CML_ISIS_LEVEL3_T;
                    description "IS-IS instance level,(1|2|3)";
                } // END of level3types definition.

                leaf waittimer  {
                    type  cml_data_types:CML_UINT16_T {
                         range "1..65535";
                    }
                    description "Number of seconds to delay in waiting state before on state";
                } // END of waittimer definition.

                leaf restarttimer  {
                    type  cml_data_types:CML_UINT16_T {
                         range "5..65535";
                    }
                    description "restart timer value";
                } // END of restarttimer definition.

            } // End of levelOptional-list

            list levelMandatory {
                key "level2Type";
                description
                    "Level context";
                leaf level2Type  {
                    type  cml_data_types:CML_ISIS_LEVEL2_T;
                    description "IS-IS instance level,(1|2)";
                } // END of level2Type definition.

                leaf trafficEng  {
                    if-feature feature_list:HAVE_ISIS_TE;
                    type  cml_data_types:CML_BOOL_T;
                    description "";
                } // END of trafficEng definition.


                list frrRouteMap {
                    key "frrRmapProto";
                    description
                        "Keeps priority values for each preference type";
                    leaf frrRmapProto  {
                        type  cml_data_types:CML_ISIS_LEVEL_PROTO_T;
                        description "";
                    } // END of frrRmapProto definition.

                    leaf frrRmapName  {
                        type  cml_data_types:CML_STRING_T;
                        description "";
                    } // END of frrRmapName definition.

                    leaf frrRmapAll  {
                        type  cml_data_types:CML_ISIS_FRR_ENUM_T;
                        description "";
                    } // END of frrRmapAll definition.

                } // End of frrRouteMap-list

                list frrProto {
                    if-feature feature_list:HAVE_ISIS_LFA;
                    key "frrLProto";
                    description
                        "Keeps user preferences for each of the LFA option";
                    leaf frrLProto  {
                        type  cml_data_types:CML_ISIS_LEVEL_PROTO_T;
                        description "";
                    } // END of frrLProto definition.


                    list frrTieBreak {
                        key "frrPrefVal";
                        description
                            "Keeps priority values for each preference type";
                        leaf frrPrefVal  {
                            type  cml_data_types:CML_ISIS_FRR_TIE_BREAK_VAL_T;
                            description "";
                        } // END of frrPrefVal definition.

                        leaf frrPrefIndex  {
                            type  cml_data_types:CML_UINT32_T {
                                 range "1..255";
                            }
                            mandatory true;
                            description "";
                        } // END of frrPrefIndex definition.

                    } // End of frrTieBreak-list
                } // End of frrProto-list
            } // End of levelMandatory-list

            list level {
                key "levelType";
                description
                    "Level context";
                leaf levelType  {
                    type  cml_data_types:CML_ISIS_LEVEL_T;
                    description "IS-IS instance level,(1|2|3)";
                } // END of levelType definition.

                leaf isislevelflags  {
                    type  cml_data_types:CML_UINT8_T;
                    config false;
                    description "IS-IS level context-Flags";
                } // END of isislevelflags definition.

                leaf lspgeninterval  {
                    type  cml_data_types:CML_UINT8_T {
                         range "1..120";
                    }
                    default "30";
                    description "lsp_gen_interval Interval in seconds 1-120";
                } // END of lspgeninterval definition.

                leaf spfmindelay  {
                    type  cml_data_types:CML_UINT32_T {
                         range "0..2147483647";
                    }
                    default "500";
                    description "Minimum delay between receiving a change to SPF calculation in milliseconds 0-2147483647";
                } // END of spfmindelay definition.

                leaf spfmaxdelay  {
                    type  cml_data_types:CML_UINT32_T {
                         range "0..2147483647";
                    }
                    default "5000";
                    description "Maximum delay between receiving a change to SPF calculation in milliseconds 0-2147483647";
                } // END of spfmaxdelay definition.

                leaf lspmtu  {
                    type  cml_data_types:CML_UINT16_T {
                         range "512..1492";
                    }
                    default "1492";
                    description "IS-IS size";
                } // END of lspmtu definition.

                leaf send-only  {
                    type  cml_data_types:CML_BOOL_T;
                    description "";
                } // END of send-only definition.

                leaf authMode  {
                    type  cml_data_types:CML_ISIS_AUTH_MODE_T;
                    description "authentication mode value (text|md5)";
                } // END of authMode definition.

                leaf keyChain  {
                    type  cml_data_types:CML_STRING_T;
                    description "Key chain used for authentication";
                } // END of keyChain definition.

                leaf topology_type  {
                    type  cml_data_types:CML_UINT8_T;
                    config false;
                    description "Topology type";
                } // END of topology_type definition.

                leaf tv_spf  {
                    type  cml_data_types:CML_STRING_T;
                    config false;
                    description "SPF calculation last performed.";
                } // END of tv_spf definition.

                leaf tv_spf_curr  {
                    type  cml_data_types:CML_STRING_T;
                    config false;
                    description "Current SPF calculation.";
                } // END of tv_spf_curr definition.

                leaf tv_prc  {
                    type  cml_data_types:CML_STRING_T;
                    config false;
                    description "PRC calculation last performed.";
                } // END of tv_prc definition.

                leaf tv_prc_curr  {
                    type  cml_data_types:CML_STRING_T;
                    config false;
                    description "Current PRC calculation.";
                } // END of tv_prc_curr definition.

                leaf prc_flags  {
                    type  cml_data_types:CML_UINT8_T;
                    config false;
                    description "";
                } // END of prc_flags definition.

                leaf auth_type_fails  {
                    type  cml_data_types:CML_UINT32_T;
                    config false;
                    description "isisSysStatAuthTypeFails";
                } // END of auth_type_fails definition.

                leaf auth_fails  {
                    type  cml_data_types:CML_UINT32_T;
                    config false;
                    description "isisSysStatAuthFails";
                } // END of auth_fails definition.

                leaf corrupted_lsps  {
                    type  cml_data_types:CML_UINT32_T;
                    config false;
                    description "isisSysStatCorrLSPs";
                } // END of corrupted_lsps definition.

                leaf lspdb_overloaded  {
                    type  cml_data_types:CML_UINT32_T;
                    config false;
                    description "isisSysStatLSPDbaseOloads";
                } // END of lspdb_overloaded definition.

                leaf man_addr_drop_area  {
                    type  cml_data_types:CML_UINT32_T;
                    config false;
                    description "isisSysStatManAddrDropFromAreas";
                } // END of man_addr_drop_area definition.

                leaf exceed_max_seqnums  {
                    type  cml_data_types:CML_UINT32_T;
                    config false;
                    description "isisSysStatAttmptToExMaxSeqNums";
                } // END of exceed_max_seqnums definition.

                leaf seqnum_skips  {
                    type  cml_data_types:CML_UINT32_T;
                    config false;
                    description "isisSysStatSeqNumSkips.";
                } // END of seqnum_skips definition.

                leaf lsp_purges  {
                    type  cml_data_types:CML_UINT32_T;
                    config false;
                    description "isisSysStatOwnLSPPurges";
                } // END of lsp_purges definition.

                leaf lsp_sourced  {
                    type  cml_data_types:CML_UINT32_T;
                    config false;
                    description "isisSysStatOwnLSPPurges";
                } // END of lsp_sourced definition.

                leaf id_len_mismatches  {
                    type  cml_data_types:CML_UINT32_T;
                    config false;
                    description "isisSysStatIDFieldLenMismatches.";
                } // END of id_len_mismatches definition.

                leaf partition_changes  {
                    type  cml_data_types:CML_UINT32_T;
                    config false;
                    description "isisSysStatPartChanges";
                } // END of partition_changes definition.

                leaf spf_calc_count  {
                    type  cml_data_types:CML_UINT32_T;
                    config false;
                    description "isisSysStatSPFRuns";
                } // END of spf_calc_count definition.

                leaf prc_calc_count  {
                    type  cml_data_types:CML_UINT32_T;
                    config false;
                    description "isisSysStatPRCRuns";
                } // END of prc_calc_count definition.

                leaf dis_elec_count  {
                    type  cml_data_types:CML_UINT32_T;
                    config false;
                    description "isisSysStatELCRuns";
                } // END of dis_elec_count definition.

                leaf lsp_error  {
                    type  cml_data_types:CML_UINT32_T;
                    config false;
                    description "isisSysStatLSPErrors";
                } // END of lsp_error definition.


                list lspdb {
                    key "lsppsnid";
                    config false;
                    description
                        "LSPDB";
                    leaf lsplock  {
                        type  cml_data_types:CML_UINT32_T;
                        description "Shared lock among multiple events";
                    } // END of lsplock definition.

                    leaf lsppsnid  {
                        type  cml_data_types:CML_UINT8_T;
                        description "PSN ID -- this is necessary to initiate";
                    } // END of lsppsnid definition.

                    leaf lspnum  {
                        type  cml_data_types:CML_UINT8_T;
                        description "LSP num -- this is necessary to initiate";
                    } // END of lspnum definition.

                    leaf lspflags  {
                        type  cml_data_types:CML_UINT8_T;
                        description "LSP administrative flags";
                    } // END of lspflags definition.

                    leaf lspseqnum  {
                        type  cml_data_types:CML_UINT32_T;
                        description "Initial Sequence Number with host byte order";
                    } // END of lspseqnum definition.

                    leaf lsptvupdate  {
                        type  cml_data_types:CML_STRING_T;
                        description "SP update timestamp";
                    } // END of lsptvupdate definition.

                    uses tlv;
                } // End of lspdb-list

                list levelproto {
                    key "protopindex";
                    config false;
                    description
                        "IPv4 protocol data";
                    leaf protopindex  {
                        type  cml_data_types:CML_UINT8_T;
                        description "Index of protocol";
                    } // END of protopindex definition.

                    leaf protoflags  {
                        type  cml_data_types:CML_UINT8_T;
                        description "Flags";
                    } // END of protoflags definition.

                    leaf ispfprotoflags  {
                        type  cml_data_types:CML_UINT8_T;
                        description "Incremental SPF flags";
                    } // END of ispfprotoflags definition.

                } // End of levelproto-list

                list vertex {
                    key "vertexdistance";
                    config false;
                    description
                        "SPF tree";
                    leaf vertexflags  {
                        type  cml_data_types:CML_UINT8_T;
                        description "Vertex Flags";
                    } // END of vertexflags definition.

                    leaf vertexdistance  {
                        type  cml_data_types:CML_UINT32_T;
                        description "Vertex Distance";
                    } // END of vertexdistance definition.


                    list vertexnexthop {
                        key "vertexnexthopsourceid";
                        config false;
                        description
                            "Actual nexthop structure";
                        leaf vertexnexthopflags  {
                            type  cml_data_types:CML_UINT8_T;
                            description "Nexthop flags";
                        } // END of vertexnexthopflags definition.

                        leaf vertexnexthopifindex  {
                            type  cml_data_types:CML_UINT32_T;
                            description "Nexthop interface index";
                        } // END of vertexnexthopifindex definition.

                        leaf vertexnexthopsourceid  {
                            type  cml_data_types:CML_STRING_T;
                            description "Nexthop neighbor source ID";
                        } // END of vertexnexthopsourceid definition.

                        leaf vertexnexthoplock  {
                            type  cml_data_types:CML_UINT32_T;
                            description "Nexthop neighbor Lock";
                        } // END of vertexnexthoplock definition.

                        leaf vertexipaddr  {
                            type  cml_data_types:CML_STRING_T;
                            description "Selected nexthops IP interface address";
                        } // END of vertexipaddr definition.

                        leaf vertexipv6addr  {
                            if-feature feature_list:HAVE_IPV6;
                            type  cml_data_types:CML_STRING_T;
                            description "Selected nexthop's IPv6 interface linklocal address";
                        } // END of vertexipv6addr definition.

                    } // End of vertexnexthop-list
                } // End of vertex-list
            } // End of level-list

            list distance {
                key "SystemID";
                description
                    "distance";
                leaf SystemID  {
                    type  cml_data_types:CML_STRING_T;
                    description "";
                } // END of SystemID definition.

                leaf distance  {
                    type  cml_data_types:CML_UINT8_T {
                         range "1..255";
                    }
                    description "";
                } // END of distance definition.

                leaf accessList  {
                    type  cml_data_types:CML_STRING_T;
                    default "";
                    description "";
                } // END of accessList definition.

            } // End of distance-list
            container vrf {
                config false;
                description
                    "IS-IS vrf";
                leaf vrfflags  {
                    type  cml_data_types:CML_UINT8_T;
                    description "ISIS instance with vrf enabled";
                } // END of vrfflags definition.

                leaf redistcount  {
                    type  cml_data_types:CML_UINT32_T;
                    description "Redistribute count";
                } // END of redistcount definition.

                uses igpshortcutlsp;
            } // END of vrf-container definition.
            container setOverload {
                description
                    "set overload bit";
                leaf setsuppress  {
                    type  cml_data_types:CML_ISIS_SUPPRESS_T;
                    description "Overload bit flags";
                } // END of setsuppress definition.

                leaf onstartup  {
                    type  cml_data_types:CML_ISIS_ONSTARTUP_T;
                    description "Overload interval after reboot";
                } // END of onstartup definition.

            } // END of setOverload-container definition.
            container protoipv4 {
                description
                    "IS-IS protocol IPV4";
                leaf pindex  {
                    type  cml_data_types:CML_UINT8_T;
                    config false;
                    description "Index of protocol";
                } // END of pindex definition.

                leaf redistribute1to2  {
                    type  cml_data_types:CML_BOOL_T;
                    description "Source of protocol";
                } // END of redistribute1to2 definition.

                leaf redistributelist1to2  {
                    type  cml_data_types:CML_STRING_T;
                    description "";
                } // END of redistributelist1to2 definition.

                leaf redistribute2to1  {
                    type  cml_data_types:CML_BOOL_T;
                    description "";
                } // END of redistribute2to1 definition.

                leaf redistributelist2to1  {
                    type  cml_data_types:CML_STRING_T;
                    description "";
                } // END of redistributelist2to1 definition.

                leaf origin  {
                    type  cml_data_types:CML_ISIS_ORIGIN_TYPE_T;
                    description "";
                } // END of origin definition.

                leaf rmapName  {
                    type  cml_data_types:CML_STRING_T;
                    default "";
                    description "";
                } // END of rmapName definition.

                leaf isis-distance  {
                    type  cml_data_types:CML_UINT8_T {
                         range "1..255";
                    }
                    default "115";
                    description "";
                } // END of isis-distance definition.

                leaf redist_update  {
                    type  cml_data_types:CML_INT32_T;
                    config false;
                    description "Redistrubution timer argument";
                } // END of redist_update definition.

                leaf tv_redist  {
                    type  cml_data_types:CML_STRING_T;
                    config false;
                    description "Redistribution last performed";
                } // END of tv_redist definition.


                list redistributeisis {
                    key "redistribute";
                    description
                        "redistributeisis";
                    leaf redistribute  {
                        type  cml_data_types:CML_ISIS_REDISTRIBUTE_T;
                        description "";
                    } // END of redistribute definition.

                    container redistconf {
                        description
                            "redistconf";
                        uses redistgrp;
                    } // END of redistconf-container definition.
                } // End of redistributeisis-list

                list summaryaddress {
                    key "summaryaddress";
                    description
                        "summaryaddress";
                    leaf summaryaddress  {
                        type  cml_data_types:CML_IPV4_PREFIX_T;
                        description "IPv4 network address";
                    } // END of summaryaddress definition.

                    leaf summarylevels  {
                        type  cml_data_types:CML_ISIS_SUMMARY_LEVEL_T;
                        mandatory true;
                        description "IS-IS instance level";
                    } // END of summarylevels definition.

                    leaf metric  {
                        type  cml_data_types:CML_UINT8_T {
                             range "1..63";
                        }
                        mandatory true;
                        description "Metric value";
                    } // END of metric definition.

                } // End of summaryaddress-list

                list route {
                    key "routedistance";
                    config false;
                    description
                        "IS-IS routing table entry";
                    leaf irflags  {
                        type  cml_data_types:CML_UINT8_T;
                        description "Flag used by iSPF and PRC";
                    } // END of irflags definition.

                    leaf routedistance  {
                        type  cml_data_types:CML_UINT8_T;
                        description "Route distance";
                    } // END of routedistance definition.

                    uses isisPath;
                    uses igpshortcutlsp;
                } // End of route-list

                list redistmap {
                    key "rmtag";
                    config false;
                    description
                        "Redistribute map table";
                    leaf rmtype  {
                        type  cml_data_types:CML_UINT8_T;
                        description "Type of protocol source";
                    } // END of rmtype definition.

                    leaf rmmtype  {
                        type  cml_data_types:CML_UINT8_T;
                        description "IS-IS Metric type";
                    } // END of rmmtype definition.

                    leaf rmlevel  {
                        type  cml_data_types:CML_UINT8_T;
                        description "IS-IS level";
                    } // END of rmlevel definition.

                    leaf rmmetric  {
                        type  cml_data_types:CML_UINT32_T;
                        description "IS-IS Metric";
                    } // END of rmmetric definition.

                    leaf rmtag  {
                        type  cml_data_types:CML_UINT32_T;
                        description "IS-IS Ta";
                    } // END of rmtag definition.

                } // End of redistmap-list
                container redistisis {
                    presence "yes";
                    description
                        "redistisis";
                    leaf isisInstanceId  {
                        type  cml_data_types:CML_STRING_T;
                        mandatory true;
                        description "";
                    } // END of isisInstanceId definition.

                    uses redistgrp;
                } // END of redistisis-container definition.
                uses isisPath;
            } // END of protoipv4-container definition.
            container cspf {
                if-feature feature_list:HAVE_ISIS_CSPF;
                config false;
                description
                    "CSPF";
                leaf cspfconfig  {
                    type  cml_data_types:CML_UINT8_T;
                    description "cspf-config flags";
                } // END of cspfconfig definition.

                leaf tiebreak  {
                    type  cml_data_types:CML_UINT8_T;
                    description "Tie-break method";
                } // END of tiebreak definition.

                leaf defretryinterval  {
                    type  cml_data_types:CML_UINT16_T;
                    description "Default retry interval";
                } // END of defretryinterval definition.

                leaf restartcounter  {
                    type  cml_data_types:CML_INT32_T;
                    description "Restart counter";
                } // END of restartcounter definition.

                leaf restartinterval  {
                    type  cml_data_types:CML_INT32_T;
                    description "Restart interval";
                } // END of restartinterval definition.


                list cspflsplist {
                    key "listcount";
                    config false;
                    description
                        "Priority lists";
                    leaf listcount  {
                        type  cml_data_types:CML_INT8_T;
                        description "Priority list count";
                    } // END of listcount definition.


                    list cspflsp {
                        key "setupPriority";
                        config false;
                        description
                            "cspf lsp";
                        leaf lspId  {
                            type  cml_data_types:CML_UINT32_T;
                            description "";
                        } // END of lspId definition.

                        leaf p2mpId  {
                            if-feature feature_list:HAVE_MPLS_P2MP;
                            type  cml_data_types:CML_UINT32_T;
                            description "";
                        } // END of p2mpId definition.

                        leaf subGrpId  {
                            if-feature feature_list:HAVE_MPLS_P2MP;
                            type  cml_data_types:CML_UINT16_T;
                            description "";
                        } // END of subGrpId definition.

                        leaf retryInterval  {
                            type  cml_data_types:CML_UINT16_T;
                            description "";
                        } // END of retryInterval definition.

                        leaf retryLimit  {
                            type  cml_data_types:CML_UINT16_T;
                            description "";
                        } // END of retryLimit definition.

                        leaf teMetric  {
                            type  cml_data_types:CML_UINT32_T;
                            description "";
                        } // END of teMetric definition.

                        leaf egress  {
                            type  cml_data_types:CML_STRING_T;
                            description "";
                        } // END of egress definition.

                        leaf ingress  {
                            type  cml_data_types:CML_STRING_T;
                            description "";
                        } // END of ingress definition.

                        leaf eti  {
                            type  cml_data_types:CML_STRING_T;
                            description "";
                        } // END of eti definition.

                        leaf lspState  {
                            type  cml_data_types:CML_UINT8_T;
                            description "";
                        } // END of lspState definition.

                        leaf clientId  {
                            type  cml_data_types:CML_UINT8_T;
                            description "";
                        } // END of clientId definition.

                        leaf setupPriority  {
                            type  cml_data_types:CML_UINT8_T;
                            description "";
                        } // END of setupPriority definition.

                        leaf holdPriority  {
                            type  cml_data_types:CML_UINT8_T;
                            description "";
                        } // END of holdPriority definition.

                        leaf shareCount  {
                            type  cml_data_types:CML_UINT16_T;
                            description "";
                        } // END of shareCount definition.

                        leaf retryCount  {
                            type  cml_data_types:CML_UINT16_T;
                            description "";
                        } // END of retryCount definition.

                        leaf routeCount  {
                            type  cml_data_types:CML_UINT16_T;
                            description "";
                        } // END of routeCount definition.

                        leaf optimizationInterval  {
                            type  cml_data_types:CML_UINT16_T;
                            description "";
                        } // END of optimizationInterval definition.

                        leaf lflag  {
                            if-feature feature_list:HAVE_GMPLS;
                            type  cml_data_types:CML_UINT8_T;
                            description "";
                        } // END of lflag definition.

                        leaf lspFlag  {
                            type  cml_data_types:CML_UINT16_T;
                            description "";
                        } // END of lspFlag definition.

                        leaf refcount  {
                            type  cml_data_types:CML_UINT8_T;
                            description "";
                        } // END of refcount definition.

                        leaf signalledholdpriority  {
                            type  cml_data_types:CML_UINT8_T;
                            description "";
                        } // END of signalledholdpriority definition.

                        leaf srlgcount  {
                            if-feature feature_list:HAVE_GMPLS;
                            type  cml_data_types:CML_UINT8_T;
                            description "";
                        } // END of srlgcount definition.

                        leaf srlglist  {
                            if-feature feature_list:HAVE_GMPLS;
                            type  cml_data_types:CML_UINT32_T;
                            description "";
                        } // END of srlglist definition.

                        leaf lspType  {
                            type  cml_data_types:CML_UINT8_T;
                            description "Primary/backup lsp";
                        } // END of lspType definition.

                        leaf resolvedexcludehoptype  {
                            type  cml_data_types:CML_UINT8_T;
                            description "";
                        } // END of resolvedexcludehoptype definition.

                        leaf binding  {
                            type  cml_data_types:CML_UINT8_T;
                            description "LSP address binding status";
                        } // END of binding definition.

                        leaf teClass  {
                            if-feature feature_list:HAVE_DSTE;
                            type  cml_data_types:CML_UINT8_T;
                            description "";
                        } // END of teClass definition.

                        leaf recoverCspf  {
                            type  cml_data_types:CML_BOOL_T;
                            description "";
                        } // END of recoverCspf definition.


                        list cspfrouteconstraint {
                            key "hopLimit";
                            config false;
                            description
                                "cspfrouteconstraint";
                            leaf crcFlags  {
                                type  cml_data_types:CML_UINT32_T;
                                description "";
                            } // END of crcFlags definition.

                            leaf bandwidthFwd  {
                                type  cml_data_types:CML_INT32_T;
                                description "";
                            } // END of bandwidthFwd definition.

                            leaf bandwidthRev  {
                                if-feature feature_list:HAVE_GMPLS;
                                type  cml_data_types:CML_UINT32_T;
                                description "";
                            } // END of bandwidthRev definition.

                            leaf hopLimit  {
                                type  cml_data_types:CML_INT8_T;
                                description "";
                            } // END of hopLimit definition.

                            leaf includeMask  {
                                type  cml_data_types:CML_INT8_T;
                                description "";
                            } // END of includeMask definition.

                            leaf excludeMask  {
                                type  cml_data_types:CML_INT8_T;
                                description "";
                            } // END of excludeMask definition.

                            leaf protectionFwd  {
                                if-feature feature_list:HAVE_GMPLS;
                                type  cml_data_types:CML_UINT32_T;
                                description "";
                            } // END of protectionFwd definition.

                            leaf protectionRev  {
                                if-feature feature_list:HAVE_GMPLS;
                                type  cml_data_types:CML_UINT32_T;
                                description "";
                            } // END of protectionRev definition.

                            leaf swCapability  {
                                if-feature feature_list:HAVE_GMPLS;
                                type  cml_data_types:CML_UINT8_T;
                                description "";
                            } // END of swCapability definition.

                            leaf encodingType  {
                                if-feature feature_list:HAVE_GMPLS;
                                type  cml_data_types:CML_UINT8_T;
                                description "";
                            } // END of encodingType definition.

                            leaf srlgValue  {
                                if-feature feature_list:HAVE_GMPLS;
                                type  cml_data_types:CML_UINT32_T;
                                description "";
                            } // END of srlgValue definition.

                            leaf srlgCountrc  {
                                if-feature feature_list:HAVE_GMPLS;
                                type  cml_data_types:CML_UINT8_T;
                                description "";
                            } // END of srlgCountrc definition.

                            leaf pathCount  {
                                type  cml_data_types:CML_UINT8_T;
                                description "";
                            } // END of pathCount definition.

                            leaf excludePathCount  {
                                type  cml_data_types:CML_UINT8_T;
                                description "";
                            } // END of excludePathCount definition.

                        } // End of cspfrouteconstraint-list
                    } // End of cspflsp-list
                } // End of cspflsplist-list
            } // END of cspf-container definition.
        } // End of isistop-list

        list isisInterface {
            key "ifName";
            description
                "ISIS interface related operations";
            leaf ifName  {
                type  cml_data_types:CML_STRING_T;
                description "interface Name";
            } // END of ifName definition.

            leaf ifindex  {
                type  cml_data_types:CML_STRING_T;
                config false;
                description "Index";
            } // END of ifindex definition.

            leaf ifinstanceTag  {
                type  cml_data_types:CML_STRING_T;
                config false;
                description "Routing Protocol IS-IS name";
            } // END of ifinstanceTag definition.

            leaf ifNetworkType  {
                type  cml_data_types:CML_STRING_T;
                config false;
                description "Network Type";
            } // END of ifNetworkType definition.

            leaf ifCircuitType  {
                type  cml_data_types:CML_STRING_T;
                config false;
                description "Circuit Type";
            } // END of ifCircuitType definition.

            leaf localCircuitId  {
                type  cml_data_types:CML_STRING_T;
                config false;
                description "Local circuit ID";
            } // END of localCircuitId definition.

            leaf extCircuitId  {
                type  cml_data_types:CML_STRING_T;
                config false;
                description "Extended Local circuit ID";
            } // END of extCircuitId definition.

            leaf localSnpa  {
                type  cml_data_types:CML_STRING_T;
                config false;
                description "Local SNPA";
            } // END of localSnpa definition.

            leaf bandwidth  {
                if-feature feature_list:HAVE_ISIS_TE;
                type  cml_data_types:CML_STRING_T;
                config false;
                description "Bandwidth";
            } // END of bandwidth definition.

            leaf maxResvBandwidth  {
                if-feature feature_list:HAVE_ISIS_TE;
                type  cml_data_types:CML_STRING_T;
                config false;
                description "Maximum reservable bandwidth";
            } // END of maxResvBandwidth definition.


            list connectedipv4 {
                key "ipv4Address";
                config false;
                description
                    "IP interface address";
                leaf ipv4Address  {
                    type  cml_data_types:CML_IPV4_ADDR_PREFIX_T;
                    description "IP interface address";
                } // END of ipv4Address definition.

            } // End of connectedipv4-list

            list connectedipv6 {
                key "ipv6Address";
                config false;
                description
                    "IPV6 interface address";
                leaf ipv6Address  {
                    type  cml_data_types:CML_IPV6_PREFIX_T;
                    description "IPV6 interface address";
                } // END of ipv6Address definition.

            } // End of connectedipv6-list

            list neighbor-LAN {
                key "nbr_source_id_lan";
                config false;
                description
                    "neighborCMLSEPLAN";
                leaf nbr_source_id_lan  {
                    type  cml_data_types:CML_STRING_T;
                    description "Source ID";
                } // END of nbr_source_id_lan definition.

                leaf nbr_type  {
                    type  cml_data_types:CML_STRING_T;
                    description "Neighbor Type";
                } // END of nbr_type definition.


                list isisNeighborLevel {
                    key "nbr_levelindex";
                    config false;
                    description
                        "Neighbor level context";
                    leaf nbr_levelindex  {
                        type  cml_data_types:CML_ISIS_LEVEL_T;
                        description "Neighbor index";
                    } // END of nbr_levelindex definition.

                    leaf nbr_state  {
                        type  cml_data_types:CML_ISIS_STATE_T;
                        description "NSM state";
                    } // END of nbr_state definition.

                    leaf nbr_adjacency_id  {
                        type  cml_data_types:CML_UINT32_T;
                        description "Neighbor adjacency ID";
                    } // END of nbr_adjacency_id definition.

                    leaf nbr_hold_time  {
                        type  cml_data_types:CML_STRING_T;
                        description "Holding time";
                    } // END of nbr_hold_time definition.

                } // End of isisNeighborLevel-list
                uses neighborattributes;
            } // End of neighbor-LAN-list

            list iflevel {
                key "iflevelindex";
                config false;
                description
                    "Level for interface";
                leaf iflevelindex  {
                    type  cml_data_types:CML_ISIS_IFLEVEL_T;
                    description "Level index";
                } // END of iflevelindex definition.

                leaf ifNextHello  {
                    type  cml_data_types:CML_STRING_T;
                    description "Next IS-IS Hello";
                } // END of ifNextHello definition.

                leaf iflevelFlag  {
                    type  cml_data_types:CML_UINT8_T;
                    description "Level flags";
                } // END of iflevelFlag definition.

                leaf ifstate  {
                    type  cml_data_types:CML_UINT8_T;
                    description "ISM State";
                } // END of ifstate definition.

                leaf ifCircuitId  {
                    type  cml_data_types:CML_STRING_T;
                    description "DIS of this interface - Source ID";
                } // END of ifCircuitId definition.

                leaf ifNbrCount  {
                    type  cml_data_types:CML_INT32_T;
                    description "Number of active adjacencies in each level";
                } // END of ifNbrCount definition.

                leaf ifAdjNbrCount  {
                    type  cml_data_types:CML_INT32_T;
                    description "Number of active adjacencies in each level(AdjsUp)";
                } // END of ifAdjNbrCount definition.

                leaf ifNextCsnp  {
                    type  cml_data_types:CML_STRING_T;
                    description "Next CSNP";
                } // END of ifNextCsnp definition.

                leaf adj_changes  {
                    type  cml_data_types:CML_UINT32_T;
                    description "isisCircAdjChanges";
                } // END of adj_changes definition.

                leaf num_adj  {
                    type  cml_data_types:CML_UINT32_T;
                    description "isisCircNumAdj";
                } // END of num_adj definition.

                leaf init_fails  {
                    type  cml_data_types:CML_UINT32_T;
                    description "isisCircInitFails";
                } // END of init_fails definition.

                leaf rej_adjs  {
                    type  cml_data_types:CML_UINT32_T;
                    description "isisCircRejAdjs";
                } // END of rej_adjs definition.

                leaf idlen_mismatches  {
                    type  cml_data_types:CML_UINT32_T;
                    description "isisCircIDFieldLenMismatches";
                } // END of idlen_mismatches definition.

                leaf maxarea_addr_mismatches  {
                    type  cml_data_types:CML_UINT32_T;
                    description "isisCircMaxAreaAddrMismatches";
                } // END of maxarea_addr_mismatches definition.

                leaf authtype_fails  {
                    type  cml_data_types:CML_UINT32_T;
                    description "isisCircAuthTypeFails";
                } // END of authtype_fails definition.

                leaf auth_fails  {
                    type  cml_data_types:CML_UINT32_T;
                    description "isisCircAuthFails";
                } // END of auth_fails definition.

                leaf dis_changes  {
                    type  cml_data_types:CML_UINT32_T;
                    description "isisCircLANDesISChanges";
                } // END of dis_changes definition.

                leaf state_change  {
                    type  cml_data_types:CML_UINT32_T;
                    description "Number of ISM state change";
                } // END of state_change definition.

                leaf hello_in  {
                    type  cml_data_types:CML_UINT32_T;
                    description "isisPacketCountIIHello";
                } // END of hello_in definition.

                leaf hello_out  {
                    type  cml_data_types:CML_UINT32_T;
                    description "isisPacketCountIIHello";
                } // END of hello_out definition.

                leaf lsp_in  {
                    type  cml_data_types:CML_UINT32_T;
                    description "isisPacketCountLSP";
                } // END of lsp_in definition.

                leaf lsp_out  {
                    type  cml_data_types:CML_UINT32_T;
                    description "isisPacketCountLSP";
                } // END of lsp_out definition.

                leaf csnp_in  {
                    type  cml_data_types:CML_UINT32_T;
                    description "isisPacketCountCSNP";
                } // END of csnp_in definition.

                leaf csnp_out  {
                    type  cml_data_types:CML_UINT32_T;
                    description "isisPacketCountCSNP";
                } // END of csnp_out definition.

                leaf psnp_in  {
                    type  cml_data_types:CML_UINT32_T;
                    description "isisPacketCountPSNP";
                } // END of psnp_in definition.

                leaf psnp_out  {
                    type  cml_data_types:CML_UINT32_T;
                    description "isisPacketCountPSNP";
                } // END of psnp_out definition.

                leaf unknown_in  {
                    type  cml_data_types:CML_UINT32_T;
                    description "isisPacketCountUnknown";
                } // END of unknown_in definition.

                leaf unknown_out  {
                    type  cml_data_types:CML_UINT32_T;
                    description "isisPacketCountUnknown";
                } // END of unknown_out definition.

                leaf t1_exp  {
                    if-feature feature_list:HAVE_RESTART;
                    type  cml_data_types:CML_UINT8_T;
                    description "number of times T1 timer expired";
                } // END of t1_exp definition.

            } // End of iflevel-list
            container neighbor-P2P {
                config false;
                description
                    "neighborCMLSEPP2P";
                leaf nbrsourceidp2p  {
                    type  cml_data_types:CML_STRING_T;
                    description "Source ID";
                } // END of nbrsourceidp2p definition.

                leaf nbrcircuitid  {
                    type  cml_data_types:CML_STRING_T;
                    description "Neighbor Local Circuit ID for P2P";
                } // END of nbrcircuitid definition.

                leaf p2p_nbr_state  {
                    type  cml_data_types:CML_STRING_T;
                    description "p2p nbr state str";
                } // END of p2p_nbr_state definition.

                leaf holdTimer  {
                    type  cml_data_types:CML_STRING_T;
                    description "timer string";
                } // END of holdTimer definition.

                leaf adjacencyType  {
                    type  cml_data_types:CML_STRING_T;
                    description "is type str";
                } // END of adjacencyType definition.

                uses neighborattributes;
            } // END of neighbor-P2P-container definition.
            container ifparams {
                description
                    "Interface parameter";
                leaf proto_type  {
                    type  cml_data_types:CML_UINT8_T;
                    config false;
                    description "Configuration for protocol supported";
                } // END of proto_type definition.

                leaf network  {
                    type  cml_data_types:CML_ISIS_NETWORK_T;
                    description "ISIS_IFTYPE_POINTTOPOINT, ISIS_IFTYPE_BROADCAST";
                } // END of network definition.

                leaf circuit-type  {
                    type  cml_data_types:CML_ISIS_CIRCUIT_TYPE_T;
                    default "level-1-2";
                    description "IS-IS Circuit-type, (1|2|3)";
                } // END of circuit-type definition.

                leaf bfd  {
                    type  cml_data_types:CML_BOOL_T;
                    description "isis bfd config flag";
                } // END of bfd definition.

                leaf bfddisable  {
                    type  cml_data_types:CML_BOOL_T;
                    description "isis bfd disable config flag";
                } // END of bfddisable definition.

                leaf isisIPv4InstanceTag  {
                    type  cml_data_types:CML_STRING_T;
                    description "IS-IS instance area tag";
                } // END of isisIPv4InstanceTag definition.

                leaf isisIPv6InstanceTag  {
                    if-feature feature_list:HAVE_IPV6;
                    type  cml_data_types:CML_STRING_T;
                    description "IS-IS instance area tag";
                } // END of isisIPv6InstanceTag definition.

                leaf iip_type  {
                    type  cml_data_types:CML_UINT8_T;
                    config false;
                    description "Network type";
                } // END of iip_type definition.

                leaf iip_circuit_type  {
                    type  cml_data_types:CML_UINT8_T;
                    config false;
                    description "Circuit type";
                } // END of iip_circuit_type definition.

                leaf iip_passive_type  {
                    type  cml_data_types:CML_UINT8_T;
                    config false;
                    description "Passive level type";
                } // END of iip_passive_type definition.

                leaf iip_vid  {
                    type  cml_data_types:CML_UINT16_T;
                    config false;
                    description "Vlan ID for Vlan interfaces";
                } // END of iip_vid definition.

                leaf lsp-interval  {
                    type  cml_data_types:CML_UINT32_T {
                         range "1..4294967295";
                    }
                    default "33";
                    description "Interval in milliseconds";
                } // END of lsp-interval definition.

                leaf retransmit-interval  {
                    type  cml_data_types:CML_UINT16_T {
                         range "1..65535";
                    }
                    default "5";
                    description "if_retransmit_interval value in seconds";
                } // END of retransmit-interval definition.

                leaf padding  {
                    type  cml_data_types:CML_BOOL_T;
                    description "";
                } // END of padding definition.

                leaf frrIfLevel1  {
                    if-feature feature_list:HAVE_ISIS_LFA;
                    type  cml_data_types:CML_BOOL_T;
                    description "";
                } // END of frrIfLevel1 definition.

                leaf frrIfLevel2  {
                    if-feature feature_list:HAVE_ISIS_LFA;
                    type  cml_data_types:CML_BOOL_T;
                    description "";
                } // END of frrIfLevel2 definition.

                leaf groupId  {
                    type  cml_data_types:CML_ISIS_MESH_TYPE_T;
                    description "Mesh group ID";
                } // END of groupId definition.


                list iflevelconf {
                    key "ifLevel";
                    description
                        "Interface Level parameter";
                    leaf ifLevel  {
                        type  cml_data_types:CML_ISIS_LEVEL_T;
                        description "";
                    } // END of ifLevel definition.

                    leaf iflevelconfig  {
                        type  cml_data_types:CML_UINT16_T;
                        config false;
                        description "isis_if_level_conf-Config flags";
                    } // END of iflevelconfig definition.

                    leaf hello-interval  {
                        type  cml_data_types:CML_ISIS_HELLO_INTERVAL_TYPE_T;
                        description "Interval in seconds";
                    } // END of hello-interval definition.

                    leaf hello-multiplier  {
                        type  cml_data_types:CML_UINT8_T {
                             range "2..100";
                        }
                        default "3";
                        description "Multiplier for Hello holding time";
                    } // END of hello-multiplier definition.

                    leaf csnp-interval  {
                        type  cml_data_types:CML_UINT16_T {
                             range "1..65535";
                        }
                        default "10";
                        description "";
                    } // END of csnp-interval definition.

                    leaf priority  {
                        type  cml_data_types:CML_UINT8_T {
                             range "0..127";
                        }
                        default "64";
                        description "Priority for Designated Router election";
                    } // END of priority definition.

                    leaf metric  {
                        type  cml_data_types:CML_UINT8_T {
                             range "1..63";
                        }
                        default "10";
                        description "Metric value";
                    } // END of metric definition.

                    leaf ifauthMode  {
                        type  cml_data_types:CML_ISIS_AUTH_MODE_T;
                        description "";
                    } // END of ifauthMode definition.

                    leaf ifkeyChain  {
                        type  cml_data_types:CML_STRING_T;
                        description "";
                    } // END of ifkeyChain definition.

                    leaf password  {
                        type  cml_data_types:CML_STRING_T;
                        description "Authentication key, null-terminated";
                    } // END of password definition.

                    leaf tag  {
                        type  cml_data_types:CML_UINT32_T {
                             range "1..4294967295";
                        }
                        description "IS-IS instance area tag";
                    } // END of tag definition.

                    leaf wide-metric  {
                        type  cml_data_types:CML_UINT32_T {
                             range "1..16777214";
                        }
                        default "10";
                        description "wide-metric value";
                    } // END of wide-metric definition.

                    leaf restart-hello-interval  {
                        type  cml_data_types:CML_UINT16_T {
                             range "1..65535";
                        }
                        default "3";
                        description "";
                    } // END of restart-hello-interval definition.

                    leaf send-only  {
                        type  cml_data_types:CML_BOOL_T;
                        description "";
                    } // END of send-only definition.

                } // End of iflevelconf-list
            } // END of ifparams-container definition.
            container syncparams {
                if-feature feature_list:HAVE_LDPD;
                description
                    "isis_sync_params";
                leaf synclevel  {
                    type  cml_data_types:CML_ISIS_SYNC_TYPE_T;
                    description "";
                } // END of synclevel definition.

                leaf holddown  {
                    type  cml_data_types:CML_UINT32_T {
                         range "1..2147483";
                    }
                    default "70000";
                    description "";
                } // END of holddown definition.

                leaf sync_flags  {
                    type  cml_data_types:CML_UINT8_T;
                    config false;
                    description "isis sync params-sync flags";
                } // END of sync_flags definition.

                leaf sync_ifname  {
                    type  cml_data_types:CML_STRING_T;
                    config false;
                    description "isis sync params-sync ifname";
                } // END of sync_ifname definition.

            } // END of syncparams-container definition.
        } // End of isisInterface-list
        container restart {
            description
                "IS-IS restart stuff";
            leaf restartflags  {
                type  cml_data_types:CML_UINT8_T;
                config false;
                description "isis_restart-flags";
            } // END of restartflags definition.

            leaf grace-period  {
                type  cml_data_types:CML_UINT16_T {
                     range "1..65535";
                }
                description "Grace period";
            } // END of grace-period definition.

            leaf helper  {
                type  cml_data_types:CML_BOOL_T;
                description "";
            } // END of helper definition.

            leaf suppress-adjacency  {
                type  cml_data_types:CML_BOOL_T;
                description "";
            } // END of suppress-adjacency definition.

            leaf tv_restart  {
                type  cml_data_types:CML_STRING_T;
                config false;
                description "Restarting time";
            } // END of tv_restart definition.

            leaf tv_expire  {
                type  cml_data_types:CML_STRING_T;
                config false;
                description "Preserve expire time";
            } // END of tv_expire definition.

        } // END of restart-container definition.
        container debugconf {
            description
                "Debug flags for configuration";
            leaf debugFlag  {
                type  cml_data_types:CML_ISIS_DEBUG_T;
                description "";
            } // END of debugFlag definition.

            leaf debugall  {
                type  cml_data_types:CML_BOOL_T;
                description "";
            } // END of debugall definition.

            leaf debughello  {
                type  cml_data_types:CML_BOOL_T;
                description "";
            } // END of debughello definition.

            leaf debuglfa  {
                if-feature feature_list:HAVE_ISIS_LFA;
                type  cml_data_types:CML_BOOL_T;
                description "";
            } // END of debuglfa definition.

            leaf-list helloIfname  {
                type  cml_data_types:CML_STRING_T;
                description "";
            } // END of helloIfname definition.

            leaf-list hellosysId  {
                type  cml_data_types:CML_STRING_T;
                description "";
            } // END of hellosysId definition.

        } // END of debugconf-container definition.
        container debugterm {
            description
                "Debug flags for terminal";
            leaf termdebugFlag  {
                type  cml_data_types:CML_ISIS_DEBUG_T;
                description "";
            } // END of termdebugFlag definition.

            leaf termdebugall  {
                type  cml_data_types:CML_BOOL_T;
                description "";
            } // END of termdebugall definition.

            leaf termdebughello  {
                type  cml_data_types:CML_BOOL_T;
                description "";
            } // END of termdebughello definition.

            leaf termdebuglfa  {
                if-feature feature_list:HAVE_ISIS_LFA;
                type  cml_data_types:CML_BOOL_T;
                description "";
            } // END of termdebuglfa definition.

            leaf-list termhelloIfname  {
                type  cml_data_types:CML_STRING_T;
                description "";
            } // END of termhelloIfname definition.

            leaf-list termhellosysId  {
                type  cml_data_types:CML_STRING_T;
                description "";
            } // END of termhellosysId definition.

        } // END of debugterm-container definition.
    } // END of isismaster-container definition.
    } // END of isismaster-container definition.


}
