/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-ldap.yang
*
*/

submodule zebos-ldap {

    belongs-to  zebos { prefix zebos; }

    import cml_data_types {
        prefix cml_data_types;
    }

    organization
        "IP Infusion Inc.";

    contact
        "Address: 3965 Freedom Circle, Suite 200, Santa Clara, CA 95054
        Phone: +1 408-400-1900
        E-mail: support@ipinfusion.com
        Web: http://www.ipinfusion.com/";

    description
        "Layer-3 ldap configurations";


    revision "2018-06-21" {
        description " Initial Version.";
        reference "";
    }


    grouping  ldap-grouping {
    description
        "ldap";
    container ldap {
        description
            "ldap";
        leaf featureLdap  {
            type  cml_data_types:CML_BOOL_T;
            description "";
        } // END of featureLdap definition.

        leaf port  {
            type  cml_data_types:CML_UINT16_T {
                 range "1..65535";
            }
            description "";
        } // END of port definition.

        leaf timeout  {
            type  cml_data_types:CML_UINT16_T {
                 range "1..60";
            }
            description "";
        } // END of timeout definition.


        list ldap {
            key "hostAddr";
            description
                "ldap";
            leaf hostAddr  {
                type  cml_data_types:CML_HOSTNAME_T {
                    length "0..255";
                }
                description "";
            } // END of hostAddr definition.

            leaf EnableSsl  {
                type  cml_data_types:CML_BOOL_T;
                description "";
            } // END of EnableSsl definition.

            leaf hostPort  {
                type  cml_data_types:CML_UINT16_T {
                     range "1..65535";
                }
                description "";
            } // END of hostPort definition.

            leaf hostDNPort  {
                type  cml_data_types:CML_UINT16_T {
                     range "1..65535";
                }
                default "389";
                description "";
            } // END of hostDNPort definition.

            leaf hostTimeout  {
                type  cml_data_types:CML_UINT16_T {
                     range "1..60";
                }
                default "5";
                description "";
            } // END of hostTimeout definition.

            leaf hostPTimeout  {
                type  cml_data_types:CML_UINT16_T {
                     range "1..60";
                }
                description "";
            } // END of hostPTimeout definition.

            leaf rootDN  {
                type  cml_data_types:CML_STRING_T {
                    length "0..255";
                }
                description "";
            } // END of rootDN definition.

        } // End of ldap-list
    } // END of ldap-container definition.
    } // END of ldap-container definition.


}
