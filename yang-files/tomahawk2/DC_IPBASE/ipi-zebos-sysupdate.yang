/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-zebos-sysupdate.yang
*
*/

submodule ipi-zebos-sysupdate {

    belongs-to  ipi-zebos { prefix ipi-zebos; }

    import cml-data-types {
        prefix cml-data-types;
    }

    organization
        "IP Infusion Inc.";

    contact
        "Address: 3965 Freedom Circle, Suite 200, Santa Clara, CA 95054
        Phone: +1 408-400-1900
        E-mail: support@ipinfusion.com
        Web: http://www.ipinfusion.com/";

    description
        "System update feature provides an option for user to upgrade/downgrade the OcNOS image in a router";


    revision "2018-02-19" {
        description " Initial Version.";
        reference "";
    }


    grouping  installers-grouping {
    description
        "Installer list";
    container installers {
        config false;
        description
            "Installer list";
        leaf-list installer  {
            type  cml-data-types:CML_STRING_T;
            description "Installer image available in device";
        } // END of installer definition.

    } // END of installers-container definition.
    } // END of installers-container definition.


}
