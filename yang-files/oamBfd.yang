/*
* Copyright (C) 2016 IP Infusion, Inc. 
*  All Rights Reserved.
*
*** Auto generated by zebmdc

* Unless required by applicable law or agreed to in writing,
* software distributed under the License is distributed on an
* "AS IS" BASIS, WITHOUT WARRANTIES OR CONDITIONS OF ANY
* KIND, either express or implied.

* File name : oamBfd.yang
*
*/

submodule oamBfd {

    belongs-to  ZebOS { prefix ZebOS; }
    include interface;


    import cml_data_types {
        prefix cml_data_types;
    }

    revision "2015-10-08" {
        description "Revisied on 2015-10-08.";    }



    grouping bfd-grouping {
        list bfd {
             

            description
                "bfd";

            config true;
            key "bfdProcessId";

            
            leaf vrId  {
                mandatory false;                
                type  leafref {
                    path  "/vr/vrId";
                }
            } // END of vrId definition.

            leaf bfdProcessId  {
                mandatory true;                
                type  cml_data_types:CML_BOOL_T;  
                config true;
            } // END of bfdProcessId definition.

            leaf bfdGtsmState  {
                mandatory false;                
                type  cml_data_types:CML_BFD_GTSM_STATE_T;  
                config true;
            } // END of bfdGtsmState definition.

            leaf bfdNotificationState  {
                mandatory false;                
                type  cml_data_types:CML_BFD_SESSION_STATE_T;  
                config true;
            } // END of bfdNotificationState definition.

            leaf bfdEchoState  {
                mandatory false;                
                type  cml_data_types:CML_BOOL_T;  
                config true;
            } // END of bfdEchoState definition.

            leaf bfdGtsmTtl  {
                mandatory false;                
                type  cml_data_types:CML_UINT8_T {
                     range "1..255";
                }
                default "255";
                config true;
            } // END of bfdGtsmTtl definition.

            leaf bfdSlowTimer  {
                mandatory false;                
                type  cml_data_types:CML_UINT32_T {
                     range "1000..30000";
                }
                default "2000";
                config true;
            } // END of bfdSlowTimer definition.

            leaf-list bfdMultihopIntervalIpv4Addr  {
                
                type  cml_data_types:CML_IPV4_ADDR_T;  
                config true;
            } // END of bfdMultihopIntervalIpv4Addr definition.

            leaf bfdIpv4MultihopMinTx  {
                mandatory false;                
                type  cml_data_types:CML_UINT32_T {
                     range "50..999";
                }
                default "250";
                config true;
            } // END of bfdIpv4MultihopMinTx definition.

            leaf bfdIpv4MultihopMinRx  {
                mandatory false;                
                type  cml_data_types:CML_UINT32_T {
                     range "50..999";
                }
                default "250";
                config true;
            } // END of bfdIpv4MultihopMinRx definition.

            leaf bfdIpv4MultihopMulti  {
                mandatory false;                
                type  cml_data_types:CML_UINT32_T {
                     range "3..50";
                }
                default "3";
                config true;
            } // END of bfdIpv4MultihopMulti definition.

            leaf bfdMultihopIntervalIpv6Addr  {
                mandatory false;                
                type  cml_data_types:CML_IPV6_ADDR_T;  
                config true;
            } // END of bfdMultihopIntervalIpv6Addr definition.

            leaf bfdIpv6MultihopMinTx  {
                mandatory false;                
                type  cml_data_types:CML_UINT32_T {
                     range "50..999";
                }
                default "250";
                config true;
            } // END of bfdIpv6MultihopMinTx definition.

            leaf bfdIpv6MultihopMinRx  {
                mandatory false;                
                type  cml_data_types:CML_UINT32_T {
                     range "50..999";
                }
                default "250";
                config true;
            } // END of bfdIpv6MultihopMinRx definition.

            leaf bfdIpv6MultihopMulti  {
                mandatory false;                
                type  cml_data_types:CML_UINT32_T {
                     range "3..50";
                }
                default "3";
                config true;
            } // END of bfdIpv6MultihopMulti definition.


            list bfdMultihopKeyChain {
                 

                description
                    "bfdMultihopKeyChain";

                config true;
                key "bfdMultihopAddr";

                
                leaf bfdMultihopAddr  {
                    mandatory true;                    
                    type  cml_data_types:CML_IP_ADDR_T;  
                    config true;
                } // END of bfdMultihopAddr definition.

                leaf bfdAuthType  {
                    mandatory true;                    
                    type  cml_data_types:CML_BFD_MULTIHOP_AUTH_TYPE_T;  
                    config true;
                } // END of bfdAuthType definition.

                leaf bfdKeyChain  {
                    mandatory true;                    
                    type  cml_data_types:CML_STRING_T;  
                    config true;
                } // END of bfdKeyChain definition.

            } // End of bfdMultihopKeyChain-list

            list bfdMultihopKeyStr {
                 

                description
                    "bfdMultihopKeyStr";

                config true;
                key "bfdMultihopAddr";

                
                leaf bfdMultihopAddr  {
                    mandatory true;                    
                    type  cml_data_types:CML_IP_ADDR_T;  
                    config true;
                } // END of bfdMultihopAddr definition.

                leaf bfdAuthType  {
                    mandatory true;                    
                    type  cml_data_types:CML_BFD_MULTIHOP_AUTH_TYPE_T;  
                    config true;
                } // END of bfdAuthType definition.

                leaf bfdMultihopKeyId  {
                    mandatory true;                    
                    type  cml_data_types:CML_UINT32_T {
                         range "0..255";
                    }
                    config true;
                } // END of bfdMultihopKeyId definition.

                leaf bfdKeyStr  {
                    mandatory true;                    
                    type  cml_data_types:CML_STRING_T;  
                    config true;
                } // END of bfdKeyStr definition.

            } // End of bfdMultihopKeyStr-list
        } // End of bfd-list
    } // END of bfd-grouping definition.


    grouping bfdInterface-grouping {
        list bfdInterface {
             

            description
                "OSPF interface related operations";

            config true;
            key "ifName";

            
            leaf ifName  {
                mandatory true;                
                type  leafref {
                    path  "/vr/interface/ifName";
                }
            } // END of ifName definition.

            leaf vrId  {
                mandatory false;                
                type  leafref {
                    path  "/vr/vrId";
                }
            } // END of vrId definition.

            leaf bfdSessionState  {
                mandatory false;                
                type  cml_data_types:CML_BOOL_T;  
                config true;
            } // END of bfdSessionState definition.

            leaf bfdIpv4State  {
                mandatory false;                
                type  cml_data_types:CML_BOOL_T;  
                config true;
            } // END of bfdIpv4State definition.

            leaf bfdMinTx  {
                mandatory false;                
                type  cml_data_types:CML_UINT32_T {
                     range "50..999";
                }
                default "250";
                config true;
            } // END of bfdMinTx definition.

            leaf bfdMinRx  {
                mandatory false;                
                type  cml_data_types:CML_UINT32_T {
                     range "50..999";
                }
                default "250";
                config true;
            } // END of bfdMinRx definition.

            leaf bfdIntervalMultiplier  {
                mandatory false;                
                type  cml_data_types:CML_UINT32_T {
                     range "3..50";
                }
                default "3";
                config true;
            } // END of bfdIntervalMultiplier definition.

            leaf bfdEchoInterval  {
                mandatory false;                
                type  cml_data_types:CML_UINT32_T {
                     range "1..4294967";
                }
                default "1000";
                config true;
            } // END of bfdEchoInterval definition.


            list bfdIpv4UserAdd {
                 

                description
                    "bfdIpv4UserAdd";

                config true;
                key "bfdUserSrcAddr";

                
                leaf bfdUserSrcAddr  {
                    mandatory true;                    
                    type  cml_data_types:CML_IPV4_ADDR_T;  
                    config true;
                } // END of bfdUserSrcAddr definition.

                leaf bfdUserDestAddr  {
                    mandatory true;                    
                    type  cml_data_types:CML_IPV4_ADDR_T;  
                    config true;
                } // END of bfdUserDestAddr definition.

                leaf multihop  {
                    mandatory true;                    
                    type  cml_data_types:CML_BOOL_T;  
                    config true;
                } // END of multihop definition.

                leaf demandMode  {
                    mandatory true;                    
                    type  cml_data_types:CML_BOOL_T;  
                    config true;
                } // END of demandMode definition.

                leaf nonPersistant  {
                    mandatory true;                    
                    type  cml_data_types:CML_BOOL_T;  
                    config true;
                } // END of nonPersistant definition.

                leaf adminDown  {
                    mandatory true;                    
                    type  cml_data_types:CML_BOOL_T;  
                    config true;
                } // END of adminDown definition.

            } // End of bfdIpv4UserAdd-list

            list bfdIpv6UserAdd {
                 

                description
                    "bfdIpv6UserAdd";

                config true;
                key "bfdIpv6UserSrcAddr";

                
                leaf bfdIpv6UserSrcAddr  {
                    mandatory true;                    
                    type  cml_data_types:CML_IPV6_ADDR_T;  
                    config true;
                } // END of bfdIpv6UserSrcAddr definition.

                leaf bfdIpv6UserDestAddr  {
                    mandatory true;                    
                    type  cml_data_types:CML_IPV6_ADDR_T;  
                    config true;
                } // END of bfdIpv6UserDestAddr definition.

                leaf ipv6Multihop  {
                    mandatory true;                    
                    type  cml_data_types:CML_BOOL_T;  
                    config true;
                } // END of ipv6Multihop definition.

                leaf ipv6DemandMode  {
                    mandatory true;                    
                    type  cml_data_types:CML_BOOL_T;  
                    config true;
                } // END of ipv6DemandMode definition.

                leaf ipv6NonPersistant  {
                    mandatory true;                    
                    type  cml_data_types:CML_BOOL_T;  
                    config true;
                } // END of ipv6NonPersistant definition.

                leaf ipv6AdminDown  {
                    mandatory true;                    
                    type  cml_data_types:CML_BOOL_T;  
                    config true;
                } // END of ipv6AdminDown definition.

            } // End of bfdIpv6UserAdd-list

            list bfdIfAuthKeyChain {
                 

                description
                    "bfdIfAuthKeyChain";

                config true;
                key "bfdIfAuthType";

                
                leaf bfdIfAuthType  {
                    mandatory true;                    
                    type  cml_data_types:CML_BFD_MULTIHOP_AUTH_TYPE_T;  
                    config true;
                } // END of bfdIfAuthType definition.

                leaf bfdIfKeyChain  {
                    mandatory true;                    
                    type  cml_data_types:CML_STRING_T;  
                    config true;
                } // END of bfdIfKeyChain definition.

            } // End of bfdIfAuthKeyChain-list

            list bfdIfAuthKeyStr {
                 

                description
                    "bfdIfAuthKeyStr";

                config true;
                key "bfdIfAuthType";

                
                leaf bfdIfAuthType  {
                    mandatory true;                    
                    type  cml_data_types:CML_BFD_MULTIHOP_AUTH_TYPE_T;  
                    config true;
                } // END of bfdIfAuthType definition.

                leaf bfdIfKeyId  {
                    mandatory true;                    
                    type  cml_data_types:CML_UINT32_T {
                         range "0..255";
                    }
                    config true;
                } // END of bfdIfKeyId definition.

                leaf bfdIfKeyStr  {
                    mandatory true;                    
                    type  cml_data_types:CML_STRING_T;  
                    config true;
                } // END of bfdIfKeyStr definition.

            } // End of bfdIfAuthKeyStr-list
        } // End of bfdInterface-list
    } // END of bfdInterface-grouping definition.

    grouping  oamMpls-grouping {
    container oamMpls {
        
        config true;

        description
            "oamMpls";

        leaf pingRequest  {
            mandatory false;            
            type  cml_data_types:CML_BOOL_T;  
            config true;
        } // END of pingRequest definition.

        leaf pingReply  {
            mandatory false;            
            type  cml_data_types:CML_BOOL_T;  
            config true;
        } // END of pingReply definition.

    } // END of oamMpls-container definition.
    } // END of oamMpls-container definition.


}
