/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : igmpsnooping.yang
*
*/

submodule igmpsnooping {

    belongs-to  ZebOS { prefix ZebOS; }
    include interface;


    import cml_data_types {
        prefix cml_data_types;
    }


    revision "2017-02-13" {
        description "changes for Jira fix-12222.";
    }

    revision "2017-02-02" {
        description "changes for Documentation.";
    }

    revision "2017-01-27" {
        description "changes for Debug command.";
    }

    revision "2016-10-14" {
        description "Initial version.";
    }



    grouping igmpSnoopInterface-grouping {
        list igmpSnoopInterface {
             
            description
                "igmpSnoopInterface";

            config true;
            key "ifName";

            
            leaf ifName  {
                type  cml_data_types:CML_STRING_T {
                    length "0..255";
                }
            } // END of ifName definition.

            leaf setIfFlag  {
                type  cml_data_types:CML_BOOL_T;  
                description "igmp snooping";
            } // END of setIfFlag definition.

            leaf setFastLeaveFlag  {
                type  cml_data_types:CML_BOOL_T;  
                description "igmp snooping fast-leave";
            } // END of setFastLeaveFlag definition.

            leaf setIfSuppressFlag  {
                type  cml_data_types:CML_BOOL_T;  
                description "igmp snooping report-suppression";
            } // END of setIfSuppressFlag definition.

            leaf mrouterIfName  {
                type  cml_data_types:CML_STRING_T {
                    length "0..255";
                }
                description "igmp snooping mrouter";
            } // END of mrouterIfName definition.

            leaf ifQuerierFlag  {
                type  cml_data_types:CML_BOOL_T;  
                description "igmp snooping querier";
            } // END of ifQuerierFlag definition.


            list igmpSnoopStaticGroup {
                 
                description
                    "igmpSnoopStaticGroup";

                config true;
                key "groupAddr";

                
                leaf groupAddr  {
                    type  cml_data_types:CML_IPV4_ADDR_T;  
                } // END of groupAddr definition.


                list igmpSnoopSourceAddress {
                     
                    description
                        "igmpSnoopSourceAddress";

                    config true;
                    key "sourceAddr";

                    
                    leaf sourceAddr  {
                        type  cml_data_types:CML_STRING_T {
                            length "0..255";
                        }
                    } // END of sourceAddr definition.


                    list igmpSnoopInterface {
                         
                        description
                            "igmpSnoopInterface";

                        config true;
                        key "vifName";

                        
                        leaf vifName  {
                            type  cml_data_types:CML_STRING_T {
                                length "0..255";
                            }
                        } // END of vifName definition.

                    } // End of igmpSnoopInterface-list
                } // End of igmpSnoopSourceAddress-list
            } // End of igmpSnoopStaticGroup-list
        } // End of igmpSnoopInterface-list
    } // END of igmpSnoopInterface-grouping definition.

    grouping  igmpConfig-grouping {
    container igmpConfig {
                config true;

        description
            "igmpConfig";

        leaf setSnoopFlag  {
            type  cml_data_types:CML_BOOL_T;  
            description "igmp snooping";
        } // END of setSnoopFlag definition.

        leaf reportSuppressFlag  {
            type  cml_data_types:CML_BOOL_T;  
            description "igmp snooping report-suppression";
        } // END of reportSuppressFlag definition.

        leaf debugIgmpSnooping  {
            type  cml_data_types:CML_COMMON_DEBUG_TYPE_T;  
            description "debug igmp snooping";
        } // END of debugIgmpSnooping definition.

        leaf termdebugIgmpSnooping  {
            type  cml_data_types:CML_COMMON_DEBUG_TYPE_T;  
        } // END of termdebugIgmpSnooping definition.

        leaf l2UnknownMcast  {
            type  cml_data_types:CML_UNKNOWN_MCAST_T;  
            default "flood";
        } // END of l2UnknownMcast definition.

    } // END of igmpConfig-container definition.
    } // END of igmpConfig-container definition.


}
