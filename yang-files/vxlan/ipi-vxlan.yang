/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-vxlan.yang
*
*/

module ipi-vxlan {

    yang-version 1.1;

    namespace   "http://www.ipinfusion.com/yang/ocnos/ipi-vxlan";

    prefix "ipi-vxlan";

    import cml-data-types {
        prefix cml-data-types;
        revision-date 2022-09-30;
    }

    import ietf-inet-types {
        prefix inet;
        revision-date 2013-07-15;
    }

    import ipi-vxlan-types {
        prefix ipi-vxlan-types;
        revision-date 2022-06-01;
    }

    import ipi-interface {
        prefix ipi-interface;
        revision-date 2022-08-24;
    }

    import ipi-vrf {
        prefix ipi-vrf;
        revision-date 2022-07-13;
    }

    import ipi-qos {
        prefix ipi-qos;
        revision-date 2022-08-24;
    }

    import ipi-network-instance {
        prefix ipi-network-instance;
        revision-date 2022-06-01;
    }

    import ietf-yang-types {
        prefix yang;
        revision-date 2013-07-15;
    }

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for VxLAN protocol";


    revision "2022-06-09" {
        description "Blocking nvo vxlan access-if cli for Jericho2";
        reference " 0.3.14.";
    }

    revision "2022-06-01" {
        description "Updated the yang file with feature";
        reference " 0.3.13.";
    }

    revision "2022-05-04" {
        description "Remove VTEP-IP dependency with secondary ip ";
        reference " 0.3.12.";
    }

    revision "2022-04-22" {
        description "Added dependent object for global vrf configs";
        reference " 0.3.11.";
    }

    revision "2022-02-16" {
        description "Added new attributes in grouping vxlan-access-port-counters-state";
        reference " 0.3.10.";
    }

    revision "2021-12-28" {
        description "VxLAN Xconnect (ELINE) get-api update";
        reference " 0.3.9.";
    }

    revision "2021-12-27" {
        description "VxLAN Xconnect inner-vid-disabled option add";
        reference " 0.3.8.";
    }

    revision "2021-11-29" {
        description "VxLAN Xconnect (ELINE) New feature";
        reference " 0.3.7.";
    }

    revision "2021-10-14" {
        description "Modified the access interface grouping as separted for arp/nd cache inorder to max-cache-disable-count dependency needed only for tagged/stacked incase of Non-Dune";
        reference " 0.3.6.";
    }

    revision "2021-09-29" {
        description "changed ordering of mac-ageing timer and arp-nd refresh timer";
        reference " 0.3.5.";
    }

    revision "2021-09-15" {
        description "Added dependency for secondary ip address config and implicit_delete for parent container";
        reference " 0.3.4.";
    }

    revision "2021-09-07" {
        description "Added dependency for API exection order for esi/system-mac";
        reference " 0.3.3.";
    }

    revision "2021-09-01" {
        description "Changed base interface module's switchport attribute name and the datatype from bool to empty";
        reference " 0.3.2.";
    }

    revision "2021-08-16" {
        description "Added default option with port only access-interface creation and deletion; Changed to allow vlan range also in case of tagged access-interface";
        reference " 0.3.1.";
    }

    revision "2021-08-01" {
        description "Updated trigger for default mode addition for missing bridges";
        reference " 0.3.0.";
    }

    revision "2021-03-31" {
        description "Added helpstrings, Modified RPC implementation on clear network/access port";
        reference " 0.2.1.";
    }

    revision "2021-03-04" {
        description "On Access Interface configuration modified when tags on switchport status check";
        reference " 0.2.0.";
    }

    revision "2020-12-15" {
        description "Change to have data-types in lower case instead of camel case";
        reference " 0.1.1.";
    }

    revision "2020-06-02" {
        description "Restructured as per Openconfig style";
        reference " 0.1.0.";
    }

    grouping vxlan-global-config {
        description
            "Grouping for global vxlan configuration";
        leaf enable-vxlan  {
            type  empty;
            mandatory true;
            description "Use this attribute to enable VxLAN module. Without this attribute
                        vxlan functionality can not be achieved";
        } // END of enable-vxlan definition.

        leaf vtep-ipv4  {
            type  inet:ipv4-address;
            description "Use this attribute to set source vtep global ip address. This will be
                        treated at vxlan tunnel source address";
        } // END of vtep-ipv4 definition.

        leaf mac-ageing-timer  {
            type  uint32 {
                 range "10..572"  {
                    description "10..572: Supported range 10 - 572";
                 }
            }
            units "seconds";
            default "300";
            description "Use this attribute to set the time till a learned mac address will
                        persist after last update";
        } // END of mac-ageing-timer definition.

        leaf arp-nd-refresh-timer  {
            if-feature feature-list:HAVE_BGP_EVPN;
            type  uint32 {
                 range "3..190"  {
                    description "3..190: Supported range 3 - 190";
                 }
            }
            units "seconds";
            description "Use this attribute to configure aging out the arp-cache and nd-cache
                        entries for given time multiplied by 3 in secs.";
        } // END of arp-nd-refresh-timer definition.

        leaf maximum-cache-disable-count  {
            if-feature feature-list:HAVE_BGP_EVPN;
            if-feature feature-list:NOT_HAVE_DUNE;
            type  uint16 {
                 range "1..200"  {
                    description "1..200: Supported range 1 - 200";
                 }
            }
            description "Use this command to configure the maximum number of ARP and ND cache
                        disables on access ports configured with
                        the port+VLAN options. This command does not limit the ARP and ND
                        cache disables on access ports created with
                        only the port option.";
        } // END of maximum-cache-disable-count definition.

    } // END of vxlan-global-config definition.
    grouping vxlan-qos-global-config {
        description
            "Grouping for global vxlan-qos configuration";
        leaf traffic-direction  {
            type  ipi-vxlan-types:vxlan_qos_dir_t;
            description "Use this attribute to set global direction(ingress/egress) for VxLAN.
                        Ingreess means traffic coming to network side and egress means traffic
                        going out from network side";
        } // END of traffic-direction definition.

        leaf qos-map-mode  {
            type  ipi-vxlan-types:vxlan_qos_global_mode_t;
            description "Use this attribute to set VxLAN-QoS Map Mode for overlay dscp";
        } // END of qos-map-mode definition.

        leaf profile-name  {
            type  string {
                length "1..1965";
                pattern "[^?' =,>|]+";
            }
            mandatory true;
            description "Use this attribute to map QOS profile name. This profile name should
                        be already configured before mapping it to vxlan tunnel";
        } // END of profile-name definition.

    } // END of vxlan-qos-global-config definition.
    grouping vxlan-tenant-global-config {
        description
            "Grouping for global vxlan-qos configuration";
        leaf vxlan-identifier  {
            type  uint32 {
                 range "1..16777215"  {
                    description "1..16777215: Supported range 1 - 16777215";
                 }
            }
            description "Use this attribute to add a tenant and the type of VPN";
        } // END of vxlan-identifier definition.

        leaf tenant-type  {
            type  ipi-vxlan-types:vxlan_tenant_type_t;
            description "Use this attribute to create tenant with multicast tunnel";
        } // END of tenant-type definition.

        leaf xconnect-identifier  {
            if-feature feature-list:HAVE_EVPN_VPWS;
            type  uint32 {
                 range "1..16777215"  {
                    description "1..16777215: Supported range 1 - 16777215";
                 }
            }
            description "Use this attribute to create Xconnect tenant";
        } // END of xconnect-identifier definition.

        leaf tenant-xconnect-type  {
            type  ipi-vxlan-types:vxlan_tenant_xconnect_type_t;
            description "Use this attribute to create tenant with different type of tunnel";
        } // END of tenant-xconnect-type definition.

    } // END of vxlan-tenant-global-config definition.
    grouping vxlan-tenant-config {
        description
            "Grouping for vxlan-tenant configuration";
        leaf vrf-name  {
            if-feature feature-list:HAVE_BGP_EVPN;
            type  leafref {
                path  "/ipi-network-instance:network-instances/ipi-network-instance:network-instance/ipi-vrf:vrf/ipi-vrf:config/ipi-vrf:vrf-name";
            }
            description "Use this attribute to map VRF to carry EVPN routes. This defines BGP
                        as the mechanism for host reachability advertisement.";
        } // END of vrf-name definition.

        leaf-list map-network  {
            type  string {
                length "1..1965";
                pattern "[^?' =,>|]+";
            }
            description "Use this attribute to map a tunnel to the tenant";
        } // END of map-network definition.

        leaf mac-hold-timer  {
            if-feature feature-list:HAVE_BGP_EVPN;
            type  int32 {
                 range "-1..300"  {
                    description "-1..300: Supported range -1 - 300";
                 }
            }
            units "seconds";
            default "0";
            description "Use this attribute to set the time a host mac entry
                        will persist after unconfiguring. Hold time range -1 to 300 in
                        seconds.
                        -1(never expire)";
        } // END of mac-hold-timer definition.

        leaf tenant-description  {
            type  string {
                length "1..10";
                pattern "[^?' =,>|]+";
            }
            description "Use this attribute to set VxLAN identifier name";
        } // END of tenant-description definition.

        leaf irb-name  {
            if-feature feature-list:HAVE_BGP_EVPN;
            type  leafref {
                path  "/ipi-interface:interfaces/ipi-interface:interface/ipi-interface:name";
            }
            description "Use this attribute to to configure default gateway behavior on a VTEP
                        for particular VNID.";
        } // END of irb-name definition.

    } // END of vxlan-tenant-config definition.
    grouping vxlan-tenant-route-count-state {
        description
            "Grouping for vxlan-tenant configuration";
        leaf total  {
            type  uint32;
            description "Use this attribute to show count of Total Route Entries";
        } // END of total definition.

        leaf mac-only  {
            type  uint32;
            description "Use this attribute to show count of Mac Only Entries";
        } // END of mac-only definition.

        leaf mac-ipv4  {
            type  uint32;
            description "Use this attribute to show count of Mac Ipv4 Entries";
        } // END of mac-ipv4 definition.

        leaf mac-ipv6  {
            if-feature feature-list:HAVE_IPV6;
            type  uint32;
            description "Use this attribute to show count of Mac Ipv6 Entries";
        } // END of mac-ipv6 definition.

    } // END of vxlan-tenant-route-count-state definition.
    grouping vxlan-tenant-xconnect-mapping-state {
        description
            "Grouping for vxlan xconnect mapping";
        leaf source-tenant-description  {
            type  string {
                length "1..1965";
                pattern "[^?' =,>|]+";
            }
            description "Use this attribute to show name of source tenant";
        } // END of source-tenant-description definition.

        leaf destination-vpws-identifier  {
            type  uint32;
            description "Use this attribute to show the remote vpws id";
        } // END of destination-vpws-identifier definition.

        leaf vlan-id  {
            type  string {
                length "1..1965";
                pattern "[^?' =,>|]+";
            }
            description "vlan id";
        } // END of vlan-id definition.

        leaf inner-vlan-id  {
            type  uint32;
            description "Inner vlan Id";
        } // END of inner-vlan-id definition.

        leaf source-interface  {
            type  string {
                length "1..1965";
                pattern "[^?' =,>|]+";
            }
            description "Use this attribute to show source connection of tunnel";
        } // END of source-interface definition.

        leaf destination-interface  {
            type  string {
                length "1..1965";
                pattern "[^?' =,>|]+";
            }
            description "Use this attribute to show destination connection of tunnel";
        } // END of destination-interface definition.

        leaf vtep-ip-address  {
            type  inet:ipv4-address;
            description "Use this attribute to show tunnel ip address";
        } // END of vtep-ip-address definition.

        leaf connection-type  {
            type  ipi-vxlan-types:vxlan_tenant_xconnect_connection_type_t;
            description "Use this attribute to show the type of network connection";
        } // END of connection-type definition.

        leaf connection-status  {
            type  ipi-vxlan-types:vxlan_tenant_xconnect_connection_status_t;
            description "Use this attribute to show status of network connection";
        } // END of connection-status definition.

    } // END of vxlan-tenant-xconnect-mapping-state definition.
    grouping vxlan-static-tenant-config {
        description
            "Grouping for vxlan-static tenant configuration";
        leaf mac-address  {
            type  cml-data-types:cml_mac_addr_t {
                length "1..1965";
            }
            description "Use this attribute to know Mac address of the
                        host.create a static route to reach a destination MAC in the VXLAN
                        forwarding table. This command helps to supports different tenants so
                        that they can have the same MAC/IP, but different VNIDs.This command
                        is required for unicast tunnels to map the remote VTEP";
        } // END of mac-address definition.

        leaf remote-vtep-ipv4  {
            type  inet:ipv4-address;
            mandatory true;
            description "Use this attribute to set unicast IP address of the destination VTEP";
        } // END of remote-vtep-ipv4 definition.

    } // END of vxlan-static-tenant-config definition.
    grouping vxlan-tenant-arp-cache-state {
        description
            "Grouping for display arp-cache information";
        leaf host-ip  {
            type  inet:ipv4-address;
            description "Use this attribute to show Host IP address";
        } // END of host-ip definition.

        leaf host-mac  {
            type  cml-data-types:cml_mac_addr_t {
                length "1..1965";
            }
            description "Use this attribute to show Host MAC address";
        } // END of host-mac definition.

        leaf host-type  {
            type  ipi-vxlan-types:vxlan_host_t;
            description "Use this attribute to show Host Type";
        } // END of host-type definition.

        leaf interface-index  {
            type  uint32;
            description "Use this attribute to show Interface Index";
        } // END of interface-index definition.

    } // END of vxlan-tenant-arp-cache-state definition.
    grouping vxlan-tenant-nd-cache-state {
        description
            "Grouping for display nd-cache information";
        leaf host-ip  {
            type  inet:ipv6-address;
            description "Use this attribute to show Host IP address";
        } // END of host-ip definition.

        leaf host-mac  {
            type  cml-data-types:cml_mac_addr_t {
                length "1..1965";
            }
            description "Use this attribute to show Host Mac Address";
        } // END of host-mac definition.

        leaf host-type  {
            type  ipi-vxlan-types:vxlan_host_t;
            description "Use this attribute to show Host Type";
        } // END of host-type definition.

        leaf interface-index  {
            type  uint32;
            description "Use this attribute to show Interface Index";
        } // END of interface-index definition.

    } // END of vxlan-tenant-nd-cache-state definition.
    grouping vxlan-tenant-mac-table-state {
        description
            "Grouping for display mac table information";
        leaf mac-address  {
            type  cml-data-types:cml_mac_addr_t {
                length "1..1965";
            }
            description "Mac Adress of the host";
        } // END of mac-address definition.

        leaf interface-name  {
            type  leafref {
                path  "/ipi-interface:interfaces/ipi-interface:interface/ipi-interface:name";
            }
            description "interface name";
        } // END of interface-name definition.

        leaf vlan-id  {
            type  string {
                length "1..1965";
                pattern "[^?' =,>|]+";
            }
            description "vlan id";
        } // END of vlan-id definition.

        leaf inner-vlan-id  {
            type  uint32;
            description "Inner vlan Id";
        } // END of inner-vlan-id definition.

        leaf vtep-ip-esi  {
            type  string {
                length "1..1965";
                pattern "[^?' =,>|]+";
            }
            description "VTEP global ip address or ESI";
        } // END of vtep-ip-esi definition.

        leaf host-type  {
            type  ipi-vxlan-types:vxlan_host_t;
            description "Host Type";
        } // END of host-type definition.

        leaf host-status  {
            type  ipi-vxlan-types:vxlan_host_status_t;
            description "Host Status";
        } // END of host-status definition.

        leaf access-port-description  {
            type  string {
                length "1..1965";
                pattern "[^?' =,>|]+";
            }
            description "Description for the port";
        } // END of access-port-description definition.

    } // END of vxlan-tenant-mac-table-state definition.
    grouping vxlan-tenant-static-host-state {
        description
            "Grouping for displaying static host state";
        leaf mac-address  {
            type  cml-data-types:cml_mac_addr_t {
                length "1..1965";
            }
            description "Mac Adress of the host";
        } // END of mac-address definition.

        leaf static-host-state  {
            type  ipi-vxlan-types:vxlan_static_host_state_t;
            description "static host state";
        } // END of static-host-state definition.

        leaf host-ipv4  {
            type  inet:ipv4-address;
            description "Host IP Adress ipv4";
        } // END of host-ipv4 definition.

    } // END of vxlan-tenant-static-host-state definition.
    grouping vxlan-tenant-static-host-ipv6-state {
        description
            "Grouping for displaying static host-ipv6 state";
        leaf mac-address  {
            type  cml-data-types:cml_mac_addr_t {
                length "1..1965";
            }
            description "Mac Adress of the host";
        } // END of mac-address definition.

        leaf static-host-state  {
            type  ipi-vxlan-types:vxlan_static_host_state_t;
            description "static host state";
        } // END of static-host-state definition.

        leaf host-ipv6  {
            if-feature feature-list:HAVE_IPV6;
            type  inet:ipv6-address;
            description "Host IP Adress ipv6";
        } // END of host-ipv6 definition.

    } // END of vxlan-tenant-static-host-ipv6-state definition.
    grouping vxlan-tunnel-state {
        description
            "Grouping for displaying tunnel information";
        leaf destination-vtep-ip  {
            type  inet:ipv4-address;
            description "Use this attribute to set Tunnel destination IP";
        } // END of destination-vtep-ip definition.

        leaf source-vtep-ip  {
            type  inet:ipv4-address;
            description "Use this attribute to set Tunnel source IP";
        } // END of source-vtep-ip definition.

        leaf up-down-time  {
            type  yang:timeticks;
            description "Use this attribute to indicate tunnel up/down time";
        } // END of up-down-time definition.

        leaf tunnel-status  {
            type  ipi-vxlan-types:vxlan_tunnel_status_t;
            description "Use this attribute to see the Status of tunnel";
        } // END of tunnel-status definition.

    } // END of vxlan-tunnel-state definition.
    grouping vxlan-tunnel-counters-state {
        description
            "Grouping for displaying tunnel counters and statistics.";
        container counters {
            config false;
            description
                "A collection of vxlan network-related statistics";
            leaf out-bytes  {
                type  yang:counter64;
                description "This indicates total number of bytes sent out from tunnel interface";
            } // END of out-bytes definition.

            leaf out-packets  {
                type  yang:counter64;
                description "This indicates total number of packets sent out from tunnel interface";
            } // END of out-packets definition.

            leaf in-bytes  {
                type  yang:counter64;
                description "This indicates total number of bytes received on tunnel interface";
            } // END of in-bytes definition.

            leaf in-packets  {
                type  yang:counter64;
                description "This indicates total number of packets received on tunnel interface";
            } // END of in-packets definition.

            leaf tx-arp-discard-packets  {
                type  yang:counter64;
                description "This Object describes Arp Discarded Packets";
            } // END of tx-arp-discard-packets definition.

            leaf tx-nd-discard-packets  {
                type  yang:counter64;
                description "This Object describes Nd Discarded Packets";
            } // END of tx-nd-discard-packets definition.

            leaf tx-arp-request-packets  {
                type  yang:counter64;
                description "This Object describes Arp request Transmitted Packets";
            } // END of tx-arp-request-packets definition.

            leaf tx-arp-reply-packets  {
                type  yang:counter64;
                description "This Object describes Arp reply Transmitted Packets";
            } // END of tx-arp-reply-packets definition.

            leaf tx-neighbor-solicitation-packets  {
                type  yang:counter64;
                description "This Object describes Neighbour Solicitation Transmitted Packets";
            } // END of tx-neighbor-solicitation-packets definition.

            leaf tx-neighbor-advertisement-packets  {
                type  yang:counter64;
                description "This Object describes Neighbour Advertisement Transmitted Packets";
            } // END of tx-neighbor-advertisement-packets definition.

            leaf tx-garp-packets  {
                type  yang:counter64;
                description "This Object describes Garp Transmitted Packets";
            } // END of tx-garp-packets definition.

            leaf tx-gna-packets  {
                type  yang:counter64;
                description "This Object describes Gna Transmitted Packets";
            } // END of tx-gna-packets definition.

        } // END of counters-container definition.
    } // END of vxlan-tunnel-counters-state definition.
    grouping vxlan-access-port-vlan-config {
        description
            "Grouping for single tagged vxlan access interface";
        leaf vlan-identifier  {
            type  string {
                length "1..1965";
                pattern "[^?' =,>|]+";
            }
            description "Use this attriute to map a VLAN on physical interface to identify the
                        tenant traffic and to enter NVO access interface mode";
        } // END of vlan-identifier definition.

    } // END of vxlan-access-port-vlan-config definition.
    grouping vxlan-access-port-stacked-vlan-config {
        description
            "Grouping for double tagged vxlan access interface";
        leaf vlan-identifier  {
            type  string {
                length "1..1965";
                pattern "[^?' =,>|]+";
            }
            description "S-VLAN on which interface is mapped";
        } // END of vlan-identifier definition.

        leaf inner-vlan-identifier  {
            type  uint32 {
                 range "2..4094"  {
                    description "2..4094: Supported range 2 - 4094";
                 }
            }
            description "Use this attriute to map VLAN'S on an interface to identify the tenant
                        traffic and to enter NVO access interface mode";
        } // END of inner-vlan-identifier definition.

    } // END of vxlan-access-port-stacked-vlan-config definition.
    grouping vxlan-access-encapsulation-config {
        description
            "Grouping for single tagged vxlan access interface";
        leaf tag-protocol-identifier  {
            type  string {
                length "1..1965";
                pattern "[^?' =,>|]+";
            }
            description "Use this attribute to set the Tpid for the outer vlan. Ox88A8: IEEE
                        802.1ad Provider Bridging and Ox9100: IEEE 802.1Q VLAN-tagged frame
                        with double tagging";
        } // END of tag-protocol-identifier definition.

    } // END of vxlan-access-encapsulation-config definition.
    grouping vxlan-access-interface-config {
        description
            "Grouping for vxlan access interface configuration";
        leaf interface-name  {
            type  leafref {
                path  "/ipi-interface:interfaces/ipi-interface:interface/ipi-interface:name";
            }
            description "Use this attriute to map a physical interface to identify the tenant
                        traffic and to enter NVO access interface mode";
        } // END of interface-name definition.

        leaf vxlan-identifier  {
            type  leafref {
                path  "/vxlan/vxlan-tenant/config/vxlan-identifier";
            }
            description "Use this attribute to map a tenant to an access-port";
        } // END of vxlan-identifier definition.

        leaf tenant-description  {
            type  leafref {
                path  "/vxlan/vxlan-tenant/config/tenant-description";
            }
            description "Use this attribute to map VXLAN Identifier Name";
        } // END of tenant-description definition.

        leaf admin-shutdown  {
            type  empty;
            description "Use this attribute to shutdown vxlan access interface";
        } // END of admin-shutdown definition.

        leaf description  {
            type  cml-data-types:cml_line_t {
                length "1..1965";
            }
            description "Use this attribute to set description of access interface";
        } // END of description definition.

        leaf dynamic-learning-disable  {
            type  empty;
            description "Use this attribute to disable dynamic learning of MACs at the access
                        port. This command also disables dynamic learning of MAC/IP from
                        ARP/ND messages received on this access port.";
        } // END of dynamic-learning-disable definition.

        leaf access-mac-hold-time  {
            type  int32 {
                 range "-1..300"  {
                    description "-1..300: Supported range -1 - 300";
                 }
            }
            description "Use this attribute to set the time a host mac entry will persist after
                        unconfiguring. The feature holds the MAC in hardware until BGP has
                        withdrawn from the neighbors. This helps to reduce flooding to other
                        access ports. This setting applies when the access port is shut down,
                        the physical port on which the access port is down, or the access port
                        is removed from the VNID using the no form of the map vnid command.
                        When the MAC hold time is configured as -1, then the MAC is not
                        removed from the hardware and is also not withdrawn from EVPN BGP";
        } // END of access-mac-hold-time definition.

        leaf arp-nd-flood-suppress  {
            if-feature feature-list:HAVE_BGP_EVPN;
            type  empty;
            description "Use this attribute to restrict the flood of ARP/ND packets towards
                        remote VTEPs or other access ports.This command applies only when the
                        ARP cache and ND cache are enabled. When the ARP cache is disabled,
                        ARP flooding is not suppressed even if this command is given. When the
                        ND cache is disabled, ND flooding is not disabled, even if this
                        command is given";
        } // END of arp-nd-flood-suppress definition.

        leaf garp-gna-enable  {
            if-feature feature-list:HAVE_BGP_EVPN;
            type  empty;
            description "Use this attribute to allow garp-gna packets advertisement";
        } // END of garp-gna-enable definition.

        leaf-list mac-address  {
            type  cml-data-types:cml_mac_addr_t {
                length "1..1965";
            }
            description "Use this attribute to set the static mac address of host";
        } // END of mac-address definition.

    } // END of vxlan-access-interface-config definition.
    grouping vxlan-untagged-access-interface-cache-config {
        description
            "Grouping for vxlan untagged access interface arp/nd cache
                        configuration";
        leaf arp-cache-disable  {
            if-feature feature-list:HAVE_BGP_EVPN;
            type  empty;
            description "Use this attribute to disable the ARP cache for MAC/IP. When the ARP
                        cache is disabled on a VxLAN access port, ZebOS-XP does not reply to
                        any ARP arriving on this port from the cache. ZebOS-XP withdraws all
                        MAC/IPs configured/learned on this access port and removes the MAC/IP
                        entry for this access port from the local ARP cache. ZebOS-XP also
                        makes sure that on withdrawing the MAC/IP route, the MAC does not
                        become unknown. If all routes for this MAC are being withdrawn because
                        of this command, then ZebOS-XP advertises a MAC-only route. This is
                        done so that the MAC does not become unknown and only the cache
                        functionality becomes disabled.See also nvo vxlan max-cache-disable.
                        Use the no form of this command to enable ARP cache for MAC/IP. Note:
                        On enabling the cache, an IP will be in conflict, then the cache
                        enable will fail. The conflict has to be manually removed and then the
                        cache enabled.";
        } // END of arp-cache-disable definition.

        leaf nd-cache-disable  {
            if-feature feature-list:HAVE_BGP_EVPN;
            type  empty;
            description "Use this attribute to disable ND cache for MAC/IPv6. When the ARP
                        cache is disabled on a VxLAN access port, ZebOS-XP does not reply to
                        any ARP arriving on this port from the cache. ZebOS-XP withdraws all
                        MAC/IPs configured/learned on this access port and removes the MAC/IP
                        entry for this access port from the local ARP cache. ZebOS-XP also
                        makes sure that on withdrawing the MAC/IP route, the MAC does not
                        become unknown. If all routes for this MAC are being withdrawn because
                        of this command, then ZebOS-XP advertises a MAC-only route. This is
                        done so that the MAC does not become unknown and only the cache
                        functionality becomes disabled. Use the no form of this command to
                        enable ND cache for MAC/IPv6. Note: On enabling the cache, an IP will
                        be in conflict, then the cache enable will fail. The conflict has to
                        be manually removed and then the cache enabled.";
        } // END of nd-cache-disable definition.

    } // END of vxlan-untagged-access-interface-cache-config definition.
    grouping vxlan-access-interface-cache-config {
        description
            "Grouping for vxlan tagged and stacked access interface arp/nd cache
                        configuration";
        leaf arp-cache-disable  {
            if-feature feature-list:HAVE_BGP_EVPN;
            type  empty;
            description "Use this attribute to disable the ARP cache for MAC/IP. When the ARP
                        cache is disabled on a VxLAN access port, ZebOS-XP does not reply to
                        any ARP arriving on this port from the cache. ZebOS-XP withdraws all
                        MAC/IPs configured/learned on this access port and removes the MAC/IP
                        entry for this access port from the local ARP cache. ZebOS-XP also
                        makes sure that on withdrawing the MAC/IP route, the MAC does not
                        become unknown. If all routes for this MAC are being withdrawn because
                        of this command, then ZebOS-XP advertises a MAC-only route. This is
                        done so that the MAC does not become unknown and only the cache
                        functionality becomes disabled.See also nvo vxlan max-cache-disable.
                        Use the no form of this command to enable ARP cache for MAC/IP. Note:
                        On enabling the cache, an IP will be in conflict, then the cache
                        enable will fail. The conflict has to be manually removed and then the
                        cache enabled.";
        } // END of arp-cache-disable definition.

        leaf nd-cache-disable  {
            if-feature feature-list:HAVE_BGP_EVPN;
            type  empty;
            description "Use this attribute to disable ND cache for MAC/IPv6. When the ARP
                        cache is disabled on a VxLAN access port, ZebOS-XP does not reply to
                        any ARP arriving on this port from the cache. ZebOS-XP withdraws all
                        MAC/IPs configured/learned on this access port and removes the MAC/IP
                        entry for this access port from the local ARP cache. ZebOS-XP also
                        makes sure that on withdrawing the MAC/IP route, the MAC does not
                        become unknown. If all routes for this MAC are being withdrawn because
                        of this command, then ZebOS-XP advertises a MAC-only route. This is
                        done so that the MAC does not become unknown and only the cache
                        functionality becomes disabled. Use the no form of this command to
                        enable ND cache for MAC/IPv6. Note: On enabling the cache, an IP will
                        be in conflict, then the cache enable will fail. The conflict has to
                        be manually removed and then the cache enabled.";
        } // END of nd-cache-disable definition.

    } // END of vxlan-access-interface-cache-config definition.
    grouping vxlan-access-mac-ipv4-config {
        description
            "Grouping for vxlan access interface configuration";
        leaf mac-address  {
            type  cml-data-types:cml_mac_addr_t {
                length "1..1965";
            }
            description "MAC Address of host connected to vxlan access port";
        } // END of mac-address definition.

        leaf ipv4-address  {
            type  inet:ipv4-address;
            description "USe this attribute to associate a static MAC address and a static IPv4
                        or IPv6 address on an access interface.";
        } // END of ipv4-address definition.

    } // END of vxlan-access-mac-ipv4-config definition.
    grouping vxlan-access-mac-ipv6-config {
        description
            "Grouping for vxlan access host configuration";
        leaf mac-address  {
            type  cml-data-types:cml_mac_addr_t {
                length "1..1965";
            }
            description "MAC Address of host connected to vxlan access port";
        } // END of mac-address definition.

        leaf ipv6-address  {
            type  inet:ipv6-address;
            description "USe this attribute to associate a static MAC address and a static IPv4
                        or IPv6 address on an access interface.";
        } // END of ipv6-address definition.

    } // END of vxlan-access-mac-ipv6-config definition.
    grouping vxlan-access-interface-qos-type-mapping-config {
        description
            "Grouping for vxlan access interface qos configuration";
        leaf profile-map-type  {
            type  ipi-vxlan-types:vxlan_qos_map_profile_type_t;
            description "Use this attribute to map the profile type for which qos profile is
                        already created globally to access port";
        } // END of profile-map-type definition.

        leaf profile-name  {
            type  string {
                length "1..1965";
                pattern "[^?' =,>|]+";
            }
            mandatory true;
            description "Use this attribute to map QOS profile name to port for which QOS
                        profile is already created globally";
        } // END of profile-name definition.

    } // END of vxlan-access-interface-qos-type-mapping-config definition.
    grouping vxlan-access-port-counters-state {
        description
            "Grouping for displaying tunnel counters and statistics.";
        leaf interface-index  {
            type  uint32;
            config false;
            description "Use this attribute to fetch nvo access port counters";
        } // END of interface-index definition.

        leaf if-name  {
            type  cml-data-types:cml_line_t {
                length "1..1965";
            }
            description "Use this attribute to fetch nvo access port name";
        } // END of if-name definition.

        container access-counters {
            config false;
            description
                "A collection of vxlan access-port-related statistics";
            leaf rx-arp-discard-packets  {
                type  yang:counter64;
                description "This Object describes Arp Discard Packets(Applicable only for logical
                            VxLAN-access ports)";
            } // END of rx-arp-discard-packets definition.

            leaf tx-arp-discard-packet  {
                type  yang:counter64;
                description "This Object describes Arp Out Discard Packets(Applicable only for
                            logical VxLAN-access ports)";
            } // END of tx-arp-discard-packet definition.

            leaf rx-arp-request-packets  {
                type  yang:counter64;
                description "This Object describes Arp request Received Packets(Applicable only for
                            logical VxLAN-access ports)";
            } // END of rx-arp-request-packets definition.

            leaf rx-arp-reply-packets  {
                type  yang:counter64;
                description "This Object describes Arp reply Received Packets(Applicable only for
                            logical VxLAN-access ports)";
            } // END of rx-arp-reply-packets definition.

            leaf tx-arp-request-packet  {
                type  yang:counter64;
                description "This Object describes Arp request Transmitted Packets(Applicable only
                            for logical VxLAN-access ports)";
            } // END of tx-arp-request-packet definition.

            leaf tx-arp-reply-packet  {
                type  yang:counter64;
                description "This Object describes Arp reply Transmitted Packets(Applicable only
                            for logical VxLAN-access ports)";
            } // END of tx-arp-reply-packet definition.

            leaf rx-nd-discard-packets  {
                type  yang:counter64;
                description "This Object describes ND Discard Packets(Applicable only for logical
                            VxLAN-access ports)";
            } // END of rx-nd-discard-packets definition.

            leaf tx-nd-discard-packet  {
                type  yang:counter64;
                description "This Object describes ND Out Discard Packets(Applicable only for
                            logical VxLAN-access ports)";
            } // END of tx-nd-discard-packet definition.

            leaf rx-neighbor-solicitation-packets  {
                type  yang:counter64;
                description "This Object describes ND Solicitaion Received Packets(Applicable only
                            for logical VxLAN-access ports)";
            } // END of rx-neighbor-solicitation-packets definition.

            leaf rx-neighbor-advertisement-packets  {
                type  yang:counter64;
                description "This Object describes ND Advertisement Received Packets(Applicable
                            only for logical VxLAN-access ports)";
            } // END of rx-neighbor-advertisement-packets definition.

            leaf tx-neighbor-solicitation-packet  {
                type  yang:counter64;
                description "This Object describes ND Solicitaion Transmitted Packets(Applicable
                            only for logical VxLAN-access ports)";
            } // END of tx-neighbor-solicitation-packet definition.

            leaf tx-neighbor-advertisement-packet  {
                type  yang:counter64;
                description "This Object describes ND Advertisement Transmitted Packets(Applicable
                            only for logical VxLAN-access ports)";
            } // END of tx-neighbor-advertisement-packet definition.

            leaf rx-gratuitous-arp-packets  {
                type  yang:counter64;
                description "This Object describes Gratuitous ARP  (Garp) Received
                            Packets(Applicable only for logical VxLAN-access ports)";
            } // END of rx-gratuitous-arp-packets definition.

            leaf tx-gratuitous-arp-packets  {
                type  yang:counter64;
                description "This Object describes Gratuitous ARP (Garp) Transmitted
                            Packets(Applicable only for logical VxLAN-access ports)";
            } // END of tx-gratuitous-arp-packets definition.

            leaf rx-gratuitous-na-packets  {
                type  yang:counter64;
                description "This Object describes Gratuitous NA (Gna) Received Packets(Applicable
                            only for logical VxLAN-access ports)";
            } // END of rx-gratuitous-na-packets definition.

            leaf tx-gratuitous-na-packets  {
                type  yang:counter64;
                description "This Object describes Gratuitous NA (Gna) Transmitted
                            Packets(Applicable only for logical VxLAN-access ports)";
            } // END of tx-gratuitous-na-packets definition.

            leaf rx-data-packets  {
                type  yang:counter64;
                description "This Object describes Received Data Packets(Applicable only for
                            logical VxLAN-access ports)";
            } // END of rx-data-packets definition.

            leaf rx-data-bytes  {
                type  yang:counter64;
                description "This Object describes Received bytes(Applicable only for logical
                            VxLAN-access ports)";
            } // END of rx-data-bytes definition.

            leaf tx-data-packets  {
                type  yang:counter64;
                description "This Object describes Transmitted Packets(Applicable only for logical
                            VxLAN-access ports)";
            } // END of tx-data-packets definition.

            leaf tx-data-bytes  {
                type  yang:counter64;
                description "This Object describes Transmitted Bytes(Applicable only for logical
                            VxLAN-access ports)";
            } // END of tx-data-bytes definition.

        } // END of access-counters-container definition.
    } // END of vxlan-access-port-counters-state definition.
    grouping vxlan-qos-global-top {
        description
            "Top level Grouping for global vxlan qos";

        list qos-tunnel-mapping {
        when " /ipi-vxlan:vxlan/ipi-vxlan:global/ipi-vxlan:config/ipi-vxlan:enable-vxlan ";
            if-feature feature-list:HAVE_QOS;
            key "qos-map-mode traffic-direction";
            description
                "Vxlan Qos configuration for mapping direction and profile";
            leaf qos-map-mode  {
                type  leafref {
                    path  "../config/qos-map-mode";
                }
                description "Use this attribute to set VxLAN-QoS Map Mode for overlay dscp";
            } // END of qos-map-mode definition.

            leaf traffic-direction  {
                type  leafref {
                    path  "../config/traffic-direction";
                }
                description "Use this attribute to set global direction(ingress/egress) for VxLAN.
                            Ingreess means traffic coming to network side and egress means traffic
                            going out from network side";
            } // END of traffic-direction definition.

            container config {
                description
                    "Configuration data";
                uses vxlan-qos-global-config;
            } // END of config-container definition.
            container state {
                config false;
                description
                    "Operational state data";
                uses vxlan-qos-global-config;
            } // END of state-container definition.
        } // End of qos-tunnel-mapping-list
    } // END of vxlan-qos-global-top definition.
    grouping vxlan-tenant-top {
        description
            "Top-Level Grouping for VxLAN Tenant";

        list vxlan-tenant {
        when " /ipi-vxlan:vxlan/ipi-vxlan:global/ipi-vxlan:config ";
            key "vxlan-identifier";
            description
                "Tenant related configurations";
            leaf vxlan-identifier  {
                type  leafref {
                    path  "../config/vxlan-identifier";
                }
                description "Use this attribute to add a tenant and the type of VPN";
            } // END of vxlan-identifier definition.

            container config {
                description
                    "Configuration data";
                uses vxlan-tenant-config;
                uses vxlan-tenant-global-config;
            } // END of config-container definition.
            container state {
                config false;
                description
                    "Operational state data";
                uses vxlan-tenant-config;
                uses vxlan-tenant-global-config;
            } // END of state-container definition.
            container route-count-info {
                config false;
                description
                    "Configuration data for VxLAN global capability configuration";
                container state {
                    config false;
                    description
                        "Operational state data";
                    uses vxlan-tenant-route-count-state;
                } // END of state-container definition.
            } // END of route-count-info-container definition.
            container xconnect-mapping-info {
                if-feature feature-list:HAVE_EVPN_VPWS;
                config false;
                description
                    "This holds data for VXLAN xconnect mapping summary";
                container state {
                    config false;
                    description
                        "Operational state data";
                    uses vxlan-tenant-xconnect-mapping-state;
                } // END of state-container definition.
            } // END of xconnect-mapping-info-container definition.
            uses vxlan-static-tenant-list;
            uses vxlan-tenant-arp-cache-list;
            uses vxlan-tenant-nd-cache-list;
            uses vxlan-tenant-mac-table-list;
            uses vxlan-tenant-static-host-list;
            uses vxlan-tenant-static-host-ipv6-list;
        } // End of vxlan-tenant-list
    } // END of vxlan-tenant-top definition.
    grouping vxlan-static-tenant-list {
        description
            "List grouping for static-vxlan-tenant configuration";

        list static-tenant {
        when " /ipi-vxlan:vxlan/ipi-vxlan:vxlan-tenant/ipi-vxlan:static-tenant/ipi-vxlan:config/ipi-vxlan:remote-vtep-ipv4 ";
            key "mac-address";
            description
                "static tenant related configurations";
            leaf mac-address  {
                type  leafref {
                    path  "../config/mac-address";
                }
                description "Use this attribute to know Mac address of the host.create
                            a static route to reach a destination MAC in the VXLAN forwarding
                            table. This command helps to supports different tenants so that they
                            can have the same MAC/IP, but different VNIDs.This command is
                            required for unicast tunnels to map the remote VTEP";
            } // END of mac-address definition.

            container config {
                description
                    "Configuration data";
                uses vxlan-static-tenant-config;
            } // END of config-container definition.
            container state {
                config false;
                description
                    "Operational state data";
                uses vxlan-static-tenant-config;
            } // END of state-container definition.
        } // End of static-tenant-list
    } // END of vxlan-static-tenant-list definition.
    grouping vxlan-tenant-arp-cache-list {
        description
            "Grouping for arp-cache information configuration";

        list arp-cache-info {
            key "host-ip";
            config false;
            description
                "arp-cache information list";
            leaf host-ip  {
                type  leafref {
                    path  "../state/host-ip";
                }
                description "Use this attribute to show Host IP address";
            } // END of host-ip definition.

            container state {
                config false;
                description
                    "Operational state data";
                uses vxlan-tenant-arp-cache-state;
            } // END of state-container definition.
        } // End of arp-cache-info-list
    } // END of vxlan-tenant-arp-cache-list definition.
    grouping vxlan-tenant-nd-cache-list {
        description
            "Grouping for nd-cache information display";

        list nd-cache-info {
            key "host-ip";
            config false;
            description
                "nd-cache information list";
            leaf host-ip  {
                type  leafref {
                    path  "../state/host-ip";
                }
                description "Use this attribute to show Host IP address";
            } // END of host-ip definition.

            container state {
                config false;
                description
                    "Operational state data";
                uses vxlan-tenant-nd-cache-state;
            } // END of state-container definition.
        } // End of nd-cache-info-list
    } // END of vxlan-tenant-nd-cache-list definition.
    grouping vxlan-tenant-mac-table-list {
        description
            "Grouping for mac table information display";

        list mac-table-info {
            key "mac-address";
            config false;
            description
                "mac table display information";
            leaf mac-address  {
                type  leafref {
                    path  "../state/mac-address";
                }
                description "Mac Adress of the host";
            } // END of mac-address definition.

            container state {
                config false;
                description
                    "Operational state data";
                uses vxlan-tenant-mac-table-state;
            } // END of state-container definition.
        } // End of mac-table-info-list
    } // END of vxlan-tenant-mac-table-list definition.
    grouping vxlan-tenant-static-host-list {
        description
            "Grouping for static host state display";

        list static-host-info {
            key "mac-address host-ipv4";
            config false;
            description
                "static host state display information";
            leaf mac-address  {
                type  leafref {
                    path  "../state/mac-address";
                }
                description "Mac Adress of the host";
            } // END of mac-address definition.

            leaf host-ipv4  {
                type  leafref {
                    path  "../state/host-ipv4";
                }
                description "Host IP Adress ipv4";
            } // END of host-ipv4 definition.

            container state {
                config false;
                description
                    "Operational state data";
                uses vxlan-tenant-static-host-state;
            } // END of state-container definition.
        } // End of static-host-info-list
    } // END of vxlan-tenant-static-host-list definition.
    grouping vxlan-tenant-static-host-ipv6-list {
        description
            "Grouping for static host-ipv6 state display";

        list static-host-ipv6-info {
            key "mac-address host-ipv6";
            config false;
            description
                "static host-ipv6 state display information";
            leaf mac-address  {
                type  leafref {
                    path  "../state/mac-address";
                }
                description "Mac Adress of the host";
            } // END of mac-address definition.

            leaf host-ipv6  {
                type  leafref {
                    path  "../state/host-ipv6";
                }
                description "Host IP Adress ipv6";
            } // END of host-ipv6 definition.

            container state {
                config false;
                description
                    "Operational state data";
                uses vxlan-tenant-static-host-ipv6-state;
            } // END of state-container definition.
        } // End of static-host-ipv6-info-list
    } // END of vxlan-tenant-static-host-ipv6-list definition.
    grouping vxlan-tunnel-top {
        description
            "Top-Level Grouping for VxLAN Tunnel";

        list tunnel {
            key "destination-vtep-ip";
            config false;
            description
                "tunnel related display information";
            leaf destination-vtep-ip  {
                type  leafref {
                    path  "../state/destination-vtep-ip";
                }
                description "Use this attribute to set Tunnel destination IP";
            } // END of destination-vtep-ip definition.

            container state {
                config false;
                description
                    "Operational state data";
                uses vxlan-tunnel-state;
                uses vxlan-tunnel-counters-state;
            } // END of state-container definition.
        } // End of tunnel-list
    } // END of vxlan-tunnel-top definition.
    grouping vxlan-access-port-default-config {
        description
            "Grouping for port only default config";
        leaf default-access-interface  {
            type  empty;
            description "Use this attribute to create default access interface";
        } // END of default-access-interface definition.

    } // END of vxlan-access-port-default-config definition.
    grouping vxlan-access-interface-top {
        description
            "Top-Level Grouping for VxLAN access interfaces";

        list untagged-access-interface {
        when " /ipi-vxlan:vxlan/ipi-vxlan:global/ipi-vxlan:config and /ipi-interface:interfaces/ipi-interface:interface/ipi-interface:config/ipi-interface:enable-switchport ";
            if-feature feature-list:NOT_HAVE_DNX;
            key "interface-name";
            description
                "untagged access port related configurations";
            leaf interface-name  {
                type  leafref {
                    path  "../config/interface-name";
                }
                description "Use this attriute to map a physical interface to identify the tenant
                            traffic and to enter NVO access interface mode";
            } // END of interface-name definition.

            container config {
                description
                    "Configuration data";
                uses vxlan-access-interface-config;
                uses vxlan-access-port-default-config;
                uses vxlan-untagged-access-interface-cache-config;
            } // END of config-container definition.
            container state {
                config false;
                description
                    "Operational state data";
                uses vxlan-access-interface-config;
                uses vxlan-access-port-default-config;
                uses vxlan-untagged-access-interface-cache-config;
            } // END of state-container definition.
            uses vxlan-access-interface-port-only-mac-ipv4-list;
            uses vxlan-access-interface-port-only-mac-ipv6-list;
            uses vxlan-access-interface-qos-map-list;
        } // End of untagged-access-interface-list

        list tagged-access-interface {
        when " /ipi-vxlan:vxlan/ipi-vxlan:global/ipi-vxlan:config and /ipi-interface:interfaces/ipi-interface:interface/ipi-interface:config/ipi-interface:enable-switchport ";
            if-feature feature-list:NOT_HAVE_DNX;
            key "interface-name vlan-identifier";
            description
                "single tagged vxlan access-port related configurations";
            leaf interface-name  {
                type  leafref {
                    path  "../config/interface-name";
                }
                description "Physical Port on which access-port is created";
            } // END of interface-name definition.

            leaf vlan-identifier  {
                type  leafref {
                    path  "../config/vlan-identifier";
                }
                description "Use this attriute to map a VLAN on physical interface to identify the
                            tenant traffic and to enter NVO access interface mode";
            } // END of vlan-identifier definition.

            container config {
                description
                    "Configuration data";
                uses vxlan-access-encapsulation-config;
                uses vxlan-access-interface-cache-config;
                uses vxlan-access-interface-config;
                uses vxlan-access-port-vlan-config;
            } // END of config-container definition.
            container state {
                config false;
                description
                    "Operational state data";
                uses vxlan-access-encapsulation-config;
                uses vxlan-access-interface-cache-config;
                uses vxlan-access-interface-config;
                uses vxlan-access-port-vlan-config;
            } // END of state-container definition.
            uses vxlan-access-interface-port-vlan-mac-ipv4-list;
            uses vxlan-access-interface-port-vlan-mac-ipv6-list;
            uses vxlan-access-interface-qos-map-list;
        } // End of tagged-access-interface-list

        list double-tagged-access-interface {
        when " /ipi-vxlan:vxlan/ipi-vxlan:global/ipi-vxlan:config and /ipi-interface:interfaces/ipi-interface:interface/ipi-interface:config/ipi-interface:enable-switchport ";
            if-feature feature-list:NOT_HAVE_DNX;
            key "interface-name vlan-identifier inner-vlan-identifier";
            description
                "double tagged access port related configurations";
            leaf interface-name  {
                type  leafref {
                    path  "../config/interface-name";
                }
                description "Physical Port on which access-port is created";
            } // END of interface-name definition.

            leaf vlan-identifier  {
                type  leafref {
                    path  "../config/vlan-identifier";
                }
                description "S-VLAN on which interface is mapped";
            } // END of vlan-identifier definition.

            leaf inner-vlan-identifier  {
                type  leafref {
                    path  "../config/inner-vlan-identifier";
                }
                description "Use this attriute to map VLAN'S on an interface to identify the tenant
                            traffic and to enter NVO access interface mode";
            } // END of inner-vlan-identifier definition.

            container config {
                description
                    "Configuration data";
                uses vxlan-access-encapsulation-config;
                uses vxlan-access-interface-cache-config;
                uses vxlan-access-interface-config;
                uses vxlan-access-port-stacked-vlan-config;
            } // END of config-container definition.
            container state {
                config false;
                description
                    "Operational state data";
                uses vxlan-access-encapsulation-config;
                uses vxlan-access-interface-cache-config;
                uses vxlan-access-interface-config;
                uses vxlan-access-port-stacked-vlan-config;
            } // END of state-container definition.
            uses vxlan-access-interface-port-stacked-vlan-mac-ipv4-list;
            uses vxlan-access-interface-port-stacked-vlan-mac-ipv6-list;
            uses vxlan-access-interface-qos-map-list;
        } // End of double-tagged-access-interface-list
    } // END of vxlan-access-interface-top definition.
    grouping vxlan-access-interface-port-only-mac-ipv4-list {
        description
            "Grouping for mac-ipv4 configuration for untagged access port";

        list host-mac-ipv4 {
            if-feature feature-list:NOT_HAVE_DNX;
            key "mac-address ipv4-address";
            description
                "untagged access side host related configurations";
            leaf mac-address  {
                type  leafref {
                    path  "../config/mac-address";
                }
                description "Use this attribute to know Mac address of the host";
            } // END of mac-address definition.

            leaf ipv4-address  {
                type  leafref {
                    path  "../config/ipv4-address";
                }
                description "USe this attribute to associate a static MAC address and a static IPv4
                            or IPv6 address on an access interface.";
            } // END of ipv4-address definition.

            container config {
                description
                    "Configuration data";
                uses vxlan-access-mac-ipv4-config;
            } // END of config-container definition.
            container state {
                config false;
                description
                    "Operational state data";
                uses vxlan-access-mac-ipv4-config;
            } // END of state-container definition.
        } // End of host-mac-ipv4-list
    } // END of vxlan-access-interface-port-only-mac-ipv4-list definition.
    grouping vxlan-access-interface-qos-map-list {
        description
            "Grouping for mapping qos profile  configuration for untagged access
                        port";

        list access-interface-qos-type-mapping {
        when " /ipi-qos:qos/ipi-qos:global/ipi-qos:config/ipi-qos:enable-qos ";
            if-feature feature-list:HAVE_QOS;
            key "profile-map-type";
            description
                "untagged access side qos-map related configurations";
            leaf profile-map-type  {
                type  leafref {
                    path  "../config/profile-map-type";
                }
                description "Use this attribute to map the profile type for which qos profile is
                            already created globally to access port";
            } // END of profile-map-type definition.

            container config {
                description
                    "Configuration data";
                uses vxlan-access-interface-qos-type-mapping-config;
            } // END of config-container definition.
            container state {
                config false;
                description
                    "Operational state data";
                uses vxlan-access-interface-qos-type-mapping-config;
            } // END of state-container definition.
        } // End of access-interface-qos-type-mapping-list
    } // END of vxlan-access-interface-qos-map-list definition.
    grouping vxlan-access-interface-port-vlan-mac-ipv4-list {
        description
            "Grouping for mac-ipv4 configuration for single tagged access port";

        list host-mac-ipv4 {
            key "mac-address ipv4-address";
            description
                "single tagged access side host related configurations";
            leaf mac-address  {
                type  leafref {
                    path  "../config/mac-address";
                }
                description "Use this attribute to know Mac address of the host";
            } // END of mac-address definition.

            leaf ipv4-address  {
                type  leafref {
                    path  "../config/ipv4-address";
                }
                description "IPv4 Address of host connected to vxlan access port";
            } // END of ipv4-address definition.

            container config {
                description
                    "Configuration data";
                uses vxlan-access-mac-ipv4-config;
            } // END of config-container definition.
            container state {
                config false;
                description
                    "Operational state data";
                uses vxlan-access-mac-ipv4-config;
            } // END of state-container definition.
        } // End of host-mac-ipv4-list
    } // END of vxlan-access-interface-port-vlan-mac-ipv4-list definition.
    grouping vxlan-access-interface-port-stacked-vlan-mac-ipv4-list {
        description
            "Grouping for mac-ipv4 configuration for double tagged access port";

        list host-mac-ipv4 {
            if-feature feature-list:NOT_HAVE_DNX;
            key "mac-address ipv4-address";
            description
                "double tagged access side host related configurations";
            leaf mac-address  {
                type  leafref {
                    path  "../config/mac-address";
                }
                description "Use this attribute to know Mac address of the host";
            } // END of mac-address definition.

            leaf ipv4-address  {
                type  leafref {
                    path  "../config/ipv4-address";
                }
                description "USe this attribute to associate a static MAC address and a static IPv4
                            or IPv6 address on an access interface.";
            } // END of ipv4-address definition.

            container config {
                description
                    "Configuration data";
                uses vxlan-access-mac-ipv4-config;
            } // END of config-container definition.
            container state {
                config false;
                description
                    "Operational state data";
                uses vxlan-access-mac-ipv4-config;
            } // END of state-container definition.
        } // End of host-mac-ipv4-list
    } // END of vxlan-access-interface-port-stacked-vlan-mac-ipv4-list definition.
    grouping vxlan-access-interface-port-only-mac-ipv6-list {
        description
            "Grouping for mac-ipv6 configuration for untagged access port";

        list host-mac-ipv6 {
            if-feature feature-list:HAVE_IPV6;
            if-feature feature-list:NOT_HAVE_DNX;
            key "mac-address ipv6-address";
            description
                "untagged access side host related configurations";
            leaf mac-address  {
                type  leafref {
                    path  "../config/mac-address";
                }
                description "Use this attribute to know Mac address of the host";
            } // END of mac-address definition.

            leaf ipv6-address  {
                type  leafref {
                    path  "../config/ipv6-address";
                }
                description "USe this attribute to associate a static MAC address and a static IPv4
                            or IPv6 address on an access interface.";
            } // END of ipv6-address definition.

            container config {
                description
                    "Configuration data";
                uses vxlan-access-mac-ipv6-config;
            } // END of config-container definition.
            container state {
                config false;
                description
                    "Operational state data";
                uses vxlan-access-mac-ipv6-config;
            } // END of state-container definition.
        } // End of host-mac-ipv6-list
    } // END of vxlan-access-interface-port-only-mac-ipv6-list definition.
    grouping vxlan-access-interface-port-vlan-mac-ipv6-list {
        description
            "Grouping for mac-ipv6 configuration for single tagged access port";

        list host-mac-ipv6 {
            if-feature feature-list:HAVE_IPV6;
            key "mac-address ipv6-address";
            description
                "single tagged access side host related configurations";
            leaf mac-address  {
                type  leafref {
                    path  "../config/mac-address";
                }
                description "Use this attribute to know Mac address of the host";
            } // END of mac-address definition.

            leaf ipv6-address  {
                type  leafref {
                    path  "../config/ipv6-address";
                }
                description "USe this attribute to associate a static MAC address and a static IPv4
                            or IPv6 address on an access interface.";
            } // END of ipv6-address definition.

            container config {
                description
                    "Configuration data";
                uses vxlan-access-mac-ipv6-config;
            } // END of config-container definition.
            container state {
                config false;
                description
                    "Operational state data";
                uses vxlan-access-mac-ipv6-config;
            } // END of state-container definition.
        } // End of host-mac-ipv6-list
    } // END of vxlan-access-interface-port-vlan-mac-ipv6-list definition.
    grouping vxlan-access-interface-port-stacked-vlan-mac-ipv6-list {
        description
            "Grouping for mac-ipv6 configuration for double tagged access port";

        list host-mac-ipv6 {
            if-feature feature-list:HAVE_IPV6;
            key "mac-address ipv6-address";
            description
                "double tagged access side host related configurations";
            leaf mac-address  {
                type  leafref {
                    path  "../config/mac-address";
                }
                description "Use this attribute to know Mac address of the host";
            } // END of mac-address definition.

            leaf ipv6-address  {
                type  leafref {
                    path  "../config/ipv6-address";
                }
                description "USe this attribute to associate a static MAC address and a static IPv4
                            or IPv6 address on an access interface.";
            } // END of ipv6-address definition.

            container config {
                description
                    "Configuration data";
                uses vxlan-access-mac-ipv6-config;
            } // END of config-container definition.
            container state {
                config false;
                description
                    "Operational state data";
                uses vxlan-access-mac-ipv6-config;
            } // END of state-container definition.
        } // End of host-mac-ipv6-list
    } // END of vxlan-access-interface-port-stacked-vlan-mac-ipv6-list definition.
    grouping vxlan-access-interface-counters-top {
        description
            "Top-Level Grouping for VxLAN access interfaces counters";
        container access-interfaces {
            config false;
            description
                "access-interfaces container";

            list access-interface {
                key "interface-index";
                config false;
                description
                    "access port counters list";
                leaf interface-index  {
                    type  leafref {
                        path  "../state/interface-index";
                    }
                    description "Use this attribute to fetch nvo access port counters";
                } // END of interface-index definition.

                container state {
                    config false;
                    description
                        "Operational state data";
                    uses vxlan-access-port-counters-state;
                } // END of state-container definition.
            } // End of access-interface-list
        } // END of access-interfaces-container definition.
    } // END of vxlan-access-interface-counters-top definition.

    grouping  vxlan-grouping {
    description
        "VxLAN global level container";
    container vxlan {
        if-feature feature-list:HAVE_VXLAN;
        description
            "VxLAN global level container";
        container global {
            when " /ipi-vxlan:vxlan/ipi-vxlan:global/ipi-vxlan:config/ipi-vxlan:enable-vxlan ";
            description
                "Configuration data for VxLAN global capability configuration";
            container config {
                presence "Enable EVPN-VxLAN";
                description
                    "Configuration data";
                uses vxlan-global-config;
            } // END of config-container definition.
            container state {
                config false;
                description
                    "Operational state data";
                uses vxlan-global-config;
            } // END of state-container definition.
        } // END of global-container definition.
        uses vxlan-qos-global-top;
        uses vxlan-tenant-top;
        uses vxlan-tunnel-top;
        uses vxlan-access-interface-top;
        uses vxlan-access-interface-counters-top;
    } // END of vxlan-container definition.
    } // END of vxlan-grouping definition.

    uses vxlan-grouping;

    rpc clear-nvo-vxlan-dynamic-mac-address-table {
        if-feature feature-list:HAVE_VXLAN;
        description "Use this RPC to clear the dynamic entries from mac address table";
    }

    rpc clear-nvo-vxlan-tunnels {
        if-feature feature-list:HAVE_VXLAN;
        description "Use this RPC to clear all the nvo vxlan tunnels";
    }

    rpc clear-nvo-id-vxlan-tunnels-destip {
        if-feature feature-list:HAVE_VXLAN;
        description "Use this RPC to clear the nvo vxlan tunnels dest ip";
        input  {
            leaf destination-vtep-ip  {
                type inet:ipv4-address;
                mandatory true;
                description "Use this attribute to include Tunnel destination IP";
            }
        }
    }

    rpc clear-nvo-vxlan-mac-stale-entries {
        if-feature feature-list:HAVE_VXLAN;
        description "Use this RPC to clear the vxlan mac stale entries";
        input  {
            leaf vxlan-identifier  {
                type uint32 {
                    range "1..16777215";
                }
                description "Use this attribute to include a tenant and the type of VPN";
            }
        }
    }

    rpc clear-vxlan-untagged-access-port-counters {
        if-feature feature-list:HAVE_VXLAN;
        description "Use this RP to clear the counters of untagged access port";
        input  {
            leaf interface-name  {
                type string;
                mandatory true;
                description "interface name";
            }
        }
    }

    rpc clear-vxlan-single-tagged-access-port-counters {
        if-feature feature-list:HAVE_VXLAN;
        description "Use this RPC to clear the counters of single tagged port counters";
        input  {
            leaf interface-name  {
                type string;
                mandatory true;
                description "interface name";
            }
            leaf vlan-identifier  {
                type string;
                mandatory true;
                description "S-VLAN on which interface is mapped";
            }
        }
    }

    rpc clear-vxlan-double-tagged-access-port-counters {
        if-feature feature-list:HAVE_VXLAN;
        description "Use this RPC to clear the counters of double tagged port";
        input  {
            leaf interface-name  {
                type string;
                mandatory true;
                description "interface name";
            }
            leaf outer-vlan-identifier  {
                type uint32 {
                    range "2..4094";
                }
                mandatory true;
                description "Outer vlan on which interface mapped";
            }
            leaf inner-vlan-identifier  {
                type uint32 {
                    range "2..4094";
                }
                mandatory true;
                description "Inner vlan on which interface mapped";
            }
        }
    }

    rpc clear-vxlan-access-port-counters-all {
        if-feature feature-list:HAVE_VXLAN;
        description "Use this RPC to clear the all the access port counters";
    }

    rpc clear-vxlan-network-port-counters {
        if-feature feature-list:HAVE_VXLAN;
        description "Use this RPC to clear the network port counters";
        input  {
            leaf destination-vtep-ip  {
                type inet:ipv4-address;
                mandatory true;
                description "Use this attribute to include Tunnel destination IP";
            }
        }
    }

    rpc clear-vxlan-network-port-counters-all {
        if-feature feature-list:HAVE_VXLAN;
        description "Use this RPC to clear all the network port counters";
    }

    notification vxlan-tunnel-status-change-notification {
        if-feature feature-list:HAVE_VXLAN;

        description "The nvoTunnelStatus trap is generated when there is any status change in Tunnel Severity level is INFO for tunnel status going to Unresolved/Deleted status and MINOR for Resolved status..";

        leaf severity {
            type cml-data-types:cml_notif_severity_t;
            description "Notification severity level";
        }

        leaf eventClass {
            type cml-data-types:cml_notif_class_t;
            description "Notification event class (value: STATE)";
        }

        leaf destination-vtep-ip {
            type  inet:ipv4-address;
        description
            "Use this attribute to set Tunnel destination IP";
        }

        leaf tunnel-status {
            type ipi-vxlan-types:vxlan_tunnel_status_t;
        description
            "Use this attribute to see the Status of tunnel";
        }
    }

}
