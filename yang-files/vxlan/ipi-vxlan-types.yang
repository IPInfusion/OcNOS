/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-vxlan-types.yang
*
*/

module ipi-vxlan-types {

    yang-version 1.1;

    namespace   "http://www.ipinfusion.com/yang/ocnos/ipi-vxlan-types";

    prefix "ipi-vxlan-types";

    organization
        "IP Infusion Inc.";

    contact
        "Address: 3965 Freedom Circle, Suite 200, Santa Clara, CA 95054
         Phone: +1 408-400-1900
         E-mail: support@ipinfusion.com
         Web: http://www.ipinfusion.com/";

    description
        "YANG version of the ipi-vxlan-types";


    revision "2022-06-01" {
        description "Updated the yang file with feature";
        reference " 0.1.5.";
    }

    revision "2021-12-28" {
        description "VxLAN Xconnect git api";
        reference " 0.1.4.";
    }

    revision "2021-12-27" {
        description "VxLAN Xconnect inner-vid-disabled option add";
        reference " 0.1.3.";
    }

    revision "2021-09-03" {
        description "Update descriptions of attribute";
        reference " 0.1.2.";
    }

    revision "2020-12-15" {
        description "Change to have data-types in lower case instead of camel case";
        reference " 0.1.1.";
    }

    revision "2020-06-02" {
        description "Restructured as per Openconfig style";
        reference " 0.1.0.";
    }



    typedef  vxlan_qos_global_mode_t {
        type enumeration {
            enum cos-dscp {
                value 1;
                description "Cos/Dscp to Overlay Dscp mapping";
            }
        }
        description "type definition for VXLAN_QOS_GLOBAL_MODE_T";
    }

    typedef  vxlan_qos_dir_t {
        type enumeration {
            enum ingress {
                value 0;
                description "Apply ingress direction(Network-Access)";
            }
            enum egress {
                value 1;
                description "Apply Egress direction(Access-Network)";
            }
        }
        description "type definition for VXLAN_QOS_DIR_T";
    }

    typedef  vxlan_host_t {
        type enumeration {
            enum Dynamic {
                value 0;
                description "Host type is Dynamic";
            }
            enum Static-Local {
                value 1;
                description "Host type is Static Local";
            }
            enum Remote-Dynamic {
                value 2;
                description "Host type is Evpn Dynamic";
            }
            enum Remote-Static {
                value 3;
                description "Host type is Evpn Static";
            }
            enum Static-Remote {
                value 4;
                description "Host type is Static Remote";
            }
        }
        description "type definition for VXLAN_HOST_T";
    }

    typedef  vxlan_static_host_state_t {
        type enumeration {
            enum Inactive {
                value 1;
                description "static host state Inactive";
            }
            enum Active {
                value 2;
                description "static host state Active";
            }
            enum Conflict {
                value 4;
                description "static host state Conflict";
            }
            enum Learnt-Conflict {
                value 8;
                description "static host state Learnt Conflict";
            }
            enum Discard-Inactive {
                value 16;
                description "static host state Discard Inactive";
            }
        }
        description "type definition for VXLAN_STATIC_HOST_STATE_T";
    }

    typedef  vxlan_tenant_type_t {
        type enumeration {
            enum default {
                value 0;
                description "Not a specific tenant which falls default type";
            }
            enum multicast {
                value 1;
                description "Point to multipoint tenant type";
            }
            enum ingress-replication {
                value 2;
                description "Head End Replication tenant type";
            }
            enum ingress-replication-inner-vid-disabled {
                value 3;
                description "Head End Replication tenant type,Inner vid disabled tenant type";
            }
        }
        description "type definition for VXLAN_TENANT_TYPE_T";
    }

    typedef  vxlan_tenant_xconnect_type_t {
        type enumeration {
            enum default {
                value 0;
                description "Not a specific tenant which falls default type";
            }
            enum inner-vid-disabled {
                value 1;
                description "Inner vid disabled tenant type";
            }
        }
        description "type definition for VXLAN_TENANT_XCONNECT_TYPE_T";
    }

    typedef  vxlan_tenant_xconnect_connection_type_t {
        type enumeration {
            enum NA {
                value 0;
                description "Connection type not available";
            }
            enum AC-AC {
                value 1;
                description "Connection type local Xconnect";
            }
            enum AC-NW {
                value 2;
                description "Connection type Xconnect over tunnle";
            }
        }
        description "type definition for VXLAN_TENANT_XCONNECT_CONNECTION_TYPE_T";
    }

    typedef  vxlan_tenant_xconnect_connection_status_t {
        type enumeration {
            enum NA {
                value 0;
                description "Connection status not available";
            }
            enum NW-SET {
                value 1;
                description "Xconnect network up";
            }
            enum AC-DN-NW-DN {
                value 2;
                description "Access port down - network down";
            }
            enum AC-DN-NW-UP {
                value 3;
                description "Access port down - network up";
            }
            enum AC-UP-NW-DN {
                value 4;
                description "Access port up - network down";
            }
        }
        description "type definition for VXLAN_TENANT_XCONNECT_CONNECTION_STATUS_T";
    }

    typedef  vxlan_tunnel_status_t {
        type enumeration {
            enum Deleted {
                value 0;
                description "Tunnel is deleted";
            }
            enum Un-Resolved {
                value 1;
                description "Tunnel not established";
            }
            enum Resolved {
                value 2;
                description "Tunnel established but not in hardware";
            }
            enum Installed {
                value 3;
                description "Tunnel established succesfully in hardware";
            }
        }
        description "type definition for VXLAN_TUNNEL_STATUS_T";
    }

    typedef  vxlan_host_status_t {
        type enumeration {
            enum --- {
                value 0;
                description "Default host status";
            }
            enum Max-Move-conflict {
                value 1;
                description "MAC has moved too many times";
            }
            enum Discard {
                value 2;
                description "MAC is moved to the discard state";
            }
        }
        description "type definition for VXLAN_HOST_STATUS_T";
    }

    typedef  vxlan_qos_map_profile_type_t {
        type enumeration {
            enum cos-to-queue {
                value 0;
                description "profile for cos to queue map (ingress direction)";
            }
            enum queue-color-to-cos {
                value 1;
                description "profile for queue color to cos map (egress direction)";
            }
        }
        description "type definition for VXLAN_QOS_MAP_PROFILE_TYPE_T";
    }

}
