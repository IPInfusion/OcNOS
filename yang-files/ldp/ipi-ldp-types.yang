/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-ldp-types.yang
*
*/

module ipi-ldp-types {

    yang-version 1.1;

    namespace   "http://www.ipinfusion.com/yang/ocnos/ipi-ldp-types";

    prefix "ipi-ldp-types";

    import ietf-inet-types {
        prefix inet;
        revision-date 2013-07-15;
    }

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "YANG version of the ipi-ldp-types";


    revision "2022-06-01" {
        description "Updated the yang file with feature";
        reference " 0.4.3.";
    }

    revision "2022-04-15" {
        description "Defined New Data Type";
        reference " 0.4.2.";
    }

    revision "2022-01-24" {
        description "Modified the defined data-type values";
        reference " 0.4.1.";
    }

    revision "2022-01-07" {
        description "Defined New Data Type";
        reference " 0.4.0.";
    }

    revision "2021-10-21" {
        description "Removed LDP_ENABLE_TYPE enum";
        reference " 0.3.4.";
    }

    revision "2021-09-03" {
        description "Update descriptions of attribute";
        reference " 0.3.3.";
    }

    revision "2021-08-30" {
        description "Updated helpstrings for debug packet elements in LDP_DEBUG datatype";
        reference " 0.3.2.";
    }

    revision "2021-08-24" {
        description "Changes to support debug packet elements in DEBUG_LDP datatype";
        reference " 0.3.1.";
    }

    revision "2021-08-06" {
        description "Changed LDP_HELPER_MODE_T to LDP_GR_MODE_T and added full and helper-only elements";
        reference " 0.3.0.";
    }

    revision "2020-12-15" {
        description "Change to have data-types in lower case instead of camel case";
        reference " 0.2.0.";
    }

    revision "2018-06-21" {
        description "Initial Version";
        reference " 0.1.0.";
    }



    typedef  cml_md5_encrypt_password_t {
        type enumeration {
            enum 0 {
                value 0;
                description "Configure password type 0 to store password as a clear text";
            }
            enum 7 {
                value 7;
                description "Configure password type 7 to encrypt password while storing";
            }
        }
        description "type definition for CML_MD5_ENCRYPT_PASSWORD_T";
    }

    typedef  ldp_md5_password_t {
        type string {
            pattern "[^? ]*";
        }
        description "type definition for LDP_MD5_PASSWORD_T";
    }

    typedef  ldp_gr_mode_t {
        type enumeration {
            enum full {
                value 0;
                description "Enable graceful restart fully";
            }
            enum helper-only {
                value 1;
                description "Enable as helper for graceful restart ";
            }
        }
        description "type definition for LDP_GR_MODE_T";
    }

    typedef  ldp_advertise_mode_t {
        type enumeration {
            enum downstream-unsolicited {
                value 0;
                description "DU advertisement mode";
            }
            enum downstream-on-demand {
                value 1;
                description "DOD advertisement mode";
            }
        }
        description "type definition for LDP_ADVERTISE_MODE_T";
    }

    typedef  ldp_controlmode_t {
        type enumeration {
            enum independent {
                value 0;
                description "DU advertisement mode";
            }
            enum ordered {
                value 1;
                description "DOD advertisement mode";
            }
        }
        description "type definition for LDP_CONTROLMODE_T";
    }

    typedef  ldp_retention_mode_t {
        type enumeration {
            enum liberal {
                value 0;
                description "Set liberal label retention mode";
            }
            enum conservative {
                value 1;
                description "Set conservative label retention mode";
            }
        }
        description "type definition for LDP_RETENTION_MODE_T";
    }

    typedef  ldp_merge_capable_t {
        type enumeration {
            enum merge-capable {
                value 0;
                description "Set merge capable";
            }
            enum non-merge-capable {
                value 1;
                description "Set non merge capable";
            }
        }
        description "type definition for LDP_MERGE_CAPABLE_T";
    }

    typedef  ldp_instance_t {
        type enumeration {
            enum ldp {
                value 1;
                description "Label Distribution Protocol (LDP)";
            }
        }
        description "type definition for LDP_INSTANCE_T";
    }

    typedef  ldp_debug_t {
        type bits {
            bit events {
                position 0;
                description "LDP events";
            }
            bit fsm {
                position 1;
                description "Enable FSM debugging";
            }
            bit hexdump {
                position 2;
                description "Enable HEXDUMP";
            }
            bit dsm {
                position 3;
                description "Enable Downstream SM";
            }
            bit usm {
                position 4;
                description "LDP Upstream SM";
            }
            bit tsm {
                position 5;
                description "LDP Trunk SM";
            }
            bit qos {
                position 6;
                description "LDP QoS";
            }
            bit nsm {
                position 7;
                description "NSM messages";
            }
            bit advertise-labels {
                position 8;
                description "List IP prefix lists of advertise-labels";
            }
            bit cspf {
                position 9;
                if-feature feature-list:HAVE_CSPF;
                description "CSPF messages";
            }
            bit vc-usm {
                position 10;
                if-feature feature-list:HAVE_MPLS_VC;
                description "LDP VC Info,LDP VC USM";
            }
            bit vc-dsm {
                position 11;
                if-feature feature-list:HAVE_MPLS_VC;
                description "LDP VC Info,LDP VC DSM";
            }
            bit graceful-restart {
                position 12;
                if-feature feature-list:HAVE_RESTART;
                description "LDP Graceful Restart Debugging";
            }
            bit rib {
                position 13;
                if-feature feature-list:HAVE_RIBD;
                description "RIB messages";
            }
            bit ha {
                position 14;
                if-feature feature-list:HAVE_HA;
                description "HA messages";
            }
            bit inter-area {
                position 15;
                if-feature feature-list:HAVE_LDP_INTER_AREA;
                description "LDP Inter-Area Information";
            }
            bit packet-notification {
                position 17;
                description "all packets,LDP notification packet";
            }
            bit packet-hello {
                position 18;
                description "all packets,LDP hello packet";
            }
            bit packet-initialization {
                position 19;
                description "all packets,LDP initialization packet";
            }
            bit packet-keepalive {
                position 20;
                description "all packets,LDP keepalive packet";
            }
            bit packet-address {
                position 21;
                description "all packets,LDP address (withdraw) packet";
            }
            bit packet-label {
                position 22;
                description "all packets,LDP label mapping/request(abort)/withdraw/release packet";
            }
        }
        description "type definition for LDP_DEBUG_T";
    }

    typedef  ldp_ip_addr_t {
        type union {
            type inet:ipv4-address {

            }
            type inet:ipv6-address {

            }
        }
        description "type definition for LDP_IP_ADDR_T";
    }

    typedef  ldp_iccp_debug_t {
        type bits {
            bit events {
                position 0;
                description "Events";
            }
            bit fsm {
                position 1;
                description "FSM";
            }
            bit hexdump {
                position 2;
                description "hexdump of messages";
            }
            bit packet {
                position 3;
                description "Packets";
            }
            bit bfd {
                position 4;
                description "BFD";
            }
        }
        description "type definition for LDP_ICCP_DEBUG_T";
    }

    typedef  ldp_label_space_identifier_t {
        type enumeration {
            enum 0 {
                value 0;
                description "Platform-wide Label space for which a transport address is being configured (Platform-wide labels are used for all interfaces that can share the same labels)";
            }
        }
        description "type definition for LDP_LABEL_SPACE_IDENTIFIER_T";
    }

    typedef  ldp_tcp_status_t {
        type enumeration {
            enum not-established {
                value 0;
                description "TCP Connection not established";
            }
            enum established {
                value 1;
                description "TCP Connection established";
            }
        }
        description "type definition for LDP_TCP_STATUS_T";
    }

    typedef  ldp_vc_state_t {
        type enumeration {
            enum down {
                value 0;
                description "VC State down (Idle, Active)";
            }
            enum up {
                value 1;
                description "VC State up (Complete)";
            }
        }
        description "type definition for LDP_VC_STATE_T";
    }

    typedef  ldp_label_merge_capability_t {
        type enumeration {
            enum non-merge-capable {
                value 0;
                description "Label-Merge capibility, non-merge capable";
            }
            enum merge-capable {
                value 1;
                description "Label-Merge capibility, merge capable";
            }
        }
        description "type definition for LDP_LABEL_MERGE_CAPABILITY_T";
    }

    typedef  ldp_session_state_t {
        type enumeration {
            enum non-existant {
                value 0;
                description "Non-Existent State";
            }
            enum initialized {
                value 1;
                description " Initialized State";
            }
            enum open-sent {
                value 2;
                description " open-sent State";
            }
            enum open-recieved {
                value 3;
                description " open-recieved State";
            }
            enum operational {
                value 4;
                description "operational State";
            }
        }
        description "type definition for LDP_SESSION_STATE_T";
    }

    typedef  ldp_session_role_t {
        type enumeration {
            enum passive {
                value 0;
                description "Passive Mode";
            }
            enum active {
                value 1;
                description "Active Mode";
            }
        }
        description "type definition for LDP_SESSION_ROLE_T";
    }

    typedef  ldp_advertisement_type_t {
        type enumeration {
            enum enable-distribution {
                value 0;
                description "Enable the distribution of all assigned labels";
            }
            enum Prevent-distribution {
                value 1;
                description "Prevent the distribution of any assigned labels";
            }
        }
        description "type definition for LDP_ADVERTISEMENT_TYPE_T";
    }

    typedef  ldp_sess_prot_status_t {
        type enumeration {
            enum disabled {
                value 0;
                description "LDP Session Protection is disabled";
            }
            enum incomplete {
                value 1;
                description "LDP Session Protection is incomplete";
            }
            enum protecting {
                value 2;
                description "LDP Session Protection is protecting";
            }
            enum expired {
                value 3;
                description "LDP Session Protection is expired";
            }
            enum ready {
                value 4;
                description "LDP Session Protection is ready";
            }
        }
        description "type definition for LDP_SESS_PROT_STATUS_T";
    }

    typedef  ldp_sess_prot_duration_default_t {
        type enumeration {
            enum infinite {
                value 0;
                description "LDP Session protection duration infinite";
            }
        }
        description "type definition for LDP_SESS_PROT_DURATION_DEFAULT_T";
    }

    typedef  ldp_sess_prot_pfx_lst_default_t {
        type enumeration {
            enum none {
                value 0;
                description "LDP Session protection prefix list none";
            }
        }
        description "type definition for LDP_SESS_PROT_PFX_LST_DEFAULT_T";
    }

    typedef  ldp_sess_prot_duration_t {
        type union {
            type ldp_sess_prot_duration_default_t {

            }
            type uint32 {
                range "5..86400";

            }
        }
        description "type definition for LDP_SESS_PROT_DURATION_T";
    }

    typedef  ldp_sess_prot_pfx_lst_t {
        type union {
            type ldp_sess_prot_pfx_lst_default_t {

            }
            type string {

            }
        }
        description "type definition for LDP_SESS_PROT_PFX_LST_T";
    }

}
