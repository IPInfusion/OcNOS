/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-ldp-interface.yang
*
*/

submodule ipi-ldp-interface {

    yang-version 1.1;

    belongs-to  ipi-ldp { prefix ipi-ldp; }

    import feature-list {
        prefix feature-list;
        revision-date 2023-02-21;
    }

    import ipi-ldp-types {
        prefix ipi-ldp-types;
        revision-date 2022-06-01;
    }

    import ipi-interface {
        prefix ipi-interface;
        revision-date 2022-08-24;
    }

    include ipi-ldp-l2vpn { revision-date 2022-06-01;}
    organization
        "IP Infusion Inc.";

    contact
        "Address: 3965 Freedom Circle, Suite 200, Santa Clara, CA 95054
         Phone: +1 408-400-1900
         E-mail: support@ipinfusion.com
         Web: http://www.ipinfusion.com/";

    description
        "Datamodel for LDP Interface information";


    revision "2022-06-01" {
        description "Updated the yang file with feature";
        reference " 0.3.2.";
    }

    revision "2021-10-21" {
        description "Updated datatype of enable-ldp attributes";
        reference " 0.3.1.";
    }

    revision "2021-09-03" {
        description "Update descriptions of attribute";
        reference " 0.3.0.";
    }

    revision "2020-12-15" {
        description "Change to have data-types in lower case instead of camel case";
        reference " 0.2.0.";
    }

    revision "2018-06-21" {
        description "Initial Version";
        reference " 0.1.0.";
    }

    grouping ldp-interface-config {
        description
            "Grouping for LDP configuration on interface";
        leaf enable-ldp-ipv4  {
            type  empty;
            description "Use this attribute to enable LDP IPv4, on a specified interface.
                        This command enables the transmission of Hello packets through the
                        current interface,
                        so that LDP adjacencies and LDP sessions can be created.";
        } // END of enable-ldp-ipv4 definition.

        leaf enable-ldp-ipv6  {
            type  empty;
            description "Use this attribute to enable LDP IPv6, on a specified interface.
                        This command enables the transmission of Hello packets through the
                        current interface,
                        so that LDP adjacencies and LDP sessions can be created.";
        } // END of enable-ldp-ipv6 definition.

        leaf multicast-hello-disable  {
            type  empty;
            description "Use this attribute to enable multicast hello exchange on specified
                        interfaces enabled for LDP.";
        } // END of multicast-hello-disable definition.

        leaf maximum-pdu-length  {
            type  uint32 {
                 range "256..65535"  {
                    description "256..65535: Supported range 256 - 65535";
                 }
            }
            default "4096";
            description "Use this attribute to specify max pdu length";
        } // END of maximum-pdu-length definition.

        leaf ldp-igp-sync-delay-interval  {
            type  uint32 {
                 range "5..60"  {
                    description "5..60: Supported range 5 - 60";
                 }
            }
            description "Use this attribute to configure a synchronization delay, that is, a
                        delay for notifications of LDP convergence to the IGP protocol used,
                        which can be either IS-IS or OSPF.";
        } // END of ldp-igp-sync-delay-interval definition.

    } // END of ldp-interface-config definition.
    grouping ldp-interface-address {
        description
            "Grouping for LDP Interface       addresses";
        leaf primary-address-ipv4  {
            type  string {
                length "1..1965";
                pattern "[^?' =,>|]+";
            }
            config false;
            description "This attribute acquires primary ipv4 address on the
                        interface";
        } // END of primary-address-ipv4 definition.

        leaf primary-address-ipv6  {
            type  string {
                length "1..1965";
                pattern "[^?' =,>|]+";
            }
            config false;
            description "This attribute acquires primary ipv6 address on the
                        interface";
        } // END of primary-address-ipv6 definition.

    } // END of ldp-interface-address definition.
    grouping ldp-interface-label-management-config {
        description
            "Grouping for LDP label management configuration";
        leaf interface-advertisement-mode  {
            type  ipi-ldp-types:ldp_advertise_mode_t;
            default "downstream-unsolicited";
            description "Use this attribute to set the label advertisement mode for an
                        interface to either downstream-ondemand (label is sent only when
                        requested) or downstream-unsolicited (label is sent unrequested).";
        } // END of interface-advertisement-mode definition.

        leaf interface-retention-mode  {
            type  ipi-ldp-types:ldp_retention_mode_t;
            default "liberal";
            description "Use this attribute to set the retention mode to be used for all labels
                        exchanged via the given interface. When an LSR receives a label
                        binding for a particular FEC (Forwarding Equivalence Class) from
                        another LSR that is not its next hop for that FEC, it might keep track
                        of such bindings or discard them. Use the liberal parameter to retain
                        all labels binding to FEC received from label distribution peers, even
                        if the LSR is not the current next-hop. Use the conservative parameter
                        to maintain only the label bindings for valid next-hops in a LSP.
                        Liberal label retention mode allows for quicker adaptation to routing
                        changes, whereas conservative label retention mode requires an LSR to
                        maintain fewer labels.";
        } // END of interface-retention-mode definition.

    } // END of ldp-interface-label-management-config definition.
    grouping ldp-interface-label-management-state {
        description
            "Grouping for LDP label management configuration";
        leaf label-merge-capability  {
            type  ipi-ldp-types:ldp_label_merge_capability_t;
            config false;
            description "This attribute acquires ldp merge capability";
        } // END of label-merge-capability definition.

        leaf ldp-identifier  {
            type  string {
                length "1..1965";
                pattern "[^?' =,>|]+";
            }
            config false;
            description "This attribute acquires LDP identifier address";
        } // END of ldp-identifier definition.

    } // END of ldp-interface-label-management-state definition.

    grouping  interfaces-grouping {
    description
        "Configuration data";
    container interfaces {
        when " /ldp/global/config ";
        if-feature feature-list:HAVE_LDPD;
        description
            "Configuration data";

        list interface {
            key "name";
            description
                "LDP interface related operations";
            leaf name  {
                type  leafref {
                    path  "/ipi-interface:interfaces/ipi-interface:interface/ipi-interface:name";
                }
                description "Reference to interface name";
            } // END of name definition.

            container config {
                description
                    "Configuration data";
                uses ldp-interface-config;
            } // END of config-container definition.
            container state {
                config false;
                description
                    "Operational state data";
                uses ldp-interface-config;
                uses ldp-interface-address;
                uses ldp-counters-state;
            } // END of state-container definition.
            container hello-timers {
                description
                    "Container for Interface hello timers configuration";
                container config {
                    description
                        "Configuration data";
                    uses ldp-hello-timers-config;
                } // END of config-container definition.
                container state {
                    config false;
                    description
                        "Operational state data";
                    uses ldp-hello-timers-config;
                } // END of state-container definition.
            } // END of hello-timers-container definition.
            container session-timers {
                description
                    "Container for Interface Session timers configuration";
                container config {
                    description
                        "Configuration data";
                    uses ldp-session-timers-config;
                } // END of config-container definition.
                container state {
                    config false;
                    description
                        "Operational state data";
                    uses ldp-session-timers-config;
                } // END of state-container definition.
            } // END of session-timers-container definition.
            container label-management {
                description
                    "Container for label management configuration";
                container config {
                    description
                        "Configuration data";
                    uses ldp-interface-label-management-config;
                } // END of config-container definition.
                container state {
                    config false;
                    description
                        "Operational state data";
                    uses ldp-interface-label-management-config;
                    uses ldp-interface-label-management-state;
                } // END of state-container definition.
            } // END of label-management-container definition.
        } // End of interface-list
    } // END of interfaces-container definition.
    } // END of interfaces-grouping definition.


}
