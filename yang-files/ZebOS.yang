/*
* Copyright (C) 2016 IP Infusion, Inc. 
*  All Rights Reserved.
*
*** Auto generated by zebmdc

* Unless required by applicable law or agreed to in writing,
* software distributed under the License is distributed on an
* "AS IS" BASIS, WITHOUT WARRANTIES OR CONDITIONS OF ANY
* KIND, either express or implied.

* File name : ZebOS.yang
*
*/

module ZebOS {

    namespace   "http://www.ipinfusion.com/CMLSchema/ZebOS";

    prefix "ZebOS";
    include nsmLACP;
    include oamBfd;
    include bridge;
    include ospf;
    include vlan;
    include mstp;
    include layer2LACP;
    include bgp;
    include vr;
    include vrf;
    include interface;
    include lldpv2;
    include ospf6;
    include rib;
    include vlaninterface;


    import cml_data_types {
        prefix cml_data_types;
    }
    organization
        "http://www.ipinfusion.com/CMLSchema";

    contact
        "http://www.ipinfusion.com/CMLSchema";

    description
        "ZebOS Managed Object";


    revision "2015-10-08" {
        description "Revisied on 2015-10-08.";    }


    uses oamMpls-grouping;
    uses lacpSystemPriority-grouping;
    uses systemDetail-grouping;
    uses ospfGlobal-grouping;
    uses hashTableInfo-grouping;
    uses vr-grouping;
    uses ospf6Global-grouping;

    rpc ospf-clear-ip-ospf-process {
        input  {
            leaf vrId  {
                type cml_data_types:CML_UINT32_T;
                mandatory true;
            }
            leaf ospfProcessId  {
                type cml_data_types:CML_INT32_T;
                mandatory true;
            }
        }
    }

    rpc ospf-clear-ip-ospf-process-all {
        input  {
            leaf vrId  {
                type cml_data_types:CML_UINT32_T;
                mandatory true;
            }
        }
    }

    rpc bgp-restartBgp {
        input  {
            leaf vrId  {
                type cml_data_types:CML_UINT32_T;
                mandatory true;
            }
        }
    }

    rpc bgp-clearBgp {
        input  {
            leaf vrId  {
                type cml_data_types:CML_UINT32_T;
                mandatory true;
            }
        }
    }

}
