/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-pim-ipv4-types.yang
*
*/

module ipi-pim-ipv4-types {

    yang-version 1.1;

    namespace   "http://www.ipinfusion.com/yang/ocnos/ipi-pim-ipv4-types";

    prefix "ipi-pim-ipv4-types";

    import cml-data-types {
        prefix cml-data-types;
        revision-date 2022-09-30;
    }

    import ietf-inet-types {
        prefix inet;
        revision-date 2013-07-15;
    }

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "PIM IPv4 types";


    revision "2022-06-01" {
        description "Updated the yang file with feature";
        reference " 0.2.0.";
    }

    revision "2022-03-15" {
        description "Restructured module in accordance with OpenConfig style";
        reference " 0.1.0.";
    }



    typedef  pim_ipv4_ssm_default_t {
        type enumeration {
            enum default {
                value 0;
                description "Use 232/8 group range for SSM";
            }
        }
        description "type definition for PIM_IPV4_SSM_DEFAULT_T";
    }

    typedef  pim_ipv4_ssm_range_t {
        type string {
            length 1..64;
        }
        description "type definition for PIM_IPV4_SSM_RANGE_T";
    }

    typedef  pim_ipv4_ssm_range_policy_type_t {
        type union {
            type pim_ipv4_ssm_range_t {

            }
            type pim_ipv4_ssm_default_t {

            }
        }
        description "type definition for PIM_IPV4_SSM_RANGE_POLICY_TYPE_T";
    }

    typedef  pim_ipv4_reg_source_t {
        type union {
            type inet:ipv4-address {

            }
            type cml-data-types:cml_ifname_t {

            }
        }
        description "type definition for PIM_IPV4_REG_SOURCE_T";
    }

    typedef  pim_ipv4_mode_clear_bsr_rp_t {
        type enumeration {
            enum sparse-mode {
                value 1;
                description "PIM sparse-mode operation";
            }
        }
        description "type definition for PIM_IPV4_MODE_CLEAR_BSR_RP_T";
    }

    typedef  pim_ipv4_mode_t {
        type enumeration {
            enum dense-mode {
                value 1;
                description "Enable PIM dense-mode operation";
            }
            enum sparse-mode {
                value 2;
                description "Enable PIM sparse-mode operation";
            }
            enum sparse-dense-mode {
                value 3;
                if-feature feature-list:HAVE_PIM_SMDM;
                description "Enable PIM sparse-mode and dense-mode operations";
            }
        }
        description "type definition for PIM_IPV4_MODE_T";
    }

    typedef  pim_ipv4_debug_t {
        type bits {
            bit events {
                position 0;
                description "PIM events";
            }
            bit packet-in {
                position 1;
                description "PIM packet,Incoming PIM packet";
            }
            bit packet-out {
                position 2;
                description "PIM packet,Outgoing PIM packet";
            }
            bit state {
                position 3;
                description "PIM state";
            }
            bit mfc {
                position 4;
                description "PIM MFC updates";
            }
            bit timer-hello-ht {
                position 5;
                description "PIM timers,Hello Timers,Hello timer";
            }
            bit timer-hello-nlt {
                position 6;
                description "PIM timers,Hello Timers,Neighbor Liveliness timer";
            }
            bit timer-hello-tht {
                position 7;
                description "PIM timers,Hello Timers,Triggered Hello timer";
            }
            bit timer-joinprune-jt {
                position 8;
                description "PIM timers,JoinPrune Timers,JoinPrune timer";
            }
            bit timer-joinprune-et {
                position 9;
                description "PIM timers,JoinPrune Timers,Expiry timer";
            }
            bit timer-joinprune-ppt {
                position 10;
                description "PIM timers,JoinPrune Timers,Prune Pending timer";
            }
            bit timer-joinprune-kat {
                position 11;
                description "PIM timers,JoinPrune Timers,Keep Alive timer";
            }
            bit timer-joinprune-ot {
                position 12;
                description "PIM timers,JoinPrune Timers,Override timer";
            }
            bit timer-assert {
                position 13;
                description "PIM timers,Assert Timers";
            }
            bit timer-register {
                position 14;
                description "PIM timers,Register Timers";
            }
            bit timer-bsr-bst {
                position 15;
                description "PIM timers,BSR Timers,Bootstrap timer";
            }
            bit timer-bsr-crp {
                position 16;
                description "PIM timers,BSR Timers,Candidate-RP timer";
            }
            bit mib {
                position 17;
                description "PIM mib";
            }
            bit nsm {
                position 18;
                description "NSM message";
            }
            bit nexthop {
                position 19;
                description "PIM nexthop";
            }
            bit mtrace {
                position 20;
                description "Mtrace messages";
            }
            bit msdp {
                position 21;
                if-feature feature-list:HAVE_PIM_MSDP;
                description "PIM MSDP";
            }
        }
        description "type definition for PIM_IPV4_DEBUG_T";
    }

    typedef  pim_ipv4_msdp_peer_state_t {
        type enumeration {
            enum Invalid {
                value 0;
                description "Peer state Invalid";
            }
            enum Disabled {
                value 1;
                description "Peer state Disabled";
            }
            enum Inactive {
                value 2;
                description "Peer state Inactive";
            }
            enum Listen {
                value 3;
                description "Peer state Listen";
            }
            enum Connecting {
                value 4;
                description "Peer state Connecting";
            }
            enum Established {
                value 5;
                description "Peer state Established";
            }
            enum Maximum {
                value 6;
                description "Peer state Maximum";
            }
        }
        description "type definition for PIM_IPV4_MSDP_PEER_STATE_T";
    }

    typedef  pim_ipv4_msdp_peer_role_t {
        type enumeration {
            enum Passive {
                value 0;
                description "Peer role passive";
            }
            enum Active {
                value 1;
                description "Peer role active";
            }
        }
        description "type definition for PIM_IPV4_MSDP_PEER_ROLE_T";
    }

    typedef  pim_ipv4_rp_mode_t {
        type enumeration {
            enum none {
                value 1;
                description "No PIM mode specified";
            }
            enum ssm {
                value 2;
                description "PIM SSM operation";
            }
            enum asm {
                value 3;
                description "PIM ASM operation";
            }
            enum bidir {
                value 4;
                description "PIM BIDIR operation";
            }
            enum dm {
                value 5;
                description "PIM DM operation";
            }
            enum other {
                value 6;
                description "Other PIM mode specified";
            }
        }
        description "type definition for PIM_IPV4_RP_MODE_T";
    }

    typedef  pim_ipv4_rp_type_t {
        type enumeration {
            enum Static {
                value 1;
                description "Static RP";
            }
            enum BSR {
                value 2;
                description "BSR RP";
            }
        }
        description "type definition for PIM_IPV4_RP_TYPE_T";
    }

    typedef  pim_ipv4_multicast_route_mode_t {
        type enumeration {
            enum None {
                value 0;
                description "PIM Muticast Route Mode None";
            }
            enum Dense {
                value 1;
                description "PIM Muticast Route Mode Dense";
            }
            enum Sparse {
                value 2;
                description "PIM Muticast Route Mode Sparse";
            }
            enum Bidir {
                value 3;
                description "PIM Muticast Route Mode Bidir";
            }
            enum Any {
                value 4;
                description "PIM Muticast Route Mode Any";
            }
        }
        description "type definition for PIM_IPV4_MULTICAST_ROUTE_MODE_T";
    }

    typedef  pim_ipv4_multicast_route_type_t {
        type enumeration {
            enum None {
                value 0;
                description "PIM Muticast Route Type None";
            }
            enum xxrp {
                value 1;
                description "PIM Muticast Route Type any source, any group and RP";
            }
            enum group-prefix {
                value 2;
                description "PIM Muticast Route Type Group or Prefix";
            }
            enum xg {
                value 3;
                description "PIM Muticast Route Type any source and group";
            }
            enum sg {
                value 4;
                description "PIM Muticast Route Type source and group";
            }
            enum sgrpt {
                value 5;
                description "PIM Muticast Route Type source, group and Rendezvous Point Tree";
            }
        }
        description "type definition for PIM_IPV4_MULTICAST_ROUTE_TYPE_T";
    }

    typedef  pim_ipv4_multicast_route_upstream_state_t {
        type enumeration {
            enum not-joined {
                value 0;
                description "PIM Muticast Route State not joined";
            }
            enum joined {
                value 1;
                description "PIM Muticast Route State joined";
            }
        }
        description "type definition for PIM_IPV4_MULTICAST_ROUTE_UPSTREAM_STATE_T";
    }

    typedef  pim_ipv4_multicast_route_upstream_sg_rpt_mode_t {
        type enumeration {
            enum not-joined {
                value 0;
                description "PIM Muticast Route Source, Group, RP-Tree State not joined";
            }
            enum pruned {
                value 1;
                description "PIM Muticast Route Source, Group, RP-Tree State pruned";
            }
            enum not-pruned {
                value 2;
                description "PIM Muticast Route Source, Group, RP-Tree State not pruned";
            }
        }
        description "type definition for PIM_IPV4_MULTICAST_ROUTE_UPSTREAM_SG_RPT_MODE_T";
    }

    typedef  pim_ipv4_multicast_route_downstream_state_t {
        type enumeration {
            enum no-info {
                value 0;
                description "PIM Muticast Route Downstream state not informed";
            }
            enum joined {
                value 1;
                description "PIM Muticast Route Downstream state joined";
            }
            enum pruned-pending {
                value 2;
                description "PIM Muticast Route Downstream state prune pending";
            }
        }
        description "type definition for PIM_IPV4_MULTICAST_ROUTE_DOWNSTREAM_STATE_T";
    }

    typedef  pim_ipv4_multicast_route_downstream_rpt_state_t {
        type enumeration {
            enum no-info {
                value 0;
                description "PIM Muticast Route Downstream state not informed";
            }
            enum pruned {
                value 1;
                description "PIM Muticast Route Downstream state pruned";
            }
            enum pruned-pending {
                value 2;
                description "PIM Muticast Route Downstream state pruned pending";
            }
            enum pruned-tmp {
                value 3;
                description "PIM Muticast Route Downstream transient state pruned";
            }
            enum pruned-pending-tmp {
                value 4;
                description "PIM Muticast Route Downstream transient state prune pending";
            }
        }
        description "type definition for PIM_IPV4_MULTICAST_ROUTE_DOWNSTREAM_RPT_STATE_T";
    }

    typedef  pim_ipv4_multicast_route_downstream_assert_state_t {
        type enumeration {
            enum no-info {
                value 0;
                description "PIM Muticast Route Downstream assert state not informed";
            }
            enum winner {
                value 1;
                description "PIM Muticast Route Downstream assert state winner";
            }
            enum loser {
                value 2;
                description "PIM Muticast Route Downstream assert state loser";
            }
        }
        description "type definition for PIM_IPV4_MULTICAST_ROUTE_DOWNSTREAM_ASSERT_STATE_T";
    }

    typedef  pim_ipv4_multicast_route_downstream_macro_state_t {
        type bits {
            bit could-assert {
                position 0;
                description "PIM Muticast Route Downstream macro state could assert";
            }
            bit assert-tracking-desired {
                position 1;
                description "PIM Muticast Route Downstream macro state assert tracking desired";
            }
        }
        description "type definition for PIM_IPV4_MULTICAST_ROUTE_DOWNSTREAM_MACRO_STATE_T";
    }

    typedef  pim_ipv4_multicast_route_upstream_macro_state_t {
        type bits {
            bit join-desired {
                position 0;
                description "PIM Muticast Route Upstream macro state join desired";
            }
            bit could-register {
                position 1;
                description "PIM Muticast Route Upstream macro state could register";
            }
            bit rpt-join-desired {
                position 2;
                description "PIM Muticast Route Upstream macro state rpt join desired";
            }
            bit prune-desired {
                position 3;
                description "PIM Muticast Route Upstream macro state prune desired";
            }
        }
        description "type definition for PIM_IPV4_MULTICAST_ROUTE_UPSTREAM_MACRO_STATE_T";
    }

    typedef  pim_ipv4_next_hop_flags_t {
        type bits {
            bit registered {
                position 0;
                description "Registered to the NSM lookup";
            }
            bit active {
                position 1;
                description "Active nexthop";
            }
            bit changed {
                position 2;
                description "Nexthop changed";
            }
            bit nexthop-to-the-source {
                position 3;
                description "Nexthop to the source";
            }
            bit nexthop-to-the-RP {
                position 4;
                description "Nexthop to the RP";
            }
            bit nexthop-by-MSDP {
                position 5;
                description "Nexthop cache created by msdp";
            }
        }
        description "type definition for PIM_IPV4_NEXT_HOP_FLAGS_T";
    }

    typedef  pim_ipv4_next_hop_type_t {
        type enumeration {
            enum default {
                value 0;
                description "Default";
            }
            enum interface-index {
                value 1;
                description "Sub type";
            }
            enum interface-name {
                value 2;
                description "Interface route";
            }
            enum IPV4 {
                value 3;
                description "IPv4 nexthop";
            }
            enum IPV4-interface-index {
                value 4;
                description "IPv4 nexthop with ifindex";
            }
            enum ipv4-interface-name {
                value 5;
                description "IPv4 nexthop with ifname";
            }
            enum IPV6 {
                value 6;
                description "IPv6 nexthop";
            }
            enum IPV6-interface-index {
                value 7;
                description "IPv6 nexthop with ifindex";
            }
            enum IPV6-interface-name {
                value 8;
                description "IPv6 nexthop with ifname";
            }
            enum MPLS {
                value 9;
                description "pass to MPLS forwarder";
            }
        }
        description "type definition for PIM_IPV4_NEXT_HOP_TYPE_T";
    }

    typedef  pim_ipv4_route_type_t {
        type enumeration {
            enum default {
                value 0;
                description "Default";
            }
            enum kernel {
                value 1;
                description "Type kernel";
            }
            enum connect {
                value 2;
                description "Type connect";
            }
            enum static {
                value 3;
                description "Type static";
            }
            enum RIP {
                value 4;
                description "Type RIP";
            }
            enum RIPNG {
                value 5;
                description "Type RIPNG";
            }
            enum OSPF {
                value 6;
                description "Type OSPF";
            }
            enum OSPF6 {
                value 7;
                description "Type OSPF6";
            }
            enum BGP {
                value 8;
                description "Type BGP";
            }
            enum ISIS {
                value 9;
                description "Type ISIS";
            }
            enum TRILL {
                value 10;
                description "Type TRILL";
            }
            enum MP {
                value 11;
                description "Type MP";
            }
            enum DUMMY {
                value 12;
                description "Type Dummy";
            }
            enum EVPN {
                value 13;
                description "Type EVPN";
            }
            enum MVPN {
                value 14;
                description "Type MVPN";
            }
            enum DHCP {
                value 15;
                description "Type DHCP";
            }
            enum MAX {
                value 16;
                description "MAX";
            }
        }
        description "type definition for PIM_IPV4_ROUTE_TYPE_T";
    }

    typedef  pim_ipv4_route_sub_type_t {
        type enumeration {
            enum default {
                value 0;
                description "Sub type default";
            }
            enum OSPF_IA {
                value 1;
                description "Sub type OSPF_IA";
            }
            enum OSPF_NSSA_1 {
                value 2;
                description "Sub type OSPF_NSSA_1";
            }
            enum OSPF_NSSA_2 {
                value 3;
                description "Sub type OSPF_NSSA_2";
            }
            enum OSPF_EXTERNAL_1 {
                value 4;
                description "Sub type OSPF_EXTERNAL_1";
            }
            enum OSPF_EXTERNAL_2 {
                value 5;
                description "Sub type OSPF_EXTERNAL_2";
            }
            enum ISIS_L1 {
                value 8;
                description "Sub type ISIS_L1";
            }
            enum ISIS_L2 {
                value 9;
                description "Sub type ISIS_L2";
            }
            enum ISIS_IA {
                value 10;
                description "Sub type ISIS_IA";
            }
            enum BGP_MPLS {
                value 11;
                description "Sub type BGP_MPLS";
            }
            enum BGP_IBGP {
                value 12;
                description "Sub type BGP_IBGP";
            }
            enum BGP_EBGP {
                value 13;
                description "Sub type BGP_EBGP";
            }
            enum BGP_INTERNAL {
                value 14;
                description "Sub type BGP_INTERNAL";
            }
            enum BGP_CONFED {
                value 15;
                description "Sub type BGP_CONFED";
            }
            enum TRILL_L1 {
                value 16;
                description "Sub type TRILL_L1";
            }
            enum TRILL_L2 {
                value 17;
                description "Sub type TRILL_L2";
            }
            enum TRILL_IA {
                value 18;
                description "Sub type TRILL_IA";
            }
            enum LFA {
                value 19;
                description "Sub type LFA";
            }
            enum BGP_EVPN {
                value 20;
                description "Sub type BGP_EVPN";
            }
            enum BGP_LEAKED_ROUTE {
                value 21;
                description "Sub type BGP_LEAKED_ROUTE";
            }
        }
        description "type definition for PIM_IPV4_ROUTE_SUB_TYPE_T";
    }

    typedef  pim_ipv4_df_state_t {
        type enumeration {
            enum Unknown {
                value 0;
                description "State Unknown";
            }
            enum Offer {
                value 1;
                description "State Offer";
            }
            enum Lose {
                value 2;
                description "State Lose";
            }
            enum Win {
                value 3;
                description "State Win";
            }
            enum BackOff {
                value 4;
                description "State BackOff";
            }
        }
        description "type definition for PIM_IPV4_DF_STATE_T";
    }

    typedef  pim_ipv4_msdp_peer_named_acl_t {
        type string {
            length 1..64;
        }
        description "type definition for PIM_IPV4_MSDP_PEER_NAMED_ACL_T";
    }

    typedef  pim_ipv4_msdp_peer_acl_t {
        type union {
            type pim_ipv4_msdp_peer_named_acl_t {

            }
            type uint32 {
                range "1..99";

            }
        }
        description "type definition for PIM_IPV4_MSDP_PEER_ACL_T";
    }

}
