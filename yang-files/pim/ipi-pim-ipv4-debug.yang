/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-pim-ipv4-debug.yang
*
*/

submodule ipi-pim-ipv4-debug {

    yang-version 1.1;

    belongs-to  ipi-pim { prefix ipi-pim; }

    import ipi-pim-ipv4-types {
        prefix ipi-pim-ipv4-types;
        revision-date 2022-06-01;
    }

    organization
        "IP Infusion Inc.";

    contact
        "Address: 3965 Freedom Circle, Suite 200, Santa Clara, CA 95054
         Phone: +1 408-400-1900
         E-mail: support@ipinfusion.com
         Web: http://www.ipinfusion.com/";

    description
        "PIM IPv4 Debug";


    revision "2022-06-01" {
        description "Updated the yang file with feature";
        reference " 0.2.0.";
    }

    revision "2022-03-15" {
        description "Restructured module in accordance with OpenConfig style";
        reference " 0.1.0.";
    }

    grouping pim-ipv4-debug-terminal-top {
        description
            "Grouping for PIM IPv4 debug";
        container terminal {
            config false;
            description
                "Container for for PIM IPv4 debugging functions";
            leaf debug-options  {
                type  ipi-pim-ipv4-types:pim_ipv4_debug_t;
                description "Use this attribute to debug the PIM IPv4 feature.";
            } // END of debug-options definition.

        } // END of terminal-container definition.
    } // END of pim-ipv4-debug-terminal-top definition.
    grouping pim-ipv4-debug-config {
        description
            "Grouping for PIM IPv4 debug configuration";
        leaf debug-options  {
            type  ipi-pim-ipv4-types:pim_ipv4_debug_t;
            description "Use this attribute to debug the PIM IPv4 feature.";
        } // END of debug-options definition.

    } // END of pim-ipv4-debug-config definition.
    grouping pim-ipv4-debug-top {
        description
            "Grouping for PIM IPv4 debug";
        container debug {
            description
                "Container for PIM IPv4 debugging functions";
            container config {
                description
                    "Configuration data PIM IPv4 debug";
                uses pim-ipv4-debug-config;
            } // END of config-container definition.
            container state {
                config false;
                description
                    "Operational state data for PIM IPv4 debug";
                uses pim-ipv4-debug-config;
                uses pim-ipv4-debug-terminal-top;
            } // END of state-container definition.
        } // END of debug-container definition.
    } // END of pim-ipv4-debug-top definition.


}
