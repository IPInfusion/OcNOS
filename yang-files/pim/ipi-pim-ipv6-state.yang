/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-pim-ipv6-state.yang
*
*/

submodule ipi-pim-ipv6-state {

    yang-version 1.1;

    belongs-to  ipi-pim { prefix ipi-pim; }

    import feature-list {
        prefix feature-list;
        revision-date 2023-02-21;
    }

    import ietf-yang-types {
        prefix yang;
        revision-date 2013-07-15;
    }

    import ietf-inet-types {
        prefix inet;
        revision-date 2013-07-15;
    }

    import ipi-pim-ipv6-types {
        prefix ipi-pim-ipv6-types;
        revision-date 2022-06-01;
    }

    organization
        "IP Infusion Inc.";

    contact
        "Address: 3965 Freedom Circle, Suite 200, Santa Clara, CA 95054
         Phone: +1 408-400-1900
         E-mail: support@ipinfusion.com
         Web: http://www.ipinfusion.com/";

    description
        "Protocol Independent Multicast (PIM) IPv6 operational state";


    revision "2022-06-06" {
        description "Removed rp-interface-name and .../upstream-xg/state/keep-alive-timer attributes";
        reference " 0.2.1.";
    }

    revision "2022-06-01" {
        description "Updated the yang file with feature";
        reference " 0.2.0.";
    }

    revision "2022-04-28" {
        description "Removed macro-state attribute from downstream-xxrp-sg-rpt/state container";
        reference " 0.1.1.";
    }

    revision "2022-03-30" {
        description "Restructured module in accordance with OpenConfig style";
        reference " 0.1.0.";
    }

    grouping pim-ipv6-register-statistics-state {
        description
            "Grouping for PIM IPv6 register packet statistics state data";
        container counters {
            config false;
            description
                "Operational state data for PIM IPv6 register packet counters";
            leaf register-packet-received  {
                type  yang:counter64;
                description "Total Register messages received by this PIM IPv6 instance.";
            } // END of register-packet-received definition.

            leaf register-null-received  {
                type  yang:counter64;
                description "Total Null-Register messages by this PIM IPv6 instance.";
            } // END of register-null-received definition.

            leaf register-stop-sent  {
                type  yang:counter64;
                description "Total Register-Stop messages sent by this PIM IPv6 instance.";
            } // END of register-stop-sent definition.

            leaf register-stop-received  {
                type  yang:counter64;
                description "Total Register-Stop messages received by this PIM IPv6 instance.";
            } // END of register-stop-received definition.

        } // END of counters-container definition.
    } // END of pim-ipv6-register-statistics-state definition.
    grouping pim-ipv6-rp-set-rp-state {
        description
            "Grouping for PIM IPv6 instance RP state data";
        leaf rp-address  {
            type  inet:ipv6-address;
            description "This attribute returns the RP address associated with this instance.";
        } // END of rp-address definition.

        leaf from  {
            type  inet:ipv6-address;
            description "This attribute returns the originating RP information address.";
        } // END of from definition.

        leaf mode  {
            type  ipi-pim-ipv6-types:pim_ipv6_rp_mode_t;
            description "This attribute returns the RP PIM mode as defined by MIB.";
        } // END of mode definition.

        leaf type  {
            type  ipi-pim-ipv6-types:pim_ipv6_rp_type_t;
            description "This attribute returns the type of RP instance.";
        } // END of type definition.

        leaf priority  {
            type  uint8;
            description "This attribute returns the RP priority, the lower the higher.";
        } // END of priority definition.

        leaf hold-time  {
            type  uint16;
            units "seconds";
            description "This attribute returns the RP hold time.";
        } // END of hold-time definition.

        leaf up-time  {
            type  string {
                length "1..1965";
                pattern "((([0-1]?[0-9])|(2[0-3])):[0-5][0-9]:[0-5][0-9])|([0-9]+d(([0-1][0-9])|(2[0-3]))h[0-5][0-9]m)";
            }
            description "This attribute returns the RP uptime.";
        } // END of up-time definition.

        leaf expiration-time  {
            type  string {
                length "1..1965";
                pattern "((([0-1]?[0-9])|(2[0-3])):[0-5][0-9]:[0-5][0-9])|([0-9]+d(([0-1][0-9])|(2[0-3]))h[0-5][0-9]m)";
            }
            description "This attribute returns the RP expiration time.";
        } // END of expiration-time definition.

    } // END of pim-ipv6-rp-set-rp-state definition.
    grouping pim-ipv6-rp-set-rp-top {
        description
            "Grouping for PIM IPv6 instance RPs data";
        container rps {
            config false;
            description
                "Operational state data for PIM IPv6 RPs";

            list rp {
                key "rp-address";
                config false;
                description
                    "List of PIM IPv6 RP instances";
                leaf rp-address  {
                    type  leafref {
                        path  "../state/rp-address";
                    }
                    description "This attribute returns the RP address associated with this instance.";
                } // END of rp-address definition.

                container state {
                    config false;
                    description
                        "Operational state data for PIM IPv6 RP";
                    uses pim-ipv6-rp-set-rp-state;
                } // END of state-container definition.
            } // End of rp-list
        } // END of rps-container definition.
    } // END of pim-ipv6-rp-set-rp-top definition.
    grouping pim-ipv6-rp-set-state {
        description
            "Grouping for PIM IPv6 instance RP-set state data";
        leaf group-address  {
            type  inet:ipv6-prefix;
            description "This attribute returns the group address associated with this
                        instance.";
        } // END of group-address definition.

        leaf fragment-tag  {
            type  uint16;
            description "This attribute returns the fragment tag associated with this
                        Rendezvous Point (RP) instance.";
        } // END of fragment-tag definition.

        leaf number-of-rp  {
            type  uint32;
            description "This attribute returns the number of Rendezvous Point (RP) instances.";
        } // END of number-of-rp definition.

        leaf expiration-time  {
            type  string {
                length "1..1965";
                pattern "((([0-1]?[0-9])|(2[0-3])):[0-5][0-9]:[0-5][0-9])|([0-9]+d(([0-1][0-9])|(2[0-3]))h[0-5][0-9]m)";
            }
            description "This attribute returns the Rendezvous Point (RP) expiration time.";
        } // END of expiration-time definition.

    } // END of pim-ipv6-rp-set-state definition.
    grouping pim-ipv6-rp-set-top {
        description
            "Grouping for PIM IPv6 instance RP-sets data";
        container rp-sets {
            config false;
            description
                "Operational state data for PIM IPv6 RP-sets";

            list rp-set {
                key "group-address";
                config false;
                description
                    "List of PIM IPv6 RP set instances";
                leaf group-address  {
                    type  leafref {
                        path  "../state/group-address";
                    }
                    description "This attribute returns the group address associated with this
                                instance.";
                } // END of group-address definition.

                container state {
                    config false;
                    description
                        "Operational state data for PIM IPv6 RP-set";
                    uses pim-ipv6-rp-set-state;
                } // END of state-container definition.
                uses pim-ipv6-rp-set-rp-top;
            } // End of rp-set-list
        } // END of rp-sets-container definition.
    } // END of pim-ipv6-rp-set-top definition.
    grouping pim-ipv6-multicast-route-ds-xxrp-sg-rpt-state {
        description
            "Grouping for PIM IPv6 multicast route table downstream info about
                        routes of type SGRPT and XXRP";
        leaf route-state  {
            type  ipi-pim-ipv6-types:pim_ipv6_multicast_route_downstream_state_t;
            description "This attribute returns the PIM IPv6 downstream route state.";
        } // END of route-state definition.

        leaf rpt-state  {
            type  ipi-pim-ipv6-types:pim_ipv6_multicast_route_downstream_rpt_state_t;
            description "This attribute returns the PIM IPv6 downstream route state.";
        } // END of rpt-state definition.

        leaf expiry-timer  {
            type  uint32;
            units "seconds";
            description "This attribute returns the PIM IPv6 route expiry timer.";
        } // END of expiry-timer definition.

        leaf prune-pending-timer  {
            type  uint32;
            units "seconds";
            description "This attribute returns the PIM IPv6 route prune pending timer.";
        } // END of prune-pending-timer definition.

    } // END of pim-ipv6-multicast-route-ds-xxrp-sg-rpt-state definition.
    grouping pim-ipv6-multicast-route-ds-xg-sg-state {
        description
            "Grouping for PIM IPv6 multicast route table downstream info about
                        routes of type SG, XG and GPREFIX";
        leaf route-state  {
            type  ipi-pim-ipv6-types:pim_ipv6_multicast_route_downstream_state_t;
            description "This attribute returns the PIM IPv6 downstream route state.";
        } // END of route-state definition.

        leaf expiry-timer  {
            type  uint32;
            units "seconds";
            description "This attribute returns the PIM IPv6 route expiry timer.";
        } // END of expiry-timer definition.

        leaf prune-pending-timer  {
            type  uint32;
            units "seconds";
            description "This attribute returns the PIM IPv6 route prune pending timer.";
        } // END of prune-pending-timer definition.

        leaf assert-state  {
            type  ipi-pim-ipv6-types:pim_ipv6_multicast_route_downstream_assert_state_t;
            description "This attribute returns the PIM IPv6 route assert state.";
        } // END of assert-state definition.

        leaf assert-timer  {
            type  uint32;
            description "This attribute returns the PIM IPv6 route assert timer.";
        } // END of assert-timer definition.

        leaf winner-address  {
            type  inet:ipv6-address;
            description "This attribute returns the PIM IPv6 route assert winner IPv6 address.";
        } // END of winner-address definition.

        leaf metric  {
            type  uint32;
            description "This attribute returns the PIM IPv6 route assert metric value.";
        } // END of metric definition.

        leaf preference  {
            type  uint32;
            description "This attribute returns the PIM IPv6 route assert metric preference
                        value.";
        } // END of preference definition.

        leaf rpt-bit  {
            type  empty;
            description "This attribute returns the PIM IPv6 route assert Rendezvous Point Tree
                        bit value.";
        } // END of rpt-bit definition.

        leaf macro-state  {
            type  ipi-pim-ipv6-types:pim_ipv6_multicast_route_downstream_macro_state_t;
            description "This attribute returns the PIM IPv6 route assert macro state.";
        } // END of macro-state definition.

    } // END of pim-ipv6-multicast-route-ds-xg-sg-state definition.
    grouping pim-ipv6-multicast-route-ds-state {
        description
            "Grouping for PIM IPv6 multicast route table downstream info";
        leaf interface-name  {
            type  string {
                length "1..1965";
                pattern "[^?' =,>|]+";
            }
            description "This attribute returns the interface name associated to this route
                        entry.";
        } // END of interface-name definition.

    } // END of pim-ipv6-multicast-route-ds-state definition.
    grouping pim-ipv6-multicast-route-downstream-top {
        description
            "Grouping for PIM IPv6 multicast route table downstream info";
        container downstream-interfaces {
            config false;
            description
                "Multicast route table downstream data";

            list downstream-interface {
                key "interface-name";
                config false;
                description
                    "List of multicast route table downstream data";
                leaf interface-name  {
                    type  leafref {
                        path  "../state/interface-name";
                    }
                    description "This attribute returns the interface name associated to this route
                                entry.";
                } // END of interface-name definition.

                container state {
                    config false;
                    description
                        "Operational state data for PIM IPv6 multicast downstream route table";
                    uses pim-ipv6-multicast-route-ds-state;
                } // END of state-container definition.
                container downstream-xg-sg {
                    config false;
                    description
                        "PIM IPv6 multicast route table downstream info about routes of type
                                (*,G), (S,G) and GPREFIX";
                    container state {
                        config false;
                        description
                            "Operational state data for PIM IPv6 multicast downstream route table
                                    for routes of type (*,G), (S,G) and GPREFIX";
                        uses pim-ipv6-multicast-route-ds-xg-sg-state;
                    } // END of state-container definition.
                } // END of downstream-xg-sg-container definition.
                container downstream-xxrp-sg-rpt {
                    config false;
                    description
                        "PIM IPv6 multicast route table downstream info about routes of type
                                (*,*,RP) and (S,G,rpt)";
                    container state {
                        config false;
                        description
                            "Operational state data for PIM IPv6 multicast downstream route table
                                    for routes of type (*,*,RP) and (S,G,rpt)";
                        uses pim-ipv6-multicast-route-ds-xxrp-sg-rpt-state;
                    } // END of state-container definition.
                } // END of downstream-xxrp-sg-rpt-container definition.
            } // End of downstream-interface-list
        } // END of downstream-interfaces-container definition.
    } // END of pim-ipv6-multicast-route-downstream-top definition.
    grouping pim-ipv6-multicast-route-fcr-state {
        description
            "Grouping for PIM IPv6 FCR muticast route table FCR state data";
        leaf address  {
            type  inet:ipv6-address;
            description "This attribute returns the FCR address.";
        } // END of address definition.

        leaf keep-alive-timer  {
            type  uint32;
            units "seconds";
            description "This attribute returns the keep alive timer value.";
        } // END of keep-alive-timer definition.

        leaf-list inherited-olist  {
            type  string {
                length "1..1965";
                pattern "[^?' =,>|]+";
            }
            description "This attribute returns the list of inherited interfaces for FCR in the
                        (*,G) state.";
        } // END of inherited-olist definition.

    } // END of pim-ipv6-multicast-route-fcr-state definition.
    grouping pim-ipv6-multicast-route-fcr-top {
        description
            "Grouping for PIM IPv6 muticast route table FCR";
        container forwarding-cache-registers {
            config false;
            description
                "Multicast Route Table FCR state data";

            list forwarding-cache-register {
                key "address";
                config false;
                description
                    "List of PIM IPv6 FCR multicast routes";
                leaf address  {
                    type  leafref {
                        path  "../state/address";
                    }
                    description "This attribute returns the FCR address.";
                } // END of address definition.

                container state {
                    config false;
                    description
                        "Operational state data for PIM IPv6 anycast Rendezvous Point";
                    uses pim-ipv6-multicast-route-fcr-state;
                } // END of state-container definition.
            } // End of forwarding-cache-register-list
        } // END of forwarding-cache-registers-container definition.
    } // END of pim-ipv6-multicast-route-fcr-top definition.
    grouping pim-ipv6-multicast-route-us-sg-rpt-state {
        description
            "Grouping for PIM IPv6 muticast route table upstream for source, group
                        and Rendezvous Point Tree";
        leaf route-state  {
            type  ipi-pim-ipv6-types:pim_ipv6_multicast_route_upstream_sgrpt_mode_t;
            description "This attribute returns the PIM multicast route state.";
        } // END of route-state definition.

        leaf override-timer  {
            type  uint32;
            description "This attribute returns the override timer value.";
        } // END of override-timer definition.

    } // END of pim-ipv6-multicast-route-us-sg-rpt-state definition.
    grouping pim-ipv6-multicast-route-us-sg-rpt-top {
        description
            "Grouping for PIM IPv6 multicast route table upstream for source, group
                        and Rendezvous Point Tree";
        container upstream-sg-rpt {
            config false;
            description
                "Multicast route table data upstream for source, group and Rendezvous
                        Point Tree";
            container state {
                config false;
                description
                    "Operational state data for PIM IPv6 multicast route table upstream for
                            PIM IPv6 source, group and Rendezvous Point Tree";
                uses pim-ipv6-multicast-route-us-sg-rpt-state;
            } // END of state-container definition.
        } // END of upstream-sg-rpt-container definition.
    } // END of pim-ipv6-multicast-route-us-sg-rpt-top definition.
    grouping pim-ipv6-multicast-route-us-sg-state {
        description
            "Grouping for PIM IPv6 muticast route table upstream for source and
                        group";
        leaf route-state  {
            type  ipi-pim-ipv6-types:pim_ipv6_multicast_route_upstream_state_t;
            description "This attribute returns the PIM multicast route state.";
        } // END of route-state definition.

        leaf join-prune-timer  {
            type  uint32;
            units "seconds";
            description "This attribute returns the join/prune interval value.";
        } // END of join-prune-timer definition.

        leaf last-rpf-neighbor-address  {
            type  inet:ipv6-address;
            description "This attribute returns the last neighbor address for reverse path
                        forwarding.";
        } // END of last-rpf-neighbor-address definition.

        leaf keep-alive-timer  {
            type  uint32;
            units "seconds";
            description "This attribute returns the keep alive timer value.";
        } // END of keep-alive-timer definition.

        leaf spt-switch  {
            type  empty;
            description "This attribute returns the state of SPT Switch flag.";
        } // END of spt-switch definition.

        leaf macro-state  {
            if-feature feature-list:HAVE_PIM_SM;
            type  ipi-pim-ipv6-types:pim_ipv6_multicast_route_upstream_macro_state_t;
            description "This attribute returns the PIM IPv6 route assert macro state.";
        } // END of macro-state definition.

    } // END of pim-ipv6-multicast-route-us-sg-state definition.
    grouping pim-ipv6-multicast-route-us-sg-top {
        description
            "Grouping for PIM IPv6 multicast route table upstream for source and
                        group";
        container upstream-sg {
            config false;
            description
                "Multicast route table data upstream for source and group";
            container state {
                config false;
                description
                    "Operational state data for PIM IPv6 multicast route table upstream for
                            source and group";
                uses pim-ipv6-multicast-route-us-sg-state;
            } // END of state-container definition.
        } // END of upstream-sg-container definition.
    } // END of pim-ipv6-multicast-route-us-sg-top definition.
    grouping pim-ipv6-multicast-route-us-xg-state {
        description
            "Grouping for PIM IPv6 muticast route table upstream for any source,
                        group route table";
        leaf route-state  {
            type  ipi-pim-ipv6-types:pim_ipv6_multicast_route_upstream_state_t;
            description "This attribute returns the PIM multicast route state.";
        } // END of route-state definition.

        leaf join-prune-timer  {
            type  uint32;
            units "seconds";
            description "This attribute returns the join/prune interval value.";
        } // END of join-prune-timer definition.

        leaf last-rpf-neighbor-address  {
            type  inet:ipv6-address;
            description "This attribute returns the last neighbor address for reverse path
                        forwarding.";
        } // END of last-rpf-neighbor-address definition.

        leaf macro-state  {
            if-feature feature-list:HAVE_PIM_SM;
            type  ipi-pim-ipv6-types:pim_ipv6_multicast_route_upstream_macro_state_t;
            description "This attribute returns the PIM IPv6 route assert macro state.";
        } // END of macro-state definition.

    } // END of pim-ipv6-multicast-route-us-xg-state definition.
    grouping pim-ipv6-multicast-route-us-xg-top {
        description
            "Grouping for PIM IPv6 multicast route table for any source, group
                        muticast route upstream";
        container upstream-xg {
            config false;
            description
                "Multicast route table data upstream for any source, group and RP";
            container state {
                config false;
                description
                    "Operational state data for PIM IPv6 multicast route table upstream for
                            any source, group and RP";
                uses pim-ipv6-multicast-route-us-xg-state;
            } // END of state-container definition.
        } // END of upstream-xg-container definition.
    } // END of pim-ipv6-multicast-route-us-xg-top definition.
    grouping pim-ipv6-multicast-route-us-xxrp-state {
        description
            "Grouping for PIM IPv6 multicast route table upstream for any source,
                        any group and RP";
        leaf route-state  {
            type  ipi-pim-ipv6-types:pim_ipv6_multicast_route_upstream_state_t;
            description "This attribute returns the PIM multicast route state.";
        } // END of route-state definition.

        leaf join-prune-timer  {
            type  uint32;
            units "seconds";
            description "This attribute returns the join/prune interval value.";
        } // END of join-prune-timer definition.

        leaf last-rpf-neighbor-address  {
            type  inet:ipv6-address;
            description "This attribute returns the last neighbor address for reverse path
                        forwarding.";
        } // END of last-rpf-neighbor-address definition.

        leaf last-rpf-next-hop-address  {
            type  inet:ipv6-address;
            description "This attribute returns the last next-hop address for reverse path
                        forwarding.";
        } // END of last-rpf-next-hop-address definition.

        leaf macro-state  {
            if-feature feature-list:HAVE_PIM_SM;
            type  ipi-pim-ipv6-types:pim_ipv6_multicast_route_upstream_macro_state_t;
            description "This attribute returns the PIM IPv6 route assert macro state.";
        } // END of macro-state definition.

    } // END of pim-ipv6-multicast-route-us-xxrp-state definition.
    grouping pim-ipv6-multicast-route-us-xxrp-top {
        description
            "Grouping for PIM IPv6 muticast route table for any source, any group
                        and RP";
        container upstream-xxrp {
            config false;
            description
                "Multicast route table data upstream for any source, any group and RP";
            container state {
                config false;
                description
                    "Operational state data for PIM IPv6 multicast route table upstream for
                            any source, any group and RP";
                uses pim-ipv6-multicast-route-us-xxrp-state;
            } // END of state-container definition.
        } // END of upstream-xxrp-container definition.
    } // END of pim-ipv6-multicast-route-us-xxrp-top definition.
    grouping pim-ipv6-multicast-route-state {
        description
            "Grouping for PIM IPv6 muticast route table state data";
        leaf source-address  {
            type  inet:ipv6-address;
            description "This attribute returns the source IP address of multicast.";
        } // END of source-address definition.

        leaf group-address  {
            type  inet:ipv6-address;
            description "This attribute returns the multicast IP address.";
        } // END of group-address definition.

        leaf mode  {
            type  ipi-pim-ipv6-types:pim_ipv6_multicast_route_mode_t;
            description "This attribute returns the PIM mode.";
        } // END of mode definition.

        leaf type  {
            type  ipi-pim-ipv6-types:pim_ipv6_multicast_route_type_t;
            description "This attribute returns the PIM route type.";
        } // END of type definition.

        leaf uptime  {
            type  string {
                length "1..1965";
                pattern "((([0-1]?[0-9])|(2[0-3])):[0-5][0-9]:[0-5][0-9])|([0-9]+d(([0-1][0-9])|(2[0-3]))h[0-5][0-9]m)";
            }
            description "This attribute returns the uptime for this multicast route entry.";
        } // END of uptime definition.

        leaf next-hop-address  {
            type  inet:ipv6-address;
            description "This attribute returns the next-hop address for this multicast route
                        entry.";
        } // END of next-hop-address definition.

        leaf next-hop-interface-name  {
            type  string {
                length "1..1965";
                pattern "[^?' =,>|]+";
            }
            description "This attribute returns the interface-name which is being used to reach
                        the next-hop.";
        } // END of next-hop-interface-name definition.

        leaf last-rendezvous-point  {
            type  inet:ipv6-address;
            description "This attribute returns the last Rendezvous Point for this multicast
                        route entry.";
        } // END of last-rendezvous-point definition.

        leaf spt-switch  {
            type  empty;
            description "This attribute returns the state of SPT Switch flag.";
        } // END of spt-switch definition.

        leaf-list local-olist  {
            type  string {
                length "1..1965";
                pattern "[^?' =,>|]+";
            }
            description "This attribute returns the local list of output interfaces.";
        } // END of local-olist definition.

        leaf-list joined-olist  {
            type  string {
                length "1..1965";
                pattern "[^?' =,>|]+";
            }
            description "This attribute returns the list of interfaces which receive join.";
        } // END of joined-olist definition.

        leaf-list inherited-olist  {
            type  string {
                length "1..1965";
                pattern "[^?' =,>|]+";
            }
            description "This attribute returns the list of inherited interfaces used for
                        forwarding.";
        } // END of inherited-olist definition.

        leaf-list pruned-olist  {
            type  string {
                length "1..1965";
                pattern "[^?' =,>|]+";
            }
            description "This attribute returns the list of interfaces which are in downstream
                        (S,G,rpt) states of prune or prune-tmp.";
        } // END of pruned-olist definition.

    } // END of pim-ipv6-multicast-route-state definition.
    grouping pim-ipv6-mrouter-table-statistics-state {
        description
            "Grouping for PIM IPv6 muticast route table statistics";
        container counters {
            config false;
            description
                "Counters for PIM IPv6 multicast route table";
            leaf xxrp-entries  {
                type  yang:counter32;
                description "This attribute returns the PIM Source, Group, Rendezvous Point include
                            entries.";
            } // END of xxrp-entries definition.

            leaf g-prefix-entries  {
                type  yang:counter32;
                description "This attribute returns the PIM Group or Prefix include entries.";
            } // END of g-prefix-entries definition.

            leaf xg-entries  {
                type  yang:counter32;
                description "This attribute returns the PIM Group include entries.";
            } // END of xg-entries definition.

            leaf sg-entries  {
                type  yang:counter32;
                description "This attribute returns the PIM Source, Group include entries.";
            } // END of sg-entries definition.

            leaf sg-rpt-entries  {
                type  yang:counter32;
                description "The RPT is the path between the RP and receivers (hosts) in a
                            multicast group. The RPT is built by means of a PIM join message from
                            a receiver's DR. This attribute returnes the PIM RPT include entries.";
            } // END of sg-rpt-entries definition.

            leaf fcr-entries  {
                type  yang:counter32;
                description "This attribute returns the Forwarding Cache Registers include entries.";
            } // END of fcr-entries definition.

        } // END of counters-container definition.
    } // END of pim-ipv6-mrouter-table-statistics-state definition.
    grouping pim-ipv6-multicast-route-top {
        description
            "Grouping for PIM IPv6 muticast route table";
        container multicast-route-table {
            config false;
            description
                "Multicast Route Table state data";
            container state {
                config false;
                description
                    "Operational state data for PIM IPv6 anycast Rendezvous Point";
                uses pim-ipv6-mrouter-table-statistics-state;
            } // END of state-container definition.
            container multicast-routes {
                config false;
                description
                    "Multicast Route Table state data";

                list multicast-route {
                    key "source-address group-address type";
                    config false;
                    description
                        "List of PIM IPv6 multicast routes";
                    leaf source-address  {
                        type  leafref {
                            path  "../state/source-address";
                        }
                        description "This attribute returns the source IP address of multicast.";
                    } // END of source-address definition.

                    leaf group-address  {
                        type  leafref {
                            path  "../state/group-address";
                        }
                        description "This attribute returns the multicast IP address.";
                    } // END of group-address definition.

                    leaf type  {
                        type  leafref {
                            path  "../state/type";
                        }
                        description "This attribute returns the PIM route type.";
                    } // END of type definition.

                    container state {
                        config false;
                        description
                            "Operational state data for PIM IPv6 anycast Rendezvous Point";
                        uses pim-ipv6-multicast-route-state;
                    } // END of state-container definition.
                    uses pim-ipv6-multicast-route-us-xxrp-top;
                    uses pim-ipv6-multicast-route-us-xg-top;
                    uses pim-ipv6-multicast-route-us-sg-top;
                    uses pim-ipv6-multicast-route-us-sg-rpt-top;
                    uses pim-ipv6-multicast-route-fcr-top;
                    uses pim-ipv6-multicast-route-downstream-top;
                } // End of multicast-route-list
            } // END of multicast-routes-container definition.
        } // END of multicast-route-table-container definition.
    } // END of pim-ipv6-multicast-route-top definition.
    grouping pim-ipv6-route-next-hop-state {
        description
            "Grouping for PIM IPv6 route next-hop operational state data";
        leaf ipv6-address  {
            type  inet:ipv6-address;
            description "This attribute returns the next-hop ipv6-address parameter.";
        } // END of ipv6-address definition.

        leaf type  {
            type  ipi-pim-ipv6-types:pim_ipv6_next_hop_type_t;
            description "This attribute returns the next-hop type parameter.";
        } // END of type definition.

        leaf recursive-active-next-hop  {
            type  uint8;
            description "This attribute returns the recursive-active-next-hop parameter.";
        } // END of recursive-active-next-hop definition.

        leaf recursive-type  {
            type  ipi-pim-ipv6-types:pim_ipv6_next_hop_type_t;
            description "This attribute returns the recursive-type parameter.";
        } // END of recursive-type definition.

        leaf recursive-interface-id  {
            type  uint8;
            description "This attribute returns the recursive-interface-id parameter.";
        } // END of recursive-interface-id definition.

        leaf interface-index  {
            type  uint16;
            description "This attribute returns the interface-index parameter.";
        } // END of interface-index definition.

        leaf bfd-interface-index  {
            type  uint16;
            description "This attribute returns the bfd-interface-index parameter.";
        } // END of bfd-interface-index definition.

        leaf interface-name  {
            type  string {
                length "1..1965";
                pattern "[^?' =,>|]+";
            }
            description "This attribute returns the interface-name parameter.";
        } // END of interface-name definition.

    } // END of pim-ipv6-route-next-hop-state definition.
    grouping pim-ipv6-route-next-hop-top {
        description
            "Grouping for PIM IPv6 route next-hop";
        container next-hops {
            config false;
            description
                "Operational state data for PIM IPv6 next-hops";

            list next-hop {
                key "ipv6-address";
                config false;
                description
                    "List of PIM IPv6 next-hop";
                leaf ipv6-address  {
                    type  leafref {
                        path  "../state/ipv6-address";
                    }
                    description "This attribute returns the next-hop ipv6-address parameter.";
                } // END of ipv6-address definition.

                container state {
                    config false;
                    description
                        "Operational state data for PIM IPv6 next-hop";
                    uses pim-ipv6-route-next-hop-state;
                } // END of state-container definition.
            } // End of next-hop-list
        } // END of next-hops-container definition.
    } // END of pim-ipv6-route-next-hop-top definition.
    grouping pim-ipv6-route-state {
        description
            "Grouping for PIM IPv6 route next-hop-destinations operational state
                        data";
        leaf destination-address  {
            type  inet:ipv6-address;
            description "This attribute returns the destination-address parameter.";
        } // END of destination-address definition.

        leaf destination-type  {
            type  ipi-pim-ipv6-types:pim_ipv6_next_hop_flags_t;
            description "This attribute returns the destination-type parameter.";
        } // END of destination-type definition.

        leaf next-hop-count  {
            type  uint32;
            description "This attribute returns the next-hop-count parameter.";
        } // END of next-hop-count definition.

        leaf preference  {
            type  uint16;
            description "This attribute returns the preference parameter.";
        } // END of preference definition.

        leaf metric  {
            type  uint32;
            description "This attribute returns the metric parameter.";
        } // END of metric definition.

        leaf reference-count  {
            type  uint32;
            description "This attribute returns the reference-count parameter.";
        } // END of reference-count definition.

        leaf route-type  {
            type  ipi-pim-ipv6-types:pim_ipv6_route_type_t;
            description "This attribute returns the route-type parameter";
        } // END of route-type definition.

        leaf route-sub-type  {
            type  ipi-pim-ipv6-types:pim_ipv6_route_sub_type_t;
            description "This attribute returns the route-sub-type parameter.";
        } // END of route-sub-type definition.

        leaf subaddress-familiy-identifier  {
            type  uint32;
            description "This attribute returns the subaddress-familiy-identifier parameter.";
        } // END of subaddress-familiy-identifier definition.

        leaf interface-index  {
            type  uint16;
            description "This attribute returns the interface-index parameter.";
        } // END of interface-index definition.

    } // END of pim-ipv6-route-state definition.
    grouping pim-ipv6-route-top {
        description
            "Grouping for PIM IPv6 next-hop-destinations";
        container next-hop-destinations {
            config false;
            description
                "Operational state data for PIM IPv6 next-hop-destinations";

            list next-hop-destination {
                key "destination-address";
                config false;
                description
                    "List of PIM IPv6 next-hop-destination";
                leaf destination-address  {
                    type  leafref {
                        path  "../state/destination-address";
                    }
                    description "This attribute returns the destination-address parameter";
                } // END of destination-address definition.

                container state {
                    config false;
                    description
                        "Operational state data for PIM IPv6 next-hop-destination";
                    uses pim-ipv6-route-state;
                } // END of state-container definition.
                uses pim-ipv6-route-next-hop-top;
            } // End of next-hop-destination-list
        } // END of next-hop-destinations-container definition.
    } // END of pim-ipv6-route-top definition.
    grouping pim-ipv6-statistics-state {
        description
            "Grouping for PIM IPv6 instance statistics state data";
        container counters {
            config false;
            description
                "Operational state data for PIM IPv6 instance packet counters";
            leaf joins-sent  {
                type  yang:counter64;
                units "packets";
                description "This attribute returns the total PIM Join messages sent by this PIM
                            IPv6 instance.";
            } // END of joins-sent definition.

            leaf joins-received  {
                type  yang:counter64;
                units "packets";
                description "This attribute returns the total PIM Join messages received by this
                            PIM IPv6 instance.";
            } // END of joins-received definition.

        } // END of counters-container definition.
    } // END of pim-ipv6-statistics-state definition.


}
