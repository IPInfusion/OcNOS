/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-pim.yang
*
*/

module ipi-pim {

    yang-version 1.1;

    namespace   "http://www.ipinfusion.com/yang/ocnos/ipi-pim";

    prefix "ipi-pim";

    import ietf-inet-types {
        prefix inet;
        revision-date 2013-07-15;
    }

    import ipi-pim-ipv4-types {
        prefix ipi-pim-ipv4-types;
        revision-date 2022-06-01;
    }

    import ipi-pim-ipv6-types {
        prefix ipi-pim-ipv6-types;
        revision-date 2022-06-01;
    }

    import feature-list {
        prefix feature-list;
        revision-date 2023-02-21;
    }

    include ipi-pim-debug { revision-date 2022-06-01;}
    include ipi-pim-ipv4 { revision-date 2022-06-06;}
    include ipi-pim-ipv6 { revision-date 2022-07-06;}
    include ipi-pim-ipv4-bidir { revision-date 2022-06-01;}
    include ipi-pim-ipv4-debug { revision-date 2022-06-01;}
    include ipi-pim-ipv4-interface { revision-date 2022-06-01;}
    include ipi-pim-ipv4-msdp { revision-date 2022-06-01;}
    include ipi-pim-ipv4-redundancy { revision-date 2022-06-01;}
    include ipi-pim-ipv6-state { revision-date 2022-06-06;}
    include ipi-pim-ipv6-interface { revision-date 2022-06-01;}
    include ipi-pim-ipv6-debug { revision-date 2022-06-01;}
    organization
        "IP Infusion Inc.";

    contact
        "Address: 3965 Freedom Circle, Suite 200, Santa Clara, CA 95054
         Phone: +1 408-400-1900
         E-mail: support@ipinfusion.com
         Web: http://www.ipinfusion.com/";

    description
        "Protocol Independent Multicast (PIM) configurations";


    revision "2022-07-06" {
        description "Fixed removal of PIMv6 embed-rp";
        reference " 0.2.7.";
    }

    revision "2022-06-06" {
        description "Added if-feature HAVE_PIM_BIDIR for rp-interface-name attribute and removed invalid PIMv6 state attributes";
        reference " 0.2.6.";
    }

    revision "2022-06-01" {
        description "Updated the yang file with feature";
        reference " 0.2.5.";
    }

    revision "2022-04-28" {
        description "Removed macro-state attribute from downstream-xxrp-sg-rpt/state containers";
        reference " 0.2.4.";
    }

    revision "2022-04-04" {
        description "The module ipi-pim-ipv6-interface was modified";
        reference " 0.2.3.";
    }

    revision "2022-03-30" {
        description "Restructured PIM IPv6 module in accordance with OpenConfig style";
        reference " 0.2.2.";
    }

    revision "2022-03-29" {
        description "Fix the range for suppress-interval attribute on PIM-IPv4";
        reference " 0.2.1.";
    }

    revision "2022-03-15" {
        description "Restructured module in accordance with OpenConfig style";
        reference " 0.2.0.";
    }

    revision "2018-06-21" {
        description "Initial Version";
        reference " 0.1.0.";
    }


    grouping  pim-grouping {
    description
        "Configuration data for PIM instances";
    container pim {
        if-feature feature-list:HAVE_PIMD;
        description
            "Configuration data for PIM instances";
        uses pim-debug-top;
        uses ipv4-grouping;
        uses ipv6-grouping;
    } // END of pim-container definition.
    } // END of pim-grouping definition.

    uses pim-grouping;

    rpc pim-snmp-restart {
        if-feature feature-list:HAVE_SNMP;
        if-feature feature-list:HAVE_PIMD;
        if-feature feature-list:HAVE_PIM_IPV4;
        description "Restart SNMP in PIM";
    }

    rpc pim-ipv4-clear-bsr-rendezvous-point {
        if-feature feature-list:HAVE_PIM_IPV4;
        if-feature feature-list:HAVE_PIM_SM;
        if-feature feature-list:HAVE_PIMD;
        description "Clear all rendezvous point (RP) sets learned through the PIMv2
                    Bootstrap Router (BSR)";
        input  {
            leaf vrf-name  {
                type string {
                    length "1..32";
                }
                description "VRF name associated with this instance.";
            }
            leaf pim-mode  {
                type ipi-pim-ipv4-types:pim_ipv4_mode_clear_bsr_rp_t;
                mandatory true;
                description "";
            }
        }
    }

    rpc pim-ipv4-clear-multicast-route {
        if-feature feature-list:HAVE_PIM_IPV4;
        if-feature feature-list:HAVE_PIMD;
        description "Clear the multicast route entries in the multicast route table";
        input  {
            leaf vrf-name  {
                type string {
                    length "1..32";
                }
                description "";
            }
            leaf pim-mode  {
                type ipi-pim-ipv4-types:pim_ipv4_mode_t;
                mandatory true;
                description "";
            }
        }
    }

    rpc pim-ipv4-clear-multicast-route-source-group {
        if-feature feature-list:HAVE_PIM_IPV4;
        if-feature feature-list:HAVE_PIMD;
        description "Clear the multicast route entries in the multicast route table";
        input  {
            leaf vrf-name  {
                type string {
                    length "1..32";
                }
                description "";
            }
            leaf group-address  {
                type inet:ipv4-address;
                mandatory true;
                description "";
            }
        }
    }

    rpc pim-ipv4-clear-multicast-route-source-group-mode {
        if-feature feature-list:HAVE_PIM_IPV4;
        if-feature feature-list:HAVE_PIMD;
        description "Clear the multicast route entries in the multicast route table";
        input  {
            leaf vrf-name  {
                type string {
                    length "1..32";
                }
                description "";
            }
            leaf group-address  {
                type inet:ipv4-address;
                mandatory true;
                description "";
            }
            leaf source-address  {
                type inet:ipv4-address;
                mandatory true;
                description "";
            }
            leaf pim-mode  {
                type ipi-pim-ipv4-types:pim_ipv4_mode_t;
                mandatory true;
                description "";
            }
        }
    }

    rpc pim-ipv4-clear-msdp-peer {
        if-feature feature-list:HAVE_PIM_IPV4;
        if-feature feature-list:HAVE_PIM_MSDP_API;
        if-feature feature-list:HAVE_PIMD;
        description "Clear the TCP connection to a Multicast Source Discovery Protocol
                    (MSDP) peer";
        input  {
            leaf vrf-name  {
                type string {
                    length "1..32";
                }
                description "";
            }
            leaf address  {
                type inet:ipv4-address;
                mandatory true;
                description "";
            }
        }
    }

    rpc pim-ipv4-clear-msdp-sa-cache {
        if-feature feature-list:HAVE_PIM_IPV4;
        if-feature feature-list:HAVE_PIM_MSDP_API;
        if-feature feature-list:HAVE_PIMD;
        description "Clear Multicast Source Discovery Protocol (MSDP) Source-Active (SA)
                    cache entries";
        input  {
            leaf vrf-name  {
                type string {
                    length "1..32";
                }
                description "";
            }
            leaf group-address  {
                type inet:ipv4-address;
                mandatory true;
                description "";
            }
        }
    }

    rpc pim-ipv4-terminal-debug-on {
        if-feature feature-list:HAVE_PIM_IPV4;
        if-feature feature-list:HAVE_PIMD;
        description "Enable PIM IPv4 debugging functions";
        input  {
            leaf vrf-name  {
                type string;
                description "VRF name associated with this instance.";
            }
            leaf debug-options  {
                type ipi-pim-ipv4-types:pim_ipv4_debug_t;
                mandatory true;
                description "Use this attribute to debug the PIM IPv4 feature.";
            }
        }
    }

    rpc pim-ipv4-terminal-debug-off {
        if-feature feature-list:HAVE_PIM_IPV4;
        if-feature feature-list:HAVE_PIMD;
        description "Disable PIM IPv4 debugging functions";
        input  {
            leaf vrf-name  {
                type string;
                description "VRF name associated with this instance.";
            }
            leaf debug-options  {
                type ipi-pim-ipv4-types:pim_ipv4_debug_t;
                mandatory true;
                description "Use this attribute to debug the PIM IPv4 feature.";
            }
        }
    }

    rpc pim-ipv4-terminal-debug-all-on {
        if-feature feature-list:HAVE_PIM_IPV4;
        if-feature feature-list:HAVE_PIMD;
        description "Enable all PIM IPv4 debugging functions";
        input  {
            leaf vrf-name  {
                type string;
                default "default";
                description "VPN routing/forwarding Instance name";
            }
        }
    }

    rpc pim-ipv4-terminal-debug-all-off {
        if-feature feature-list:HAVE_PIM_IPV4;
        if-feature feature-list:HAVE_PIMD;
        description "Disable all PIM IPv4 debugging functions";
        input  {
            leaf vrf-name  {
                type string;
                default "default";
                description "VPN routing/forwarding Instance name";
            }
        }
    }

    rpc pim-ipv6-clear-bsr-rendezvous-point {
        if-feature feature-list:HAVE_PIM_IPV6;
        if-feature feature-list:HAVE_PIM_SM;
        if-feature feature-list:HAVE_PIMD;
        description "";
        input  {
            leaf vrf-name  {
                type string {
                    length "1..32";
                }
                description "VRF name associated with this instance.";
            }
            leaf pim-mode  {
                type ipi-pim-ipv6-types:pim_ipv6_mode_clear_bsr_rp_t;
                mandatory true;
                description "";
            }
        }
    }

    rpc pim-ipv6-clear-multicast-route {
        if-feature feature-list:HAVE_PIM_IPV6;
        if-feature feature-list:HAVE_PIMD;
        description "Clear the multicast route entries in the multicast route table";
        input  {
            leaf vrf-name  {
                type string {
                    length "1..32";
                }
                description "";
            }
            leaf pim-mode  {
                type ipi-pim-ipv6-types:pim_ipv6_mode_t;
                mandatory true;
                description "";
            }
        }
    }

    rpc pim-ipv6-clear-multicast-route-source-group {
        if-feature feature-list:HAVE_PIM_IPV6;
        if-feature feature-list:HAVE_PIMD;
        description "Clear the multicast route entries in the multicast route table";
        input  {
            leaf vrf-name  {
                type string {
                    length "1..32";
                }
                description "";
            }
            leaf group-address  {
                type inet:ipv6-address;
                mandatory true;
                description "";
            }
        }
    }

    rpc pim-ipv6-clear-multicast-route-source-group-mode {
        if-feature feature-list:HAVE_PIM_IPV6;
        if-feature feature-list:HAVE_PIMD;
        description "Clear the multicast route entries in the multicast route table";
        input  {
            leaf vrf-name  {
                type string {
                    length "1..32";
                }
                description "";
            }
            leaf group-address  {
                type inet:ipv6-address;
                mandatory true;
                description "";
            }
            leaf source-address  {
                type inet:ipv6-address;
                mandatory true;
                description "";
            }
            leaf pim-mode  {
                type ipi-pim-ipv6-types:pim_ipv6_mode_t;
                mandatory true;
                description "";
            }
        }
    }

    rpc pim-terminal-debug-bfd-on {
        if-feature feature-list:HAVE_PIM_IPV4;
        if-feature feature-list:HAVE_PIM_IPV6;
        if-feature feature-list:HAVE_BFD;
        if-feature feature-list:HAVE_PIMD;
        description "Enable PIM BFD debugging functions";
    }

    rpc pim-terminal-debug-bfd-off {
        if-feature feature-list:HAVE_PIM_IPV4;
        if-feature feature-list:HAVE_PIM_IPV6;
        if-feature feature-list:HAVE_BFD;
        if-feature feature-list:HAVE_PIMD;
        description "Disable PIM BFD debugging functions";
    }

    rpc pim-ipv6-terminal-debug-on {
        if-feature feature-list:HAVE_PIM_IPV6;
        if-feature feature-list:HAVE_PIMD;
        description "Enable PIM IPv6 debugging functions";
        input  {
            leaf vrf-name  {
                type string;
                description "VRF name associated with this instance.";
            }
            leaf debug-options  {
                type ipi-pim-ipv6-types:pim_ipv6_debug_t;
                mandatory true;
                description "Use this attribute to debug the PIM IPv6 feature.";
            }
        }
    }

    rpc pim-ipv6-terminal-debug-off {
        if-feature feature-list:HAVE_PIM_IPV6;
        if-feature feature-list:HAVE_PIMD;
        description "Disable PIM IPv6 debugging functions";
        input  {
            leaf vrf-name  {
                type string;
                description "VRF name associated with this instance";
            }
            leaf debug-options  {
                type ipi-pim-ipv6-types:pim_ipv6_debug_t;
                mandatory true;
                description "Use this attribute to debug the PIM IPv6 feature.";
            }
        }
    }

    rpc pim-ipv6-terminal-debug-all-on {
        if-feature feature-list:HAVE_PIM_IPV6;
        if-feature feature-list:HAVE_PIMD;
        description "Enable all PIM IPv6 debugging functions";
        input  {
            leaf vrf-name  {
                type string;
                default "default";
                description "VPN routing/forwarding Instance name";
            }
        }
    }

    rpc pim-ipv6-terminal-debug-all-off {
        if-feature feature-list:HAVE_PIM_IPV6;
        if-feature feature-list:HAVE_PIMD;
        description "Disable all PIM IPv6 debugging functions";
        input  {
            leaf vrf-name  {
                type string;
                default "default";
                description "VPN routing/forwarding Instance name";
            }
        }
    }

}
