/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-pim-ipv4-bidir.yang
*
*/

submodule ipi-pim-ipv4-bidir {

    yang-version 1.1;

    belongs-to  ipi-pim { prefix ipi-pim; }

    import feature-list {
        prefix feature-list;
        revision-date 2023-02-21;
    }

    import ietf-yang-types {
        prefix yang;
        revision-date 2013-07-15;
    }

    import ipi-pim-ipv4-types {
        prefix ipi-pim-ipv4-types;
        revision-date 2022-06-01;
    }

    import ietf-inet-types {
        prefix inet;
        revision-date 2013-07-15;
    }

    organization
        "IP Infusion Inc.";

    contact
        "Address: 3965 Freedom Circle, Suite 200, Santa Clara, CA 95054
         Phone: +1 408-400-1900
         E-mail: support@ipinfusion.com
         Web: http://www.ipinfusion.com/";

    description
        "PIM IPv4 Bidirectional (BIDIR)";


    revision "2022-06-01" {
        description "Updated the yang file with feature";
        reference " 0.2.0.";
    }

    revision "2022-03-15" {
        description "Restructured module in accordance with OpenConfig style";
        reference " 0.1.0.";
    }

    grouping pim-ipv4-interface-bidir-df-state {
        description
            "Grouping for PIM IPv4 Interface BIDIR operational state data";
        leaf rp-address  {
            type  inet:ipv4-address;
            description "This attribute returns the PIM bidirectional rendezvous point address
                        of multicast groups.";
        } // END of rp-address definition.

        leaf router-id  {
            type  inet:ipv4-address;
            description "This attribute returns the PIM the interface router identifier.";
        } // END of router-id definition.

        leaf df-state  {
            type  ipi-pim-ipv4-types:pim_ipv4_df_state_t;
            description "This attribute returns the PIM designated forwarder election, protocol
                        state.";
        } // END of df-state definition.

        leaf df-address  {
            type  inet:ipv4-address;
            description "This attribute returns the PIM designated forwarder IP address.";
        } // END of df-address definition.

        leaf metric-preference  {
            type  uint32;
            description "This attribute returns the PIM last winner metric preference.";
        } // END of metric-preference definition.

        leaf metric  {
            type  uint32;
            description "This attribute returns the PIM last winner metric.";
        } // END of metric definition.

        leaf offer-count  {
            type  yang:counter64;
            description "This attribute returns the PIM offer count.";
        } // END of offer-count definition.

    } // END of pim-ipv4-interface-bidir-df-state definition.
    grouping pim-ipv4-interface-bidir-df-top {
        description
            "Grouping for PIM IPv4 Interface BIDIR operational state";
        container designated-forwarders {
            config false;
            description
                "Operational state data for PIM IPv4 Interface BIDIR";

            list designated-forwarder {
                key "rp-address";
                config false;
                description
                    "List of PIM IPv4 Interface BIDIR designated-forwarder";
                leaf rp-address  {
                    type  leafref {
                        path  "../state/rp-address";
                    }
                    description "This attribute returns the PIM bidirectional rendezvous point address
                                of multicast groups.";
                } // END of rp-address definition.

                container state {
                    config false;
                    description
                        "Operational state data for PIM IPv4 Interface BIDIR";
                    uses pim-ipv4-interface-bidir-df-state;
                } // END of state-container definition.
            } // End of designated-forwarder-list
        } // END of designated-forwarders-container definition.
    } // END of pim-ipv4-interface-bidir-df-top definition.
    grouping pim-ipv4-interface-bidir-config {
        description
            "Grouping for PIM IPv4 Interface BIDIR configuration data";
        leaf neighbor-access-control-list-filter  {
            type  string {
                length "1..64";
                pattern "[^?' =,>|]+";
            }
            description ">Use this attribute to configure an access list (ACL) to specify the
                        bidirectionally capable neighbors that participate in the designated
                        forwarder (DF) election.";
        } // END of neighbor-access-control-list-filter definition.

    } // END of pim-ipv4-interface-bidir-config definition.
    grouping pim-ipv4-interface-bidir-top {
        description
            "Grouping for PIM IPv4 Interface BIDIR";
        container bidir {
            if-feature feature-list:HAVE_PIM_BIDIR;
            description
                "Configuration data for PIM IPv4 Interface BIDIR";
            container config {
                description
                    "Configuration data for PIM IPv4 Interface BIDIR";
                uses pim-ipv4-interface-bidir-config;
            } // END of config-container definition.
            container state {
                config false;
                description
                    "Operational state data for PIM IPv4 Interface BIDIR";
                uses pim-ipv4-interface-bidir-config;
            } // END of state-container definition.
            uses pim-ipv4-interface-bidir-df-top;
        } // END of bidir-container definition.
    } // END of pim-ipv4-interface-bidir-top definition.
    grouping pim-ipv4-rp-static-rp-bidir-config {
        description
            "Grouping for PIM IPv4 static rendezvous point BIDIR configuration data";
        leaf rp-address  {
            type  inet:ipv4-address;
            description "Use this attribute to statically configure Rendezvous Point (RP)
                        address for multicast groups.";
        } // END of rp-address definition.

        leaf access-control-list  {
            type  string {
                length "1..64";
                pattern "[^?' =,>|]+";
            }
            mandatory true;
            description "Use this attribute to configure the name of access control list (ACL).";
        } // END of access-control-list definition.

        leaf override-dynamically-learned-rp  {
            type  empty;
            description "Use this attribute do configure the flag to overrides dynamically
                        learned RP mappings.";
        } // END of override-dynamically-learned-rp definition.

    } // END of pim-ipv4-rp-static-rp-bidir-config definition.
    grouping pim-ipv4-rp-static-rp-bidir-top {
        description
            "Grouping for PIM IPv4 static rendezvous point bidirectional mode";

        list static-rp-bidir {
        // when " ipi-pim-ipv4:ipv4/instances/instance/bidir/config/enable ";
            if-feature feature-list:HAVE_PIM_BIDIR;
            key "rp-address";
            description
                "List of PIM IPv4 static rendezvous points bidirectional mode";
            leaf rp-address  {
                type  leafref {
                    path  "../config/rp-address";
                }
                description "Use this attribute to statically configure Rendezvous Point (RP)
                            address for multicast groups.";
            } // END of rp-address definition.

            container config {
                description
                    "Configuration data for PIM IPv4 static rendezvous point bidirectional
                            mode";
                uses pim-ipv4-rp-static-rp-bidir-config;
            } // END of config-container definition.
            container state {
                config false;
                description
                    "Operational state data for PIM IPv4 static rendezvous point
                            bidirectional mode";
                uses pim-ipv4-rp-static-rp-bidir-config;
            } // END of state-container definition.
        } // End of static-rp-bidir-list
    } // END of pim-ipv4-rp-static-rp-bidir-top definition.
    grouping pim-ipv4-bidir-df-election-config {
        description
            "Grouping for PIM IPv4 BIDIR Designated Forwarder Election
                        configuration attributes";
        leaf offer-interval  {
            type  uint16 {
                 range "1..20000"  {
                    description "1..20000: Supported range 1 - 20000";
                 }
            }
            units "seconds";
            default "100";
            description ">Use this attribute to configure the Designated Forwarder (DF)
                        Election offer message interval time.";
        } // END of offer-interval definition.

        leaf offer-interval-in-milliseconds  {
            when " /pim/ipv4/instances/instance/bidir/designated-forwarder-election/config/offer-interval ";
            type  empty;
            description ">Use this attribute to configure the Designated Forwarder (DF)
                        Election offer message interval time.";
        } // END of offer-interval-in-milliseconds definition.

        leaf offer-limit  {
            type  uint16 {
                 range "4..100"  {
                    description "4..100: Supported range 4 - 100";
                 }
            }
            default "100";
            description ">Use this attribute to configure the bidirectionally capable number of
                        unanswered offers before the device changes to the designated
                        forwarder (DF).";
        } // END of offer-limit definition.

    } // END of pim-ipv4-bidir-df-election-config definition.
    grouping pim-ipv4-bidir-df-election-top {
        description
            "Grouping for PIM IPv4 BIDIR Designated Forwarder Election";
        container designated-forwarder-election {
            if-feature feature-list:HAVE_PIM_BIDIR;
            description
                "Configuration data for PIM IPv4 DF Election";
            container config {
                when " /pim/ipv4/instances/instance/bidir/designated-forwarder-election/config/offer-interval  or /pim/ipv4/instances/instance/bidir/designated-forwarder-election/config/offer-limit ";
                presence "yes";
                description
                    "Configuration data for PIM IPv4 DF Election";
                uses pim-ipv4-bidir-df-election-config;
            } // END of config-container definition.
            container state {
                config false;
                description
                    "Operational state data for PIM IPv4 DF Election";
                uses pim-ipv4-bidir-df-election-config;
            } // END of state-container definition.
        } // END of designated-forwarder-election-container definition.
    } // END of pim-ipv4-bidir-df-election-top definition.
    grouping pim-ipv4-bidir-config {
        description
            "Grouping for PIM IPv4 BIDIR configuration data";
        leaf enable  {
            type  empty;
            description ">Use this attribute to enable Bidirectional PIM.";
        } // END of enable definition.

    } // END of pim-ipv4-bidir-config definition.
    grouping pim-ipv4-bidir-top {
        description
            "Grouping for PIM IPv4 BIDIR";
        container bidir {
            if-feature feature-list:HAVE_PIM_BIDIR;
            description
                "Configuration data for PIM IPv4 BIDIR";
            container config {
                description
                    "Configuration data for PIM IPv4 BIDIR";
                uses pim-ipv4-bidir-config;
            } // END of config-container definition.
            container state {
                config false;
                description
                    "Operational state data for PIM IPv4 BIDIR";
                uses pim-ipv4-bidir-config;
            } // END of state-container definition.
            uses pim-ipv4-bidir-df-election-top;
        } // END of bidir-container definition.
    } // END of pim-ipv4-bidir-top definition.


}
