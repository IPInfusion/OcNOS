/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-pim-debug.yang
*
*/

submodule ipi-pim-debug {

    yang-version 1.1;

    belongs-to  ipi-pim { prefix ipi-pim; }

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "PIM IPv4 Debug";


    revision "2022-06-01" {
        description "Updated the yang file with feature";
        reference " 0.1.1.";
    }

    revision "2022-03-15" {
        description "Restructured module in accordance with OpenConfig style";
        reference " 0.1.0.";
    }

    grouping pim-debug-terminal-top {
        description
            "Grouping for PIM debug";
        container terminal {
            config false;
            description
                "Container for for PIM debugging functions";
            leaf bfd-enable  {
                type  empty;
                description "Use this attribute to debug the PIM BFD feature.";
            } // END of bfd-enable definition.

        } // END of terminal-container definition.
    } // END of pim-debug-terminal-top definition.
    grouping pim-debug-config {
        description
            "Grouping for PIM debug configuration";
        leaf bfd  {
            type  empty;
            description "Use this attribute to debug the PIM BFD feature.";
        } // END of bfd definition.

    } // END of pim-debug-config definition.
    grouping pim-debug-top {
        description
            "Grouping for PIM debug";
        container debug {
            if-feature feature-list:HAVE_BFD;
            description
                "Container for PIM debugging functions";
            container config {
                description
                    "Configuration data PIM debug";
                uses pim-debug-config;
            } // END of config-container definition.
            container state {
                config false;
                description
                    "Operational state data for PIM debug";
                uses pim-debug-config;
                uses pim-debug-terminal-top;
            } // END of state-container definition.
        } // END of debug-container definition.
    } // END of pim-debug-top definition.


}
