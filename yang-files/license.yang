/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : license.yang
*
*/

submodule license {

    belongs-to  ZebOS { prefix ZebOS; }


    import cml_data_types {
        prefix cml_data_types;
    }

    description
        "license configurations";


    revision "2016-12-27" {
        description "Added snmp oid and documentation tag.";
    }

    revision "2016-10-28" {
        description "Initial version of license datamodel.";
    }



}
