/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-ospf-te-link.yang
*
*/

submodule ipi-ospf-te-link {

    yang-version 1.1;

    belongs-to  ipi-ospf { prefix ipi-ospf; }

    import feature-list {
        prefix feature-list;
        revision-date 2023-02-21;
    }

    import ipi-ospf-types {
        prefix ipi-ospf-types;
        revision-date 2022-06-01;
    }

    organization
        "IP Infusion Inc.";

    contact
        "Address: 3965 Freedom Circle, Suite 200, Santa Clara, CA 95054
         Phone: +1 408-400-1900
         E-mail: support@ipinfusion.com
         Web: http://www.ipinfusion.com/";

    description
        "Layer-3 OSPF traffic engineering link";


    revision "2022-06-01" {
        description "Updated the yang file with feature";
        reference " 0.3.";
    }

    revision "2021-09-03" {
        description "Update descriptions of attribute";
        reference "Initial Version";
    }

    revision "2021-04-06" {
        description "Restructured module in accordance with OpenConfig style";
        reference "Initial Version";
    }

    grouping ospfv2-flooding-config {
        description
            "Grouping for OSPF flooding configuration data";
        leaf ospf-process-id  {
            type  uint16 {
                 range "0..65535"  {
                    description "0..65535: Supported range 0 - 65535";
                 }
            }
            description "Use this attribute to set OSPF process ID in which te-flooding is
                        enabled.";
        } // END of ospf-process-id definition.

        leaf area-id  {
            type  ipi-ospf-types:ospf_area_t;
            description "Use this attribute to set OSPF area ID in which te-flooding is
                        enabled.";
        } // END of area-id definition.

    } // END of ospfv2-flooding-config definition.
    grouping ospfv2-flooding-top {
        description
            "Grouping for OSPF flooding";
        container flooding {
            description
                "OSPF flooding";
            container ospfv2-processes {
                description
                    "OSPF flooding process";

                list ospfv2-process {
                    key "ospf-process-id area-id";
                    max-elements 1;
                    description
                        "List of OSPF flooding process";
                    leaf ospf-process-id  {
                        type  leafref {
                            path  "../config/ospf-process-id";
                        }
                        description "Use this attribute to set OSPF process ID in which te-flooding is
                                    enabled.";
                    } // END of ospf-process-id definition.

                    leaf area-id  {
                        type  leafref {
                            path  "../config/area-id";
                        }
                        description "Use this attribute to set OSPF area ID in which te-flooding is
                                    enabled.";
                    } // END of area-id definition.

                    container config {
                        description
                            "Configuration data for OSPF flooding process";
                        uses ospfv2-flooding-config;
                    } // END of config-container definition.
                    container state {
                        config false;
                        description
                            "Operational state data for OSPF flooding process";
                        uses ospfv2-flooding-config;
                    } // END of state-container definition.
                } // End of ospfv2-process-list
            } // END of ospfv2-processes-container definition.
        } // END of flooding-container definition.
    } // END of ospfv2-flooding-top definition.
    grouping ospfv2-traffic-engineering-link-config {
        description
            "Grouping for OSPF traffic engineering link configuration data";
        leaf teName  {
            type  string {
                length "1..1965";
                pattern "[^?' =,>|]+";
            }
            description "Use this attribute to set the Traffic Engineering (TE) link name.";
        } // END of teName definition.

        leaf metric  {
            type  uint16 {
                 range "1..65535"  {
                    description "1..65535: Supported range 1 - 65535";
                 }
            }
            description "Use this attribute to set the OSPF TE metric.";
        } // END of metric definition.

        leaf link-local-exchange  {
            type  empty;
            description "Use this attribute to enable OSPF TE link local exchange.";
        } // END of link-local-exchange definition.

    } // END of ospfv2-traffic-engineering-link-config definition.
    grouping ospfv2-traffic-engineering-link-top {
        description
            "Grouping for OSPF traffic engineering link";
        container traffic-engineering-links {
            if-feature feature-list:HAVE_OSPF_TE;
            if-feature feature-list:HAVE_GMPLS;
            description
                "OSPF traffic engineering links";

            list traffic-engineering-link {
                key "teName";
                description
                    "List of OSPF traffic engineering links";
                leaf teName  {
                    type  leafref {
                        path  "../config/teName";
                    }
                    description "Use this attribute to set the Traffic Engineering (TE) link name.";
                } // END of teName definition.

                container config {
                    description
                        "Configuration data for OSPF traffic engineering link";
                    uses ospfv2-traffic-engineering-link-config;
                } // END of config-container definition.
                container state {
                    config false;
                    description
                        "Operational state data for OSPF traffic engineering link";
                    uses ospfv2-traffic-engineering-link-config;
                } // END of state-container definition.
                uses ospfv2-flooding-top;
            } // End of traffic-engineering-link-list
        } // END of traffic-engineering-links-container definition.
    } // END of ospfv2-traffic-engineering-link-top definition.


}
