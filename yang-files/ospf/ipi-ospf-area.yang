/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-ospf-area.yang
*
*/

submodule ipi-ospf-area {

    yang-version 1.1;

    belongs-to  ipi-ospf { prefix ipi-ospf; }

    import feature-list {
        prefix feature-list;
        revision-date 2023-02-21;
    }

    import ietf-inet-types {
        prefix inet;
        revision-date 2013-07-15;
    }

    import ietf-yang-types {
        prefix yang;
        revision-date 2013-07-15;
    }

    import ipi-interface {
        prefix ipi-interface;
        revision-date 2022-08-24;
    }

    import ipi-ospf-types {
        prefix ipi-ospf-types;
        revision-date 2022-06-01;
    }

    import cml-data-types {
        prefix cml-data-types;
        revision-date 2022-09-30;
    }

    include ipi-ospf-authentication { revision-date 2022-06-01;}
    include ipi-ospf-timers { revision-date 2022-06-01;}
    organization
        "IP Infusion Inc.";

    contact
        "Address: 3965 Freedom Circle, Suite 200, Santa Clara, CA 95054
         Phone: +1 408-400-1900
         E-mail: support@ipinfusion.com
         Web: http://www.ipinfusion.com/";

    description
        "Layer-3 OSPF area configurations";


    revision "2022-06-01" {
        description "Updated the yang file with feature";
        reference "Initial Version";
    }

    revision "2021-09-03" {
        description "Update descriptions of attribute";
        reference "Initial Version";
    }

    revision "2021-08-20" {
        description "Add a config false, for the TE link-delay state container";
        reference "Initial Version";
    }

    revision "2021-08-18" {
        description "State attributes for Segment Routing, TI LFA and TE";
        reference "Initial Version";
    }

    revision "2021-07-06" {
        description "Added support for sham-links";
        reference "Initial Version";
    }

    revision "2021-05-07" {
        description "Fix NSSA CLI command to avoid show duplicate nssa input";
        reference "Initial Version";
    }

    revision "2021-04-30" {
        description "Restructured filter-list prefix-list and acl-list from lists to containers";
        reference "Initial Version";
    }

    revision "2021-04-06" {
        description "Restructured module in accordance with OpenConfig style";
        reference "Initial Version";
    }

    grouping ospfv2-area-state {
        description
            "Grouping for OSPF area state";
        leaf interface-count  {
            type  yang:counter64;
            description "Use this attribute to retrieve area interface counter.";
        } // END of interface-count definition.

        leaf neighbor-count  {
            type  yang:counter64;
            description "Use this attribute to retrieve area neighbor counter.";
        } // END of neighbor-count definition.

        leaf spf-last-execution-time  {
            type  string {
                length "1..1965";
                pattern "[^?' =,>|]+";
            }
            description "Use this attribute to retrieve SPF last execution time.";
        } // END of spf-last-execution-time definition.

        leaf spf-execution-count  {
            type  yang:counter64;
            description "Use this attribute to retrieve SPF execution counter.";
        } // END of spf-execution-count definition.

        leaf lsa-count  {
            type  yang:counter64;
            description "Use this attribute to retrieve area LSA counter.";
        } // END of lsa-count definition.

        leaf lsa-checksum  {
            type  yang:phys-address {
                pattern "([0-9a-fA-F]{2}(:[0-9a-fA-F]{2})*)?";
                }
                description "Use this attribute to retrieve area LSA checksum.";
            } // END of lsa-checksum definition.

    } // END of ospfv2-area-state definition.
    grouping ospfv2-traffic-engineering-database-lsdb-tlv-state {
        description
            "Grouping for OSPF traffic engineering(TE) database TLV state
                        attributes";
        leaf type  {
            type  ipi-ospf-types:ospf_tlv_type_t;
            description "This attributes returns the tlv type value.";
        } // END of type definition.

        leaf link-type  {
            type  ipi-ospf-types:ospf_tlv_link_type_t;
            description "This attribute returns the link-type value.";
        } // END of link-type definition.

        leaf-list local-interface-addresses  {
            type  inet:ipv4-address;
            description "This attribute returns the local-interface-addresses values.";
        } // END of local-interface-addresses definition.

        leaf-list remote-interface-addresses  {
            type  inet:ipv4-address;
            description "This attribute returns the local-interface-addresses values.";
        } // END of remote-interface-addresses definition.

        leaf-list local-ids  {
            if-feature feature-list:HAVE_GMPLS;
            type  inet:ipv4-address;
            description "This attribute returns the local-ids values.";
        } // END of local-ids definition.

        leaf-list remote-ids  {
            if-feature feature-list:HAVE_GMPLS;
            type  inet:ipv4-address;
            description "This attribute returns the local-ids values.";
        } // END of remote-ids definition.

        leaf local-interface-id  {
            if-feature feature-list:HAVE_GMPLS;
            type  uint32;
            description "This attribute returns the local-interface-id value.";
        } // END of local-interface-id definition.

        leaf local-remote-interface-id  {
            if-feature feature-list:HAVE_GMPLS;
            type  uint32;
            description "This attribute returns the local-remote-interface-id value.";
        } // END of local-remote-interface-id definition.

        leaf metric  {
            type  uint32;
            description "This attribute returns the metric value.";
        } // END of metric definition.

        leaf maximum-bandwidth  {
            type  string {
                length "1..1965";
                pattern "[^?' =,>|]+";
            }
            units "Kbps";
            description "This attribute returns the maximum bandwidth in kbps.";
        } // END of maximum-bandwidth definition.

        leaf maximum-reservable-bandwidth  {
            type  string {
                length "1..1965";
                pattern "[^?' =,>|]+";
            }
            units "Kbps";
            description "This attribute returns the maximum reservable bandwidth in kbps.";
        } // END of maximum-reservable-bandwidth definition.

        leaf bandwidth-constraint-model  {
            if-feature feature-list:HAVE_DSTE;
            type  string {
                length "1..1965";
                pattern "[^?' =,>|]+";
            }
            description "This attribute returns the bandwidth constraint model.";
        } // END of bandwidth-constraint-model definition.

        leaf bandwidth-constraint  {
            if-feature feature-list:HAVE_DSTE;
            type  string {
                length "1..1965";
                pattern "[^?' =,>|]+";
            }
            units "Kbps";
            description "This attribute returns the bandwidth constraint value.";
        } // END of bandwidth-constraint definition.

        leaf-list resource-color-values  {
            type  decimal64 {
                 fraction-digits 6;            }
            description "This attribute returns the resource color values.";
        } // END of resource-color-values definition.

        leaf protection-type  {
            type  cml-data-types:cml_gmpls_protection_type_t;
            description "This attribute returns the protection type.";
        } // END of protection-type definition.

        leaf shared-risk-link-groups  {
            type  uint32;
            description "This attribute returns the shared risk link groups values.";
        } // END of shared-risk-link-groups definition.

    } // END of ospfv2-traffic-engineering-database-lsdb-tlv-state definition.
    grouping ospfv2-traffic-engineering-database-lsdb-router-state {
        description
            "Grouping for OSPF traffic engineering(TE) database TLV router state
                        attributes";
        leaf router-id  {
            type  inet:ipv4-address;
            description "This attributes returns the TLV router-id value.";
        } // END of router-id definition.

    } // END of ospfv2-traffic-engineering-database-lsdb-router-state definition.
    grouping ospfv2-traffic-engineering-database-lsdb-link-state {
        description
            "Grouping for OSPF traffic engineering(TE) database TLV link state
                        attributes";
        leaf link-id  {
            type  inet:ipv4-address;
            description "This attribute returns the link-id value.";
        } // END of link-id definition.

    } // END of ospfv2-traffic-engineering-database-lsdb-link-state definition.
    grouping ospfv2-traffic-engineering-database-lsdb-tlv-capability-state {
        description
            "Grouping for OSPF traffic engineering(TE) database TLV capability
                        state attributes";
        leaf type  {
            if-feature feature-list:HAVE_GMPLS;
            type  cml-data-types:cml_gmpls_capability_type_t;
            description "This attribute returns the GMPLS capability value.";
        } // END of type definition.

        leaf encoding-type  {
            if-feature feature-list:HAVE_GMPLS;
            type  cml-data-types:cml_gmpls_encoding_type_t;
            description "This attribute returns the GMPLS encoding type value.";
        } // END of encoding-type definition.

        leaf mtu  {
            type  uint16;
            description "This attribute returns the MTU value.";
        } // END of mtu definition.

        leaf minimum-lsp-bandwidth  {
            if-feature feature-list:HAVE_GMPLS;
            type  string {
                length "1..1965";
                pattern "[^?' =,>|]+";
            }
            units "Kbps";
            description "This attribute returns the minimum lsp bandwidth in kbps.";
        } // END of minimum-lsp-bandwidth definition.

        leaf sdh-indication  {
            if-feature feature-list:HAVE_TDM;
            type  cml-data-types:cml_gmpls_sdh_indication_t;
            description "This attribute returns the GMPLS SONET/SDH indication.";
        } // END of sdh-indication definition.

    } // END of ospfv2-traffic-engineering-database-lsdb-tlv-capability-state definition.
    grouping ospfv2-traffic-engineering-database-bandwidth-state {
        description
            "Grouping for OSPF traffic engineering(TE) database bandwidth
                        attributes";
        leaf priority  {
            type  uint8;
            description "This attribute returns the priority value.";
        } // END of priority definition.

        leaf bandwidth  {
            type  string {
                length "1..1965";
                pattern "[^?' =,>|]+";
            }
            units "Kbps";
            description "This attribute returns the bandwidth value in kbps.";
        } // END of bandwidth definition.

    } // END of ospfv2-traffic-engineering-database-bandwidth-state definition.
    grouping ospfv2-traffic-engineering-database-lsps-bandwidth {
        description
            "Grouping for OSPF traffic engineering(TE) database TLV capability
                        maximum lsp bandwidth";
        container maximum-lsp-bandwidths {
            config false;
            description
                "OSPF traffic engineering(TE) database TLV capability maximum lsp
                        bandwidth";

            list maximum-lsp-bandwidth {
                key "priority";
                config false;
                description
                    "List of maximum lsp bandwidths";
                leaf priority  {
                    type  leafref {
                        path  "../state/priority";
                    }
                    description "This attribute returns the priority value.";
                } // END of priority definition.

                container state {
                    config false;
                    description
                        "Operational state data";
                    uses ospfv2-traffic-engineering-database-bandwidth-state;
                } // END of state-container definition.
            } // End of maximum-lsp-bandwidth-list
        } // END of maximum-lsp-bandwidths-container definition.
    } // END of ospfv2-traffic-engineering-database-lsps-bandwidth definition.
    grouping ospfv2-traffic-engineering-database-lsdb-tlv-capability {
        description
            "Grouping for OSPF traffic engineering(TE) database TLV capability";
        container capability {
            config false;
            description
                "OSPF traffic engineering(TE) database TLV capability";
            container state {
                config false;
                description
                    "Operational state data for TE database TLV capability";
                uses ospfv2-traffic-engineering-database-lsdb-tlv-capability-state;
            } // END of state-container definition.
            uses ospfv2-traffic-engineering-database-lsps-bandwidth;
        } // END of capability-container definition.
    } // END of ospfv2-traffic-engineering-database-lsdb-tlv-capability definition.
    grouping ospfv2-traffic-engineering-database-unreserved-bandwidth {
        description
            "Grouping for OSPF traffic engineering(TE) database TLV unreserved
                        bandwidth";
        container unreserved-bandwidths {
            config false;
            description
                "OSPF traffic engineering(TE) database TLV unreserved bandwidths";

            list unreserved-bandwidth {
                key "priority";
                config false;
                description
                    "List of unreserved bandwidths";
                leaf priority  {
                    type  leafref {
                        path  "../state/priority";
                    }
                    description "This attribute returns the priority value.";
                } // END of priority definition.

                container state {
                    config false;
                    description
                        "Operational state data";
                    uses ospfv2-traffic-engineering-database-bandwidth-state;
                } // END of state-container definition.
            } // End of unreserved-bandwidth-list
        } // END of unreserved-bandwidths-container definition.
    } // END of ospfv2-traffic-engineering-database-unreserved-bandwidth definition.
    grouping ospfv2-traffic-engineering-database-link-delay-state {
        description
            "Grouping for OSPF traffic engineering(TE) link delay state attributes";
        leaf anomalous-bit  {
            type  empty;
            description "This attribute returns the Anomalous (A) bit value. The A bit is set
                        when the measured value of this parameter exceeds its configured
                        maximum threshold. The A bit is cleared when the measured value falls
                        below its configured reuse threshold.";
        } // END of anomalous-bit definition.

        leaf delay  {
            type  uint32;
            units "microseconds";
            description "This attribute returns the average link delay in microseconds.";
        } // END of delay definition.

    } // END of ospfv2-traffic-engineering-database-link-delay-state definition.
    grouping ospfv2-traffic-engineering-database-link-delay {
        description
            "Grouping for OSPF traffic engineering(TE) database TLV link delay";
        container link-delay {
            config false;
            description
                "OSPF traffic engineering(TE) database TLV link delay";
            container state {
                config false;
                description
                    "Operational state data";
                uses ospfv2-traffic-engineering-database-link-delay-state;
            } // END of state-container definition.
        } // END of link-delay-container definition.
    } // END of ospfv2-traffic-engineering-database-link-delay definition.
    grouping ospfv2-traffic-engineering-database-link-min-max-delay-state {
        description
            "Grouping for OSPF traffic engineering(TE) link min/max delay state
                        attributes";
        leaf anomalous-bit  {
            type  empty;
            description "This attribute returns the Anomalous (A) bit value. The A bit is set
                        when the measured value of this parameter exceeds its configured
                        maximum threshold. The A bit is cleared when the measured value falls
                        below its configured reuse threshold.";
        } // END of anomalous-bit definition.

        leaf minimum-delay  {
            type  uint32;
            units "microseconds";
            description "This attribute returns the minimum delay value in microseconds.";
        } // END of minimum-delay definition.

        leaf maximum-delay  {
            type  uint32;
            units "microseconds";
            description "This attribute returns the maximum delay value in microseconds.";
        } // END of maximum-delay definition.

    } // END of ospfv2-traffic-engineering-database-link-min-max-delay-state definition.
    grouping ospfv2-traffic-engineering-database-link-min-max-delay {
        description
            "Grouping for OSPF traffic engineering(TE) database TLV link min/max
                        delay";
        container link-min-max-delay {
            config false;
            description
                "OSPF traffic engineering(TE) database TLV link min/max delay";
            container state {
                config false;
                description
                    "Operational state data";
                uses ospfv2-traffic-engineering-database-link-min-max-delay-state;
            } // END of state-container definition.
        } // END of link-min-max-delay-container definition.
    } // END of ospfv2-traffic-engineering-database-link-min-max-delay definition.
    grouping ospfv2-traffic-engineering-database-link-delay-variation-state {
        description
            "Grouping for OSPF traffic engineering(TE) link delay variation state
                        attributes";
        leaf delay-variation  {
            type  uint32;
            units "microseconds";
            description "This attribute returns the average link delay variation value in
                        microseconds.";
        } // END of delay-variation definition.

    } // END of ospfv2-traffic-engineering-database-link-delay-variation-state definition.
    grouping ospfv2-traffic-engineering-database-link-delay-variation {
        description
            "Grouping for OSPF traffic engineering(TE) database TLV link delay
                        variation";
        container link-delay-variation {
            config false;
            description
                "OSPF traffic engineering(TE) database TLV link delay variation";
            container state {
                config false;
                description
                    "Operational state data";
                uses ospfv2-traffic-engineering-database-link-delay-variation-state;
            } // END of state-container definition.
        } // END of link-delay-variation-container definition.
    } // END of ospfv2-traffic-engineering-database-link-delay-variation definition.
    grouping ospfv2-traffic-engineering-database-link-loss-state {
        description
            "Grouping for OSPF traffic engineering(TE) link loss state attributes";
        leaf anomalous-bit  {
            type  empty;
            description "This attribute returns the Anomalous (A) bit value. The A bit is set
                        when the measured value of this parameter exceeds its configured
                        maximum threshold. The A bit is cleared when the measured value falls
                        below its configured reuse threshold.";
        } // END of anomalous-bit definition.

        leaf loss  {
            type  string {
                length "1..1965";
                pattern "[^?' =,>|]+";
            }
            units "%";
            description "This attribute returns the link packet loss as percentage of total
                        traffic sent over a configurable interval.";
        } // END of loss definition.

    } // END of ospfv2-traffic-engineering-database-link-loss-state definition.
    grouping ospfv2-traffic-engineering-database-link-loss {
        description
            "Grouping for OSPF traffic engineering(TE) database TLV link loss";
        container link-loss {
            config false;
            description
                "OSPF traffic engineering(TE) database TLV link loss";
            container state {
                config false;
                description
                    "Operational state data";
                uses ospfv2-traffic-engineering-database-link-loss-state;
            } // END of state-container definition.
        } // END of link-loss-container definition.
    } // END of ospfv2-traffic-engineering-database-link-loss definition.
    grouping ospfv2-traffic-engineering-database-link-bandwidth-state {
        description
            "Grouping for OSPF traffic engineering(TE) link bandwidth state
                        attributes";
        leaf residual-bandwidth  {
            type  string {
                length "1..1965";
                pattern "[^?' =,>|]+";
            }
            units "Kbps";
            description "This attribute returns the residual bandwidth value.";
        } // END of residual-bandwidth definition.

        leaf available-bandwidth  {
            type  string {
                length "1..1965";
                pattern "[^?' =,>|]+";
            }
            units "Kbps";
            description "This attribute returns the available bandwidth value.";
        } // END of available-bandwidth definition.

        leaf utilized-bandwidth  {
            type  string {
                length "1..1965";
                pattern "[^?' =,>|]+";
            }
            units "Kbps";
            description "This attribute returns the utilized bandwidth value.";
        } // END of utilized-bandwidth definition.

    } // END of ospfv2-traffic-engineering-database-link-bandwidth-state definition.
    grouping ospfv2-traffic-engineering-database-link-bandwidth {
        description
            "Grouping for OSPF traffic engineering(TE) database TLV link bandwidth";
        container link-bandwidth {
            config false;
            description
                "OSPF traffic engineering(TE) database TLV link bandwidth";
            container state {
                config false;
                description
                    "Operational state data";
                uses ospfv2-traffic-engineering-database-link-bandwidth-state;
            } // END of state-container definition.
        } // END of link-bandwidth-container definition.
    } // END of ospfv2-traffic-engineering-database-link-bandwidth definition.
    grouping ospfv2-traffic-engineering-database-lsdb-tlv {
        description
            "Grouping for OSPF traffic engineering(TE) database TLV";
        container tlv {
            config false;
            description
                "OSPF traffic engineering(TE) database TLV";
            container state {
                config false;
                description
                    "Operational state data for TE database TLV";
                uses ospfv2-traffic-engineering-database-lsdb-tlv-state;
            } // END of state-container definition.
            uses ospfv2-traffic-engineering-database-lsdb-tlv-capability;
            uses ospfv2-traffic-engineering-database-unreserved-bandwidth;
            uses ospfv2-traffic-engineering-database-link-delay;
            uses ospfv2-traffic-engineering-database-link-min-max-delay;
            uses ospfv2-traffic-engineering-database-link-delay-variation;
            uses ospfv2-traffic-engineering-database-link-loss;
            uses ospfv2-traffic-engineering-database-link-bandwidth;
        } // END of tlv-container definition.
    } // END of ospfv2-traffic-engineering-database-lsdb-tlv definition.
    grouping ospfv2-traffic-engineering-database-lsdb-state {
        description
            "Grouping for OSPF traffic engineering(TE) database lsdb state
                        attributes";
        leaf advertising-router  {
            type  inet:ipv4-address;
            description "This attribute returns the advertising-router value.";
        } // END of advertising-router definition.

        leaf ls-options  {
            type  string {
                length "1..1965";
                pattern "[^?' =,>|]+";
            }
            description "This attribute returns the ls-options value.";
        } // END of ls-options definition.

        leaf ls-opaque-type  {
            type  uint32;
            description "This attribute returns the ls-opaque type value.";
        } // END of ls-opaque-type definition.

        leaf ls-age  {
            type  uint16;
            description "This attribute returns the ls-age value.";
        } // END of ls-age definition.

        leaf ls-type  {
            type  ipi-ospf-types:ospf_lsdb_type_t;
            description "This attribute returns the ls-type value.";
        } // END of ls-type definition.

        leaf ls-instance  {
            type  string {
                length "1..1965";
                pattern "[^?' =,>|]+";
            }
            description "This attribute returns the ls-instance value.";
        } // END of ls-instance definition.

        leaf ls-sequence-number  {
            type  string {
                length "1..1965";
                pattern "[^?' =,>|]+";
            }
            description "This attribute returns the ls-sequence-number value.";
        } // END of ls-sequence-number definition.

        leaf ls-checksum  {
            type  string {
                length "1..1965";
                pattern "[^?' =,>|]+";
            }
            description "This attribute returns the ls-checksum value.";
        } // END of ls-checksum definition.

        leaf ls-length  {
            type  uint16;
            description "This attribute returns the ls-length value.";
        } // END of ls-length definition.

    } // END of ospfv2-traffic-engineering-database-lsdb-state definition.
    grouping ospfv2-traffic-engineering-database-lsdb {
        description
            "Grouping for OSPF traffic engineering(TE) database lsdb";
        container traffic-engineering-database {
            if-feature feature-list:HAVE_OSPF_CSPF;
            config false;
            description
                "OSPF traffic engineering(TE) database lsdb";

            list link {
                key "advertising-router link-id";
                config false;
                description
                    "List of TLV links for link state database";
                leaf advertising-router  {
                    type  leafref {
                        path  "../state/advertising-router";
                    }
                    description "This attributes returns the advertising-router value.";
                } // END of advertising-router definition.

                leaf link-id  {
                    type  leafref {
                        path  "../state/link-id";
                    }
                    description "This attributes returns the link-id value.";
                } // END of link-id definition.

                container state {
                    config false;
                    description
                        "Operational state data for TLV links";
                    uses ospfv2-traffic-engineering-database-lsdb-link-state;
                    uses ospfv2-traffic-engineering-database-lsdb-state;
                } // END of state-container definition.
                uses ospfv2-traffic-engineering-database-lsdb-tlv;
            } // End of link-list

            list router {
                key "router-id";
                config false;
                description
                    "List of TLV routers for link state database";
                leaf router-id  {
                    type  leafref {
                        path  "../state/router-id";
                    }
                    description "This attributes returns the router-id value.";
                } // END of router-id definition.

                container state {
                    config false;
                    description
                        "Operational state data for TLV routers";
                    uses ospfv2-traffic-engineering-database-lsdb-router-state;
                    uses ospfv2-traffic-engineering-database-lsdb-state;
                } // END of state-container definition.
            } // End of router-list
        } // END of traffic-engineering-database-container definition.
    } // END of ospfv2-traffic-engineering-database-lsdb definition.
    grouping ospfv2-area-access-control-list-filter-in-config {
        description
            "Grouping for OSPF area filter access control list configuration data";
        leaf name  {
            type  string {
                length "1..1965";
                pattern "[^?' =,>|]+";
            }
            description "Use this attribute to set name of the access control list.";
        } // END of name definition.

    } // END of ospfv2-area-access-control-list-filter-in-config definition.
    grouping ospfv2-area-access-control-list-filter-out-config {
        description
            "Grouping for OSPF area filter access control list configuration data";
        leaf name  {
            type  string {
                length "1..1965";
                pattern "[^?' =,>|]+";
            }
            description "Use this attribute to set name of the access control list.";
        } // END of name definition.

    } // END of ospfv2-area-access-control-list-filter-out-config definition.
    grouping ospfv2-area-access-control-list-top {
        description
            "Grouping for OSPF area filter access control list";
        container access-control-list {
            if-feature feature-list:HAVE_ACL;
            description
                "OSPF area filter access control list fiter-in and filter-out";
            container filter-in {
                description
                    "Container for OSPF area filter access control list in, filtering
                            routes into this area";
                container config {
                    description
                        "Configuration data for OSPF area filter access control list in";
                    uses ospfv2-area-access-control-list-filter-in-config;
                } // END of config-container definition.
                container state {
                    config false;
                    description
                        "Operational state data for OSPF area filter access control list in";
                    uses ospfv2-area-access-control-list-filter-in-config;
                } // END of state-container definition.
            } // END of filter-in-container definition.
            container filter-out {
                description
                    "Container for OSPF area filter access control list in, filtering
                            routes from this area into other areas";
                container config {
                    description
                        "Configuration data for OSPF area filter access control list out";
                    uses ospfv2-area-access-control-list-filter-out-config;
                } // END of config-container definition.
                container state {
                    config false;
                    description
                        "Operational state data for OSPF area filter access control list out";
                    uses ospfv2-area-access-control-list-filter-out-config;
                } // END of state-container definition.
            } // END of filter-out-container definition.
        } // END of access-control-list-container definition.
    } // END of ospfv2-area-access-control-list-top definition.
    grouping ospfv2-area-prefix-list-filter-in-config {
        description
            "Grouping for OSPF area filter prefix list configuration data";
        leaf name  {
            type  string {
                length "1..1965";
                pattern "[^?' =,>|]+";
            }
            description "Use this attribute to set name of the prefix list.";
        } // END of name definition.

    } // END of ospfv2-area-prefix-list-filter-in-config definition.
    grouping ospfv2-area-prefix-list-filter-out-config {
        description
            "Grouping for OSPF area filter prefix list configuration data";
        leaf name  {
            type  string {
                length "1..1965";
                pattern "[^?' =,>|]+";
            }
            description "Use this attribute to set name of the prefix list.";
        } // END of name definition.

    } // END of ospfv2-area-prefix-list-filter-out-config definition.
    grouping ospfv2-area-prefix-list-top {
        description
            "Grouping for OSPF area filter prefix list";
        container prefix-list {
            if-feature feature-list:HAVE_ACL;
            description
                "OSPF area filter prefix list fiter-in and filter-out";
            container filter-in {
                description
                    "Container for OSPF area filter prefix list in, filtering routes into
                            this area";
                container config {
                    description
                        "Configuration data for OSPF area filter prefix list in";
                    uses ospfv2-area-prefix-list-filter-in-config;
                } // END of config-container definition.
                container state {
                    config false;
                    description
                        "Operational state data for OSPF area filter prefix list in";
                    uses ospfv2-area-prefix-list-filter-in-config;
                } // END of state-container definition.
            } // END of filter-in-container definition.
            container filter-out {
                description
                    "Container for OSPF area filter prefix list in, filtering routes from
                            this area into other areas";
                container config {
                    description
                        "Configuration data for OSPF area filter prefix list out";
                    uses ospfv2-area-prefix-list-filter-out-config;
                } // END of config-container definition.
                container state {
                    config false;
                    description
                        "Operational state data for OSPF area filter prefix list out";
                    uses ospfv2-area-prefix-list-filter-out-config;
                } // END of state-container definition.
            } // END of filter-out-container definition.
        } // END of prefix-list-container definition.
    } // END of ospfv2-area-prefix-list-top definition.
    grouping ospfv2-area-filter-list-top {
        description
            "Grouping for OSPF area filter list";
        container filter-list {
            if-feature feature-list:HAVE_ACL;
            description
                "OSPF area filter list";
            uses ospfv2-area-prefix-list-top;
            uses ospfv2-area-access-control-list-top;
        } // END of filter-list-container definition.
    } // END of ospfv2-area-filter-list-top definition.
    grouping ospfv2-area-range-config {
        description
            "Grouping for OSPF area range configuration data";
        leaf address  {
            type  inet:ipv4-prefix;
            description "Use this attribute to summarize routes matching address/mask (border
                        routers only).";
        } // END of address definition.

        leaf disable-advertise  {
            type  empty;
            description "Use this attribute to disable the advertisement of these routes.";
        } // END of disable-advertise definition.

    } // END of ospfv2-area-range-config definition.
    grouping ospfv2-area-range-top {
        description
            "Grouping for OSPF area range";
        container area-ranges {
            description
                "OSPF area ranges";

            list area-range {
                key "address";
                description
                    "List of OSPF area ranges";
                leaf address  {
                    type  leafref {
                        path  "../config/address";
                    }
                    description "Use this attribute to summarize routes matching address/mask (border
                                routers only).";
                } // END of address definition.

                container config {
                    description
                        "Configuration data for OSPF area range";
                    uses ospfv2-area-range-config;
                } // END of config-container definition.
                container state {
                    config false;
                    description
                        "Operational state data for OSPF area range";
                    uses ospfv2-area-range-config;
                } // END of state-container definition.
            } // End of area-range-list
        } // END of area-ranges-container definition.
    } // END of ospfv2-area-range-top definition.
    grouping ospfv2-area-nssa-state {
        description
            "Grouping for OSPF area NSSA operational state data";
        leaf translator-count  {
            type  yang:counter64;
            description "NSSA translator counter.";
        } // END of translator-count definition.

        leaf translator-state  {
            type  ipi-ospf-types:ospf_nssa_translator_state_t;
            description "NSSA translator state.";
        } // END of translator-state definition.

    } // END of ospfv2-area-nssa-state definition.
    grouping ospfv2-area-nssa-config {
        description
            "Grouping for OSPF area NSSA configuration data";
        leaf nssa-enable  {
            type  ipi-ospf-types:ospf_nssa_t;
            description "Use this attribute to enable the OSPF area as NSSA.";
        } // END of nssa-enable definition.

        leaf no-summary  {
            type  empty;
            description "Use this attribute to prevent injection of inter-area routes into the
                        NSSA.";
        } // END of no-summary definition.

        leaf stability-interval  {
            type  uint32 {
                 range "0..2147483647"  {
                    description "0..2147483647: Supported range 0 - 2147483647";
                 }
            }
            units "seconds";
            default "40";
            description "Use this attribute to set stability interval. If an elected translator
                        determines its services are no
                        longer required, it continues to perform its duties for this time
                        interval. This minimizes
                        excess flushing of translated Type-7 LSAs and provides a more stable
                        translator
                        transition.";
        } // END of stability-interval definition.

        leaf translator-role  {
            type  ipi-ospf-types:ospf_translator_role_t;
            description "Use this attribute to set the NSSA-ABR translator role.";
        } // END of translator-role definition.

        leaf no-redistribution  {
            type  empty;
            description "Use this attribute to not redistribute into the NSSA area.";
        } // END of no-redistribution definition.

        leaf default-information-originate  {
            type  empty;
            description "Use this attribute to originate Type-7 default LSA into the NSSA.";
        } // END of default-information-originate definition.

        leaf metric  {
            when " /ospfv2/processes/process/areas/area/nssas/nssa/config/default-information-originate ";
            type  uint32 {
                 range "0..16777214"  {
                    description "0..16777214: Supported range 0 - 16777214";
                 }
            }
            default "0";
            description "Use this attribute to set the OSPF area with default metric.";
        } // END of metric definition.

        leaf metric-type  {
            when " /ospfv2/processes/process/areas/area/nssas/nssa/config/default-information-originate ";
            type  ipi-ospf-types:ospf_metric_type_t;
            default "2";
            description "Use this attribute to set the OSPF area default metric type.";
        } // END of metric-type definition.

        leaf route-map  {
            when " /ospfv2/processes/process/areas/area/nssas/nssa/config/default-information-originate ";
            type  string {
                length "1..1965";
                pattern "[^?' =,>|]+";
            }
            description "Use this attribute to set route-map instance.";
        } // END of route-map definition.

    } // END of ospfv2-area-nssa-config definition.
    grouping ospfv2-area-nssa-top {
        description
            "Grouping for OSPF area Not-So-Stubby Area (NSSA)";
        container nssas {
            if-feature feature-list:HAVE_NSSA;
            description
                "OSPF area Not-So-Stubby Areas";

            list nssa {
                key "nssa-enable";
                description
                    "List of OSPF area Not-So-Stubby Areas";
                leaf nssa-enable  {
                    type  leafref {
                        path  "../config/nssa-enable";
                    }
                    description "Use this attribute to enable the OSPF area as NSSA.";
                } // END of nssa-enable definition.

                container config {
                    description
                        "Configuration data for OSPF area NSSA";
                    uses ospfv2-area-nssa-config;
                } // END of config-container definition.
                container state {
                    config false;
                    description
                        "Operational state data for OSPF area NSSA";
                    uses ospfv2-area-nssa-config;
                    uses ospfv2-area-nssa-state;
                } // END of state-container definition.
            } // End of nssa-list
        } // END of nssas-container definition.
    } // END of ospfv2-area-nssa-top definition.
    grouping ospfv2-area-stub-config {
        description
            "Grouping for OSPF area stub configuration data";
        leaf is-stub  {
            type  empty;
            description "Use this attribute to set the OSPF area as stub.";
        } // END of is-stub definition.

        leaf no-summary  {
            type  empty;
            description "Use this attribute to set the OSPF area stub with no-summary, this
                        will prevent an ABR from sending summary link state advertisements
                        into the stub area.";
        } // END of no-summary definition.

    } // END of ospfv2-area-stub-config definition.
    grouping ospfv2-area-stub-top {
        description
            "Grouping for OSPF area stub";
        container stub {
            description
                "OSPF area stub";
            container config {
                description
                    "Configuration data for OSPF area stub";
                uses ospfv2-area-stub-config;
            } // END of config-container definition.
            container state {
                config false;
                description
                    "Operational state data for OSPF area stub";
                uses ospfv2-area-stub-config;
            } // END of state-container definition.
        } // END of stub-container definition.
    } // END of ospfv2-area-stub-top definition.
    grouping ospfv2-area-interface-config {
        description
            "Grouping for OSPF area interface configuration data";
        leaf name  {
            type  string {
                length "1..1965";
                pattern "[^?' =,>|]+";
            }
            description "Use this attribute to set the interface to enable OSPF area.";
        } // END of name definition.

        leaf network-type  {
            type  ipi-ospf-types:ospf_network_t;
            description "Use this attribute to set the area interface network type.";
        } // END of network-type definition.

        leaf passive  {
            type  empty;
            description "Use this attribute to set area interface as passive.";
        } // END of passive definition.

    } // END of ospfv2-area-interface-config definition.
    grouping ospfv2-area-interface-top {
        description
            "Grouping for OSPF area interface";
        container interfaces {
            description
                "OSPF area interfaces";

            list interface {
            when " /ospfv2/global/config/area-interface-config-mode and /ipi-interface:interfaces/ipi-interface:interface/ipi-interface:name ";
                key "name";
                description
                    "List of OSPF area interfaces";
                leaf name  {
                    type  leafref {
                        path  "../config/name";
                    }
                    description "Use this attribute to set the interface to enable OSPF area.";
                } // END of name definition.

                container config {
                    description
                        "Configuration data for OSPF area interface";
                    uses ospfv2-area-interface-config;
                    uses ospfv2-authentication-config;
                } // END of config-container definition.
                container state {
                    config false;
                    description
                        "Operational state data for OSPF area interface";
                    uses ospfv2-area-interface-config;
                    uses ospfv2-authentication-config;
                } // END of state-container definition.
            } // End of interface-list
        } // END of interfaces-container definition.
    } // END of ospfv2-area-interface-top definition.
    grouping ospfv2-area-host-config {
        description
            "Grouping for OSPF area host configuration data";
        leaf ip-address  {
            type  inet:ipv4-address;
            description "Use this attribute to set a stub host entry.";
        } // END of ip-address definition.

        leaf cost  {
            type  uint16 {
                 range "0..65535"  {
                    description "0..65535: Supported range 0 - 65535";
                 }
            }
            description "Use this attribute to set the stub host cost.";
        } // END of cost definition.

    } // END of ospfv2-area-host-config definition.
    grouping ospfv2-area-host-top {
        description
            "Grouping for OSPF area host";
        container hosts {
            description
                "OSPF area hosts";

            list host {
                key "ip-address";
                description
                    "List of OSPF area hosts";
                leaf ip-address  {
                    type  leafref {
                        path  "../config/ip-address";
                    }
                    description "Use this attribute to set a stub host entry.";
                } // END of ip-address definition.

                container config {
                    description
                        "Configuration data for OSPF area host";
                    uses ospfv2-area-host-config;
                } // END of config-container definition.
                container state {
                    config false;
                    description
                        "Operational state data for OSPF area host";
                    uses ospfv2-area-host-config;
                } // END of state-container definition.
            } // End of host-list
        } // END of hosts-container definition.
    } // END of ospfv2-area-host-top definition.
    grouping ospfv2-area-network-config {
        description
            "Grouping for OSPF area network configuration data";
        leaf prefix  {
            type  inet:ipv4-prefix;
            description "Use this attribute to set the area network prefix. This enables OSPF
                        routing on interfaces with IP addresses that match the specified
                        network address.";
        } // END of prefix definition.

        leaf instance-id  {
            if-feature feature-list:HAVE_OSPF_MULTI_INST;
            type  uint8 {
                 range "0..255"  {
                    description "0..255: Supported range 0 - 255";
                 }
            }
            mandatory true;
            description "Use this attribute to set the instance ID. Use this command with OSPF
                        multiple-instance support enabled.";
        } // END of instance-id definition.

    } // END of ospfv2-area-network-config definition.
    grouping ospfv2-area-network-top {
        description
            "Grouping for OSPF area network";
        container networks {
            description
                "OSPF area networks";

            list network {
            when " not(/ospfv2/global/config/area-interface-config-mode) ";
                key "prefix";
                description
                    "List OSPF area networks";
                leaf prefix  {
                    type  leafref {
                        path  "../config/prefix";
                    }
                    description "Use this attribute to set the area network prefix. This enables OSPF
                                routing on interfaces with IP addresses that match the specified
                                network address.";
                } // END of prefix definition.

                container config {
                    description
                        "Configuration data for OSPF area network";
                    uses ospfv2-area-network-config;
                } // END of config-container definition.
                container state {
                    config false;
                    description
                        "Operational state data for OSPF area network";
                    uses ospfv2-area-network-config;
                } // END of state-container definition.
            } // End of network-list
        } // END of networks-container definition.
    } // END of ospfv2-area-network-top definition.
    grouping ospfv2-area-virtual-link-state {
        description
            "Grouping for OSPF area virtual link operational state data";
        leaf name  {
            type  string {
                length "1..1965";
                pattern "[^?' =,>|]+";
            }
            description "Use this attribute to retrieve the name of this virtual link.";
        } // END of name definition.

        leaf interface  {
            type  string {
                length "1..1965";
                pattern "[^?' =,>|]+";
            }
            description "Use this attribute to retrieve the interface of this virtual link.";
        } // END of interface definition.

        leaf virtual-link-interface-state  {
            type  ipi-ospf-types:ospf_vlink_interface_state_t;
            description "Use this attribute to retrieve the interface state of this virtual
                        link.";
        } // END of virtual-link-interface-state definition.

        leaf link-state  {
            type  ipi-ospf-types:ospf_vlink_status_t;
            description "Use this attribute to retrieve the link state of this virtual link.";
        } // END of link-state definition.

        leaf adjacency-state  {
            type  ipi-ospf-types:ospf_vlink_adj_state_t;
            description "Use this attribute to retrieve the adjacency state of this virtual
                        link.";
        } // END of adjacency-state definition.

        leaf hello-packet-due-in  {
            type  string {
                length "1..1965";
                pattern "[^?' =,>|]+";
            }
            description "Use this attribute to retrieve remaining time before a hello packet is
                        sent out on this virtual link.";
        } // END of hello-packet-due-in definition.

        leaf local-address  {
            type  inet:ipv4-prefix;
            description "Use this attribute to retrieve the local address of this virtual link.";
        } // END of local-address definition.

        leaf remote-address  {
            type  inet:ipv4-prefix;
            description "Use this attribute to retrieve the remote address of this virtual
                        link.";
        } // END of remote-address definition.

    } // END of ospfv2-area-virtual-link-state definition.
    grouping ospfv2-area-virtual-link-authentication-top {
        description
            "Grouping for OSPF virtual link authentication";
        container authentication {
            description
                "OSPF virtual link authentication";
            container config {
                description
                    "Configuration data for OSPF virtual link authentication";
                uses ospfv2-authentication-config;
            } // END of config-container definition.
            container state {
                config false;
                description
                    "Operational state data for OSPF virtual link authentication";
                uses ospfv2-authentication-config;
            } // END of state-container definition.
            uses ospfv2-authentication-message-digest-top;
        } // END of authentication-container definition.
    } // END of ospfv2-area-virtual-link-authentication-top definition.
    grouping ospfv2-area-virtual-link-bfd-config {
        description
            "Grouping for OSPF area virtual link BFD configuration data";
        leaf fall-over  {
            if-feature feature-list:HAVE_BFD;
            type  empty;
            description "Fall-over detection with Bidirectional Forwarding Detection (BFD).";
        } // END of fall-over definition.

    } // END of ospfv2-area-virtual-link-bfd-config definition.
    grouping ospfv2-area-virtual-link-bfd-top {
        description
            "Grouping for OSPF area virtual link Bidirectional Forwarding Detection
                        (BFD)";
        container bfd {
            description
                "OSPF area virtual link BFD";
            container config {
                description
                    "Configuration data for OSPF area virtual link BFD";
                uses ospfv2-area-virtual-link-bfd-config;
            } // END of config-container definition.
            container state {
                config false;
                description
                    "Operational state data for OSPF area virtual link BFD";
                uses ospfv2-area-virtual-link-bfd-config;
            } // END of state-container definition.
        } // END of bfd-container definition.
    } // END of ospfv2-area-virtual-link-bfd-top definition.
    grouping ospfv2-area-virtual-link-config {
        description
            "Grouping for OSPF area virtual link configuration data";
        leaf remote-router-id  {
            type  inet:ipv4-address;
            description "Use this attribute to set the interface IP address of the neighbor.";
        } // END of remote-router-id definition.

    } // END of ospfv2-area-virtual-link-config definition.
    grouping ospfv2-area-virtual-link-top {
        description
            "Grouping for OSPF area virtual link";
        container virtual-links {
            description
                "OSPF area virtual links";

            list virtual-link {
                key "remote-router-id";
                description
                    "List of OSPF area virtual links";
                leaf remote-router-id  {
                    type  leafref {
                        path  "../config/remote-router-id";
                    }
                    description "Use this attribute to set the interface IP address of the neighbor.";
                } // END of remote-router-id definition.

                container config {
                    description
                        "Configuration data for OSPF area virtual link";
                    uses ospfv2-area-virtual-link-config;
                } // END of config-container definition.
                container state {
                    config false;
                    description
                        "Operational state data for OSPF area virtual link";
                    uses ospfv2-area-virtual-link-config;
                    uses ospfv2-area-virtual-link-state;
                } // END of state-container definition.
                uses ospfv2-area-virtual-link-bfd-top;
                uses ospfv2-area-virtual-link-authentication-top;
                uses ospfv2-area-virtual-link-timers-top;
                uses ospfv2-virtual-link-interface-state-change;
                uses ospfv2-virtual-neighbor-state-change;
                uses ospfv2-virtual-link-interface-rx-bad-packet;
                uses ospfv2-virtual-link-interface-tx-retransmit;
                uses ospfv2-virtual-link-interface-config-error;
            } // End of virtual-link-list
        } // END of virtual-links-container definition.
    } // END of ospfv2-area-virtual-link-top definition.
    grouping ospfv2-area-sham-link-config {
        description
            "Grouping for OSPF area sham link configuration data";
        leaf source-id  {
            type  inet:ipv4-address;
            description "Use this attribute to set the source IP address of sham link.";
        } // END of source-id definition.

        leaf destination-id  {
            type  inet:ipv4-address;
            description "Use this attribute to set the destination IP address of sham link.";
        } // END of destination-id definition.

        leaf cost  {
            type  uint16 {
                 range "1..65535"  {
                    description "1..65535: Supported range 1 - 65535";
                 }
            }
            default "1";
            description "Use this attribute to set the sham link cost.";
        } // END of cost definition.

    } // END of ospfv2-area-sham-link-config definition.
    grouping ospfv2-area-sham-link-top {
        description
            "Grouping for OSPF area sham link";
        container sham-links {
            if-feature feature-list:HAVE_VRF_OSPF;
            if-feature feature-list:HAVE_MPLS;
            description
                "OSPF area sham links";

            list sham-link {
                key "source-id destination-id";
                description
                    "List of OSPF area sham links";
                leaf source-id  {
                    type  leafref {
                        path  "../config/source-id";
                    }
                    description "Use this attribute to set the source IP address of sham link.";
                } // END of source-id definition.

                leaf destination-id  {
                    type  leafref {
                        path  "../config/destination-id";
                    }
                    description "Use this attribute to set the destination IP address of sham link.";
                } // END of destination-id definition.

                container config {
                    description
                        "Configuration data for OSPF area sham link";
                    uses ospfv2-area-sham-link-config;
                } // END of config-container definition.
            } // End of sham-link-list
        } // END of sham-links-container definition.
    } // END of ospfv2-area-sham-link-top definition.
    grouping ospfv2-area-config {
        description
            "Grouping for OSPF area configuration data";
        leaf area-id  {
            type  ipi-ospf-types:ospf_area_t;
            description "Use this attribute to set the OSPF area ID.";
        } // END of area-id definition.

        leaf authentication-type  {
            when " not(/ospfv2/global/config/area-interface-config-mode) ";
            type  ipi-ospf-types:ospf_area_authentication_type_t;
            description "Use this attribute to set the area authentication type.";
        } // END of authentication-type definition.

        leaf default-cost  {
            type  uint32 {
                 range "0..16777215"  {
                    description "0..16777215: Supported range 0 - 16777215";
                 }
            }
            description "Use this attribute to set the summary-default cost of a NSSA or stub
                        area.";
        } // END of default-cost definition.

        leaf shortcut  {
            type  ipi-ospf-types:ospf_area_shortcut_type_t;
            description "Use this attribute to set the area shortcutting mode.";
        } // END of shortcut definition.

    } // END of ospfv2-area-config definition.
    grouping ospfv2-area-global-config {
        description
            "ospfv2CMLSEPareaCMLSEPglobalCMLSEPconfig";
        leaf maximum-areas-number  {
            type  uint32 {
                 range "1..4294967294"  {
                    description "1..4294967294: Supported range 1 - 4294967294";
                 }
            }
            description "Use this attribute to set the maximum number of OSPF areas (excluding
                        Backbone Area).";
        } // END of maximum-areas-number definition.

    } // END of ospfv2-area-global-config definition.
    grouping ospfv2-area-top {
        description
            "Grouping for OSPF area";
        container areas {
            description
                "OSPF areas";

            list area {
                key "area-id";
                description
                    "List of OSPF areas";
                leaf area-id  {
                    type  leafref {
                        path  "../config/area-id";
                    }
                    description "Use this attribute to set the OSPF area ID.";
                } // END of area-id definition.

                container config {
                    description
                        "Configuration data for OSPF area";
                    uses ospfv2-area-config;
                } // END of config-container definition.
                container state {
                    config false;
                    description
                        "Operational state data for OSPF area";
                    uses ospfv2-area-config;
                    uses ospfv2-area-state;
                } // END of state-container definition.
                uses ospfv2-area-interface-top;
                uses ospfv2-area-stub-top;
                uses ospfv2-area-nssa-top;
                uses ospfv2-area-filter-list-top;
                uses ospfv2-area-host-top;
                uses ospfv2-area-network-top;
                uses ospfv2-area-range-top;
                uses ospfv2-area-virtual-link-top;
                uses ospfv2-area-sham-link-top;
                uses ospfv2-traffic-engineering-database-lsdb;
            } // End of area-list
            container config {
                description
                    "Configuration data for OSPF area global";
                uses ospfv2-area-global-config;
            } // END of config-container definition.
            container state {
                config false;
                description
                    "Operational state data for OSPF area global";
                uses ospfv2-area-global-config;
            } // END of state-container definition.
        } // END of areas-container definition.
    } // END of ospfv2-area-top definition.
    grouping ospfv2-virtual-link-interface-config-error {
        description
            "ospfv2CMLSEPvirtualCMLSEPlinkCMLSEPinterfaceCMLSEPconfigCMLSEPerror";
        container virtual-link-interface-config-error {
            config false;
            description
                "Virtual link interface configuration error";
            leaf router-id  {
                type  inet:ipv4-address;
                description "The originator Router ID.";
            } // END of router-id definition.

            leaf error-type  {
                type  ipi-ospf-types:ospf_config_error_type_t;
                description "Error type.";
            } // END of error-type definition.

            leaf packet-type  {
                type  ipi-ospf-types:ospf_packet_type_t;
                description "OSPF packet type.";
            } // END of packet-type definition.

        } // END of virtual-link-interface-config-error-container definition.
    } // END of ospfv2-virtual-link-interface-config-error definition.
    grouping ospfv2-virtual-link-interface-state-change {
        description
            "ospfv2CMLSEPvirtualCMLSEPlinkCMLSEPinterfaceCMLSEPstateCMLSEPchange";
        container virtual-link-interface-state-change {
            config false;
            description
                "Virtual link interface state change";
            leaf router-id  {
                type  inet:ipv4-address;
                description "The originator Router ID.";
            } // END of router-id definition.

            leaf interface-state  {
                type  ipi-ospf-types:ospf_interface_state_t;
                description "Interface status.";
            } // END of interface-state definition.

        } // END of virtual-link-interface-state-change-container definition.
    } // END of ospfv2-virtual-link-interface-state-change definition.
    grouping ospfv2-virtual-neighbor-state-change {
        description
            "OSPFv2 virtual neighbor state change grouping";
        container virtual-neighbor-state-change {
            config false;
            description
                "Virtual neighbor state change";
            leaf router-id  {
                type  inet:ipv4-address;
                description "The originator Router ID.";
            } // END of router-id definition.

            leaf neighbor-state  {
                type  ipi-ospf-types:ospf_neighbor_state_change_t;
                description "Neighbor state.";
            } // END of neighbor-state definition.

        } // END of virtual-neighbor-state-change-container definition.
    } // END of ospfv2-virtual-neighbor-state-change definition.
    grouping ospfv2-virtual-link-interface-rx-bad-packet {
        description
            "fv2CMLSEPvirtualCMLSEPlinkCMLSEPinterfaceCMLSEPrxCMLSEPbadCMLSEPpacket";
        container virtual-link-interface-rx-bad-packet {
            config false;
            description
                "Link state change";
            leaf router-id  {
                type  inet:ipv4-address;
                description "Router ID for the OSPF process.";
            } // END of router-id definition.

            leaf packet-type  {
                type  ipi-ospf-types:ospf_packet_type_t;
                description "OSPF packet type.";
            } // END of packet-type definition.

        } // END of virtual-link-interface-rx-bad-packet-container definition.
    } // END of ospfv2-virtual-link-interface-rx-bad-packet definition.
    grouping ospfv2-virtual-link-interface-tx-retransmit {
        description
            "ospfv2CMLSEPvirtualCMLSEPlinkCMLSEPinterfaceCMLSEPtxCMLSEPretransmit";
        container virtual-link-interface-tx-retransmit {
            config false;
            description
                "OSPF Virtual interface TX retransmit";
            leaf router-id  {
                type  inet:ipv4-address;
                description "Use this attribute to set a router ID for the OSPF process. Configure
                            each router OSPF with an unique router ID.";
            } // END of router-id definition.

            leaf packet-type  {
                type  ipi-ospf-types:ospf_packet_type_t;
                description "OSPF patcket type.";
            } // END of packet-type definition.

            leaf lsdb-type  {
                type  ipi-ospf-types:ospf_lsdb_type_t;
                description "LSDB Type.";
            } // END of lsdb-type definition.

            leaf lsdb-lsid  {
                type  inet:ipv4-address;
                description "The Link State ID.";
            } // END of lsdb-lsid definition.

            leaf lsdb-router-id  {
                type  inet:ipv4-address;
                description "LSDB router ID.";
            } // END of lsdb-router-id definition.

        } // END of virtual-link-interface-tx-retransmit-container definition.
    } // END of ospfv2-virtual-link-interface-tx-retransmit definition.


}
