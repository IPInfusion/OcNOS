/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-ospf-authentication.yang
*
*/

submodule ipi-ospf-authentication {

    yang-version 1.1;

    belongs-to  ipi-ospf { prefix ipi-ospf; }

    import ipi-ospf-types {
        prefix ipi-ospf-types;
        revision-date 2022-06-01;
    }

    organization
        "IP Infusion Inc.";

    contact
        "Address: 3965 Freedom Circle, Suite 200, Santa Clara, CA 95054
         Phone: +1 408-400-1900
         E-mail: support@ipinfusion.com
         Web: http://www.ipinfusion.com/";

    description
        "Layer-3 OSPF authentication";


    revision "2022-06-01" {
        description "Updated the yang file with feature";
        reference " 0.4.0.";
    }

    revision "2022-01-07" {
        description "Modified Data Type";
        reference " 0.3.0.";
    }

    revision "2021-09-03" {
        description "Update descriptions of attribute";
        reference " 0.2.0.";
    }

    revision "2021-04-06" {
        description "Restructured module in accordance with OpenConfig style";
        reference " 0.1.0.";
    }

    grouping ospfv2-authentication-message-digest-config {
        description
            "Grouping for OSPF authentication message digest configuration data";
        leaf message-digest-id  {
            type  uint8 {
                 range "1..255"  {
                    description "1..255: Supported range 1 - 255";
                 }
            }
            description "Use this attribute to set the authentication message digest key ID.";
        } // END of message-digest-id definition.

        leaf message-digest-encryption-type  {
            type  ipi-ospf-types:ospf_cipher_type_t;
            mandatory true;
            description "Use this attribute to set the authentication encryption algorithm.";
        } // END of message-digest-encryption-type definition.

        leaf message-digest-key  {
            type  ipi-ospf-types:ospf_md5_password_t {
                length "1..1965";
            }
            mandatory true;
            description "Use this attribute to set the authentication message digest password
                        (key).";
        } // END of message-digest-key definition.

    } // END of ospfv2-authentication-message-digest-config definition.
    grouping ospfv2-authentication-message-digest-top {
        description
            "Grouping for OSPF authentication message digest";
        container message-digests {
            description
                "OSPF authentication messages digest";

            list message-digest {
                key "message-digest-id";
                description
                    "List of OSPF authentication messages digest";
                leaf message-digest-id  {
                    type  leafref {
                        path  "../config/message-digest-id";
                    }
                    description "Use this attribute to set the authentication message digest key ID.";
                } // END of message-digest-id definition.

                container config {
                    description
                        "Configuration data for OSPF authentication message digest";
                    uses ospfv2-authentication-message-digest-config;
                } // END of config-container definition.
                container state {
                    config false;
                    description
                        "Operational state data for OSPF authentication message digest";
                    uses ospfv2-authentication-message-digest-config;
                } // END of state-container definition.
            } // End of message-digest-list
        } // END of message-digests-container definition.
    } // END of ospfv2-authentication-message-digest-top definition.
    grouping ospfv2-authentication-config {
        description
            "Grouping for OSPF authentication configuration data";
        leaf authentication-type  {
            type  ipi-ospf-types:ospf_if_authentication_type_t;
            description "Use this attribute to configure authentication on this interface.";
        } // END of authentication-type definition.

        leaf key  {
            type  ipi-ospf-types:ospf_md5_password_t {
                length "1..1965";
            }
            description "Use this attribute to set the authentication password (key).";
        } // END of key definition.

    } // END of ospfv2-authentication-config definition.


}
