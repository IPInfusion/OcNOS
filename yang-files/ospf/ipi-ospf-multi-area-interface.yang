/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-ospf-multi-area-interface.yang
*
*/

submodule ipi-ospf-multi-area-interface {

    yang-version 1.1;

    belongs-to  ipi-ospf { prefix ipi-ospf; }

    import feature-list {
        prefix feature-list;
        revision-date 2023-02-21;
    }

    import ietf-inet-types {
        prefix inet;
        revision-date 2013-07-15;
    }

    import ipi-interface {
        prefix ipi-interface;
        revision-date 2022-08-24;
    }

    import ipi-ospf-types {
        prefix ipi-ospf-types;
        revision-date 2022-06-01;
    }

    organization
        "IP Infusion Inc.";

    contact
        "Address: 3965 Freedom Circle, Suite 200, Santa Clara, CA 95054
         Phone: +1 408-400-1900
         E-mail: support@ipinfusion.com
         Web: http://www.ipinfusion.com/";

    description
        "Layer-3 OSPF multi area interface";


    revision "2022-06-01" {
        description "Updated the yang file with feature";
        reference " 0.3.0.";
    }

    revision "2021-09-03" {
        description "Update descriptions of attribute";
        reference "Initial Version";
    }

    revision "2021-04-06" {
        description "Restructured module in accordance with OpenConfig style";
        reference "Initial Version";
    }

    grouping ospv2-multi-area-neighbor-config {
        description
            "Grouping for OSPF multi-area neighbor configuration data";
        leaf area-id  {
            type  ipi-ospf-types:ospf_area_t;
            description "Use this attribute to set the OSPF area ID.";
        } // END of area-id definition.

        leaf neighbor  {
            type  inet:ipv4-address;
            mandatory true;
            description "Use this attribute to set the neighbor IPv4 address.";
        } // END of neighbor definition.

    } // END of ospv2-multi-area-neighbor-config definition.
    grouping ospv2-multi-area-neighbor {
        description
            "Grouping for OSPF multi-area neighbor";
        container multi-areas-neighbors {
            description
                "OSPF multi-area neighbors";

            list multi-area-neighbor {
            when " not(/ospfv2/global/config/area-interface-config-mode) ";
                key "area-id";
                description
                    "List of OSPF multi-area neighbors";
                leaf area-id  {
                    type  leafref {
                        path  "../config/area-id";
                    }
                    description "Use this attribute to set the OSPF area ID in which to enable
                                multi-area adjacency.";
                } // END of area-id definition.

                container config {
                    description
                        "Configuration data for OSPF multi-area neighbor";
                    uses ospv2-multi-area-neighbor-config;
                } // END of config-container definition.
                container state {
                    config false;
                    description
                        "Operational state data for OSPF multi-area neighbor";
                    uses ospv2-multi-area-neighbor-config;
                } // END of state-container definition.
            } // End of multi-area-neighbor-list
        } // END of multi-areas-neighbors-container definition.
    } // END of ospv2-multi-area-neighbor definition.
    grouping ospv2-multi-area-config {
        description
            "Grouping for OSPF multi-area configuration data";
        leaf area-id  {
            type  ipi-ospf-types:ospf_area_t;
            description "Use this attribute to set the OSPF area ID in which to enable
                        multi-area adjacency.";
        } // END of area-id definition.

    } // END of ospv2-multi-area-config definition.
    grouping ospv2-multi-area {
        description
            "Grouping for OSPF multi-area";
        container multi-areas {
            description
                "OSPF multi-areas";

            list multi-area {
            when " not(/ospfv2/global/config/area-interface-config-mode) ";
                key "area-id";
                description
                    "List of OSPF multi-areas";
                leaf area-id  {
                    type  leafref {
                        path  "../config/area-id";
                    }
                    description "Use this attribute to set the OSPF area ID in which to enable
                                multi-area adjacency.";
                } // END of area-id definition.

                container config {
                    description
                        "Configuration data for OSPF multi-area";
                    uses ospv2-multi-area-config;
                } // END of config-container definition.
                container state {
                    config false;
                    description
                        "Operational state data for OSPF multi-area";
                    uses ospv2-multi-area-config;
                } // END of state-container definition.
            } // End of multi-area-list
        } // END of multi-areas-container definition.
    } // END of ospv2-multi-area definition.
    grouping ospfv2-process-multi-area-config {
        description
            "Grouping for OSPF multi-area interface OSPF process configuration data";
        leaf ospf-process-id  {
            type  uint16;
            description "Use this attribute to set the OSPF process ID in which to enable
                        multi-area adjacency.";
        } // END of ospf-process-id definition.

    } // END of ospfv2-process-multi-area-config definition.
    grouping ospfv2-process-multi-area-top {
        description
            "Grouping for OSPF multi-area interface OSPF process";
        container ospfv2-processes {
            description
                "OSPF multi-area interface OSPF processes";

            list ospfv2-process {
            when " not(/ospfv2/global/config/area-interface-config-mode) ";
                key "ospf-process-id";
                description
                    "List of OSPF multi-area interface OSPF processes";
                leaf ospf-process-id  {
                    type  leafref {
                        path  "../config/ospf-process-id";
                    }
                    description "Use this attribute to set the OSPF process ID in which to enable
                                multi-area adjacency.";
                } // END of ospf-process-id definition.

                container config {
                    description
                        "Configuration data for OSPFOSPF multi-area interface OSPF process";
                    uses ospfv2-process-multi-area-config;
                } // END of config-container definition.
                container state {
                    config false;
                    description
                        "Operational state data for OSPF multi-area interface OSPF process";
                    uses ospfv2-process-multi-area-config;
                } // END of state-container definition.
                uses ospv2-multi-area;
                uses ospv2-multi-area-neighbor;
            } // End of ospfv2-process-list
        } // END of ospfv2-processes-container definition.
    } // END of ospfv2-process-multi-area-top definition.
    grouping ospfv2-multi-area-interface-top {
        description
            "Grouping for OSPF multi-area interface";
        container multi-area-interfaces {
            if-feature feature-list:HAVE_OSPF_MULTI_AREA;
            description
                "OSPF multi-area interfaces";

            list multi-area-interface {
            when " not(/ospfv2/global/config/area-interface-config-mode) ";
                key "name";
                description
                    "List of OSPF multi-area interfaces";
                leaf name  {
                    type  leafref {
                        path  "/ipi-interface:interfaces/ipi-interface:interface/ipi-interface:name";
                    }
                    description "The interface name to configure the OSPF parameters.";
                } // END of name definition.

                uses ospfv2-process-multi-area-top;
            } // End of multi-area-interface-list
        } // END of multi-area-interfaces-container definition.
    } // END of ospfv2-multi-area-interface-top definition.


}
