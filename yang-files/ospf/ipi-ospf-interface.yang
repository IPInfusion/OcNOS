/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-ospf-interface.yang
*
*/

submodule ipi-ospf-interface {

    yang-version 1.1;

    belongs-to  ipi-ospf { prefix ipi-ospf; }

    import feature-list {
        prefix feature-list;
        revision-date 2023-02-21;
    }

    import ietf-inet-types {
        prefix inet;
        revision-date 2013-07-15;
    }

    import ietf-yang-types {
        prefix yang;
        revision-date 2013-07-15;
    }

    import ipi-interface {
        prefix ipi-interface;
        revision-date 2022-08-24;
    }

    import ipi-ospf-types {
        prefix ipi-ospf-types;
        revision-date 2022-06-01;
    }

    include ipi-ospf-authentication { revision-date 2022-06-01;}
    include ipi-ospf-global { revision-date 2022-06-01;}
    organization
        "IP Infusion Inc.";

    contact
        "Address: 3965 Freedom Circle, Suite 200, Santa Clara, CA 95054
         Phone: +1 408-400-1900
         E-mail: support@ipinfusion.com
         Web: http://www.ipinfusion.com/";

    description
        "Layer-3 OSPF interface";


    revision "2022-06-01" {
        description "Updated the yang file with feature";
        reference " 0.4.";
    }

    revision "2021-09-03" {
        description "Update descriptions of attribute";
        reference "Initial Version";
    }

    revision "2021-06-11" {
        description "Added the new attribute ldp-igp-sync-enable for the mpls ldp-igp sync ospf";
        reference "Initial Version";
    }

    revision "2021-04-06" {
        description "Restructured module in accordance with OpenConfig style";
        reference "Initial Version";
    }

    grouping ospfv2-backup-designated-router-state {
        description
            "Grouping for OSPF designated router operational state data";
        container backup-designated-router {
            config false;
            description
                "OSPF backup designated router";
            container state {
                config false;
                description
                    "Operational state data for OSPF backup designated router";
                leaf router-id  {
                    type  inet:ipv4-address;
                    description "Backup designated router ID.";
                } // END of router-id definition.

                leaf address  {
                    type  inet:ipv4-address;
                    description "Backup designated router address.";
                } // END of address definition.

            } // END of state-container definition.
        } // END of backup-designated-router-container definition.
    } // END of ospfv2-backup-designated-router-state definition.
    grouping ospfv2-designated-router-state {
        description
            "Grouping for OSPF designated router operational state data";
        container designated-router {
            config false;
            description
                "OSPF designated router";
            container state {
                config false;
                description
                    "Operational state data for OSPF designated router";
                leaf router-id  {
                    type  inet:ipv4-address;
                    description "Designated router ID.";
                } // END of router-id definition.

                leaf address  {
                    type  inet:ipv4-address;
                    description "Designated router address.";
                } // END of address definition.

            } // END of state-container definition.
        } // END of designated-router-container definition.
    } // END of ospfv2-designated-router-state definition.
    grouping ospfv2-statistic {
        description
            "Grouping for OSPF interface statistic operational state data";
        container statistics {
            config false;
            description
                "OSPF interface statistic";
            container errors {
                config false;
                description
                    "OSPF interface errors statistics";
                leaf discarded-in  {
                    type  yang:counter64;
                    description "Discarded in errors.";
                } // END of discarded-in definition.

                leaf discarded-out  {
                    type  yang:counter64;
                    description "Discarded out errors.";
                } // END of discarded-out definition.

                leaf hello-in  {
                    type  yang:counter64;
                    description "Hello in errors.";
                } // END of hello-in definition.

                leaf database-descriptor-in  {
                    type  yang:counter64;
                    description "Database descriptor in errors.";
                } // END of database-descriptor-in definition.

                leaf ls-request-in  {
                    type  yang:counter64;
                    description "ls request in errors.";
                } // END of ls-request-in definition.

                leaf ls-update-in  {
                    type  yang:counter64;
                    description "ls update in errors.";
                } // END of ls-update-in definition.

                leaf ls-acknowledge-in  {
                    type  yang:counter64;
                    description "ls acknowledge in errors.";
                } // END of ls-acknowledge-in definition.

                leaf unknown-in  {
                    type  yang:counter64;
                    description "Unknown in errors.";
                } // END of unknown-in definition.

                leaf unknown-out  {
                    type  yang:counter64;
                    description "Unknown out errors.";
                } // END of unknown-out definition.

                leaf bad-version  {
                    type  yang:counter64;
                    description "Bad version errors.";
                } // END of bad-version definition.

                leaf bad-crc  {
                    type  yang:counter64;
                    description "Bad CRC errors.";
                } // END of bad-crc definition.

                leaf invalid-source  {
                    type  yang:counter64;
                    description "Invalid source errors.";
                } // END of invalid-source definition.

                leaf invalid-destination  {
                    type  yang:counter64;
                    description "Invalid destination errors.";
                } // END of invalid-destination definition.

                leaf no-neighbor  {
                    type  yang:counter64;
                    description "No neighbor errors.";
                } // END of no-neighbor definition.

                leaf passive  {
                    type  yang:counter64;
                    description "Passive errors.";
                } // END of passive definition.

                leaf wrong-area  {
                    type  yang:counter64;
                    description "Wrong area errors.";
                } // END of wrong-area definition.

                leaf packet-length  {
                    type  yang:counter64;
                    description "Packet length errors.";
                } // END of packet-length definition.

                leaf authentication  {
                    type  yang:counter64;
                    description "Authentication errors.";
                } // END of authentication definition.

            } // END of errors-container definition.
            container traffic {
                config false;
                description
                    "Grouping for OSPF interface statistics traffic operational state data";
                leaf total-packets-in  {
                    type  yang:counter64;
                    description "Total number of packets received.";
                } // END of total-packets-in definition.

                leaf total-packets-out  {
                    type  yang:counter64;
                    description "Total number of packets sent.";
                } // END of total-packets-out definition.

                leaf hello-packets-in  {
                    type  yang:counter64;
                    description "Number of hello packets received.";
                } // END of hello-packets-in definition.

                leaf hello-packets-out  {
                    type  yang:counter64;
                    description "Number of hello packets sent.";
                } // END of hello-packets-out definition.

                leaf database-descriptor-packets-in  {
                    type  yang:counter64;
                    description "Number of database descriptor packets received.";
                } // END of database-descriptor-packets-in definition.

                leaf database-descriptor-packets-out  {
                    type  yang:counter64;
                    description "Number of database descriptor packets sent.";
                } // END of database-descriptor-packets-out definition.

                leaf ls-request-packets-in  {
                    type  yang:counter64;
                    description "Number of ls request packets received.";
                } // END of ls-request-packets-in definition.

                leaf ls-request-packets-out  {
                    type  yang:counter64;
                    description "Number of ls request packets sent.";
                } // END of ls-request-packets-out definition.

                leaf ls-update-packets-in  {
                    type  yang:counter64;
                    description "Number of ls update packets received.";
                } // END of ls-update-packets-in definition.

                leaf ls-update-packets-out  {
                    type  yang:counter64;
                    description "Number of ls update packets sent.";
                } // END of ls-update-packets-out definition.

                leaf ls-acknowledge-packets-in  {
                    type  yang:counter64;
                    description "Number of ls acknowledge packets received.";
                } // END of ls-acknowledge-packets-in definition.

                leaf ls-acknowledge-packets-out  {
                    type  yang:counter64;
                    description "Number of ls acknowledge packets sent.";
                } // END of ls-acknowledge-packets-out definition.

            } // END of traffic-container definition.
        } // END of statistics-container definition.
    } // END of ospfv2-statistic definition.
    grouping ospfv2-interface-address-timers {
        description
            "Grouping for OSPF interface address timers";
        container timers {
            description
                "OSPF interface address timers";
            container config {
                description
                    "Configuration data for OSPF interface address timers";
                uses ospfv2-interface-timers-config;
            } // END of config-container definition.
            container state {
                config false;
                description
                    "Operational state data for OSPF interface address timers";
                uses ospfv2-interface-timers-config;
            } // END of state-container definition.
        } // END of timers-container definition.
    } // END of ospfv2-interface-address-timers definition.
    grouping ospfv2-interface-states {
        description
            "Grouping for OSPF interface states operational state data";
        leaf interface-state  {
            type  int32;
            description "The interface operational state.";
        } // END of interface-state definition.

        leaf lsa-count  {
            type  int32;
            description "The interface lsa message count.";
        } // END of lsa-count definition.

        leaf lsa-checksum  {
            type  int32;
            description "The interface lsa checksum.";
        } // END of lsa-checksum definition.

        leaf interface-events  {
            type  int32;
            description "The interface state change events count.";
        } // END of interface-events definition.

        leaf addressless-interface  {
            type  int32;
            description "The value of interface index for interfaces with no IP address.";
        } // END of addressless-interface definition.

    } // END of ospfv2-interface-states definition.
    grouping ospfv2-interface-address-config {
        description
            "Grouping for OSPF interface address configuration data";
        leaf interface-address  {
            type  inet:ipv4-address;
            description "Use this attribute to set the interface address to configure the OSPF
                        parameters.";
        } // END of interface-address definition.

    } // END of ospfv2-interface-address-config definition.
    grouping ospfv2-interface-address {
        description
            "Grouping for OSPF interface address";
        container addresses {
            when " not(/ospfv2/global/config/area-interface-config-mode) ";
            description
                "OSPF interface addresses";

            list address {
            when " /ospfv2/interfaces/interface/addresses/address/config/cost  or /ospfv2/interfaces/interface/addresses/address/config/priority  or /ospfv2/interfaces/interface/addresses/address/config/mtu-ignore  or /ospfv2/interfaces/interface/addresses/address/database-filter  or /ospfv2/interfaces/interface/addresses/address/authentication  or /ospfv2/interfaces/interface/addresses/address/timers ";
                key "interface-address";
                description
                    "List of OSPF interface addresses";
                leaf interface-address  {
                    type  leafref {
                        path  "../config/interface-address";
                    }
                    description "Use this attribute to set the interface address to configure the OSPF
                                parameters.";
                } // END of interface-address definition.

                container config {
                    description
                        "Configuration data for OSPF interface address";
                    uses ospfv2-interface-address-config;
                    uses ospfv2-interface-config-common;
                } // END of config-container definition.
                container state {
                    config false;
                    description
                        "Operational state data for OSPF interface address";
                    uses ospfv2-interface-address-config;
                    uses ospfv2-interface-config-common;
                    uses ospfv2-designated-router-state;
                    uses ospfv2-backup-designated-router-state;
                    uses ospfv2-interface-timers-state;
                } // END of state-container definition.
                uses ospfv2-interface-authentication;
                uses ospfv2-interface-address-timers;
                uses ospfv2-database-filter;
            } // End of address-list
        } // END of addresses-container definition.
    } // END of ospfv2-interface-address definition.
    grouping ospfv2-interface-timers-state {
        description
            "Grouping for OSPF interface timers state";
        container timers {
            config false;
            description
                "OSPF interface timers state";
            container state {
                config false;
                description
                    "Operational state data for OSPF interface timers";
                leaf runtime-dead-interval  {
                    type  uint32;
                    description "Use this attribute to get the dead interval value.";
                } // END of runtime-dead-interval definition.

            } // END of state-container definition.
        } // END of timers-container definition.
    } // END of ospfv2-interface-timers-state definition.
    grouping ospfv2-interface-ldp-timers-config {
        description
            "Grouping for OSPF-LDP interface timers configuration data";
        leaf ldp-igp-sync-enable  {
            if-feature feature-list:HAVE_LDPD;
            type  empty;
            description "Use this attribute to enable the MPLS LDP IGP SYNC on OSPF.";
        } // END of ldp-igp-sync-enable definition.

        leaf holddown-timer  {
            when " /ospfv2/interfaces/interface/timers/config/ldp-igp-sync-enable ";
            if-feature feature-list:HAVE_LDPD;
            type  uint32 {
                 range "1..2147483"  {
                    description "1..2147483: Supported range 1 - 2147483";
                 }
            }
            units "seconds";
            default "70000";
            description "Use this attribute to configure the hold-down timer for which OSPF
                        will wait for LDP to converge and advertises Max cost.
                        When the configured time expires, OSPF starts advertising the actual
                        cost in the Router-LSA.";
        } // END of holddown-timer definition.

    } // END of ospfv2-interface-ldp-timers-config definition.
    grouping ospfv2-interface-timers-config {
        description
            "Grouping for OSPF interface timers configuration data";
        leaf dead-interval  {
            type  uint16 {
                 range "1..65535"  {
                    description "1..65535: Supported range 1 - 65535";
                 }
            }
            units "seconds";
            description "Use this attribute to set the interval during which the router waits
                        to receive an OSPF hello packet from the neighbor before declaring the
                        neighbor down.";
        } // END of dead-interval definition.

        leaf hello-interval  {
            type  uint16 {
                 range "1..65535"  {
                    description "1..65535: Supported range 1 - 65535";
                 }
            }
            units "seconds";
            default "10";
            description "Use this attribute to specify the interval between hello packets.";
        } // END of hello-interval definition.

        leaf transmit-delay  {
            type  uint16 {
                 range "1..3600"  {
                    description "1..3600: Supported range 1 - 3600";
                 }
            }
            units "seconds";
            default "1";
            description "Use this attribute to set the estimated time it takes to transmit a
                        link-state-update packet on the interface.";
        } // END of transmit-delay definition.

        leaf retransmission-interval  {
            type  uint16 {
                 range "1..3600"  {
                    description "1..3600: Supported range 1 - 3600";
                 }
            }
            units "seconds";
            default "5";
            description "Use this attribute to specify the time between link-state
                        advertisement (LSA) retransmissions for adjacencies belonging to the
                        interface.";
        } // END of retransmission-interval definition.

        leaf resync-timeout  {
            type  uint16 {
                 range "1..65535"  {
                    description "1..65535: Supported range 1 - 65535";
                 }
            }
            units "seconds";
            default "40";
            description "Use this attribute to configure the interval after which adjacency is
                        reset if oob-resync is not started.";
        } // END of resync-timeout definition.

    } // END of ospfv2-interface-timers-config definition.
    grouping ospfv2-interface-timers {
        description
            "Grouping for OSPF interface timers";
        container timers {
            description
                "OSPF interface timers";
            container config {
                description
                    "Configuration data for OSPF interface timers";
                uses ospfv2-interface-ldp-timers-config;
                uses ospfv2-interface-timers-config;
            } // END of config-container definition.
            container state {
                config false;
                description
                    "Operational state data for OSPF interface timers";
                uses ospfv2-interface-ldp-timers-config;
                uses ospfv2-interface-timers-config;
            } // END of state-container definition.
        } // END of timers-container definition.
    } // END of ospfv2-interface-timers definition.
    grouping ospfv2-database-filter-config {
        description
            "Grouping for OSPF interface database filter configuration data";
        leaf filter-out  {
            type  empty;
            description "Use this attribute to turn on the LSA database-filter for a particular
                        interface.
                        OSPF floods new LSAs over all interfaces in an area, except the
                        interface on which the LSA arrives. This redundancy ensures robust
                        flooding. However, too much redundancy can waste bandwidth and might
                        lead to excessive link and CPU usage in certain topologies, resulting
                        in destabilizing the network. To avoid this, use this attribute to
                        block flooding of LSAs over specified interfaces.";
        } // END of filter-out definition.

    } // END of ospfv2-database-filter-config definition.
    grouping ospfv2-database-filter {
        description
            "Grouping for OSPF interface database filter";
        container database-filter {
            description
                "OSPF interface database filter";
            container lsa {
                description
                    "LSA";
                container config {
                    description
                        "Configuration data for OSPF interface database filter";
                    uses ospfv2-database-filter-config;
                } // END of config-container definition.
                container state {
                    config false;
                    description
                        "Operational state data for OSPF interface database filter";
                    uses ospfv2-database-filter-config;
                } // END of state-container definition.
            } // END of lsa-container definition.
        } // END of database-filter-container definition.
    } // END of ospfv2-database-filter definition.
    grouping ospfv2-interface-authentication {
        description
            "Grouping for OSPF interface authentication";
        container authentication {
            when " not(/ospfv2/global/config/area-interface-config-mode) ";
            description
                "OSPF interface authentication";
            container config {
                description
                    "Configuration data for OSPF interface authentication";
                uses ospfv2-authentication-config;
            } // END of config-container definition.
            container state {
                config false;
                description
                    "Operational state data for OSPF interface authentication";
                uses ospfv2-authentication-config;
            } // END of state-container definition.
            uses ospfv2-authentication-message-digest-top;
        } // END of authentication-container definition.
    } // END of ospfv2-interface-authentication definition.
    grouping ospfv2-interface-config-common {
        description
            "Grouping for OSPF interface common configuration data";
        leaf cost  {
            type  uint16 {
                 range "1..65535"  {
                    description "1..65535: Supported range 1 - 65535";
                 }
            }
            default "10";
            description "Use this attribute to explicitly specify the cost of the link-state
                        metric in a router-LSA.";
        } // END of cost definition.

        leaf priority  {
            type  uint8 {
                 range "0..255"  {
                    description "0..255: Supported range 0 - 255";
                 }
            }
            default "1";
            description "Use this attribute to set the router priority to determine the
                        designated router (DR) for the network.";
        } // END of priority definition.

        leaf mtu-ignore  {
            type  empty;
            description "Use this attribute to configure OSPF so that it does not check the MTU
                        size during DD (Database Description) exchange.";
        } // END of mtu-ignore definition.

    } // END of ospfv2-interface-config-common definition.
    grouping ospfv2-interface-config {
        description
            "Grouping for OSPF interface configuration data";
        leaf name  {
            type  leafref {
                path  "/ipi-interface:interfaces/ipi-interface:interface/ipi-interface:name";
            }
            description "The interface name to configure the OSPF parameters.";
        } // END of name definition.

        leaf network-type  {
            when " not(/ospfv2/global/config/area-interface-config-mode) ";
            type  ipi-ospf-types:ospf_network_t;
            description "Use this attribute to set the interface network type.";
        } // END of network-type definition.

        leaf disable-all-ospf  {
            type  empty;
            description "Use this attribute to completely disable OSPF packet processing on an
                        interface.";
        } // END of disable-all-ospf definition.

        leaf traffic-engineering-metric  {
            if-feature feature-list:HAVE_OSPF_TE;
            type  uint16 {
                 range "1..65535"  {
                    description "1..65535: Supported range 1 - 65535";
                 }
            }
            description "Use this attribute to set the minimum delay in milliseconds between
                        accepting the same LSA from neighbors.";
        } // END of traffic-engineering-metric definition.

        leaf mtu  {
            type  uint16 {
                 range "576..65535"  {
                    description "576..65535: Supported range 576 - 65535";
                 }
            }
            default "576";
            description "Use this attribute to set MTU size for OSPF to construct packets based
                        on this value.";
        } // END of mtu definition.

        leaf enable-flood-reduction  {
            type  empty;
            description "Use this attribute to enable flood reduction on an interface.";
        } // END of enable-flood-reduction definition.

        leaf enable-demand-circuit  {
            if-feature feature-list:HAVE_OSPF_OD;
            if-feature feature-list:HAVE_OSPF_MULTI_INST;
            type  empty;
            description "Use this attribute to enable Hello Suppression and LSA Suppression
                        sent on OSPF interface.";
        } // END of enable-demand-circuit definition.

        leaf enable-bfd  {
            if-feature feature-list:HAVE_BFD;
            type  ipi-ospf-types:ospf_bfd_state;
            description "Use this attribute to enable Bidirectional Forwarding Detection (BFD).";
        } // END of enable-bfd definition.

        leaf disable-fast-reroute  {
            if-feature feature-list:HAVE_OSPF_LFA;
            type  empty;
            description "Use this attribute to prohibit the interface from being used as the
                        next hop in a repair path.";
        } // END of disable-fast-reroute definition.

    } // END of ospfv2-interface-config definition.
    grouping ospfv2-interface-config-error {
        description
            "ospfv2CMLSEPinterfaceCMLSEPconfigCMLSEPerror";
        container interface-config-error {
            config false;
            description
                "Interface configuration error";
            leaf router-id  {
                type  inet:ipv4-address;
                description "OSPF router ID.";
            } // END of router-id definition.

            leaf name  {
                type  string {
                    length "1..1965";
                    pattern "[^?' =,>|]+";
                }
                description "Interface name.";
            } // END of name definition.

            leaf interface-address  {
                type  inet:ipv4-address;
                description "Interface address.";
            } // END of interface-address definition.

            leaf address-less-interface  {
                type  uint32;
                description "Address less interface.";
            } // END of address-less-interface definition.

            leaf error-type  {
                type  ipi-ospf-types:ospf_config_error_type_t;
                description "Error type.";
            } // END of error-type definition.

            leaf packet-type  {
                type  ipi-ospf-types:ospf_packet_type_t;
                description "Packet type.";
            } // END of packet-type definition.

        } // END of interface-config-error-container definition.
    } // END of ospfv2-interface-config-error definition.
    grouping ospfv2-interface-link-state-change {
        description
            "ospfv2CMLSEPinterfaceCMLSEPlinkCMLSEPstateCMLSEPchange";
        container link-state-change {
            config false;
            description
                "Link state change";
            leaf router-id  {
                type  inet:ipv4-address;
                description "OSPF router ID.";
            } // END of router-id definition.

            leaf name  {
                type  string {
                    length "1..1965";
                    pattern "[^?' =,>|]+";
                }
                description "Interface name.";
            } // END of name definition.

            leaf interface-address  {
                type  inet:ipv4-address;
                description "Interface address.";
            } // END of interface-address definition.

            leaf address-less-interface  {
                type  uint32;
                description "Address less interface.";
            } // END of address-less-interface definition.

            leaf interface-state  {
                type  ipi-ospf-types:ospf_interface_state_t;
                description "Interface status.";
            } // END of interface-state definition.

        } // END of link-state-change-container definition.
    } // END of ospfv2-interface-link-state-change definition.
    grouping ospfv2-interface-rx-bad-backet {
        description
            "ospfv2CMLSEPinterfaceCMLSEPrxCMLSEPbadCMLSEPbacket";
        container rx-bad-packet {
            config false;
            description
                "Link state change";
            leaf router-id  {
                type  inet:ipv4-address;
                description "OSPF router ID.";
            } // END of router-id definition.

            leaf name  {
                type  string {
                    length "1..1965";
                    pattern "[^?' =,>|]+";
                }
                description "Interface name.";
            } // END of name definition.

            leaf interface-address  {
                type  inet:ipv4-address;
                description "Interface address.";
            } // END of interface-address definition.

            leaf address-less-interface  {
                type  uint32;
                description "Address less interface.";
            } // END of address-less-interface definition.

            leaf packet-src  {
                type  inet:ipv4-address;
                description "Source address.";
            } // END of packet-src definition.

            leaf packet-type  {
                type  ipi-ospf-types:ospf_packet_type_t;
                description "Packet type.";
            } // END of packet-type definition.

        } // END of rx-bad-packet-container definition.
    } // END of ospfv2-interface-rx-bad-backet definition.

    grouping  interfaces-grouping {
    description
        "OSPF interfaces";
    container interfaces {
        if-feature feature-list:HAVE_OSPFD;
        description
            "OSPF interfaces";

        list interface {
        // when " ipi-interface:interfaces/interface/config/enable-switchport != '1' ";
            key "name";
            description
                "List of OSPF interfaces";
            leaf name  {
                type  leafref {
                    path  "../config/name";
                }
                description "The interface name to configure the OSPF parameters.";
            } // END of name definition.

            container config {
                description
                    "Configuration data for OSPF interface";
                uses ospfv2-interface-config-common;
                uses ospfv2-interface-config;
            } // END of config-container definition.
            container state {
                config false;
                description
                    "Operational state data for OSPF interface";
                uses ospfv2-interface-config-common;
                uses ospfv2-interface-config;
                uses ospfv2-interface-link-state-change;
                uses ospfv2-interface-rx-bad-backet;
                uses ospfv2-interface-config-error;
            } // END of state-container definition.
            container interface-states {
                config false;
                description
                    "OSPF interface states";
                container state {
                    config false;
                    description
                        "Operational state data for OSPF interface states";
                    uses ospfv2-interface-states;
                } // END of state-container definition.
                uses ospfv2-statistic;
                uses ospfv2-designated-router-state;
                uses ospfv2-backup-designated-router-state;
                uses ospfv2-interface-timers-state;
            } // END of interface-states-container definition.
            uses ospfv2-interface-authentication;
            uses ospfv2-database-filter;
            uses ospfv2-interface-timers;
            uses ospfv2-interface-address;
        } // End of interface-list
    } // END of interfaces-container definition.
    } // END of interfaces-grouping definition.


}
