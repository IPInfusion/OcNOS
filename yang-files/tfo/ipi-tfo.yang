/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-tfo.yang
*
*/

module ipi-tfo {

    yang-version 1.1;

    namespace   "http://www.ipinfusion.com/yang/ocnos/ipi-tfo";

    prefix "ipi-tfo";

    import ipi-interface {
        prefix ipi-interface;
        revision-date 2022-08-24;
    }

    import cml-data-types {
        prefix cml-data-types;
        revision-date 2022-09-30;
    }

    import ipi-tfo-types {
        prefix ipi-tfo-types;
        revision-date 2022-06-01;
    }

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for TFO Configuration";


    revision "2022-07-18" {
        description "Added implicit_delele tag in tfo_groups containers";
        reference " 0.4.4.";
    }

    revision "2022-06-17" {
        description "Added implicit_delele tag in tfo config and tfo_groups containers";
        reference " 0.4.3.";
    }

    revision "2022-06-14" {
        description "link-type config is not deleting with tfo disable";
        reference " 0.4.2.";
    }

    revision "2022-06-08" {
        description "Added a dependent object for TFO to handel re-ordering of configuration";
        reference " 0.4.1.";
    }

    revision "2022-06-01" {
        description "Updated the yang file with feature";
        reference " 0.4.0.";
    }

    revision "2022-05-18" {
        description "link-type config getting removed while deleting fog type when global fog is disable";
        reference " 0.3.0.";
    }

    revision "2021-10-19" {
        description "TFO Configuration are not deleting after global tfo disable";
        reference " 0.2.0.";
    }

    revision "2021-07-28" {
        description "Initial Version";
        reference " 0.1.0.";
    }

    grouping trigger-failover-config {
        description
            "Grouping for trigger-failover config objects.";
        leaf admin-status  {
            type  cml-data-types:cml_enable_disable_t;
            description "Use this attribute to enable or disable trigger failover (TFO).TFO can
                        be enabled only if the bridge mode is STP or RSTP.";
        } // END of admin-status definition.

    } // END of trigger-failover-config definition.
    grouping trigger-failover-interface-config {
        description
            "Grouping for trigger-failover interface config objects.";
        leaf name  {
            type  leafref {
                path  "/ipi-interface:interfaces/ipi-interface:interface/ipi-interface:name";
            }
            description "Use this attribute to map links in a FOG.";
        } // END of name definition.

        leaf link-type  {
            type  ipi-tfo-types:tfo_fog_link_type_t;
            description "Use this attribute to make a port an uplink or downlink.";
        } // END of link-type definition.

    } // END of trigger-failover-interface-config definition.
    grouping trigger-failover-tfo-group-config {
        description
            "Grouping for trigger-failover interface config objects.";
        leaf group-id  {
            type  uint32 {
                 range "1..64"  {
                    description "1..64: Supported range 1 - 64";
                 }
            }
            description "Use this attribute to Create or delete a failover group (FOG) on
                        interface.";
        } // END of group-id definition.

        leaf group-type  {
            type  ipi-tfo-types:tfo_fog_group_type_t;
            mandatory true;
            description "Use this attribute to map upstream/downstream links in a FOG as a
                        Monitor Port Group (MPG) or Control Port Group (CPG).";
        } // END of group-type definition.

    } // END of trigger-failover-tfo-group-config definition.
    grouping trigger-failover-group-config {
        description
            "Grouping for trigger-failover group config objects.";
        leaf group-id  {
            type  uint32 {
                 range "1..64"  {
                    description "1..64: Supported range 1 - 64";
                 }
            }
            description "Use this attribute to Create or delete a failover group (FOG).";
        } // END of group-id definition.

        leaf admin-status  {
            type  cml-data-types:cml_enable_disable_t;
            mandatory true;
            description "FOG admin status";
        } // END of admin-status definition.

        leaf failover-trigger-count  {
            type  uint32 {
                 range "0..63"  {
                    description "0..63: Supported range 0 - 63";
                 }
            }
            description "Use this attribute to set the number of links to trigger failover for
                        a Monitor Port Groups (MPG).";
        } // END of failover-trigger-count definition.

    } // END of trigger-failover-group-config definition.
    grouping trigger-failover-group-state {
        description
            "Grouping for trigger-failover group operation state objects.";
        leaf cpg-disable-status  {
            type  boolean;
            config false;
            description "To track CPG status";
        } // END of cpg-disable-status definition.

        leaf mpg-disable-status  {
            type  boolean;
            config false;
            description "To track MPG status";
        } // END of mpg-disable-status definition.

    } // END of trigger-failover-group-state definition.
    grouping trigger-failover-group-counters {
        description
            "Grouping for trigger-failover group counters.";
        leaf mpg-link-failure-count  {
            type  uint64;
            config false;
            description "MPG Failure detection count";
        } // END of mpg-link-failure-count definition.

        leaf mpg-link-recover-count  {
            type  uint64;
            config false;
            description "MPG link recover count";
        } // END of mpg-link-recover-count definition.

        leaf cpg-auto-disable-count  {
            type  uint64;
            config false;
            description "CPG Auto Disable Count";
        } // END of cpg-auto-disable-count definition.

        leaf cpg-auto-enable-count  {
            type  uint64;
            config false;
            description "CPG auto enable count";
        } // END of cpg-auto-enable-count definition.

    } // END of trigger-failover-group-counters definition.

    grouping  trigger-failover-grouping {
    description
        "Top level container for Trigger Failover, including configuration and
                state data";
    container trigger-failover {
        if-feature feature-list:HAVE_TFO;
        description
            "Top level container for Trigger Failover, including configuration and
                    state data";
        container config {
            description
                "This container defines Trigger Failover configuration.";
            uses trigger-failover-config;
        } // END of config-container definition.
        container state {
            config false;
            description
                "This container defines hardware-profile Operational states.";
            uses trigger-failover-config;
        } // END of state-container definition.
        container interfaces {
            description
                "This container defines Trigger Failover Interfaces configuration and
                        state information.";

            list interface {
                key "name";
                description
                    "Objectlist will be list of strict interface. which will point MPG
                                links and CPG links";
                leaf name  {
                    type  leafref {
                        path  "../config/name";
                    }
                    description "Use this attribute to map links in a FOG.";
                } // END of name definition.

                container config {
                    description
                        "This container defines Trigger Failover Interface configuration.";
                    uses trigger-failover-interface-config;
                } // END of config-container definition.
                container state {
                    config false;
                    description
                        "This container defines Trigger Failover Interface Operational states.";
                    uses trigger-failover-interface-config;
                } // END of state-container definition.
                container tfo-groups {
                    description
                        "This container defines Trigger Failover Interfaces configuration and
                                state information.";

                    list tfo-group {
                    when " /ipi-tfo:trigger-failover/ipi-tfo:failover-groups/ipi-tfo:failover-group/ipi-tfo:config/ipi-tfo:admin-status ";
                        key "group-id";
                        description
                            "Objectlist will be list of strict interface. which will point MPG
                                        links and CPG links";
                        leaf group-id  {
                            type  leafref {
                                path  "../config/group-id";
                            }
                            description "Use this attribute to Create or delete a failover group (FOG) on
                                        interface.";
                        } // END of group-id definition.

                        container config {
                            description
                                "This container defines Trigger Failover Interface configuration.";
                            uses trigger-failover-tfo-group-config;
                        } // END of config-container definition.
                        container state {
                            config false;
                            description
                                "This container defines Trigger Failover Interface Operational states.";
                            uses trigger-failover-tfo-group-config;
                        } // END of state-container definition.
                    } // End of tfo-group-list
                } // END of tfo-groups-container definition.
            } // End of interface-list
        } // END of interfaces-container definition.
        container failover-groups {
            description
                "This container defines Trigger Failover Groups configuration and state
                        information.";

            list failover-group {
                key "group-id";
                description
                    "Objectlist will be list of Trigger Failover Groups.";
                leaf group-id  {
                    type  leafref {
                        path  "../config/group-id";
                    }
                    description "Use this attribute to Create or delete a failover group (FOG).";
                } // END of group-id definition.

                container config {
                    description
                        "This container defines Trigger Failover Group configuration.";
                    uses trigger-failover-group-config;
                } // END of config-container definition.
                container state {
                    config false;
                    description
                        "This container defines Trigger Failover Group Operational states.";
                    uses trigger-failover-group-config;
                    uses trigger-failover-group-state;
                } // END of state-container definition.
                container counters {
                    config false;
                    description
                        "This container defines Trigger Failover Group Operational Counters.";
                    uses trigger-failover-group-counters;
                } // END of counters-container definition.
            } // End of failover-group-list
        } // END of failover-groups-container definition.
    } // END of trigger-failover-container definition.
    } // END of trigger-failover-grouping definition.

    uses trigger-failover-grouping;

    rpc tfo-clear-counters-all {
        if-feature feature-list:HAVE_TFO;
        description "Use this attribute to clear the TFO counters.This command clears
                    counters for all FOG indexes.";
    }

    rpc tfo-clear-fog-counters {
        if-feature feature-list:HAVE_TFO;
        description "Use this attribute to clear the TFO counters.This command clears
                    counters for specified FOG indexes.";
        input  {
            leaf group-id  {
                type uint32 {
                    range "1..64";
                }
                mandatory true;
                description "Use this attribute for failover group (FOG) Id.";
            }
        }
    }

}
