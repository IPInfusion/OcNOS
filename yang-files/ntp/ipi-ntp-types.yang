/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-ntp-types.yang
*
*/

module ipi-ntp-types {

    yang-version 1.1;

    namespace   "http://www.ipinfusion.com/yang/ocnos/ipi-ntp-types";

    prefix "ipi-ntp-types";

    import ietf-inet-types {
        prefix inet;
        revision-date 2013-07-15;
    }

    organization
        "IP Infusion Inc.";

    contact
        "Address: 3965 Freedom Circle, Suite 200, Santa Clara, CA 95054
         Phone: +1 408-400-1900
         E-mail: support@ipinfusion.com
         Web: http://www.ipinfusion.com/";

    description
        "Datatypes for NTP data model";


    revision "2022-06-01" {
        description "Updated the yang file with feature";
        reference " 0.3.0.";
    }

    revision "2021-09-03" {
        description "Update descriptions of attribute";
        reference " 0.2.0.";
    }

    revision "2021-06-25" {
        description "Initial Version";
        reference " 0.1.0.";
    }



    typedef  ntp_client_ip_net_mask_t {
        type union {
            type inet:ipv4-address {

            }
            type uint8 {
                range "1..128";

            }
        }
        description "type definition for NTP_CLIENT_IP_NET_MASK_T";
    }

    typedef  ntp_acl_options_t {
        type bits {
            bit kod {
                position 0;
                description "Send a kiss-of-death packet if the client limit has exceeded";
            }
            bit nopeer {
                position 1;
                description "Prevent the client from establishing a peer association";
            }
            bit noserve {
                position 2;
                description "Prevent the client from performing time queries";
            }
            bit noquery {
                position 3;
                description "Prevent the client from performing ntpq and ntpdc queries, but not time queries";
            }
            bit nomodify {
                position 4;
                description "Restrict the client from making any changes to the NTP configurations";
            }
            bit notrap {
                position 5;
                description "Prevent the client from configuring control message traps";
            }
            bit limited {
                position 6;
                description "Deny time service if the packet violates the rate limits established by the discard command";
            }
        }
        description "type definition for NTP_ACL_OPTIONS_T";
    }

    typedef  ntp_statistics_type_t {
        type enumeration {
            enum all-peers {
                value 0;
                description "Clear per-peer statistics counter of all peers";
            }
            enum io {
                value 1;
                description "Clear input-output statistics";
            }
            enum local {
                value 2;
                description "Clear counters maintained by the local NTP";
            }
            enum memory {
                value 3;
                description "Clear statistics counters related to memory code";
            }
        }
        description "type definition for NTP_STATISTICS_TYPE_T";
    }

    typedef  ntp_hostp_key_type_t {
        type enumeration {
            enum 0 {
                value 0;
                description "To specify shared key in clear-text form";
            }
            enum 7 {
                value 1;
                description "To specify shared key in encrypted form";
            }
        }
        description "type definition for NTP_HOSTP_KEY_TYPE_T";
    }

}
