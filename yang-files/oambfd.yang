/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : oambfd.yang
*
*/

submodule oambfd {

    belongs-to  ZebOS { prefix ZebOS; }
    include interface;


    import cml_data_types {
        prefix cml_data_types;
    }

    import feature_list {
        prefix feature_list;
    }


    revision "2016-12-26" {
        description "Adding desc and ignore_doc changes.";
    }

    revision "2016-10-10" {
        description "Adding the new OAM-LPS DM.";
    }



    grouping bfd-grouping {
        list bfd {
                         if-feature feature_list:HAVE_BFD_MONO;

            description
                "BFD basic configurations";

            config true;
            key "bfdProcessId";

            
            leaf vrId  {
                type  cml_data_types:CML_INT32_T;  
            } // END of vrId definition.

            leaf bfdProcessId  {
                type  cml_data_types:CML_INT32_T;  
            } // END of bfdProcessId definition.

            leaf enGtsmProtection  {
                type  cml_data_types:CML_BFD_SESSION_STATE_T;  
                description "bfd gtsm";
            } // END of enGtsmProtection definition.

            leaf bfdNotfEn  {
                type  cml_data_types:CML_BFD_SESSION_STATE_T;  
                description "bfd notification ";
            } // END of bfdNotfEn definition.

            leaf isEchoSet  {
                type  cml_data_types:CML_BOOL_T;  
                description "bfd echo";
            } // END of isEchoSet definition.

            leaf gtsmTtl  {
                type  cml_data_types:CML_UINT8_T {
                     range "1..255";
                }
                default "255";
                description "bfd gtsm ttl";
            } // END of gtsmTtl definition.

            leaf bfdStartTime  {
                type  cml_data_types:CML_STRING_T {
                    length "0..255";
                }
                config false;
            } // END of bfdStartTime definition.

            leaf bfdSessionCount  {
                type  cml_data_types:CML_UINT32_T;  
                config false;
            } // END of bfdSessionCount definition.

            leaf bfdAdminState  {
                type  cml_data_types:CML_OAMBFD_ADMIN_STATE_T;  
                config false;
            } // END of bfdAdminState definition.

            leaf bfdImageType  {
                type  cml_data_types:CML_OAMBFD_IMAGE_TYPE_T;  
                config false;
            } // END of bfdImageType definition.

            leaf bfdLocalDisc  {
                type  cml_data_types:CML_UINT32_T;  
                config false;
            } // END of bfdLocalDisc definition.

            leaf slowTimerIntvl  {
                type  cml_data_types:CML_UINT32_T {
                     range "1000..30000";
                }
                default "2000";
                description "bfd slow-timer";
            } // END of slowTimerIntvl definition.


            list bfdSession {
                 
                description
                    "bfd Session table for runtime attrs";

                config false;
                key "bfdSessionIndex";

                
                leaf bfdSessionIndex  {
                    type  cml_data_types:CML_UINT32_T;  
                } // END of bfdSessionIndex definition.

                leaf bfdSessRemoteDisc  {
                    type  cml_data_types:CML_UINT32_T;  
                } // END of bfdSessRemoteDisc definition.

                leaf bfdLlType  {
                    type  cml_data_types:CML_OAMBFD_SESS_LOWER_LAYER_T;  
                } // END of bfdLlType definition.

                leaf bfdSessionType  {
                    type  cml_data_types:CML_OAMBFD_SESSION_TYPE_T;  
                } // END of bfdSessionType definition.

                leaf bfdSessionState  {
                    type  cml_data_types:CML_OAMBFD_SESSION_STATE_T;  
                } // END of bfdSessionState definition.

                leaf bfdSessionUptime  {
                    type  cml_data_types:CML_STRING_T {
                        length "0..255";
                    }
                } // END of bfdSessionUptime definition.

                leaf bfdRemoteAddr  {
                    type  cml_data_types:CML_STRING_T {
                        length "0..255";
                    }
                } // END of bfdRemoteAddr definition.

                leaf bfdSessIfIdx  {
                    type  cml_data_types:CML_UINT32_T;  
                } // END of bfdSessIfIdx definition.

                leaf bfdSessVersion  {
                    type  cml_data_types:CML_UINT32_T;  
                } // END of bfdSessVersion definition.

                leaf bfdSessLocDisc  {
                    type  cml_data_types:CML_UINT32_T;  
                } // END of bfdSessLocDisc definition.

                leaf bfdSessLocAddr  {
                    type  cml_data_types:CML_STRING_T {
                        length "0..255";
                    }
                } // END of bfdSessLocAddr definition.

                leaf bfdRemotePort  {
                    type  cml_data_types:CML_UINT32_T;  
                } // END of bfdRemotePort definition.

                leaf bfdLocalPort  {
                    type  cml_data_types:CML_UINT32_T;  
                } // END of bfdLocalPort definition.

                leaf bfdLocalEchoPort  {
                    type  cml_data_types:CML_UINT32_T;  
                } // END of bfdLocalEchoPort definition.

                leaf bfdMplsLspType  {
                    type  cml_data_types:CML_UINT32_T;  
                } // END of bfdMplsLspType definition.

                leaf bfdMplsTnlName  {
                    type  cml_data_types:CML_STRING_T {
                        length "0..255";
                    }
                } // END of bfdMplsTnlName definition.

                leaf bfdMplsFecAddr  {
                    type  cml_data_types:CML_STRING_T {
                        length "0..255";
                    }
                } // END of bfdMplsFecAddr definition.

                leaf bfdMplsLspPingItvl  {
                    type  cml_data_types:CML_UINT32_T;  
                } // END of bfdMplsLspPingItvl definition.

                leaf bfdMplsFtnIndx  {
                    type  cml_data_types:CML_UINT32_T;  
                } // END of bfdMplsFtnIndx definition.

                leaf bfdMplsMinTx  {
                    type  cml_data_types:CML_UINT32_T;  
                } // END of bfdMplsMinTx definition.

                leaf bfdMplsMinRx  {
                    type  cml_data_types:CML_UINT32_T;  
                } // END of bfdMplsMinRx definition.

                leaf bfdMplsMult  {
                    type  cml_data_types:CML_UINT32_T;  
                } // END of bfdMplsMult definition.

                leaf bfdMplsTnlLabel  {
                    type  cml_data_types:CML_UINT32_T;  
                } // END of bfdMplsTnlLabel definition.

                leaf bfdVccvVcId  {
                    type  cml_data_types:CML_UINT32_T;  
                } // END of bfdVccvVcId definition.

                leaf bfdVccvInVcLabel  {
                    type  cml_data_types:CML_UINT32_T;  
                } // END of bfdVccvInVcLabel definition.

                leaf bfdVccvOutVcLabel  {
                    type  cml_data_types:CML_UINT32_T;  
                } // END of bfdVccvOutVcLabel definition.

                leaf bfdVccvCcType  {
                    type  cml_data_types:CML_UINT32_T;  
                } // END of bfdVccvCcType definition.

                leaf bfdVccvCvType  {
                    type  cml_data_types:CML_UINT32_T;  
                } // END of bfdVccvCvType definition.

                leaf bfdVccvAcIx  {
                    type  cml_data_types:CML_UINT32_T;  
                } // END of bfdVccvAcIx definition.

                leaf bfdVccvTnlLabel  {
                    type  cml_data_types:CML_UINT32_T;  
                } // END of bfdVccvTnlLabel definition.

                leaf bfdVccvPeerAddr  {
                    type  cml_data_types:CML_UINT32_T;  
                } // END of bfdVccvPeerAddr definition.

                leaf bfdMplstpMegName  {
                    type  cml_data_types:CML_STRING_T {
                        length "0..255";
                    }
                } // END of bfdMplstpMegName definition.

                leaf bfdMplstpMeName  {
                    type  cml_data_types:CML_STRING_T {
                        length "0..255";
                    }
                } // END of bfdMplstpMeName definition.

                leaf bfdMplstpPathType  {
                    type  cml_data_types:CML_UINT8_T;  
                } // END of bfdMplstpPathType definition.

                leaf bfdSessOptionFlag  {
                    type  cml_data_types:CML_OAMBFD_SESSION_FLAGS_T;  
                } // END of bfdSessOptionFlag definition.

                leaf bfdSessPerfDiag  {
                    type  cml_data_types:CML_OAMBFD_PERFORM_DIAG_T;  
                } // END of bfdSessPerfDiag definition.

                leaf bfdSessMinTx  {
                    type  cml_data_types:CML_UINT32_T;  
                } // END of bfdSessMinTx definition.

                leaf bfdSessMinRx  {
                    type  cml_data_types:CML_UINT32_T;  
                } // END of bfdSessMinRx definition.

                leaf bfdSessMultplier  {
                    type  cml_data_types:CML_UINT32_T;  
                } // END of bfdSessMultplier definition.

                leaf bfdSessNegTx  {
                    type  cml_data_types:CML_UINT32_T;  
                } // END of bfdSessNegTx definition.

                leaf bfdSessNegRx  {
                    type  cml_data_types:CML_UINT32_T;  
                } // END of bfdSessNegRx definition.

                leaf bfdSessNegMultiplier  {
                    type  cml_data_types:CML_UINT32_T;  
                } // END of bfdSessNegMultiplier definition.

                leaf bfdSessEchoTx  {
                    type  cml_data_types:CML_UINT32_T;  
                } // END of bfdSessEchoTx definition.

                leaf bfdSessEchoRx  {
                    type  cml_data_types:CML_UINT32_T;  
                } // END of bfdSessEchoRx definition.

                leaf bfdSessEchoIntvl  {
                    type  cml_data_types:CML_UINT32_T;  
                } // END of bfdSessEchoIntvl definition.

                leaf bfdSessStorTye  {
                    type  cml_data_types:CML_UINT32_T;  
                } // END of bfdSessStorTye definition.

                leaf bfdSessDownTime  {
                    type  cml_data_types:CML_STRING_T {
                        length "0..255";
                    }
                } // END of bfdSessDownTime definition.

                leaf bfdSessDisconTime  {
                    type  cml_data_types:CML_STRING_T {
                        length "0..255";
                    }
                } // END of bfdSessDisconTime definition.

                leaf bfdSessAuthKeyId  {
                    type  cml_data_types:CML_UINT32_T;  
                } // END of bfdSessAuthKeyId definition.

                leaf bfdSessPktIn  {
                    type  cml_data_types:CML_STRING_T {
                        length "0..255";
                    }
                } // END of bfdSessPktIn definition.

                leaf bfdSessPktOut  {
                    type  cml_data_types:CML_STRING_T {
                        length "0..255";
                    }
                } // END of bfdSessPktOut definition.

                leaf bfdSessEchoOut  {
                    type  cml_data_types:CML_STRING_T {
                        length "0..255";
                    }
                } // END of bfdSessEchoOut definition.

                leaf bfdSessIpv6EchoOut  {
                    type  cml_data_types:CML_STRING_T {
                        length "0..255";
                    }
                } // END of bfdSessIpv6EchoOut definition.

                leaf bfdSessIpv6PktOut  {
                    type  cml_data_types:CML_STRING_T {
                        length "0..255";
                    }
                } // END of bfdSessIpv6PktOut definition.

                leaf bfdSessIpv6PktIn  {
                    type  cml_data_types:CML_STRING_T {
                        length "0..255";
                    }
                } // END of bfdSessIpv6PktIn definition.

                leaf bfdSessUpCount  {
                    type  cml_data_types:CML_UINT32_T;  
                } // END of bfdSessUpCount definition.

                leaf bfdSessUpTime  {
                    type  cml_data_types:CML_STRING_T {
                        length "0..255";
                    }
                } // END of bfdSessUpTime definition.

                leaf bfdSessHoldCntr  {
                    type  cml_data_types:CML_UINT32_T;  
                } // END of bfdSessHoldCntr definition.

                leaf bfdSessHoldDown  {
                    type  cml_data_types:CML_UINT32_T;  
                } // END of bfdSessHoldDown definition.

                leaf bfdSessFwdHelloCntr  {
                    type  cml_data_types:CML_UINT32_T;  
                } // END of bfdSessFwdHelloCntr definition.

                leaf bfdSessPktVersion  {
                    type  cml_data_types:CML_UINT32_T;  
                } // END of bfdSessPktVersion definition.

                leaf bfdSessPktDiag  {
                    type  cml_data_types:CML_UINT32_T;  
                } // END of bfdSessPktDiag definition.

                leaf bfdSessPktState  {
                    type  cml_data_types:CML_UINT32_T;  
                } // END of bfdSessPktState definition.

                leaf bfdSessPktDemandEn  {
                    type  cml_data_types:CML_UINT32_T;  
                } // END of bfdSessPktDemandEn definition.

                leaf bfdSessPktPollSeq  {
                    type  cml_data_types:CML_UINT32_T;  
                } // END of bfdSessPktPollSeq definition.

                leaf bfdSessPktFlagState  {
                    type  cml_data_types:CML_STRING_T {
                        length "0..255";
                    }
                } // END of bfdSessPktFlagState definition.

                leaf bfdSessPktMult  {
                    type  cml_data_types:CML_UINT32_T;  
                } // END of bfdSessPktMult definition.

                leaf bfdSessPktLength  {
                    type  cml_data_types:CML_UINT32_T;  
                } // END of bfdSessPktLength definition.

                leaf bfdSessPktMyDisc  {
                    type  cml_data_types:CML_UINT32_T;  
                } // END of bfdSessPktMyDisc definition.

                leaf bfdSessPktUrDisc  {
                    type  cml_data_types:CML_UINT32_T;  
                } // END of bfdSessPktUrDisc definition.

                leaf bfdSessPktMinTx  {
                    type  cml_data_types:CML_UINT32_T;  
                } // END of bfdSessPktMinTx definition.

                leaf bfdSessPktMinRx  {
                    type  cml_data_types:CML_UINT32_T;  
                } // END of bfdSessPktMinRx definition.

                leaf bfdSessPktMinEchoIntvl  {
                    type  cml_data_types:CML_UINT32_T;  
                } // END of bfdSessPktMinEchoIntvl definition.


                list bfdSessionClientInfo {
                     
                    description
                        "BFD session client Info";

                    config false;
                    key "bfdSessProtoClientId";

                    
                    leaf bfdSessProtoClientId  {
                        type  cml_data_types:CML_UINT32_T;  
                    } // END of bfdSessProtoClientId definition.

                    leaf bfdSessClientFlag  {
                        type  cml_data_types:CML_STRING_T {
                            length "0..255";
                        }
                    } // END of bfdSessClientFlag definition.

                } // End of bfdSessionClientInfo-list
            } // End of bfdSession-list

            list bfdMultihopKeyChain {
                 
                description
                    "BFD multihop peer configs";

                config true;
                key "bfdMultihopAddr";

                
                leaf bfdMultihopAddr  {
                    type  cml_data_types:CML_STRING_T {
                        length "0..255";
                    }
                } // END of bfdMultihopAddr definition.

                leaf bfdAuthType  {
                    type  cml_data_types:CML_BFD_MULTIHOP_AUTH_TYPE_T;  
                } // END of bfdAuthType definition.

                leaf bfdKeyChain  {
                    type  cml_data_types:CML_STRING_T {
                        length "0..255";
                    }
                } // END of bfdKeyChain definition.

                leaf bfdMultihopKeyId  {
                    type  cml_data_types:CML_UINT32_T {
                         range "0..255";
                    }
                } // END of bfdMultihopKeyId definition.

                leaf bfdKeyStr  {
                    type  cml_data_types:CML_STRING_T {
                        length "0..255";
                    }
                } // END of bfdKeyStr definition.

                leaf bfdTransmitIntvl  {
                    type  cml_data_types:CML_UINT32_T {
                         range "50..999";
                    }
                } // END of bfdTransmitIntvl definition.

                leaf bfdRecieveIntvl  {
                    type  cml_data_types:CML_UINT32_T {
                         range "50..999";
                    }
                } // END of bfdRecieveIntvl definition.

                leaf bfdHelloMultiplier  {
                    type  cml_data_types:CML_UINT32_T {
                         range "3..50";
                    }
                    default "3";
                    description "bfd interval ";
                } // END of bfdHelloMultiplier definition.

            } // End of bfdMultihopKeyChain-list
        } // End of bfd-list
    } // END of bfd-grouping definition.


    grouping bfdInterface-grouping {
        list bfdInterface {
             
            description
                "BFD interface related operations";

            config true;
            key "ifName";

            
            leaf ifName  {
                type  cml_data_types:CML_STRING_T {
                    length "0..255";
                }
            } // END of ifName definition.

            leaf vrId  {
                type  cml_data_types:CML_INT32_T;  
            } // END of vrId definition.

            leaf isBfdDisable  {
                type  cml_data_types:CML_BFD_SESSION_STATE_T;  
                description "bfd disable";
            } // END of isBfdDisable definition.

            leaf bfdIfTransmitIntvl  {
                type  cml_data_types:CML_UINT32_T {
                     range "50..999";
                }
            } // END of bfdIfTransmitIntvl definition.

            leaf bfdIfRecieveIntvl  {
                type  cml_data_types:CML_UINT32_T {
                     range "50..999";
                }
            } // END of bfdIfRecieveIntvl definition.

            leaf bfdIfHelloMultiplier  {
                type  cml_data_types:CML_UINT32_T {
                     range "3..50";
                }
                default "3";
                description "bfd interval";
            } // END of bfdIfHelloMultiplier definition.

            leaf bfdEchoInterval  {
                type  cml_data_types:CML_UINT32_T {
                     range "1..4294967";
                }
                description "bfd echo interval";
            } // END of bfdEchoInterval definition.

            leaf bfdIfSrcAddr  {
                type  cml_data_types:CML_STRING_T {
                    length "0..255";
                }
                description "echo ipv4 source";
            } // END of bfdIfSrcAddr definition.

            leaf bfdIfAuthType  {
                type  cml_data_types:CML_BFD_MULTIHOP_AUTH_TYPE_T;  
            } // END of bfdIfAuthType definition.

            leaf bfdIfKeyChain  {
                type  cml_data_types:CML_STRING_T {
                    length "0..255";
                }
                description "bfd multihop-peer A.B.C.D|X:X::X:X";
            } // END of bfdIfKeyChain definition.

            leaf bfdIfKeyId  {
                type  cml_data_types:CML_UINT32_T {
                     range "0..255";
                }
            } // END of bfdIfKeyId definition.

            leaf bfdIfKeyStr  {
                type  cml_data_types:CML_STRING_T {
                    length "0..255";
                }
                description "bfd multihop-peer";
            } // END of bfdIfKeyStr definition.

            leaf bfdIfIndex  {
                type  cml_data_types:CML_UINT32_T;  
                config false;
            } // END of bfdIfIndex definition.

            leaf bfdIfState  {
                type  cml_data_types:CML_STRING_T {
                    length "0..255";
                }
                config false;
            } // END of bfdIfState definition.


            list bfdIpv4UserIntfSessSrc {
                 
                description
                    "BFD ipv4 user intf src related configs";

                config true;
                key "bfdIpv4UserSrcAddr";

                
                leaf bfdIpv4UserSrcAddr  {
                    type  cml_data_types:CML_STRING_T {
                        length "0..255";
                    }
                } // END of bfdIpv4UserSrcAddr definition.


                list bfdIpv4UserIntfSessDest {
                     
                    description
                        "BFD ipv4 user intf dest related configs";

                    config true;
                    key "bfdIpv4UserDestAddr";

                    
                    leaf bfdIpv4UserDestAddr  {
                        type  cml_data_types:CML_STRING_T {
                            length "0..255";
                        }
                    } // END of bfdIpv4UserDestAddr definition.

                    leaf multihopIpv4  {
                        type  cml_data_types:CML_BOOL_T;  
                    } // END of multihopIpv4 definition.

                    leaf demandModeIpv4  {
                        type  cml_data_types:CML_BOOL_T;  
                    } // END of demandModeIpv4 definition.

                    leaf nonPersistantIpv4  {
                        type  cml_data_types:CML_BOOL_T;  
                    } // END of nonPersistantIpv4 definition.

                    leaf adminDownIpv4  {
                        type  cml_data_types:CML_BOOL_T;  
                        description "bfd session ";
                    } // END of adminDownIpv4 definition.

                } // End of bfdIpv4UserIntfSessDest-list
            } // End of bfdIpv4UserIntfSessSrc-list

            list bfdIpv6UserIntfSessSrc {
                 
                description
                    "BFD ipv6 user intf src related configs";

                config true;
                key "bfdIpv6UserSrcAddr";

                
                leaf bfdIpv6UserSrcAddr  {
                    type  cml_data_types:CML_STRING_T {
                        length "0..255";
                    }
                } // END of bfdIpv6UserSrcAddr definition.


                list bfdIpv6UserIntfSessDest {
                     
                    description
                        "BFD ipv6 user intf dest related configs";

                    config true;
                    key "bfdIpv6UserDestAddr";

                    
                    leaf bfdIpv6UserDestAddr  {
                        type  cml_data_types:CML_STRING_T {
                            length "0..255";
                        }
                    } // END of bfdIpv6UserDestAddr definition.

                    leaf multihopIpv6  {
                        type  cml_data_types:CML_BOOL_T;  
                    } // END of multihopIpv6 definition.

                    leaf demandModeIpv6  {
                        type  cml_data_types:CML_BOOL_T;  
                    } // END of demandModeIpv6 definition.

                    leaf nonPersistantIpv6  {
                        type  cml_data_types:CML_BOOL_T;  
                    } // END of nonPersistantIpv6 definition.

                    leaf adminDownIpv6  {
                        type  cml_data_types:CML_BOOL_T;  
                        description "bfd session";
                    } // END of adminDownIpv6 definition.

                } // End of bfdIpv6UserIntfSessDest-list
            } // End of bfdIpv6UserIntfSessSrc-list
        } // End of bfdInterface-list
    } // END of bfdInterface-grouping definition.


    grouping confModeDebug-grouping {
        list confModeDebug {
             
            description
                "config mode debug commands";

            config true;
            key "vrId";

            
            leaf vrId  {
                type  cml_data_types:CML_INT32_T;  
            } // END of vrId definition.

            leaf isConfDebugAll  {
                type  cml_data_types:CML_BOOL_T;  
            } // END of isConfDebugAll definition.

            leaf confModePackets  {
                type  cml_data_types:CML_BOOL_T;  
            } // END of confModePackets definition.

            leaf confModeEvents  {
                type  cml_data_types:CML_BOOL_T;  
            } // END of confModeEvents definition.

            leaf confModeIpcErr  {
                type  cml_data_types:CML_BOOL_T;  
            } // END of confModeIpcErr definition.

            leaf confModeIpcEvent  {
                type  cml_data_types:CML_BOOL_T;  
            } // END of confModeIpcEvent definition.

            leaf confModeSession  {
                type  cml_data_types:CML_BOOL_T;  
            } // END of confModeSession definition.

            leaf confModeNsm  {
                type  cml_data_types:CML_BOOL_T;  
            } // END of confModeNsm definition.

        } // End of confModeDebug-list
    } // END of confModeDebug-grouping definition.


    grouping execModeDebug-grouping {
        list execModeDebug {
             
            description
                "exec mode debug commands";

            config true;
            key "vrId";

            
            leaf vrId  {
                type  cml_data_types:CML_INT32_T;  
            } // END of vrId definition.

            leaf isExecDebugAll  {
                type  cml_data_types:CML_BOOL_T;  
            } // END of isExecDebugAll definition.

            leaf execModePackets  {
                type  cml_data_types:CML_BOOL_T;  
            } // END of execModePackets definition.

            leaf execModeEvents  {
                type  cml_data_types:CML_BOOL_T;  
            } // END of execModeEvents definition.

            leaf execModeIpcErr  {
                type  cml_data_types:CML_BOOL_T;  
            } // END of execModeIpcErr definition.

            leaf execModeIpcEvent  {
                type  cml_data_types:CML_BOOL_T;  
            } // END of execModeIpcEvent definition.

            leaf execModeSession  {
                type  cml_data_types:CML_BOOL_T;  
            } // END of execModeSession definition.

            leaf execModeNsm  {
                type  cml_data_types:CML_BOOL_T;  
            } // END of execModeNsm definition.

        } // End of execModeDebug-list
    } // END of execModeDebug-grouping definition.

    grouping  oamMpls-grouping {
    container oamMpls {
                config true;

        description
            "Oam mpls configs";

        leaf mplsPingReq  {
            if-feature feature_list:HAVE_MPLS_OAM;
            type  cml_data_types:CML_BOOL_T;  
            description "mpls ping request dsmap tlv";
        } // END of mplsPingReq definition.

        leaf mplsPingReply  {
            if-feature feature_list:HAVE_MPLS_OAM;
            type  cml_data_types:CML_BOOL_T;  
            description "mpls ping reply tlv";
        } // END of mplsPingReply definition.

    } // END of oamMpls-container definition.
    } // END of oamMpls-container definition.


}
