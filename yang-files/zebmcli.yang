/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebmcli.yang
*
*/



module zebmcli {
    namespace "http://ipinfusion.com/ns/zebmcli";

    prefix zebmcli;

    import cml_data_types {
        prefix cml_data_types;
    }

    revision "2015-10-15" {
        description "initial version: revisied on 2015-10-15.";}

    rpc rollback-transaction {

        input {
            leaf savepointName {
                type cml_data_types:CML_STRING_T;
                mandatory true;
            }
        }
    }

    rpc create-savepoint {

        input {
            leaf savepointName {
                type cml_data_types:CML_STRING_T;
                mandatory true;
            }
        }
    }

    rpc delete-savepoint {

        input {
            leaf savepointName {
                type cml_data_types:CML_STRING_T;
                mandatory true;
            }
        }
    }

    rpc set-transaction-limit {

        input {
            leaf transaction-limit {
                type cml_data_types:CML_UINT32_T;
                mandatory true;
            }
        }
    }

    rpc show-savepoint {
        output {
            leaf-list savepoint {
                type cml_data_types:CML_STRING_T;
            }
        }
    }

    rpc show-transaction-limit {
        output {
            leaf transaction-limit {
                type cml_data_types:CML_STRING_T;
            }
        }
    }

}
