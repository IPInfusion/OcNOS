/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : lag.yang
*
*/

submodule lag {

    belongs-to  ZebOS { prefix ZebOS; }
    include interface;


    import cml_data_types {
        prefix cml_data_types;
    }

    import feature_list {
        prefix feature_list;
    }

    description
        "Layer-2 lacp  configurations";


    revision "2015-10-21" {
        description "Initial version of datamodel.";
    }



    grouping lacpInterface-grouping {
        list lacpInterface {
             
            description
                "LACP interface related operations";

            config true;
            key "ifName";

            
            leaf ifName  {
                type  cml_data_types:CML_STRING_T {
                    length "0..255";
                }
            } // END of ifName definition.

            leaf portPriority  {
                type  cml_data_types:CML_UINT32_T {
                     range "1..65535";
                }
                default "32768";
            } // END of portPriority definition.

            leaf TimeOut  {
                type  cml_data_types:CML_LACP_TIMEOUT_T;  
                default "long";
            } // END of TimeOut definition.

            leaf bridgeType  {
                type  cml_data_types:CML_LACP_BRIDGETYPE_T;  
                default "multicast-group-address";
            } // END of bridgeType definition.

            leaf discardConv  {
                if-feature feature_list:HAVE_LACPV2;
                type  cml_data_types:CML_LACP_DISCARD_CONV_T;  
                default "disable";
            } // END of discardConv definition.

        } // End of lacpInterface-list
    } // END of lacpInterface-grouping definition.

    grouping  lacpSystemPriority-grouping {
    container lacpSystemPriority {
                config true;

        description
            "lacpSystemPriority";

        leaf systemPriority  {
            type  cml_data_types:CML_UINT32_T {
                 range "1..65535";
            }
            default "32768";
        } // END of systemPriority definition.

    } // END of lacpSystemPriority-container definition.
    } // END of lacpSystemPriority-container definition.

    grouping  lacpdebug-grouping {
    container lacpdebug {
                config true;

        description
            "lacpdebug";

        leaf debugLacp  {
            type  cml_data_types:CML_LACP_DEBUG_TYPE_T;  
        } // END of debugLacp definition.

    } // END of lacpdebug-container definition.
    } // END of lacpdebug-container definition.


}
