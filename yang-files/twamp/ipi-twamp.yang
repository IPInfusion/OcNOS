/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-twamp.yang
*
*/

module ipi-twamp {

    yang-version 1.1;

    namespace   "http://www.ipinfusion.com/yang/ocnos/ipi-twamp";

    prefix "ipi-twamp";

    import cml-data-types {
        prefix cml-data-types;
        revision-date 2022-09-30;
    }

    import ietf-yang-types {
        prefix yang;
        revision-date 2013-07-15;
    }

    import ipi-twamp-types {
        prefix ipi-twamp-types;
        revision-date 2022-07-05;
    }

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "Two-Way Active Measurement Protocol (TWAMP)";


    revision "2022-07-08" {
        description "Increased the test-session max-elements from 8 to 64";
        reference " 0.7.0.";
    }

    revision "2022-07-05" {
        description "Changed the data type for the reflector source UDP port";
        reference " 0.6.0.";
    }

    revision "2022-06-01" {
        description "Updated the yang file with feature";
        reference " 0.5.0.";
    }

    revision "2022-03-17" {
        description "Added sender ip and port in reflector session";
        reference " 0.4.0.";
    }

    revision "2022-01-31" {
        description "Added VRF name handling for both test-session and reflector";
        reference " 0.3.0.";
    }

    revision "2022-01-28" {
        description "Introduced Multiple Reflector Session";
        reference " 0.2.0.";
    }

    revision "2021-09-10" {
        description "Restructured module in accordance with OpenConfig style";
        reference " 0.1.0.";
    }

    revision "2020-02-20" {
        description "Initial Version";
        reference "Initial Version";
    }

    grouping twamp-session-reflector-config {
        description
            "Grouping for TWAMP Light Session Reflector configuration data";
        leaf enable  {
            type  empty;
            mandatory true;
            description "Enables TWAMP Light Session Reflector";
        } // END of enable definition.

        leaf administrative-state  {
            type  cml-data-types:cml_enable_disable_t;
            default "disable";
            description "Sets TWAMP Light Session Reflector administrative state";
        } // END of administrative-state definition.

    } // END of twamp-session-reflector-config definition.
    grouping twamp-session-reflector-address-top {
        description
            "TWAMP session reflector address grouping";
        container sessions {
            description
                "TWAMP reflector sessions";

            list session {
            when " /ipi-twamp:twamp/ipi-twamp:light/ipi-twamp:session-reflector/ipi-twamp:config/ipi-twamp:enable ";
                key "name";
                description
                    "List of TWAMP Light Reflector sessions";
                leaf name  {
                    type  leafref {
                        path  "../config/name";
                    }
                    description "Sets Reflector Session Name";
                } // END of name definition.

                container config {
                    description
                        "Configuration data for TWAMP Light Session Reflector Ip address";
                    uses twamp-session-reflector-address-config;
                } // END of config-container definition.
                container state {
                    config false;
                    description
                        "operational state data for TWAMP Light Session Reflector IP address";
                    uses twamp-session-reflector-address-config;
                } // END of state-container definition.
            } // End of session-list
        } // END of sessions-container definition.
    } // END of twamp-session-reflector-address-top definition.
    grouping twamp-session-reflector-address-config {
        description
            "Grouping for TWAMP Light Session Reflector configuration data";
        leaf name  {
            type  string {
                length "1..128";
                pattern "[^?' =,>|]+";
            }
            description "Sets Reflector Session Name";
        } // END of name definition.

        leaf reflector-ip-address  {
            type  ipi-twamp-types:twamp_hostname_t;
            mandatory true;
            description "Set TWAMP Reflector Session IP address";
        } // END of reflector-ip-address definition.

        leaf reflector-udp-port  {
            type  ipi-twamp-types:twamp_udp_port_t;
            mandatory true;
            description "Use this attribute to set Reflector UDP Port";
        } // END of reflector-udp-port definition.

        leaf sender-ip-address  {
            type  ipi-twamp-types:twamp_hostname_t;
            description "Set TWAMP Reflector Session sender IP address";
        } // END of sender-ip-address definition.

        leaf sender-udp-port  {
            type  ipi-twamp-types:twamp_ref_src_udp_port_t;
            description "Use this attribute to set the sender UDP Port";
        } // END of sender-udp-port definition.

        leaf vrf-name  {
            type  string {
                length "1..1965";
                pattern "[^?' =,>|]+";
            }
            mandatory true;
            description "Use this attribute to set the Reflector VRF name";
        } // END of vrf-name definition.

    } // END of twamp-session-reflector-address-config definition.
    grouping twamp-session-reflector-top {
        description
            "Grouping for TWAMP Session Reflector";
        container session-reflector {
            description
                "Configuration data for TWAMP Light Session Reflector";
            container config {
                presence "yes";
                description
                    "Configuration data for TWAMP Light Session Reflector";
                uses twamp-session-reflector-config;
            } // END of config-container definition.
            container state {
                config false;
                description
                    "operational state data for TWAMP Light Reflector Session";
                uses twamp-session-reflector-config;
            } // END of state-container definition.
            uses twamp-session-reflector-address-top;
        } // END of session-reflector-container definition.
    } // END of twamp-session-reflector-top definition.
    grouping twamp-control-test-session-statistics-common {
        description
            "Grouping for TWAMP Light Test Session Statistics common operational
                        state data. When attribute is not present, it might indicate that the
                        clock is not in sync between Sender and Reflector";
        leaf minimum  {
            type  uint64;
            units "microseconds";
            description "This attribute represents the minimum value within the statistics";
        } // END of minimum definition.

        leaf maximum  {
            type  uint64;
            units "microseconds";
            description "This attribute represents the maximum value within the statistics";
        } // END of maximum definition.

        leaf average  {
            type  uint64;
            units "microseconds";
            description "This attribute represents the average value within the statistics";
        } // END of average definition.

    } // END of twamp-control-test-session-statistics-common definition.
    grouping twamp-control-test-session-statistics-round-trip-delay {
        description
            "Grouping for Test Session Statistics Round-trip Delay operational
                        state data";
        container round-trip-delay {
            config false;
            description
                "Test Session Statistics Round-trip Delay";
            uses twamp-control-test-session-statistics-common;
        } // END of round-trip-delay-container definition.
    } // END of twamp-control-test-session-statistics-round-trip-delay definition.
    grouping twamp-control-test-session-statistics-forward-delay {
        description
            "Grouping for Test Session Statistics Forward Delay operational state
                        data";
        container forward-delay {
            config false;
            description
                "Test Session Statistics Forward Delay";
            uses twamp-control-test-session-statistics-common;
        } // END of forward-delay-container definition.
    } // END of twamp-control-test-session-statistics-forward-delay definition.
    grouping twamp-control-test-session-statistics-reverse-delay {
        description
            "Grouping for Test Session Statistics Reverse Delay operational state
                        data";
        container reverse-delay {
            config false;
            description
                "Test Session Statistics Reverse Delay";
            uses twamp-control-test-session-statistics-common;
        } // END of reverse-delay-container definition.
    } // END of twamp-control-test-session-statistics-reverse-delay definition.
    grouping twamp-control-test-session-statistics-round-trip-delay-variation {
        description
            "Grouping for Test Session Statistics Round-trip Delay Variation
                        operational state data";
        container round-trip-delay-variation {
            config false;
            description
                "Test Session Statistics Round-trip Delay Variation";
            uses twamp-control-test-session-statistics-common;
        } // END of round-trip-delay-variation-container definition.
    } // END of twamp-control-test-session-statistics-round-trip-delay-variation definition.
    grouping twamp-control-test-session-statistics-forward-delay-variation {
        description
            "Grouping for Test Session Statistics Forward Delay Variation
                        operational state data";
        container forward-delay-variation {
            config false;
            description
                "Test Session Statistics Forward Delay Variation";
            uses twamp-control-test-session-statistics-common;
        } // END of forward-delay-variation-container definition.
    } // END of twamp-control-test-session-statistics-forward-delay-variation definition.
    grouping twamp-control-test-session-statistics-reverse-delay-variation {
        description
            "Grouping for Test Session Statistics Reverse Delay Variation
                        operational state data";
        container reverse-delay-variation {
            config false;
            description
                "Test Session Statistics Reverse Delay Variation";
            uses twamp-control-test-session-statistics-common;
        } // END of reverse-delay-variation-container definition.
    } // END of twamp-control-test-session-statistics-reverse-delay-variation definition.
    grouping twamp-control-test-session-statistics-state {
        description
            "Grouping for TWAMP Light Control Test Session statistics operational
                        state data";
        container statistics {
            config false;
            description
                "Operational state data for TWAMP Light Control Test Session statistics";
            leaf packets-sent  {
                type  yang:counter64;
                description "This attribute represents the amount of sent packets for a Test
                            Session";
            } // END of packets-sent definition.

            leaf packets-received  {
                type  yang:counter64;
                description "This attribute represents the amount of received packets for a Test
                            Session";
            } // END of packets-received definition.

            leaf packet-loss  {
                type  decimal64 {
                     fraction-digits 4;                }
                description "This attribute represents the amount of lost packets for a Test
                            Session";
            } // END of packet-loss definition.

            uses twamp-control-test-session-statistics-round-trip-delay;
            uses twamp-control-test-session-statistics-forward-delay;
            uses twamp-control-test-session-statistics-reverse-delay;
            uses twamp-control-test-session-statistics-round-trip-delay-variation;
            uses twamp-control-test-session-statistics-forward-delay-variation;
            uses twamp-control-test-session-statistics-reverse-delay-variation;
        } // END of statistics-container definition.
    } // END of twamp-control-test-session-statistics-state definition.
    grouping twamp-control-test-session-state {
        description
            "Grouping for TWAMP Light Control Test Session operational state data";
        leaf start-time  {
            type  yang:date-and-time {
                pattern "\\d{4}-\\d{2}-\\d{2}T\\d{2}:\\d{2}:\\d{2}(\\.\\d+)?(Z|[\\+\\-]\\d{2}:\\d{2})";
                }
                description "This attribute represents the start time of a Test Session";
            } // END of start-time definition.

            leaf elapsed-time  {
                type  uint32;
                units "milliseconds";
                description "This attribute represents the elapsed time of a Test Session";
            } // END of elapsed-time definition.

        uses twamp-control-test-session-statistics-state;
    } // END of twamp-control-test-session-state definition.
    grouping twamp-control-test-session-config {
        description
            "Grouping for TWAMP Light Control Test Session configuration data";
        leaf session-name  {
            type  string {
                length "1..128";
                pattern "[^?' =,>|]+";
            }
            description "Use this attribute to set test session name";
        } // END of session-name definition.

        leaf sender-ip-address  {
            type  ipi-twamp-types:twamp_hostname_t;
            mandatory true;
            description "Use this attribute to set test session sender IP address";
        } // END of sender-ip-address definition.

        leaf sender-udp-port  {
            when " /ipi-twamp:twamp/ipi-twamp:light/ipi-twamp:control/ipi-twamp:test-sessions/ipi-twamp:test-session/ipi-twamp:config/ipi-twamp:sender-ip-address ";
            type  ipi-twamp-types:twamp_udp_port_t;
            mandatory true;
            description "Use this attribute to set test session sender UDP port";
        } // END of sender-udp-port definition.

        leaf reflector-ip-address  {
            type  ipi-twamp-types:twamp_hostname_t;
            mandatory true;
            description "Use this attribute to set test session reflector IP address";
        } // END of reflector-ip-address definition.

        leaf reflector-udp-port  {
            when " /ipi-twamp:twamp/ipi-twamp:light/ipi-twamp:control/ipi-twamp:test-sessions/ipi-twamp:test-session/ipi-twamp:config/ipi-twamp:reflector-ip-address ";
            type  ipi-twamp-types:twamp_udp_port_t;
            mandatory true;
            description "Use this attribute to set test session reflector UDP port";
        } // END of reflector-udp-port definition.

        leaf dscp-value  {
            type  ipi-twamp-types:twamp_dscp_t;
            description "Use this attribute to set test session DSCP value";
        } // END of dscp-value definition.

        leaf vrf-name  {
            type  string {
                length "1..1965";
                pattern "[^?' =,>|]+";
            }
            mandatory true;
            description "Use this attribute to set the session VRF name";
        } // END of vrf-name definition.

    } // END of twamp-control-test-session-config definition.
    grouping twamp-control-test-sessions-top {
        description
            "Grouping for TWAMP Control Test Sessions";
        container test-sessions {
            description
                "Container for TWAMP Light Control Test Sessions list";

            list test-session {
            when " /ipi-twamp:twamp/ipi-twamp:light/ipi-twamp:control/ipi-twamp:config/ipi-twamp:enable ";
                key "session-name";
                max-elements 64;
                description
                    "List of TWAMP Light Control Test Session";
                leaf session-name  {
                    type  leafref {
                        path  "../config/session-name";
                    }
                    description "Test Session name associated with this instance";
                } // END of session-name definition.

                container config {
                    description
                        "Configuration data for TWAMP Light Control Test Session";
                    uses twamp-control-test-session-config;
                } // END of config-container definition.
                container state {
                    config false;
                    description
                        "Operational state data for TWAMP Light Control Test Session";
                    uses twamp-control-test-session-config;
                    uses twamp-control-test-session-state;
                } // END of state-container definition.
            } // End of test-session-list
        } // END of test-sessions-container definition.
    } // END of twamp-control-test-sessions-top definition.
    grouping twamp-control-config {
        description
            "Grouping for TWAMP Light Control configuration data";
        leaf enable  {
            type  empty;
            mandatory true;
            description "Enables TWAMP Light Control";
        } // END of enable definition.

        leaf administrative-state  {
            type  cml-data-types:cml_enable_disable_t;
            default "disable";
            description "Sets TWAMP Light Control administrative state";
        } // END of administrative-state definition.

    } // END of twamp-control-config definition.
    grouping twamp-control-top {
        description
            "Grouping for TWAMP Light Control";
        container control {
            description
                "TWAMP Light Control";
            container config {
                presence "yes";
                description
                    "Configuration data for TWAMP Light Control";
                uses twamp-control-config;
            } // END of config-container definition.
            container state {
                config false;
                description
                    "Operational state data for TWAMP Light Control";
                uses twamp-control-config;
            } // END of state-container definition.
            uses twamp-control-test-sessions-top;
        } // END of control-container definition.
    } // END of twamp-control-top definition.
    grouping twamp-light-top {
        description
            "twampCMLSEPlightCMLSEPtop";
        container light {
            description
                "TWAMP Light implementation";
            uses twamp-control-top;
            uses twamp-session-reflector-top;
        } // END of light-container definition.
    } // END of twamp-light-top definition.
    grouping twamp-debug-config {
        description
            "Grouping for debug configuration for TWAMP";
        leaf debug-options  {
            type  ipi-twamp-types:twamp_debug_t;
            description "Use this attribute to debug the twamp session";
        } // END of debug-options definition.

    } // END of twamp-debug-config definition.
    grouping twamp-debug-terminal-state {
        description
            "Grouping for terminal debug operational state";
        leaf twamp-debug-status  {
            type  ipi-twamp-types:twamp_debug_t;
            description "Terminal debug option";
        } // END of twamp-debug-status definition.

    } // END of twamp-debug-terminal-state definition.
    grouping twamp-debug-top {
        description
            "Grouping for debug top";
        container debug {
            description
                "Debug Flags";
            container config {
                description
                    "Debug flags for configuration";
                uses twamp-debug-config;
            } // END of config-container definition.
            container state {
                config false;
                description
                    "Debug flags state information";
                container terminal-debug {
                    config false;
                    description
                        "Terminal debug operational state";
                    uses twamp-debug-terminal-state;
                } // END of terminal-debug-container definition.
                uses twamp-debug-config;
            } // END of state-container definition.
        } // END of debug-container definition.
    } // END of twamp-debug-top definition.

    grouping  twamp-grouping {
    description
        "Two-Way Active Measurement Protocol (TWAMP) data model";
    container twamp {
        if-feature feature-list:HAVE_TWAMP;
        description
            "Two-Way Active Measurement Protocol (TWAMP) data model";
        uses twamp-light-top;
        uses twamp-debug-top;
    } // END of twamp-container definition.
    } // END of twamp-grouping definition.

    uses twamp-grouping;

    rpc twamp-test-session-start {
        if-feature feature-list:HAVE_TWAMP;
        description "Start TWAMP Light Control Test Session";
        input  {
            leaf session-name  {
                type string {
                    length "1..128";
                }
                mandatory true;
                description "Test Session name";
            }
            leaf packet-count  {
                type uint16 {
                    range "1..65535";
                }
                mandatory true;
                description "Number of packets to send";
            }
            leaf packet-interval  {
                type uint16 {
                    range "500..10000";
                }
                default "1000";
                description "Interval between each packet";
            }
        }
    }

    rpc twamp-test-session-stop {
        if-feature feature-list:HAVE_TWAMP;
        description "Stop TWAMP Light Control Test Session";
        input  {
            leaf session-name  {
                type string {
                    length "1..128";
                }
                mandatory true;
                description "Test Session name";
            }
        }
    }

    rpc twamp-terminal-debug-on {
        if-feature feature-list:HAVE_TWAMP;
        description "Enable TWAMP debug categories";
        input  {
            leaf twamp-debug-status  {
                type ipi-twamp-types:twamp_debug_t;
                mandatory true;
                description "Two-may Active Measurement Protocol TWAMP debug categories";
            }
        }
    }

    rpc twamp-terminal-debug-off {
        if-feature feature-list:HAVE_TWAMP;
        description "Enable TWAMP debug categories";
        input  {
            leaf twamp-debug-status  {
                type ipi-twamp-types:twamp_debug_t;
                mandatory true;
                description "Two-may Active Measurement Protocol TWAMP debug categories";
            }
        }
    }

}
