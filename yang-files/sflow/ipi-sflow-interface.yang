/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-sflow-interface.yang
*
*/

module ipi-sflow-interface {

    yang-version 1.1;

    namespace   "http://www.ipinfusion.com/yang/ocnos/ipi-sflow-interface";

    prefix "ipi-sflow-interface";

    import ipi-sflow {
        prefix ipi-sflow;
        revision-date 2022-09-30;
    }

    import ipi-sflow-types {
        prefix ipi-sflow-types;
        revision-date 2022-06-01;
    }

    import ipi-interface {
        prefix ipi-interface;
        revision-date 2022-08-24;
    }

    import ietf-yang-types {
        prefix yang;
        revision-date 2013-07-15;
    }

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "This module provides user with the possibility to configure sflow
                interface parameters";


    revision "2022-06-01" {
        description "Updated the yang file with feature";
        reference " 0.2.0.";
    }

    revision "2021-07-30" {
        description "sFlow restructured";
        reference "Initial Version";
    }

    grouping sflow-interface-egress-state {
        description
            "sflowCMLSEPinterfaceCMLSEPegressCMLSEPstate";
        leaf sampling-status  {
            type  ipi-sflow-types:sflow_egress_ingress_t;
            description "Egress status";
        } // END of sampling-status definition.

        leaf sampled-packet-count  {
            type  yang:counter32;
            description "Retrieved from SFLOWSampler";
        } // END of sampled-packet-count definition.

    } // END of sflow-interface-egress-state definition.
    grouping sflow-interface-egress-config {
        description
            "sflowCMLSEPinterfaceCMLSEPegressCMLSEPconfig";
        leaf sampling-rate  {
            type  uint32 {
                 range "1024..16777215"  {
                    description "1024..16777215: Supported range 1024 - 16777215";
                 }
            }
            mandatory true;
            description "The statistical sampling rate for packet sampling from this source Set
                        to N to sample 1/Nth of the packets in the monitored flows.An agent
                        should choose its own algorithm to introduce variance into the
                        sampling so that exactly every Nth packet is not counted. A sampling
                        rateof 1 counts all packets. A sampling rate of 0 disables
                        sampling.The agent is permitted to have minimum and maximum allowable
                        values for the sampling rate. A minimum rate lets the agent designer
                        set an upper bound on the overhead associated with sampling, and a
                        maximum rate may be the result of hardware restrictions (such as
                        counter size). In addition not all values between the maximum and
                        minimum may be realizable as the sampling rate (again because of
                        implementation considerations).When the sampling rate is set the agent
                        is free to adjust the value so that it lies between the maximum and
                        minimum values and has the closest achievable value.When read, the
                        agent must return the actual sampling rate it will be using (after the
                        adjustments previously described). The sampling algorithm must
                        converge so that over time the number of packets sampled approaches
                        1/Nth of the total number of packets in the monitored flows.";
        } // END of sampling-rate definition.

        leaf sample-size  {
            type  uint16 {
                 range "16..256"  {
                    description "16..256: Supported range 16 - 256";
                 }
            }
            mandatory true;
            description "The maximum number of bytes that should be copied from a sampled
                        packet. The agent may have an internal maximum and minimum permissible
                        sizes. If an attempt is made to set this value outside the permissible
                        range then the agent should adjust the value to the closest
                        permissible value.";
        } // END of sample-size definition.

    } // END of sflow-interface-egress-config definition.
    grouping sflow-interface-egress-top {
        description
            "sflowCMLSEPinterfaceCMLSEPegressCMLSEPtop";
        container egress {
            description
                "sFlow egress configuration data";
            container config {
                presence "yes";
                description
                    "Configuration data for interface sFlow egress";
                uses sflow-interface-egress-config;
            } // END of config-container definition.
            container state {
                config false;
                description
                    "Operational state data for for interface sFlow egress";
                uses sflow-interface-egress-config;
                uses sflow-interface-egress-state;
            } // END of state-container definition.
        } // END of egress-container definition.
    } // END of sflow-interface-egress-top definition.
    grouping sflow-interface-ingress-state {
        description
            "sflowCMLSEPinterfaceCMLSEPingressCMLSEPstate";
        leaf sampling-status  {
            type  ipi-sflow-types:sflow_egress_ingress_t;
            description "Sampling ingress status";
        } // END of sampling-status definition.

        leaf sampled-packet-count  {
            type  yang:counter32;
            description "Retrieved from SFLOWSampler";
        } // END of sampled-packet-count definition.

    } // END of sflow-interface-ingress-state definition.
    grouping sflow-interface-ingress-config {
        description
            "sflowCMLSEPinterfaceCMLSEPingressCMLSEPconfig";
        leaf sampling-rate  {
            type  uint32 {
                 range "1024..16777215"  {
                    description "1024..16777215: Supported range 1024 - 16777215";
                 }
            }
            mandatory true;
            description "The statistical sampling rate for packet sampling from this source.
                        Set to N to sample 1/Nth of the packets in the monitored flows.An
                        agent should choose its own algorithm to introduce variance into the
                        sampling so that exactly every Nth packet is not counted. A sampling
                        rateof 1 counts all packets. A sampling rate of 0 disables
                        sampling.The agent is permitted to have minimum and maximum allowable
                        values for the sampling rate. A minimum rate lets the agent designer
                        set an upper bound on the overhead associated with sampling, and a
                        maximum rate may be the result of hardware restrictions (such as
                        counter size). In addition not all values between the maximum and
                        minimum may be realizable as the sampling rate (again because of
                        implementation considerations).When the sampling rate is set the agent
                        is free to adjust the value so that it lies between the maximum and
                        minimum values and has the closest achievable value.When read, the
                        agent must return the actual sampling rate it will be using (after the
                        adjustments previously described). The sampling algorithm must
                        converge so that over time the number of packets sampled approaches
                        1/Nth of the total number of packets in the monitored flows.";
        } // END of sampling-rate definition.

        leaf sample-size  {
            type  uint16 {
                 range "16..256"  {
                    description "16..256: Supported range 16 - 256";
                 }
            }
            mandatory true;
            description "The maximum number of bytes that should be copied from a sampled
                        packet. The agent may have an internal maximum and minimum permissible
                        sizes. If an attempt is made to set this value outside the permissible
                        range then the agent should adjust the value to the closest
                        permissible value.";
        } // END of sample-size definition.

    } // END of sflow-interface-ingress-config definition.
    grouping sflow-interface-ingress-top {
        description
            "sflowCMLSEPinterfaceCMLSEPingressCMLSEPtop";
        container ingress {
            description
                "sFlow ingress configuration data";
            container config {
                presence "yes";
                description
                    "Configuration data for interface sFlow ingress";
                uses sflow-interface-ingress-config;
            } // END of config-container definition.
            container state {
                config false;
                description
                    "Operational state data for interface sFlow ingress";
                uses sflow-interface-ingress-config;
                uses sflow-interface-ingress-state;
            } // END of state-container definition.
        } // END of ingress-container definition.
    } // END of sflow-interface-ingress-top definition.
    grouping sflow-interface-state {
        description
            "sflowCMLSEPinterfaceCMLSEPstate";
        leaf polling-count  {
            type  yang:counter32;
            description "Retrieved from SFLOWPoller";
        } // END of polling-count definition.

        leaf hw-sampling-rate-limit  {
            if-feature feature-list:HAVE_UT;
            if-feature feature-list:HAVE_MARVELL;
            type  uint32;
            description "hw configured sampling rate";
        } // END of hw-sampling-rate-limit definition.

        leaf sampled-packet-count  {
            if-feature feature-list:HAVE_UT;
            if-feature feature-list:HAVE_MARVELL;
            type  yang:counter32;
            description "packet sampled count in the hw";
        } // END of sampled-packet-count definition.

        leaf countdown-count  {
            if-feature feature-list:HAVE_UT;
            if-feature feature-list:HAVE_MARVELL;
            type  yang:counter32;
            description "packet count down information";
        } // END of countdown-count definition.

    } // END of sflow-interface-state definition.
    grouping sflow-interface-config {
        description
            "Grouping for sFlow configuration on interface";
        leaf name  {
            type  leafref {
                path  "/ipi-interface:interfaces/ipi-interface:interface/ipi-interface:name";
            }
            description "Interface name for which sFlow is being configured";
        } // END of name definition.

        leaf enabled  {
            when " /ipi-sflow:sampling/ipi-sflow:sflow/ipi-sflow-interface:interfaces/ipi-sflow-interface:interface/ipi-sflow-interface:ingress/ipi-sflow-interface:config/ipi-sflow-interface:sampling-rate  or /ipi-sflow:sampling/ipi-sflow:sflow/ipi-sflow-interface:interfaces/ipi-sflow-interface:interface/ipi-sflow-interface:egress/ipi-sflow-interface:config/ipi-sflow-interface:sampling-rate ";
            type  empty;
            description "To enable or disable sampling on an interface after giving the sflow
                        sampling-rate command on the same interface";
        } // END of enabled definition.

        leaf polling-interval  {
            type  uint8 {
                 range "5..60"  {
                    description "5..60: Supported range 5 - 60";
                 }
            }
            description "The maximum number of seconds between successive samples of the
                        counters associated with this data source. A sampling interval of 0
                        disables counter sampling.The agent is permitted to have minimum and
                        maximum allowable values for the counter polling interval. A minimum
                        interval lets the agent designer set an upper bound on the overhead
                        associated with polling, anda maximum interval may be the result of
                        implementation restrictions (such as counter size).In addition notall
                        values between the maximum and minimum may be realizable as the
                        sampling interval (again because of implementation
                        considerations).When the sampling rate is set the agent is free to
                        adjust the value so that it lies between the maximum and minimum
                        values and has the closest achievable value.When read, the agent must
                        return the actual sampling interval it will be using (after the
                        adjustments previously described).The sampling algorithm must converge
                        so that over time the number of packets sampledapproaches 1/Nth of the
                        total number of packets in the monitored flows.";
        } // END of polling-interval definition.

    } // END of sflow-interface-config definition.

    grouping  interfaces-grouping {
    description
        "Configuration data for interface sFlow";
    container interfaces {
        if-feature feature-list:HAVE_SFLOW;
        description
            "Configuration data for interface sFlow";

        list interface {
            key "name";
            description
                "Configuration data list for interface sFlow";
            leaf name  {
                type  leafref {
                    path  "../config/name";
                }
                description "Interface name for which sFlow is being configured";
            } // END of name definition.

            container config {
                description
                    "Configuration data for interface sFlow";
                uses sflow-interface-config;
            } // END of config-container definition.
            container state {
                config false;
                description
                    "Operational state data for interface sFlow";
                uses sflow-interface-config;
                uses sflow-interface-state;
            } // END of state-container definition.
            uses sflow-interface-ingress-top;
            uses sflow-interface-egress-top;
        } // End of interface-list
    } // END of interfaces-container definition.
    } // END of interfaces-grouping definition.

    augment /ipi-sflow:sampling/ipi-sflow:sflow {
    when " /ipi-sflow:sampling/ipi-sflow:sflow/ipi-sflow:config/ipi-sflow:enabled ";
        if-feature feature-list:HAVE_SFLOW;
        description
            "Configuration data for interface sFlow";
        uses interfaces-grouping;
    }


    rpc sflow-clear-statistics {
        if-feature feature-list:HAVE_SFLOW;
        description "Use to clear all sFlow statistics from a specific interface";
        input  {
            leaf interface  {
                type string;
                mandatory true;
                description "Interface name for which sFlow statistics will be cleaned";
            }
        }
    }

}
