/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : auth.yang
*
*/

submodule auth {

    belongs-to  ZebOS { prefix ZebOS; }
    include interface;


    import cml_data_types {
        prefix cml_data_types;
    }

    import feature_list {
        prefix feature_list;
    }

    description
        "auth configurations";


    revision "2017-02-20" {
        description "Fixed rollback issue(JIRA-13609).";
    }

    revision "2017-02-10" {
        description "Initial version of AUTHD datamodel.";
    }



    grouping authPort-grouping {
        list authPort {
             
            description
                "AUTH interface related operations";

            config true;
            key "ifName";

            
            leaf ifName  {
                type  cml_data_types:CML_STRING_T {
                    length "0..255";
                }
            } // END of ifName definition.

            leaf dot1xinitialize  {
                type  cml_data_types:CML_BOOL_T;  
            } // END of dot1xinitialize definition.

            leaf authmacPortControl  {
                if-feature feature_list:HAVE_MAC_AUTH;
                type  cml_data_types:CML_ENABLE_DISABLE_T;  
            } // END of authmacPortControl definition.

            leaf authmacPortMode  {
                if-feature feature_list:HAVE_MAC_AUTH;
                type  cml_data_types:CML_AUTH_PORT_SEC_MODE;  
                default "shutdown";
            } // END of authmacPortMode definition.

            leaf RestrictVlan  {
                if-feature feature_list:HAVE_MAC_AUTH;
                type  cml_data_types:CML_UINT32_T {
                     range "2..4094";
                }
            } // END of RestrictVlan definition.

            leaf DropTraffic  {
                if-feature feature_list:HAVE_MAC_AUTH;
                type  cml_data_types:CML_BOOL_T;  
                default true;
            } // END of DropTraffic definition.

            leaf dynamicVlanCreation  {
                if-feature feature_list:HAVE_MAC_AUTH;
                type  cml_data_types:CML_ENABLE_DISABLE_T;  
                default "disable";
            } // END of dynamicVlanCreation definition.

            leaf macAddressAging  {
                if-feature feature_list:HAVE_MAC_AUTH;
                type  cml_data_types:CML_ENABLE_DISABLE_T;  
                default "enable";
            } // END of macAddressAging definition.

            leaf protocolVersion  {
                type  cml_data_types:CML_UINT32_T {
                     range "1..2";
                }
                default "2";
            } // END of protocolVersion definition.

            leaf portCtrl  {
                type  cml_data_types:CML_AUTH_PORT_CTRL;  
                default "force-authorized";
            } // END of portCtrl definition.

            container authCtrlDir {
                                config true;

                description
                    "authCtrlDir";

                leaf adminControlledDirections  {
                    type  cml_data_types:CML_AUTH_CTRL_DIR_T;  
                } // END of adminControlledDirections definition.

            } // END of authCtrlDir-container definition.
            container authPae {
                                config true;

                description
                    "Authenticator PAE state machine";

                leaf quietPeriod  {
                    type  cml_data_types:CML_UINT32_T {
                         range "1..65535";
                    }
                    default "60";
                } // END of quietPeriod definition.

                leaf reauthMax  {
                    type  cml_data_types:CML_UINT32_T {
                         range "1..10";
                    }
                    default "2";
                } // END of reauthMax definition.

                leaf txPeriod  {
                    type  cml_data_types:CML_UINT32_T {
                         range "1..65535";
                    }
                    default "30";
                } // END of txPeriod definition.

            } // END of authPae-container definition.
            container reauthTimer {
                                config true;

                description
                    "Reauthentication Timer state machine";

                leaf reAuthPeriod  {
                    type  cml_data_types:CML_UINT32_T {
                         range "1..4294967295";
                    }
                    default "3600";
                } // END of reAuthPeriod definition.

                leaf reAuthEnabled  {
                    type  cml_data_types:CML_BOOL_T;  
                } // END of reAuthEnabled definition.

            } // END of reauthTimer-container definition.
            container authBe {
                                config true;

                description
                    "authenticator be state machine";

                leaf suppTimeout  {
                    type  cml_data_types:CML_UINT32_T {
                         range "1..65535";
                    }
                    default "30";
                } // END of suppTimeout definition.

                leaf serverTimeout  {
                    type  cml_data_types:CML_UINT32_T {
                         range "1..65535";
                    }
                    default "30";
                } // END of serverTimeout definition.

            } // END of authBe-container definition.
            container authKeyXmit {
                                config true;

                description
                    "Authenticator Key Transmit State Machine";

                leaf keyTxEnabled  {
                    type  cml_data_types:CML_BOOL_T;  
                } // END of keyTxEnabled definition.

            } // END of authKeyXmit-container definition.
        } // End of authPort-list
    } // END of authPort-grouping definition.

    grouping  authmac-grouping {
    container authmac {
                config true;

        description
            "authmac";

        leaf systemAuthCtrl  {
            type  cml_data_types:CML_BOOL_T;  
        } // END of systemAuthCtrl definition.

        leaf portControl  {
            type  cml_data_types:CML_BOOL_T;  
        } // END of portControl definition.

        leaf initialize  {
            type  cml_data_types:CML_STRING_T {
                length "0..255";
            }
        } // END of initialize definition.

        leaf reauthenticate  {
            type  cml_data_types:CML_STRING_T {
                length "0..255";
            }
        } // END of reauthenticate definition.

    } // END of authmac-container definition.
    } // END of authmac-container definition.

    grouping  debugdot1x-grouping {
    container debugdot1x {
                config true;

        description
            "debugdot1x";

        leaf debugtermFlag  {
            type  cml_data_types:CML_DOT1X_DEBUG_T;  
        } // END of debugtermFlag definition.

        leaf debugconfFlag  {
            type  cml_data_types:CML_DOT1X_DEBUG_T;  
        } // END of debugconfFlag definition.

    } // END of debugdot1x-container definition.
    } // END of debugdot1x-container definition.


}
