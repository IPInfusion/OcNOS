/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : keychain.yang
*
*/

submodule keychain {

    belongs-to  ZebOS { prefix ZebOS; }


    import cml_data_types {
        prefix cml_data_types;
    }

    description
        "keychain configurations";


    revision "2016-10-24" {
        description "Updated key chain mode commands.";
    }

    revision "2016-09-16" {
        description "Initial version of key-chain commands.";
    }

    revision "2016-02-03" {
        description "Added utils function for encryption cases.";
    }



    grouping keychain-grouping {
        list keychain {
             
            description
                "keychain";

            config true;
            key "key-chain";

            
            leaf vrId  {
                type  cml_data_types:CML_UINT32_T;  
                default "0";
                description "Virtual Router ID";
            } // END of vrId definition.

            leaf key-chain  {
                type  cml_data_types:CML_STRING_T {
                    length "0..255";
                }
                description "key chain";
            } // END of key-chain definition.


            list keyId {
                 
                description
                    "keyId";

                config true;
                key "key";

                
                leaf key  {
                    type  cml_data_types:CML_UINT32_T {
                         range "0..2147483647";
                    }
                    description "key";
                } // END of key definition.

                leaf keyString  {
                    type  cml_data_types:CML_STRING_T {
                        length "1..80";
                    }
                    description "key-string";
                } // END of keyString definition.


                list accept {
                     
                    description
                        "accept-time commands";

                    config true;
                    key "accepttime";

                    
                    leaf accepttime  {
                        type  cml_data_types:CML_ACCEPT_LIFETIME_T;  
                    } // END of accepttime definition.

                    uses keyLifetime;
                } // End of accept-list

                list send {
                     
                    description
                        "accept-time commands";

                    config true;
                    key "sendtime";

                    
                    leaf sendtime  {
                        type  cml_data_types:CML_SEND_LIFETIME_T;  
                    } // END of sendtime definition.

                    uses keyLifetime;
                } // End of send-list
            } // End of keyId-list
        } // End of keychain-list
    } // END of keychain-grouping definition.
    grouping keyLifetime {
                leaf starttime  {
            type  cml_data_types:CML_STRING_T {
                length "0..255";
            }
        } // END of starttime definition.

        leaf startday  {
            type  cml_data_types:CML_UINT8_T {
                 range "1..31";
            }
        } // END of startday definition.

        leaf startmonth  {
            type  cml_data_types:CML_STRING_T {
                length "0..255";
            }
        } // END of startmonth definition.

        leaf startyear  {
            type  cml_data_types:CML_INT32_T {
                 range "1993..2035";
            }
        } // END of startyear definition.

        leaf endtime  {
            type  cml_data_types:CML_STRING_T {
                length "0..255";
            }
        } // END of endtime definition.

        leaf endday  {
            type  cml_data_types:CML_UINT8_T {
                 range "1..31";
            }
        } // END of endday definition.

        leaf endmonth  {
            type  cml_data_types:CML_STRING_T {
                length "0..255";
            }
        } // END of endmonth definition.

        leaf endyear  {
            type  cml_data_types:CML_INT32_T {
                 range "1993..2035";
            }
        } // END of endyear definition.

        leaf infinite  {
            type  cml_data_types:CML_BOOL_T;  
        } // END of infinite definition.

        leaf duration  {
            type  cml_data_types:CML_UINT32_T {
                 range "1..2147483646";
            }
        } // END of duration definition.

    } // END of keyLifetime definition.


}
