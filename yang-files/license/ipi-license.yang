/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-license.yang
*
*/

module ipi-license {

    yang-version 1.1;

    namespace   "http://www.ipinfusion.com/yang/ocnos/ipi-license";

    prefix "ipi-license";

    import ipi-license-types {
        prefix ipi-license-types;
        revision-date 2022-06-01;
    }

    import ipi-network-instance {
        prefix ipi-network-instance;
        revision-date 2022-06-01;
    }

    import ietf-inet-types {
        prefix inet;
        revision-date 2013-07-15;
    }

    import ipi-vrf {
        prefix ipi-vrf;
        revision-date 2022-07-13;
    }

    import cml-data-types {
        prefix cml-data-types;
        revision-date 2022-09-30;
    }

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "license module allows use to manage license configurations in the
                device";


    revision "2022-09-30" {
        description "Import cml-data-types used by notifications";
        reference " 0.5.0.";
    }

    revision "2022-06-01" {
        description "Updated the yang file with feature";
        reference " 0.4.0.";
    }

    revision "2021-08-23" {
        description "Using Epoch value for service-end-date attribute";
        reference " 0.3.0.";
    }

    revision "2021-07-30" {
        description "Module attributes Restructured";
        reference " 0.2.0.";
    }

    revision "2018-06-21" {
        description "Initial Version";
        reference " 0.1.0.";
    }

    grouping license-info-state {
        description
            "licenseCMLSEPinfoCMLSEPstate";
        leaf slot-count  {
            type  uint32;
            description "license slot count";
        } // END of slot-count definition.

        leaf status  {
            type  ipi-license-types:license_status_type_t;
            description "license status";
        } // END of status definition.

        leaf msg  {
            type  string {
                length "1..1965";
            }
            description "license log message for all clients";
        } // END of msg definition.

        leaf service-end-date  {
            type  uint64;
            description "The Unix Epoch value. It represents the license end date. Zero if it
                        does not expire";
        } // END of service-end-date definition.

        leaf remaining-days  {
            type  int32;
            description "remaining days to license expiry or remaining lease";
        } // END of remaining-days definition.

        leaf device-software  {
            type  string {
                length "1..1965";
                pattern "[^?' =,>|]+";
            }
            description "Device software";
        } // END of device-software definition.

        leaf node-id  {
            type  string {
                length "1..1965";
                pattern "[^?' =,>|]+";
            }
            description "Node id";
        } // END of node-id definition.

        leaf validity  {
            type  ipi-license-types:license_validity_type_t;
            description "Validity of license";
        } // END of validity definition.

        leaf type  {
            type  ipi-license-types:license_type_t;
            description "License Type";
        } // END of type definition.

    } // END of license-info-state definition.
    grouping license-info-top {
        description
            "licenseCMLSEPinfoCMLSEPtop";
        container info {
            description
                "Container that holds license information";
            container state {
                config false;
                description
                    "Operational state data for license information";
                uses license-info-state;
            } // END of state-container definition.
        } // END of info-container definition.
    } // END of license-info-top definition.
    grouping license-server-config {
        description
            "licenseCMLSEPserverCMLSEPconfig";
        leaf url  {
            type  inet:uri;
            mandatory true;
            description "Server pool URL used";
        } // END of url definition.

        leaf vrf  {
            when " /ipi-license:license/ipi-license:server/ipi-license:config/ipi-license:url ";
            type  leafref {
                path  "/ipi-network-instance:network-instances/ipi-network-instance:network-instance/ipi-vrf:vrf/ipi-vrf:config/ipi-vrf:vrf-name";
            }
            mandatory true;
            description "VRF name for which the server can be reached";
        } // END of vrf definition.

    } // END of license-server-config definition.
    grouping license-server-top {
        description
            "licenseCMLSEPserverCMLSEPtop";
        container server {
            description
                "Container that stores all info about license servers";
            container config {
                presence "yes";
                description
                    "Configuration data for license server";
                uses license-server-config;
            } // END of config-container definition.
            container state {
                config false;
                description
                    "Operational state data for license server";
                uses license-server-config;
            } // END of state-container definition.
        } // END of server-container definition.
    } // END of license-server-top definition.

    grouping  license-grouping {
    description
        "Container for all data related to licenses";
    container license {
        if-feature feature-list:HAVE_FLEXLM;
        description
            "Container for all data related to licenses";
        uses license-server-top;
        uses license-info-top;
    } // END of license-container definition.
    } // END of license-grouping definition.

    uses license-grouping;

    rpc license-get {
        if-feature feature-list:HAVE_FLEXLM;
        description "Use this attribute to fetch the license for this device from a network
                    path or a USB mount path.This attribute validates the license against
                    the device identifier.";
        input  {
            leaf source-interface  {
                type string;
                mandatory true;
                description "Source interface name to be used to reach url";
            }
            leaf url  {
                type inet:uri;
                mandatory true;
                description "The URL to be reached to get license";
            }
        }
    }

    rpc license-refresh {
        if-feature feature-list:HAVE_FLEXLM;
        description "This attribute is used to refresh the license file";
        input  {
            leaf license-file  {
                type string;
                description "License filename present in the device or downloaded earlier";
            }
        }
    }

    rpc license-get-pool {
        if-feature feature-list:HAVE_FLEXLM;
        description "Use this rpc to fetch the license from license server";
        input  {
            leaf url  {
                type inet:uri;
                mandatory true;
                description "Server pool URL used";
            }
            leaf vrf  {
                type string;
                mandatory true;
                description "VRF name for which the server can be reached";
            }
        }
    }

    rpc license-release {
        if-feature feature-list:HAVE_FLEXLM;
        description "Use this rpc to remove license present on device, and release license
                    aquired from license server";
    }

    notification license-log-message {
        if-feature feature-list:HAVE_FLEXLM;

        description "license messages to all northbound.";

        leaf severity {
            type cml-data-types:cml_notif_severity_t;
            description "Notification severity level";
        }

        leaf eventClass {
            type cml-data-types:cml_notif_class_t;
            description "Notification event class (value: STATE)";
        }

        leaf msg {
            type  string;
        description
            "license log message for all clients";
        }
    }

    notification license-status {
        if-feature feature-list:HAVE_FLEXLM;

        description "license success or failure.";

        leaf severity {
            type cml-data-types:cml_notif_severity_t;
            description "Notification severity level";
        }

        leaf eventClass {
            type cml-data-types:cml_notif_class_t;
            description "Notification event class (value: STATE)";
        }

        leaf status {
            type ipi-license-types:license_status_type_t;
        description
            "license status";
        }
    }

    notification license-remaining-days {
        if-feature feature-list:HAVE_FLEXLM;

        description "license remaining days.";

        leaf severity {
            type cml-data-types:cml_notif_severity_t;
            description "Notification severity level";
        }

        leaf eventClass {
            type cml-data-types:cml_notif_class_t;
            description "Notification event class (value: STATE)";
        }

        leaf remaining-days {
            type  int32;
        description
            "remaining days to license expiry or remaining lease";
        }
    }

}
