/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-license-types.yang
*
*/

module ipi-license-types {

    yang-version 1.1;

    namespace   "http://www.ipinfusion.com/yang/ocnos/ipi-license-types";

    prefix "ipi-license-types";

    organization
        "IP Infusion Inc.";

    contact
        "Address: 3965 Freedom Circle, Suite 200, Santa Clara, CA 95054
         Phone: +1 408-400-1900
         E-mail: support@ipinfusion.com
         Web: http://www.ipinfusion.com/";

    description
        "ipi-license datatypes";


    revision "2022-06-01" {
        description "Updated the yang file with feature";
        reference " 0.2.0.";
    }

    revision "2021-07-30" {
        description "Initial Version";
        reference "Initial Version";
    }



    typedef  license_status_type_t {
        type enumeration {
            enum Success {
                value 0;
                description "Specifies that current license status is Success";
            }
            enum Failure {
                value 1;
                description "Specifies that current license status is Failure";
            }
        }
        description "type definition for LICENSE_STATUS_TYPE_T";
    }

    typedef  license_validity_type_t {
        type enumeration {
            enum Not-Applicable {
                value 0;
                description "Specifies that validity is not applicable for license";
            }
            enum Permanent {
                value 1;
                description "Specifies that validity is permanent for license";
            }
            enum Expired {
                value 2;
                description "Specifies that validity is expired for license";
            }
        }
        description "type definition for LICENSE_VALIDITY_TYPE_T";
    }

    typedef  license_type_t {
        type enumeration {
            enum Evaluation-Limited-edition {
                value 0;
                description "Specifies that license is of type evaluation/limited-edition";
            }
            enum Device-Locked-Full-edition {
                value 1;
                description "Specifies that license is of type device-locked/full-edition";
            }
            enum Trial-edition {
                value 2;
                description "Specifies that license is of type trial-edition";
            }
            enum Lease-Full-edition {
                value 3;
                description "Specifies that license is of type lease/full-edition";
            }
        }
        description "type definition for LICENSE_TYPE_T";
    }

}
