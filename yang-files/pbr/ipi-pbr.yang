/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-pbr.yang
*
*/

module ipi-pbr {

    yang-version 1.1;

    namespace   "http://www.ipinfusion.com/yang/ocnos/ipi-pbr";

    prefix "ipi-pbr";

    import ipi-interface {
        prefix ipi-interface;
        revision-date 2022-08-24;
    }

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "This module provides Policy Based Routing configurations";


    revision "2022-06-01" {
        description "Updated the yang file with feature";
        reference " 0.3.0.";
    }

    revision "2021-11-16" {
        description "Module restructuring";
        reference " 0.2.0.";
    }

    revision "2018-06-21" {
        description "Initial Version";
        reference " 0.1.0.";
    }

    grouping pbr-interfaces-config {
        description
            "PBR interfaces configuration";
        leaf name  {
            type  leafref {
                path  "/ipi-interface:interfaces/ipi-interface:interface/ipi-interface:name";
            }
            description "Attribute to specify interface name";
        } // END of name definition.

        leaf route-map-name  {
            type  string {
                length "1..1965";
                pattern "[^?' =,>|]+";
            }
            description "Use this attribute to set ip policy for route-map.";
        } // END of route-map-name definition.

        leaf route-map-v6-name  {
            if-feature feature-list:HAVE_IPV6;
            type  string {
                length "1..1965";
                pattern "[^?' =,>|]+";
            }
            description "Use this attribute to set ipv6 policy for route-map.";
        } // END of route-map-v6-name definition.

    } // END of pbr-interfaces-config definition.
    grouping pbr-interfaces-top {
        description
            "PBR interfaces top level configuration";
        container interfaces {
            description
                "Containers that holds all interfaces configuration for pbr";

            list interface {
            when " /ipi-pbr:pbr/ipi-pbr:config/ipi-pbr:enabled ";
                key "name";
                description
                    "Interface list to hold pbr configuration";
                leaf name  {
                    type  leafref {
                        path  "../config/name";
                    }
                    description "Attribute to specify interface name";
                } // END of name definition.

                container config {
                    description
                        "Configuration data for pbr interface";
                    uses pbr-interfaces-config;
                } // END of config-container definition.
                container state {
                    config false;
                    description
                        "Operational state data for pbr interface";
                    uses pbr-interfaces-config;
                } // END of state-container definition.
            } // End of interface-list
        } // END of interfaces-container definition.
    } // END of pbr-interfaces-top definition.
    grouping pbr-config {
        description
            "PBR configuration";
        leaf enabled  {
            type  empty;
            description "Use this attribute to enable pbr support";
        } // END of enabled definition.

    } // END of pbr-config definition.

    grouping  pbr-grouping {
    description
        "Container for all Policy Based Routing configuration";
    container pbr {
        if-feature feature-list:HAVE_PBR;
        description
            "Container for all Policy Based Routing configuration";
        container config {
            description
                "Configuration data for pbr feature enable";
            uses pbr-config;
        } // END of config-container definition.
        container state {
            config false;
            description
                "Operational state data for pbr feature enable";
            uses pbr-config;
        } // END of state-container definition.
        uses pbr-interfaces-top;
    } // END of pbr-container definition.
    } // END of pbr-grouping definition.

    uses pbr-grouping;

    rpc clear-route-map-pbr-statistics {
        if-feature feature-list:HAVE_PBR;
        description "Use this RPC to clear route-map";
        input  {
            leaf route-map-name  {
                type string;
                mandatory true;
                description "";
            }
        }
    }

}
