/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : vlan.yang
*
*/

submodule vlan {

    belongs-to  ZebOS { prefix ZebOS; }
    include interface;


    import cml_data_types {
        prefix cml_data_types;
    }

    import feature_list {
        prefix feature_list;
    }

    description
        "vlan configuration";


    revision "2017-03-05" {
        description "added support for deletion of vlan type.";
    }

    revision "2017-03-03" {
        description "Added support for private-vlan host and promiscuous.";
    }

    revision "2017-02-25" {
        description "added support for show cml running-config.";
    }

    revision "2017-02-24" {
        description "cliflag added in vlanAccess objectlist.";
    }

    revision "2017-02-21" {
        description "changes for private-vlan.";
    }

    revision "2017-02-14" {
        description "adding missing flag for cli generation.";
    }

    revision "2017-01-28" {
        description "mapped vlan objectlist with nsm vlan structure.";
    }



    grouping vlan-grouping {
        list vlan {
             
            description
                "vlan";

            config true;
            key "vlanId";

            
            leaf bridgeId  {
                type  cml_data_types:CML_STRING_T {
                    length "1..32";
                }
            } // END of bridgeId definition.

            leaf vlanName  {
                type  cml_data_types:CML_STRING_T {
                    length "0..255";
                }
                default "NULL";
            } // END of vlanName definition.

            leaf vlanId  {
                type  cml_data_types:CML_UINT16_T {
                     range "2..4094";
                }
                description "vlanId to be created ";
            } // END of vlanId definition.

            leaf vlanType  {
                type  cml_data_types:CML_VLAN_TYPE_T;  
            } // END of vlanType definition.

            leaf associateAddRemove  {
                type  cml_data_types:CML_PVLAN_ADD_REMOVE_TYPE_T;  
            } // END of associateAddRemove definition.

            leaf associateVid  {
                type  cml_data_types:CML_STRING_T;  
            } // END of associateVid definition.

            leaf pvlanConfigured  {
                if-feature feature_list:HAVE_PVLAN;
                type  cml_data_types:CML_INT32_T;  
                config false;
            } // END of pvlanConfigured definition.

            leaf evcId  {
                type  cml_data_types:CML_INT8_T;  
                config false;
            } // END of evcId definition.

            leaf ovcId  {
                type  cml_data_types:CML_INT8_T;  
                config false;
            } // END of ovcId definition.

            leaf pvlanType  {
                type  cml_data_types:CML_PVLAN_TYPE_T;  
            } // END of pvlanType definition.

            leaf preserveCos  {
                if-feature feature_list:HAVE_PROVIDER_BRIDGE;
                type  cml_data_types:CML_INT8_T;  
                config false;
            } // END of preserveCos definition.

            leaf preserveVlanid  {
                if-feature feature_list:HAVE_PROVIDER_BRIDGE;
                type  cml_data_types:CML_INT8_T;  
                config false;
            } // END of preserveVlanid definition.

            leaf maxUni  {
                if-feature feature_list:HAVE_PROVIDER_BRIDGE;
                type  cml_data_types:CML_INT8_T;  
                config false;
            } // END of maxUni definition.

            leaf dscpCos  {
                if-feature feature_list:HAVE_PROVIDER_BRIDGE;
                type  cml_data_types:CML_INT8_T;  
                config false;
            } // END of dscpCos definition.

            leaf pcpCos  {
                if-feature feature_list:HAVE_PROVIDER_BRIDGE;
                type  cml_data_types:CML_INT8_T;  
                config false;
            } // END of pcpCos definition.

            leaf pcpDscpFlag  {
                if-feature feature_list:HAVE_PROVIDER_BRIDGE;
                type  cml_data_types:CML_INT8_T;  
                config false;
            } // END of pcpDscpFlag definition.

            leaf vlanState  {
                mandatory true;
                type  cml_data_types:CML_VLANSTATE_T;  
                description "vlan state";
            } // END of vlanState definition.

            leaf mtuVal  {
                type  cml_data_types:CML_UINT32_T;  
                default "1500";
            } // END of mtuVal definition.

            leaf instance  {
                type  cml_data_types:CML_INT32_T;  
                config false;
            } // END of instance definition.

            leaf primaryVid  {
                if-feature feature_list:HAVE_G8032V2;
                type  cml_data_types:CML_INT8_T;  
                config false;
            } // END of primaryVid definition.

            leaf erpsBitmask  {
                if-feature feature_list:NSM_VLAN_ERPS_CONF;
                type  cml_data_types:CML_INT8_T;  
                config false;
            } // END of erpsBitmask definition.

            leaf operStatus  {
                if-feature feature_list:NSM_VLAN_ERPS_CONF;
                type  cml_data_types:CML_INT8_T;  
                config false;
            } // END of operStatus definition.

            leaf bind  {
                if-feature feature_list:HAVE_NVO;
                type  cml_data_types:CML_INT8_T;  
                config false;
            } // END of bind definition.

            leaf isAllowed  {
                type  cml_data_types:CML_ALLOWED_FORBIDDEN_T;  
                default "forbidden";
            } // END of isAllowed definition.

            leaf multicast  {
                type  cml_data_types:CML_BOOL_T;  
                default false;
            } // END of multicast definition.

            leaf addFlag  {
                type  cml_data_types:CML_ADD_REMOVE_T;  
                default "remove";
            } // END of addFlag definition.

            leaf ifName  {
                type  cml_data_types:CML_STRING_T {
                    length "0..255";
                }
            } // END of ifName definition.

            leaf bridgeName  {
                type  cml_data_types:CML_STRING_T {
                    length "0..255";
                }
                config false;
            } // END of bridgeName definition.

            leaf vlanRuntimeName  {
                type  cml_data_types:CML_STRING_T {
                    length "0..255";
                }
                config false;
            } // END of vlanRuntimeName definition.

            leaf vlanRuntimeState  {
                type  cml_data_types:CML_STRING_T {
                    length "0..255";
                }
                config false;
            } // END of vlanRuntimeState definition.

            leaf taggedInterface  {
                type  cml_data_types:CML_STRING_T {
                    length "0..255";
                }
                config false;
            } // END of taggedInterface definition.

            container nsmvlanbmp {
                                config false;

                description
                    "nsm vlan bitmap information";

                leaf bitmap  {
                    if-feature feature_list:HAVE_PROVIDER_BRIDGE;
                    type  cml_data_types:CML_INT32_T;  
                } // END of bitmap definition.

            } // END of nsmvlanbmp-container definition.
            container nsmOvcInfo {
                                config false;

                description
                    "nsm ovc vlan information";

                leaf ovcId  {
                    type  cml_data_types:CML_INT8_T;  
                } // END of ovcId definition.

                leaf oepid  {
                    type  cml_data_types:CML_INT8_T;  
                } // END of oepid definition.

                leaf preserveVlan  {
                    type  cml_data_types:CML_INT8_T;  
                } // END of preserveVlan definition.

                leaf num_ovcs  {
                    type  cml_data_types:CML_INT16_T;  
                } // END of num_ovcs definition.

            } // END of nsmOvcInfo-container definition.
        } // End of vlan-list
    } // END of vlan-grouping definition.


    grouping pvlan-grouping {
        list pvlan {
             
            description
                "mapped private-vlan instance with nsm pvlan struct";

            config true;
            key "ifName";

            
            leaf ifName  {
                type  cml_data_types:CML_STRING_T {
                    length "0..255";
                }
            } // END of ifName definition.

            leaf pvlanId  {
                type  cml_data_types:CML_UINT16_T {
                     range "2..4094";
                }
                description "vlanId to be created ";
            } // END of pvlanId definition.

            leaf pvlanMode  {
                type  cml_data_types:CML_PVLAN_MODE_T;  
            } // END of pvlanMode definition.

            leaf pvlanMapAssociateAddRemove  {
                type  cml_data_types:CML_PVLAN_ADD_REMOVE_TYPE_T;  
            } // END of pvlanMapAssociateAddRemove definition.

            leaf pvlanAssociate  {
                type  cml_data_types:CML_UINT32_T;  
            } // END of pvlanAssociate definition.

            leaf pvlanMapVid  {
                type  cml_data_types:CML_STRING_T;  
            } // END of pvlanMapVid definition.

        } // End of pvlan-list
    } // END of pvlan-grouping definition.


    grouping vlanAccessMap-grouping {
        list vlanAccessMap {
             
            description
                "vlanAccessMap";

            config true;
            key "accessMap";

            
            leaf vrId  {
                type  cml_data_types:CML_INT32_T;  
                default "0";
            } // END of vrId definition.

            leaf accessMap  {
                type  cml_data_types:CML_STRING_T {
                    length "1..32";
                }
            } // END of accessMap definition.

            leaf sequenceNum  {
                mandatory true;
                type  cml_data_types:CML_UINT32_T {
                     range "1..4294967295";
                }
            } // END of sequenceNum definition.

            leaf statisticsEntry  {
                type  cml_data_types:CML_INT32_T;  
            } // END of statisticsEntry definition.

            leaf acttype  {
                type  cml_data_types:CML_ACLTYPE_T;  
            } // END of acttype definition.

            leaf accessGroup  {
                type  cml_data_types:CML_STRING_T {
                    length "0..255";
                }
            } // END of accessGroup definition.

            leaf vlanFilter  {
                type  cml_data_types:CML_STRING_T {
                    length "0..255";
                }
            } // END of vlanFilter definition.

            leaf vlanRange  {
                type  cml_data_types:CML_STRING_T {
                    length "0..255";
                }
            } // END of vlanRange definition.

            leaf actionType  {
                type  cml_data_types:CML_ACTIONTYPE_T;  
            } // END of actionType definition.

            leaf ifName  {
                type  cml_data_types:CML_STRING_T {
                    length "0..255";
                }
            } // END of ifName definition.

            leaf vlanAccessEnd  {
                type  cml_data_types:CML_INT32_T;  
            } // END of vlanAccessEnd definition.

        } // End of vlanAccessMap-list
    } // END of vlanAccessMap-grouping definition.


}
