/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-g8031-elps.yang
*
*/

submodule ipi-g8031-elps {

    yang-version 1.1;

    belongs-to  ipi-g8031 { prefix ipi-g8031; }

    import feature-list {
        prefix feature-list;
        revision-date 2023-02-21;
    }

    import ipi-g8031-elps-types {
        prefix ipi-g8031-elps-types;
        revision-date 2022-06-28;
    }

    import ietf-yang-types {
        prefix yang;
        revision-date 2013-07-15;
    }

    organization
        "IP Infusion Inc.";

    contact
        "Address: 3965 Freedom Circle, Suite 200, Santa Clara, CA 95054
         Phone: +1 408-400-1900
         E-mail: support@ipinfusion.com
         Web: http://www.ipinfusion.com/";

    description
        "Ethernet Linear Protection Switching";


    revision "2022-07-06" {
        description "Removed implicit delete tag on debug config container";
        reference " 0.3.4.";
    }

    revision "2022-06-01" {
        description "Updated the yang file with feature";
        reference " 0.3.3.";
    }

    revision "2022-04-27" {
        description "Added debug support for g8031";
        reference " 0.3.2.";
    }

    revision "2022-04-06" {
        description "Added dependency between protection-type and elps-instance-id";
        reference " 0.3.1.";
    }

    revision "2022-03-17" {
        description "Restructured module as per open-config";
        reference " 0.3.0.";
    }

    revision "2021-12-09" {
        description "Updated dependentObject tag where CFM XPath is used";
        reference " 0.2.0.";
    }

    revision "2021-09-25" {
        description "Admin-cmds changed to RPC due to DB-Sync issues";
        reference " 0.1.2.";
    }

    revision "2021-09-20" {
        description "Block local-lockout configuration";
        reference " 0.1.1.";
    }

    revision "2021-05-14" {
        description "Initial Version";
        reference " 0.1.0.";
    }

    grouping g8031-debug-terminal-top {
        description
            "Bridge Ethernet Linear Protection Switching debug state attributes";
        container terminal {
            config false;
            description
                "Container for g8031 debugging functions";
            uses g8031-debug-config;
        } // END of terminal-container definition.
    } // END of g8031-debug-terminal-top definition.
    grouping g8031-debug-config {
        description
            "Bridge Ethernet Linear Protection Switching debug configuration
                        attributes";
        leaf debug-options  {
            type  ipi-g8031-elps-types:g8031_debug_t;
            description "Supported debug options for g8031";
        } // END of debug-options definition.

    } // END of g8031-debug-config definition.
    grouping elps-traffic-switch-config {
        description
            "Grouping for Ethernet Linear Protection Switching traffic switching
                        commands";
        leaf local-freeze  {
            when " /g8031/instances/instance/elps/config/protection-type ";
            type  empty;
            description "Freezes the state of the protection group.";
        } // END of local-freeze definition.

    } // END of elps-traffic-switch-config definition.
    grouping elps-timers-config {
        description
            "Ethernet Linear Protection Switching configuration attributes for
                        restoration and swicthing timers";
        leaf wait-to-restore  {
            when " /g8031/instances/instance/elps/config/protection-type and /g8031/instances/instance/elps/config/enable-revertive-mode ";
            type  uint16 {
                 range "300..720"  {
                    description "300..720: Supported range 300 - 720";
                 }
            }
            units "seconds";
            description "EPS wait-to-restore timer";
        } // END of wait-to-restore definition.

        leaf hold-off  {
            when " /g8031/instances/instance/elps/config/protection-type ";
            type  uint8 {
                 range "0..10"  {
                    description "0..10: Supported range 0 - 10";
                 }
            }
            units "seconds";
            description "EPS hold-off timer";
        } // END of hold-off definition.

    } // END of elps-timers-config definition.
    grouping elps-state {
        description
            "Bridge Ethernet Linear Protection switching state data";
        leaf direction  {
            type  ipi-g8031-elps-types:g8031_direction_type_t;
            description "Direction of ELPS";
        } // END of direction definition.

        leaf active-path  {
            type  ipi-g8031-elps-types:g8031_active_path_type_t;
            description "Indicates the path currently active";
        } // END of active-path definition.

        leaf request-signal  {
            type  ipi-g8031-elps-types:g8031_request_signal_type_t;
            description "Request signal operation state";
        } // END of request-signal definition.

        leaf current-state  {
            type  ipi-g8031-elps-types:g8031_current_state_type_t;
            description "Current state of ELPS";
        } // END of current-state definition.

        leaf failure-of-protocol-state  {
            type  ipi-g8031-elps-types:g8031_failure_of_protocol_state_type_t;
            description "Indicates the status of failure in ELPS protocol";
        } // END of failure-of-protocol-state definition.

        leaf rx-lps-frame-count  {
            type  yang:counter32;
            description "LPS PDU Rx count";
        } // END of rx-lps-frame-count definition.

        leaf tx-lps-frame-count  {
            type  yang:counter32;
            description "LPS PDU Tx count";
        } // END of tx-lps-frame-count definition.

    } // END of elps-state definition.
    grouping elps-config {
        description
            "Ethernet Linear Protection Switching configuration attributes";
        leaf protection-type  {
            when " /g8031/instances/instance/config/elps-instance-id ";
            type  ipi-g8031-elps-types:g8031_elps_protection_type_t;
            description "protection bridge mode";
        } // END of protection-type definition.

        leaf enable-revertive-mode  {
            when " /g8031/instances/instance/elps/config/protection-type ";
            type  empty;
            description "protection restoration mode";
        } // END of enable-revertive-mode definition.

        leaf level-identifier  {
            when " /g8031/instances/instance/elps/config/protection-type ";
            type  uint8 {
                 range "0..7"  {
                    description "0..7: Supported range 0 - 7";
                 }
            }
            description "Ethernet Linear Protection switching level";
        } // END of level-identifier definition.

    } // END of elps-config definition.
    grouping elps-timers-top {
        description
            "Ethernet Linear Protection Switching configuration attributes for
                        restoration and swicthing timers";
        container timers {
            description
                "Top level configuration container for Ethernet Linear Protection
                        Switching restoration and switching timers";
            container config {
                description
                    "Configuration container for Ethernet Linear Protection Switching
                            restoration and switching timers";
                uses elps-timers-config;
            } // END of config-container definition.
            container state {
                config false;
                description
                    "Top level state container for Ethernet Linear Protection Switching";
                uses elps-timers-config;
            } // END of state-container definition.
        } // END of timers-container definition.
    } // END of elps-timers-top definition.
    grouping elps-traffic-switch-top {
        description
            "Top level grouping for Ethernet Linear Protection Switching traffic
                        switching commands";
        container traffic-switch {
            description
                "Top level configuration data for Ethernet Linear Protection Switching
                        traffic switching commands";
            container config {
                description
                    "Configuration data for Ethernet Linear Protection Switching traffic
                            switching commands";
                uses elps-traffic-switch-config;
            } // END of config-container definition.
            container state {
                config false;
                description
                    "Top level state container for Ethernet Linear Protection Switching";
                uses elps-traffic-switch-config;
            } // END of state-container definition.
        } // END of traffic-switch-container definition.
    } // END of elps-traffic-switch-top definition.
    grouping elps-top {
        description
            "Ethernet Linear Protection Switching configuration attributes for
                        restoration and swicthing type";
        container config {
            description
                "Top level configuration container for Ethernet Linear Protection
                        Switching";
            uses elps-config;
        } // END of config-container definition.
        container state {
            config false;
            description
                "Top level state container for Ethernet Linear Protection Switching";
            uses elps-config;
            uses elps-state;
        } // END of state-container definition.
        uses elps-timers-top;
        uses elps-traffic-switch-top;
    } // END of elps-top definition.

    grouping  elps-grouping {
    description
        "Ethernet Linear Protection Switching main container";
    container elps {
        if-feature feature-list:HAVE_G8031;
        if-feature feature-list:HAVE_ONMD;
        description
            "Ethernet Linear Protection Switching main container";
        uses elps-top;
    } // END of elps-container definition.
    } // END of elps-grouping definition.

    grouping  debug-grouping {
    description
        "Container for g8031 debugging functions";
    container debug {
        if-feature feature-list:HAVE_G8031;
        if-feature feature-list:HAVE_ONMD;
        description
            "Container for g8031 debugging functions";
        container config {
            description
                "Configuration data for g8031 debug";
            uses g8031-debug-config;
        } // END of config-container definition.
        container state {
            config false;
            description
                "Operational state data for g8031 debug";
            uses g8031-debug-config;
            uses g8031-debug-terminal-top;
        } // END of state-container definition.
    } // END of debug-container definition.
    } // END of debug-grouping definition.


}
