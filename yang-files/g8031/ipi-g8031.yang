/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-g8031.yang
*
*/

module ipi-g8031 {

    yang-version 1.1;

    namespace   "http://www.ipinfusion.com/yang/ocnos/ipi-g8031";

    prefix "ipi-g8031";

    import ipi-g8031-elps-types {
        prefix ipi-g8031-elps-types;
        revision-date 2022-06-28;
    }

    import ipi-network-instance {
        prefix ipi-network-instance;
        revision-date 2022-06-01;
    }

    import cml-data-types {
        prefix cml-data-types;
        revision-date 2022-09-30;
    }

    import ipi-interface {
        prefix ipi-interface;
        revision-date 2022-08-24;
    }

    import ipi-bridge {
        prefix ipi-bridge;
        revision-date 2022-07-19;
    }

    import ipi-vlan {
        prefix ipi-vlan;
        revision-date 2022-07-11;
    }

    import feature-list {
        prefix feature-list;
        revision-date 2023-02-21;
    }

    include ipi-g8031-elps { revision-date 2022-07-06;}
    organization
        "IP Infusion Inc.";

    contact
        "Address: 3965 Freedom Circle, Suite 200, Santa Clara, CA 95054
         Phone: +1 408-400-1900
         E-mail: support@ipinfusion.com
         Web: http://www.ipinfusion.com/";

    description
        "Ethernet Linear Protection Switching";


    revision "2022-07-12" {
        description "Removed implicit delete tag on debug config container in g8031-elps submodule";
        reference " 0.3.9.";
    }

    revision "2022-07-11" {
        description "Updated dependency module ipi-vlan";
        reference " 0.3.8.";
    }

    revision "2022-07-04" {
        description "Added authentication dependency for bridge configuration in interface";
        reference " 0.3.7.";
    }

    revision "2022-06-27" {
        description "Updated when expressions in yang file";
        reference " 0.3.6.";
    }

    revision "2022-06-06" {
        description "Changed data-vlans attribute data type from leafref CML_UINT16_T to CML_RANGE_T for attribute data-vlans";
        reference " 0.3.5.";
    }

    revision "2022-06-01" {
        description "Updated the yang file with feature";
        reference " 0.3.4.";
    }

    revision "2022-04-27" {
        description "Added debug support for g8031";
        reference " 0.3.3.";
    }

    revision "2022-04-06" {
        description "Updated attribute dependency in g8031-elps submodule";
        reference " 0.3.2.";
    }

    revision "2022-03-29" {
        description "Added when clause to match the instance-type of the bridge";
        reference " 0.3.1.";
    }

    revision "2022-03-17" {
        description "Restructured module as per open-config";
        reference " 0.3.0.";
    }

    revision "2021-12-09" {
        description "Updated dependentObject tag where CFM XPath is used";
        reference " 0.2.0.";
    }

    revision "2021-05-14" {
        description "Initial Version";
        reference " 0.1.0.";
    }

    grouping g8031-instances-config {
        description
            "Bridge Ethernet Linear Protection Switching configuration data";
        leaf eps-id  {
            type  uint8 {
                 range "1..32"  {
                    description "1..32: Supported range 1 - 32";
                 }
            }
            description "unique ID to identify a EPS Protection Group";
        } // END of eps-id definition.

        leaf bridge-id  {
            when " /ipi-network-instance:network-instances/ipi-network-instance:network-instance/ipi-network-instance:instance-type = 'l2ni' ";
            type  leafref {
                path  "/ipi-network-instance:network-instances/ipi-network-instance:network-instance/ipi-network-instance:instance-name";
            }
            mandatory true;
            description "Network Instance Name";
        } // END of bridge-id definition.

        leaf working-port  {
            when " ../protection-port ";
            type  leafref {
                path  "/ipi-interface:interfaces/ipi-interface:interface/ipi-interface:name";
            }
            description "port for the working EPS path";
        } // END of working-port definition.

        leaf protection-port  {
            when " ../working-port ";
            type  leafref {
                path  "/ipi-interface:interfaces/ipi-interface:interface/ipi-interface:name";
            }
            description "port for the protection EPS path";
        } // END of protection-port definition.

        leaf elps-instance-id  {
            when " ../working-port and ../protection-port ";
            type  uint8 {
                 range "1..63"  {
                    description "1..63: Supported range 1 - 63";
                 }
            }
            description "MSTP Instance Identifier";
        } // END of elps-instance-id definition.

        leaf data-vlans  {
            type  cml-data-types:cml_range_t;
            description "VLAN Identifier";
        } // END of data-vlans definition.

        leaf primary-vlan  {
            type  leafref {
                path  "/ipi-network-instance:network-instances/ipi-network-instance:network-instance/ipi-bridge:bridge/ipi-vlan:vlans/ipi-vlan:vlan/ipi-vlan:vlan-id";
            }
            description "Indicates if the given VLAN is primary VLAN of protection group";
        } // END of primary-vlan definition.

    } // END of g8031-instances-config definition.
    grouping g8031-instances-top {
        description
            "Top level grouping for bridge Ethernet Linear Protection Switching
                        configuration data";
        container instances {
            description
                "Instances of Ethernet Linear Protection Switching protocol
                        configuration data";

            list instance {
                if-feature feature-list:HAVE_G8031;
                key "eps-id";
                description
                    "Top level objectlist for Ethernet Linear Protection Switching
                                configuration";
                leaf eps-id  {
                    type  leafref {
                        path  "../config/eps-id";
                    }
                    description "unique ID to identify a EPS Protection Group";
                } // END of eps-id definition.

                container config {
                    description
                        "Ethernet Linear Protection Switching Instance configuration data";
                    uses g8031-instances-config;
                } // END of config-container definition.
                container state {
                    config false;
                    description
                        "Ethernet Linear Protection Switching protocol operational state data";
                    uses g8031-instances-config;
                } // END of state-container definition.
                uses elps-grouping;
            } // End of instance-list
        } // END of instances-container definition.
    } // END of g8031-instances-top definition.

    grouping  g8031-grouping {
    description
        "Top level container for Ethernet Linear Protection Switching";
    container g8031 {
        if-feature feature-list:HAVE_G8031;
        description
            "Top level container for Ethernet Linear Protection Switching";
        uses g8031-instances-top;
        uses debug-grouping;
    } // END of g8031-container definition.
    } // END of g8031-grouping definition.

    uses g8031-grouping;

    rpc g8031-lockout {
        if-feature feature-list:HAVE_G8031;
        if-feature feature-list:HAVE_ONMD;
        description "Enable G8031 lockout";
        input  {
            leaf instance-name  {
                type string;
                mandatory true;
                description "Instance name for the lockout on G8031 Protection Group";
            }
            leaf eps-id  {
                type uint8 {
                    range "1..32";
                }
                mandatory true;
                description "unique ID to identify a EPS Protection Group";
            }
        }
    }

    rpc g8031-force-switch {
        if-feature feature-list:HAVE_G8031;
        if-feature feature-list:HAVE_ONMD;
        description "Trigger force-switch";
        input  {
            leaf instance-name  {
                type string;
                mandatory true;
                description "Instance name for the lockout on G8031 Protection Group";
            }
            leaf eps-id  {
                type uint8 {
                    range "1..32";
                }
                mandatory true;
                description "unique ID to identify a EPS Protection Group";
            }
        }
    }

    rpc g8031-manual-switch {
        if-feature feature-list:HAVE_G8031;
        if-feature feature-list:HAVE_ONMD;
        description "Trigger manual-switch";
        input  {
            leaf instance-name  {
                type string;
                mandatory true;
                description "Instance name for the lockout on G8031 Protection Group";
            }
            leaf eps-id  {
                type uint8 {
                    range "1..32";
                }
                mandatory true;
                description "unique ID to identify a EPS Protection Group";
            }
        }
    }

    rpc g8031-exercise {
        if-feature feature-list:HAVE_G8031;
        if-feature feature-list:HAVE_ONMD;
        description "Perform G8031 exercise";
        input  {
            leaf instance-name  {
                type string;
                mandatory true;
                description "Instance name for the lockout on G8031 Protection Group";
            }
            leaf eps-id  {
                type uint8 {
                    range "1..32";
                }
                mandatory true;
                description "unique ID to identify a EPS Protection Group";
            }
        }
    }

    rpc g8031-clear {
        if-feature feature-list:HAVE_G8031;
        if-feature feature-list:HAVE_ONMD;
        description "G8031 clear operation";
        input  {
            leaf instance-name  {
                type string;
                mandatory true;
                description "Instance name for the lockout on G8031 Protection Group";
            }
            leaf eps-id  {
                type uint8 {
                    range "1..32";
                }
                mandatory true;
                description "unique ID to identify a EPS Protection Group";
            }
        }
    }

    rpc g8031-terminal-debug-on {
        if-feature feature-list:HAVE_G8031;
        if-feature feature-list:HAVE_ONMD;
        description "Enable g8031 debugging functions";
        input  {
            leaf debug-options  {
                type ipi-g8031-elps-types:g8031_debug_t;
                mandatory true;
                description "Use this attribute to debug g8031 feature.";
            }
        }
    }

    rpc g8031-terminal-debug-off {
        if-feature feature-list:HAVE_G8031;
        if-feature feature-list:HAVE_ONMD;
        description "Disable g8031 debugging functions";
        input  {
            leaf debug-options  {
                type ipi-g8031-elps-types:g8031_debug_t;
                mandatory true;
                description "Use this attribute to debug g8031 feature.";
            }
        }
    }

}
