/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : vxlan.yang
*
*/

submodule vxlan {

    belongs-to  ZebOS { prefix ZebOS; }
    include interface;
    include vlan;
    include vrf;


    import cml_data_types {
        prefix cml_data_types;
    }

    import feature_list {
        prefix feature_list;
    }

    description
        "vxlan datamodel";


    revision "2016-12-28" {
        description "Added extra commands in vxlan .";
    }

    revision "2016-03-05" {
        description "changes for Jira-13917.";
    }

    revision "2016-02-20" {
        description "changes for bug fixes.";
    }

    revision "2016-02-10" {
        description "Added Get APIs  in vxlan.";
    }

    revision "2015-10-22" {
        description "Initial draft version.";
    }


    grouping  nsmnvo-grouping {
    container nsmnvo {
        presence "yes"; 
                config true;

        description
            "nsm_nvo_master structure";

        leaf nvoGlobalFlag  {
            type  cml_data_types:CML_STRING_T {
                length "0..255";
            }
            config false;
        } // END of nvoGlobalFlag definition.

        leaf vxlanEnable  {
            mandatory true;
            type  cml_data_types:CML_BOOL_T;  
        } // END of vxlanEnable definition.

        leaf vtepIpv4  {
            type  cml_data_types:CML_IPV4_ADDR_T;  
        } // END of vtepIpv4 definition.

        leaf isDynamicLearning  {
            type  cml_data_types:CML_BOOL_T;  
            config false;
        } // END of isDynamicLearning definition.

        leaf vxlanVtepGlobal  {
            type  cml_data_types:CML_BOOL_T;  
            config false;
        } // END of vxlanVtepGlobal definition.

        leaf vtepMcastSock  {
            type  cml_data_types:CML_INT32_T;  
            config false;
        } // END of vtepMcastSock definition.

        leaf nvgreEnable  {
            if-feature feature_list:HAVE_NVGRE;
            type  cml_data_types:CML_BOOL_T;  
            config false;
        } // END of nvgreEnable definition.

        leaf nvgreBgpEnable  {
            if-feature feature_list:HAVE_NVGRE;
            type  cml_data_types:CML_BOOL_T;  
            config false;
        } // END of nvgreBgpEnable definition.

        leaf isBgpUp  {
            if-feature feature_list:HAVE_BGP_EVPN;
            type  cml_data_types:CML_BOOL_T;  
            config false;
        } // END of isBgpUp definition.


        list nvoTenant {
                         if-feature feature_list:HAVE_NVO;

            description
                "nvoTenant";

            config true;
            key "nvoId";

            
            leaf nvoId  {
                type  cml_data_types:CML_UINT32_T {
                     range "1..16777215";
                }
            } // END of nvoId definition.

            leaf type  {
                type  cml_data_types:CML_BOOL_T;  
            } // END of type definition.

            leaf mcastIp  {
                type  cml_data_types:CML_STRING_T {
                    length "0..255";
                }
            } // END of mcastIp definition.

            leaf ingRepl  {
                type  cml_data_types:CML_BOOL_T;  
            } // END of ingRepl definition.

            leaf innerVidDisabled  {
                type  cml_data_types:CML_BOOL_T;  
            } // END of innerVidDisabled definition.

            leaf hostReachabilityProtocol  {
                type  cml_data_types:CML_BOOL_T;  
            } // END of hostReachabilityProtocol definition.

            leaf vrfName  {
                type  cml_data_types:CML_STRING_T {
                    length "0..255";
                }
            } // END of vrfName definition.

            leaf rdStr  {
                if-feature feature_list:HAVE_BGP_EVPN;
                type  cml_data_types:CML_STRING_T {
                    length "0..255";
                }
            } // END of rdStr definition.

            leaf rtStr  {
                if-feature feature_list:HAVE_BGP_EVPN;
                type  cml_data_types:CML_STRING_T {
                    length "0..255";
                }
            } // END of rtStr definition.

            leaf mode  {
                type  cml_data_types:CML_VXLAN_MODE_T;  
                config false;
            } // END of mode definition.

            leaf vrfId  {
                type  cml_data_types:CML_UINT32_T;  
                config false;
            } // END of vrfId definition.

            leaf config  {
                type  cml_data_types:CML_UINT32_T;  
                config false;
            } // END of config definition.

            leaf vtepFlag  {
                type  cml_data_types:CML_BOOL_T;  
                config false;
            } // END of vtepFlag definition.


            list nvoIfInfo {
                 
                description
                    "nvo_if_info";

                config true;
                key "ifName";

                
                leaf ifName  {
                    type  cml_data_types:CML_STRING_T {
                        length "0..255";
                    }
                } // END of ifName definition.

            } // End of nvoIfInfo-list

            list nvoIfVlanInfo {
                 
                description
                    "nvo_if_info";

                config true;
                key "ifName";

                
                leaf ifName  {
                    type  cml_data_types:CML_STRING_T {
                        length "0..255";
                    }
                } // END of ifName definition.

                leaf-list vlanId  {
                    type  cml_data_types:CML_STRING_T {
                        length "0..255";
                    }
                } // END of vlanId definition.

                leaf dfFlags  {
                    if-feature feature_list:HAVE_BGP_EVPN;
                    type  cml_data_types:CML_STRING_T {
                        length "0..255";
                    }
                    config false;
                } // END of dfFlags definition.

            } // End of nvoIfVlanInfo-list

            list nvoTunnelIndex {
                 
                description
                    "nvoTunnel";

                config false;
                key "index";

                
                leaf index  {
                    type  cml_data_types:CML_UINT8_T;  
                } // END of index definition.


                list nvoTunnel {
                     
                    description
                        "nvoTunnel";

                    config false;
                    key "sip";

                    
                    leaf sip  {
                        type  cml_data_types:CML_UINT8_T;  
                    } // END of sip definition.

                    leaf type  {
                        type  cml_data_types:CML_UINT8_T;  
                    } // END of type definition.

                    leaf mode  {
                        type  cml_data_types:CML_UINT8_T;  
                    } // END of mode definition.

                    leaf resolved  {
                        type  cml_data_types:CML_BOOL_T;  
                    } // END of resolved definition.

                    leaf addedToHw  {
                        type  cml_data_types:CML_BOOL_T;  
                    } // END of addedToHw definition.

                    leaf refCount  {
                        type  cml_data_types:CML_UINT16_T;  
                    } // END of refCount definition.

                    leaf egressIfindex  {
                        type  cml_data_types:CML_UINT32_T;  
                    } // END of egressIfindex definition.

                    leaf dip  {
                        type  cml_data_types:CML_INT32_T;  
                    } // END of dip definition.

                    leaf sport  {
                        type  cml_data_types:CML_UINT16_T;  
                    } // END of sport definition.

                    leaf dport  {
                        type  cml_data_types:CML_UINT16_T;  
                    } // END of dport definition.

                } // End of nvoTunnel-list
            } // End of nvoTunnelIndex-list

            list nvoArpCacheInfo {
                 
                description
                    "nvoArpCacheInfo";

                config false;
                key "hostIp";

                
                leaf hostIp  {
                    type  cml_data_types:CML_IPV4_ADDR_T;  
                } // END of hostIp definition.

                leaf hostMac  {
                    type  cml_data_types:CML_UINT8_T;  
                } // END of hostMac definition.

                leaf hostType  {
                    type  cml_data_types:CML_UINT8_T;  
                } // END of hostType definition.

                leaf ifindex  {
                    type  cml_data_types:CML_INT32_T;  
                } // END of ifindex definition.

            } // End of nvoArpCacheInfo-list

            list nvoMacMapping {
                 
                description
                    "nvoMacMapping";

                config false;
                key "macAddr";

                
                leaf macAddr  {
                    type  cml_data_types:CML_UINT8_T;  
                } // END of macAddr definition.

                leaf prefix  {
                    type  cml_data_types:CML_IPV4_ADDR_T;  
                } // END of prefix definition.

                leaf type  {
                    type  cml_data_types:CML_UINT8_T;  
                } // END of type definition.

                leaf sticky  {
                    type  cml_data_types:CML_BOOL_T;  
                } // END of sticky definition.

            } // End of nvoMacMapping-list

            list nvoIfMap {
                 
                description
                    "nvoIfMap";

                config false;
                key "ifmapindex";

                
                leaf ifmapindex  {
                    type  cml_data_types:CML_UINT32_T;  
                } // END of ifmapindex definition.

                leaf nvoMapType  {
                    type  cml_data_types:CML_UINT8_T;  
                } // END of nvoMapType definition.

                leaf vlanCount  {
                    type  cml_data_types:CML_UINT32_T;  
                } // END of vlanCount definition.

                leaf dfFlags  {
                    type  cml_data_types:CML_UINT8_T;  
                } // END of dfFlags definition.

            } // End of nvoIfMap-list
        } // End of nvoTenant-list
    } // END of nsmnvo-container definition.
    } // END of nsmnvo-container definition.


}
