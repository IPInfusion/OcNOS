/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-management-server-notification-types.yang
*
*/

module ipi-management-server-notification-types {

    yang-version 1.1;

    namespace   "http://www.ipinfusion.com/yang/ocnos/ipi-management-server-notification-types";

    prefix "ipi-management-server-notification-types";

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "netconf notification data types";


    revision "2022-09-30" {
        description "Move notification severity type to cml-data-types";
        reference " 0.2.1.";
    }

    revision "2022-06-20" {
        description "Added the feature tag";
        reference " 0.2.0.";
    }

    revision "2022-04-27" {
        description "Initial version to include netconf notification configs";
        reference " 0.1.0.";
    }



    typedef  notif_module_names_t {
        type enumeration {
            enum auth {
                value 1;
                if-feature feature-list:HAVE_AUTHD;
                description "Set notification configuration for auth module";
            }
            enum bgp {
                value 2;
                description "Set notification configuration for bgp module";
            }
            enum cmm {
                value 3;
                if-feature feature-list:HAVE_CMMD;
                description "Set notification configuration for cmm module";
            }
            enum dvmrp {
                value 4;
                if-feature feature-list:HAVE_DVMRPD;
                description "Set notification configuration for dvmrp module";
            }
            enum hostp {
                value 5;
                if-feature feature-list:HAVE_HOSTPD;
                description "Set notification configuration for hostp module";
            }
            enum hsl {
                value 6;
                description "Set notification configuration for hsl module";
            }
            enum isis {
                value 7;
                if-feature feature-list:HAVE_ISISD;
                description "Set notification configuration for isis module";
            }
            enum ldp {
                value 8;
                if-feature feature-list:HAVE_LDPD;
                description "Set notification configuration for ldp module";
            }
            enum lag {
                value 9;
                if-feature feature-list:HAVE_LAGD;
                description "Set notification configuration for lagd module";
            }
            enum l2mrib {
                value 10;
                description "Set notification configuration for l2mrib module";
            }
            enum mstp {
                value 11;
                description "Set notification configuration for mstp module";
            }
            enum mrib {
                value 12;
                description "Set notification configuration for mrib module";
            }
            enum nsm {
                value 13;
                description "Set notification configuration for nsm module";
            }
            enum onm {
                value 14;
                if-feature feature-list:HAVE_ONMD;
                description "Set notification configuration for onm module";
            }
            enum oam {
                value 15;
                description "Set notification configuration for oam module";
            }
            enum ospf {
                value 16;
                description "Set notification configuration for ospf module";
            }
            enum ospf6 {
                value 17;
                description "Set notification configuration for ospf6 module";
            }
            enum ptp {
                value 18;
                if-feature feature-list:HAVE_PTPD;
                description "Set notification configuration for ptp module";
            }
            enum rip {
                value 19;
                description "Set notification configuration for rip module";
            }
            enum rmon {
                value 20;
                if-feature feature-list:HAVE_RMOND;
                description "Set notification configuration for rmon module";
            }
            enum pim {
                value 21;
                description "Set notification configuration for pim module";
            }
            enum rib {
                value 22;
                description "Set notification configuration for rib module";
            }
            enum vrrp {
                value 23;
                description "Set notification configuration for vrrp module";
            }
            enum sflow {
                value 24;
                if-feature feature-list:HAVE_SFLOW;
                description "Set notification configuration for sflow module";
            }
            enum trill {
                value 25;
                if-feature feature-list:HAVE_TRILLD;
                description "Set notification configuration for trill module";
            }
            enum rsvp {
                value 26;
                if-feature feature-list:HAVE_RSVPD;
                description "Set notification configuration for rsvp module";
            }
            enum pserv {
                value 27;
                if-feature feature-list:HAVE_PSERVD;
                description "Set notification configuration for pservd module";
            }
            enum cml {
                value 28;
                if-feature feature-list:HAVE_CMLD;
                description "Set notification configuration for cml module";
            }
            enum ndd {
                value 29;
                if-feature feature-list:HAVE_NDD;
                description "Set notification configuration for ndd module";
            }
            enum ripng {
                value 30;
                description "Set notification configuration for ripng module";
            }
            enum vlog {
                value 31;
                description "Set notification configuration for vlog module";
            }
            enum all {
                value 32;
                description "Set notification configuration for all modules";
            }
            enum synce {
                value 33;
                if-feature feature-list:HAVE_SYNCED;
                description "Set notification configuration for synce module";
            }
            enum pon {
                value 34;
                if-feature feature-list:HAVE_POND;
                description "Set notification configuration for pon module";
            }
            enum pcep {
                value 35;
                if-feature feature-list:HAVE_PCEP;
                description "Set notification configuration for pcep module";
            }
            enum udld {
                value 36;
                if-feature feature-list:HAVE_UDLD;
                description "Set notification configuration for udld module";
            }
        }
        description "type definition for NOTIF_MODULE_NAMES_T";
    }

}
