/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-management-server-notification.yang
*
*/

submodule ipi-management-server-notification {

    yang-version 1.1;

    belongs-to  ipi-management-server { prefix ipi-management-server; }

    import feature-list {
        prefix feature-list;
        revision-date 2023-02-21;
    }

    import cml-data-types {
        prefix cml-data-types;
        revision-date 2022-09-30;
    }

    import ipi-management-server-notification-types {
        prefix ipi-management-server-notification-types;
        revision-date 2022-09-30;
    }

    organization
        "IP Infusion Inc.";

    contact
        "Address: 3965 Freedom Circle, Suite 200, Santa Clara, CA 95054
         Phone: +1 408-400-1900
         E-mail: support@ipinfusion.com
         Web: http://www.ipinfusion.com/";

    description
        "Model for Common management layer notification related configuration";


    revision "2022-09-30" {
        description "Move notification severity type to cml-data-types";
        reference " 0.2.1.";
    }

    revision "2022-06-20" {
        description "Added the feature tag";
        reference " 0.2.0.";
    }

    revision "2022-04-27" {
        description "Initial version to include netconf notification configs";
        reference " 0.1.0.";
    }

    grouping notification-config {
        description
            "Grouping for notification configuration";
        leaf module-name  {
            type  ipi-management-server-notification-types:notif_module_names_t;
            description "Module name of process for which notification configuration need to be
                        done";
        } // END of module-name definition.

        leaf enable  {
            type  cml-data-types:cml_enable_disable_t;
            mandatory true;
            description "Enable Disable notification for the module";
        } // END of enable definition.

        leaf severity  {
            type  cml-data-types:cml_notif_severity_t;
            default "all";
            description "If notification enabled, all the notifications having severity higher
                        than or equal to this severity allowed.If notification disabled, all
                        the notifications having severity lower than or equal to this severity
                        not allowed";
        } // END of severity definition.

    } // END of notification-config definition.
    grouping notification-top {
        description
            "Top level grouping for notification configuration";

        list module-notification {
            key "module-name";
            description
                "Object list for configuring module notification";
            leaf module-name  {
                type  leafref {
                    path  "../config/module-name";
                }
                description "Module name of process for which notification configuration need to be
                            done";
            } // END of module-name definition.

            container config {
                description
                    "Configuration data";
                uses notification-config;
            } // END of config-container definition.
            container state {
                config false;
                description
                    "Operational state data";
                uses notification-config;
            } // END of state-container definition.
        } // End of module-notification-list
    } // END of notification-top definition.

    grouping  management-server-grouping {
    description
        "Top level container for management server configuration";
    container management-server {
        if-feature feature-list:HAVE_CMLD;
        description
            "Top level container for management server configuration";
        container notifications {
            description
                "Container for notification configuration";
            uses notification-top;
        } // END of notifications-container definition.
    } // END of management-server-container definition.
    } // END of management-server-grouping definition.


}
