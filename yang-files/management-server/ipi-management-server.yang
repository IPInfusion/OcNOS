/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-management-server.yang
*
*/

module ipi-management-server {

    yang-version 1.1;

    namespace   "http://www.ipinfusion.com/yang/ocnos/ipi-management-server";

    prefix "ipi-management-server";

    import ietf-inet-types {
        prefix inet;
        revision-date 2013-07-15;
    }

    import ipi-interface {
        prefix ipi-interface;
        revision-date 2022-08-24;
    }

    import feature-list {
        prefix feature-list;
        revision-date 2023-02-21;
    }

    include ipi-management-server-notification { revision-date 2022-09-30;}
    organization
        "IP Infusion Inc.";

    contact
        "Address: 3965 Freedom Circle, Suite 200, Santa Clara, CA 95054
         Phone: +1 408-400-1900
         E-mail: support@ipinfusion.com
         Web: http://www.ipinfusion.com/";

    description
        "Data model for management server related configurations";


    revision "2022-09-30" {
        description "Move notification severity type to cml-data-types";
        reference " 0.1.5.";
    }

    revision "2022-06-20" {
        description "Added the feature tag";
        reference " 0.1.4.";
    }

    revision "2022-06-14" {
        description "Added leafref for management port leaf with interface module and support for retry-max-attemp 0";
        reference " 0.1.3.";
    }

    revision "2022-06-01" {
        description "Updated the yang file with feature";
        reference " 0.1.2.";
    }

    revision "2022-05-13" {
        description "Adding support for non-default management port";
        reference " 0.1.1.";
    }

    revision "2022-04-27" {
        description "Initial version to include callhome configs";
        reference " 0.1.0.";
    }


    grouping  netconf-server-grouping {
    description
        "Top level container for netconf server configurations";
    container netconf-server {
        if-feature feature-list:HAVE_NETCONF;
        if-feature feature-list:HAVE_CMLD;
        description
            "Top level container for netconf server configurations";
        container callhome {
            presence "yes";
            description
                "Top level container for netconf server callhome configurations";
            leaf feature-enabled  {
                type  empty;
                mandatory true;
                description "Enable callhome feature on the Netconf server";
            } // END of feature-enabled definition.

            leaf management-port  {
                type  leafref {
                    path  "/ipi-interface:interfaces/ipi-interface:interface/ipi-interface:name";
                }
                description "Interface to be used to connect the callhome server";
            } // END of management-port definition.


            list netconf-client {
                key "name";
                max-elements 5;
                description
                    "Object list for configuring callhome servers";
                leaf name  {
                    type  string {
                        length "1..64";
                        pattern "[^?' =,>|]+";
                    }
                    description "An arbitrary name for the NETCONF listen endpoint";
                } // END of name definition.

                leaf address  {
                    type  string {
                        length "1..63";
                        pattern "[^?' =,>|]+";
                    }
                    mandatory true;
                    description "The host address of the callhome server (IPv4/IPv6 address or Hostname
                                or DNS name)";
                } // END of address definition.

                leaf port  {
                    type  inet:port-number {
                         range "1..65535"  {
                            description "1..65535: Supported range 1 - 65535";
                         }
                    }
                    default "4334";
                    description "Callhome server listening port number";
                } // END of port definition.

            } // End of netconf-client-list
            container reconnect {
                presence "yes";
                description
                    "Container for Reconnect strategy configurations";
                leaf enable  {
                    type  empty;
                    mandatory true;
                    description "Specifies whether server will reconnect after client closes the
                                session";
                } // END of enable definition.

                leaf retry-max-attempts  {
                    type  uint8 {
                         range "0..255"  {
                            description "0..255: Supported range 0 - 255";
                         }
                    }
                    default "3";
                    description "Specifies the number of retry attempts the server should attempt to
                                the callhome server before giving up. Set 0 to retry infinitely.";
                } // END of retry-max-attempts definition.

                leaf retry-interval  {
                    type  uint32 {
                         range "1..86400"  {
                            description "1..86400: Supported range 1 - 86400";
                         }
                    }
                    units "seconds";
                    default "300";
                    description "Specifies the number of seconds to wait after a connect attempt to the
                                callhome server has failed";
                } // END of retry-interval definition.

            } // END of reconnect-container definition.
        } // END of callhome-container definition.
        container debug {
            description
                "Top level container for debug related configurations";
            leaf callhome-debug  {
                type  empty;
                description "Enable debugging info for callhome";
            } // END of callhome-debug definition.

        } // END of debug-container definition.
    } // END of netconf-server-container definition.
    } // END of netconf-server-grouping definition.

    uses netconf-server-grouping;
    uses management-server-grouping;

}
