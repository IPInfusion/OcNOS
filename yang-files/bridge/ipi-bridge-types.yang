/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-bridge-types.yang
*
*/

module ipi-bridge-types {

    yang-version 1.1;

    namespace   "http://www.ipinfusion.com/yang/ocnos/ipi-bridge-types";

    prefix "ipi-bridge-types";

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "This module defines types related to the spanning-tree protocol model";


    revision "2022-06-01" {
        description "Updated the yang file with feature";
        reference " 0.9.0.";
    }

    revision "2022-03-30" {
        description "Fixed Hybrid port VLAN Netconf issues and enabled support for Bridge related RPCs";
        reference " 0.8.0.";
    }

    revision "2022-01-25" {
        description "Added if-feature for BRIDGE_MAC_TYPE_T data type";
        reference " 0.7.0.";
    }

    revision "2022-01-13" {
        description "Added if-feature for data types";
        reference " 0.6.0.";
    }

    revision "2021-10-06" {
        description "Change helpstring for provider-mstp and provider-rstp";
        reference " 0.5.0.";
    }

    revision "2021-09-03" {
        description "Update descriptions of attribute";
        reference " 0.4.0.";
    }

    revision "2021-01-27" {
        description "RSTP vlan ring type bridge protocol added";
        reference " 0.3.0.";
    }

    revision "2020-12-15" {
        description "Change to have data-types in lower case instead of camel case";
        reference " 0.2.0.";
    }

    revision "2018-06-21" {
        description "Initial Version";
        reference " 0.1.0.";
    }



    typedef  bridge_protocol_t {
        type enumeration {
            enum ieee {
                value 1;
                description "IEEE 801.1Q spanning-tree protocol";
            }
            enum ieee-vlan-bridge {
                value 2;
                if-feature feature-list:HAVE_VLAN;
                description "IEEE 801.1Q spanning-tree protocol,Vlan aware bridge";
            }
            enum rstp {
                value 3;
                description "IEEE 801.1w rapid spanning-tree protocol";
            }
            enum rstp-vlan-bridge {
                value 4;
                description "IEEE 801.1w rapid spanning-tree protocol,Vlan aware bridge";
            }
            enum mstp {
                value 5;
                description "IEEE 802.1s multiple spanning-tree protocol";
            }
            enum provider-rstp {
                value 6;
                if-feature feature-list:HAVE_PROVIDER_BRIDGE;
                description "IEEE 802.1s provider rapid spanning-tree protocol";
            }
            enum provider-mstp {
                value 7;
                if-feature feature-list:HAVE_PROVIDER_BRIDGE;
                description "IEEE 802.1s provider multiple spanning-tree protocol";
            }
            enum rpvst+ {
                value 8;
                if-feature feature-list:HAVE_RPVST_PLUS;
                description "IEEE 801.1w rapid per vlan spanning-tree protocol";
            }
            enum rstp-ring {
                value 10;
                description "IEEE 801.1w rapid spanning-tree protocol,Enable Rapid Ring spanning-tree";
            }
            enum mstp-ring {
                value 11;
                description "IEEE 802.1s multiple spanning-tree protocol,Enable Rapid Ring spanning-tree";
            }
            enum provider-rstp-edge {
                value 12;
                if-feature feature-list:HAVE_PROVIDER_BRIDGE;
                description "IEEE 802.1s multiple spanning-tree protocol,Configure as Edge bridge";
            }
            enum provider-mstp-edge {
                value 13;
                if-feature feature-list:HAVE_PROVIDER_BRIDGE;
                description "IEEE 802.1s rapid spanning-tree protocol,Configure as Edge bridge";
            }
            enum rstp-vlan-bridge-ring {
                value 14;
                description "IEEE 801.1w rapid spanning-tree protocol,Vlan aware bridge,Enable Rapid Ring spanning-tree";
            }
            enum trill {
                value 20;
                if-feature feature-list:HAVE_TRILLD;
                description "Transparent Interconnection of Lots of Link";
            }
            enum evb {
                value 97;
                if-feature feature-list:HAVE_DCB;
                description "evb";
            }
            enum svlan-evb {
                value 98;
                if-feature feature-list:HAVE_DCB;
                description "Svlan aware evb";
            }
        }
        description "type definition for BRIDGE_PROTOCOL_T";
    }

    typedef  bridge_spanningtree_enable_disable_t {
        type enumeration {
            enum enable {
                value 0;
                description "Enable spanning tree on interface";
            }
            enum disable {
                value 1;
                description "Disable spanning tree on interface";
            }
        }
        description "type definition for BRIDGE_SPANNINGTREE_ENABLE_DISABLE_T";
    }

    typedef  bridge_discardforward_t {
        type enumeration {
            enum discard {
                value 0;
                description "discard frames";
            }
            enum forward {
                value 1;
                description "forward frames";
            }
        }
        description "type definition for BRIDGE_DISCARDFORWARD_T";
    }

    typedef  bridge_mac_type_t {
        type enumeration {
            enum multicast {
                value 2;
                description "Clear all multicast entries";
            }
        }
        description "type definition for BRIDGE_MAC_TYPE_T";
    }

}
