/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-telnet.yang
*
*/

module ipi-telnet {

    yang-version 1.1;

    namespace   "http://www.ipinfusion.com/yang/ocnos/ipi-telnet";

    prefix "ipi-telnet";

    import cml-data-types {
        prefix cml-data-types;
        revision-date 2022-09-30;
    }

    import ipi-network-instance {
        prefix ipi-network-instance;
        revision-date 2022-06-01;
    }

    import ipi-vrf {
        prefix ipi-vrf;
        revision-date 2022-07-13;
    }

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "Data model for telnet Module";


    revision "2022-06-01" {
        description "Updated the yang file with feature";
        reference " 0.2.0.";
    }

    revision "2021-07-14" {
        description "Initial Version";
        reference " 0.1.0.";
    }

    grouping telnet-server-config {
        description
            "telnet Server Configurations";
        leaf vrf-name  {
            type  leafref {
                path  "/ipi-network-instance:network-instances/ipi-network-instance:network-instance/ipi-vrf:vrf/ipi-vrf:config/ipi-vrf:vrf-name";
            }
            description "VRF Name associated with this instance";
        } // END of vrf-name definition.

        leaf enable  {
            type  boolean;
            mandatory true;
            description "Use this attribute to enable the Telnet server.";
        } // END of enable definition.

        leaf port  {
            if-feature feature-list:HAVE_TELNET_SERVER;
            type  uint32 {
                 range "1024..65535"  {
                    description "1024..65535: Supported range 1024 - 65535";
                 }
            }
            description "Use this attribute to set the port number on which the telnet server
                        listens for connections. The default port on which the telnet server
                        listens is 23.";
        } // END of port definition.

        leaf session-limit  {
            if-feature feature-list:HAVE_TELNET_SERVER;
            type  uint8 {
                 range "1..40"  {
                    description "1..40: Supported range 1 - 40";
                 }
            }
            description "Use this attribute to set the maximum number of simultaneous sessions
                        allowed. By default, 40 ssh-telnet sessions are allowed";
        } // END of session-limit definition.

    } // END of telnet-server-config definition.
    grouping telnet-server-debug-config {
        description
            "Telnet Server debug Configurations";
        leaf enable  {
            type  empty;
            description "Use this attribute to enable telnet debugging configurations";
        } // END of enable definition.

    } // END of telnet-server-debug-config definition.
    grouping telnet-server-debug-state {
        description
            "Telnet Server debug state";
        leaf terminal-debug-status  {
            type  cml-data-types:cml_on_off_t;
            description "Use this attribute to display telnet terminal debugging information.";
        } // END of terminal-debug-status definition.

    } // END of telnet-server-debug-state definition.
    grouping telnet-server-top {
        description
            "Telnet Server top configurations";
        container vrfs {
            description
                "telnet vrf configurations";

            list vrf {
                key "vrf-name";
                description
                    "telnet vrf instance configurations";
                leaf vrf-name  {
                    type  leafref {
                        path  "../config/vrf-name";
                    }
                    description "VPN routing/forwarding Instance name";
                } // END of vrf-name definition.

                container config {
                    description
                        "config container for telnet vrf instance configurations";
                    uses telnet-server-config;
                } // END of config-container definition.
                container state {
                    config false;
                    description
                        "state container for ssh vrf instance configurations";
                    uses telnet-server-config;
                } // END of state-container definition.
            } // End of vrf-list
        } // END of vrfs-container definition.
    } // END of telnet-server-top definition.

    grouping  telnet-server-grouping {
    description
        "telnet-server configurations";
    container telnet-server {
        if-feature feature-list:HAVE_HOSTPD;
        description
            "telnet-server configurations";
        container debug {
            description
                "telnet debug configurations";
            container config {
                description
                    "config container for telnet debug configurations";
                uses telnet-server-debug-config;
            } // END of config-container definition.
            container state {
                config false;
                description
                    "state container for telnet debug configurations";
                uses telnet-server-debug-config;
                uses telnet-server-debug-state;
            } // END of state-container definition.
        } // END of debug-container definition.
        uses telnet-server-top;
    } // END of telnet-server-container definition.
    } // END of telnet-server-grouping definition.

    uses telnet-server-grouping;

    rpc telnet-terminal-debugging-on {
        if-feature feature-list:HAVE_HOSTPD;
        description "Use this RPC to enable debugging for telnet server";
    }

    rpc telnet-terminal-debugging-off {
        if-feature feature-list:HAVE_HOSTPD;
        description "Use this RPC to disable debugging for telnet server";
    }

}
