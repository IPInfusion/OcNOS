/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-sys-update.yang
*
*/

module ipi-sys-update {

    yang-version 1.1;

    namespace   "http://www.ipinfusion.com/yang/ocnos/ipi-sys-update";

    prefix "ipi-sys-update";

    import cml-data-types {
        prefix cml-data-types;
        revision-date 2022-09-30;
    }

    import ipi-sys-update-types {
        prefix ipi-sys-update-types;
        revision-date 2022-06-01;
    }

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "sys-update provides the possibility for users to upgrade/downgrade
                OcNOS image in a router";


    revision "2022-06-29" {
        description "Adding support for sys-update details runtime attrs";
        reference " 0.3.1.";
    }

    revision "2022-06-01" {
        description "Updated the yang file with feature";
        reference " 0.3.0.";
    }

    revision "2022-03-22" {
        description "Adding support for docker container CLI support";
        reference " 0.2.0.";
    }

    revision "2021-07-30" {
        description "sys-update restructured";
        reference " 0.1.0.";
    }

    grouping system-update-state {
        description
            "systemCMLSEPupdateCMLSEPstate";
        leaf name  {
            type  string {
                length "1..1965";
                pattern "[^?' =,>|]+";
            }
            description "Installer image available in the device.";
        } // END of name definition.

    } // END of system-update-state definition.
    grouping system-update-top {
        description
            "systemCMLSEPupdateCMLSEPtop";
        container installers {
            config false;
            description
                "Container for system-update installers";

            list installer {
                key "name";
                config false;
                description
                    "List of installers";
                leaf name  {
                    type  leafref {
                        path  "../state/name";
                    }
                    description "Installer image available in the device.";
                } // END of name definition.

                container state {
                    config false;
                    description
                        "Installer operational data";
                    uses system-update-state;
                } // END of state-container definition.
            } // End of installer-list
        } // END of installers-container definition.
    } // END of system-update-top definition.
    grouping system-update-installer-details {
        description
            "systemCMLSEPupdateCMLSEPinstallerCMLSEPdetails";
        leaf previous-version  {
            type  cml-data-types:cml_line_t {
                length "1..1965";
            }
            description "Previously installed OcNOS image";
        } // END of previous-version definition.

        leaf current-version  {
            type  cml-data-types:cml_line_t {
                length "1..1965";
            }
            description "Presently installed/commited OcNOS image";
        } // END of current-version definition.

        leaf last-upgraded-time  {
            type  cml-data-types:cml_line_t {
                length "1..1965";
            }
            description "Time at when image was last upgraded";
        } // END of last-upgraded-time definition.

        leaf auto-rollback-end-time  {
            type  cml-data-types:cml_line_t {
                length "1..1965";
            }
            description "Time at which auto rollback happened";
        } // END of auto-rollback-end-time definition.

    } // END of system-update-installer-details definition.
    grouping system-update-details-top {
        description
            "systemCMLSEPupdateCMLSEPdetailsCMLSEPtop";
        container system-update-details {
            config false;
            description
                "Container system update installer details";
            container state {
                config false;
                description
                    "Container operational data";
                uses system-update-installer-details;
            } // END of state-container definition.
        } // END of system-update-details-container definition.
    } // END of system-update-details-top definition.
    grouping system-docker-images {
        description
            "systemCMLSEPdockerCMLSEPimages";
        container images {
            config false;
            description
                "Container for system container images";

            list image {
                key "name";
                config false;
                description
                    "List of container images";
                leaf name  {
                    type  leafref {
                        path  "../state/name";
                    }
                    description "Container image available in the device.";
                } // END of name definition.

                container state {
                    config false;
                    description
                        "Container operational data";
                    leaf name  {
                        type  string {
                            length "1..1965";
                            pattern "[^?' =,>|]+";
                        }
                        description "Container image available in the device.";
                    } // END of name definition.

                } // END of state-container definition.
            } // End of image-list
        } // END of images-container definition.
    } // END of system-docker-images definition.
    grouping system-docker-info {
        description
            "systemCMLSEPdockerCMLSEPinfo";
        leaf version  {
            type  string {
                length "1..1965";
                pattern "[^?' =,>|]+";
            }
            description "Version of current container installed on device.";
        } // END of version definition.

        leaf status  {
            type  string {
                length "1..1965";
                pattern "[^?' =,>|]+";
            }
            description "Running status of current container installed on device.";
        } // END of status definition.

    } // END of system-docker-info definition.
    grouping system-docker-info-top {
        description
            "systemCMLSEPdockerCMLSEPinfoCMLSEPtop";
        container info {
            config false;
            description
                "Container for system container images";
            container state {
                config false;
                description
                    "Container operational data";
                uses system-docker-info;
            } // END of state-container definition.
        } // END of info-container definition.
    } // END of system-docker-info-top definition.
    grouping system-docker-download {
        description
            "systemCMLSEPdockerCMLSEPdownload";
        leaf inprogress  {
            type  boolean;
            description "Inprogress state of container image";
        } // END of inprogress definition.

    } // END of system-docker-download definition.
    grouping system-docker-download-status {
        description
            "systemCMLSEPdockerCMLSEPdownloadCMLSEPstatus";
        container download-status {
            config false;
            description
                "Container ongoing download status";
            container state {
                config false;
                description
                    "Container operational data";
                uses system-docker-download;
            } // END of state-container definition.
        } // END of download-status-container definition.
    } // END of system-docker-download-status definition.

    grouping  system-update-grouping {
    description
        "Container for system-update";
    container system-update {
        if-feature feature-list:HAVE_PSERVD;
        if-feature feature-list:NOT_HAVE_TIBIT;
        description
            "Container for system-update";
        container docker {
            description
                "Container for system docker";
            uses system-docker-images;
            uses system-docker-info-top;
            uses system-docker-download-status;
        } // END of docker-container definition.
        uses system-update-top;
        uses system-update-details-top;
    } // END of system-update-container definition.
    } // END of system-update-grouping definition.

    uses system-update-grouping;

    rpc sys-update-install {
        if-feature feature-list:HAVE_PSERVD;
        if-feature feature-list:NOT_HAVE_TIBIT;
        description "Use this RPC to upgrade current software to a newer/older version.
                    Device will restore the startup configuration post upgrade, so to save
                    the running configuration into startup configuration perform
                    copy-config operation before sys-update operation. When device doesn't
                    have valid license this operation cannot performed. To download the
                    installer image management interface is used when source-interface
                    attribute is not specified";
        input  {
            leaf installer-name  {
                type string;
                mandatory true;
                description "Installer filename";
            }
            leaf ignore-feature-check  {
                type boolean;
                mandatory true;
                description "Ignore license feature check";
            }
        }
    }

    rpc sys-update-uninstall {
        if-feature feature-list:HAVE_PSERVD;
        if-feature feature-list:NOT_HAVE_TIBIT;
        description "Use this RPC to uninstall device software";
        reference "None";
    }

    rpc sys-update-get {
        if-feature feature-list:HAVE_PSERVD;
        if-feature feature-list:NOT_HAVE_TIBIT;
        description "Use this RPC to download an installer image.";
        input  {
            leaf source-interface  {
                type string;
                mandatory true;
                description "Source interface";
            }
            leaf url  {
                type string;
                mandatory true;
                description "Installer URL";
            }
        }
    }

    rpc sys-update-delete {
        if-feature feature-list:HAVE_PSERVD;
        if-feature feature-list:NOT_HAVE_TIBIT;
        description "Use this RPC to delete a downloaded image.";
        input  {
            leaf image-name  {
                type string;
                mandatory true;
                description "Installer filename";
            }
        }
    }

    rpc sys-update-cancel-download {
        if-feature feature-list:HAVE_PSERVD;
        if-feature feature-list:NOT_HAVE_TIBIT;
        description "Use this RPC to cancel the download which is running in the
                    background.";
    }

    rpc sys-container-install {
        if-feature feature-list:HAVE_PSERVD;
        if-feature feature-list:NOT_HAVE_TIBIT;
        description "Use this RPC to install or update the container image.";
        input  {
            leaf type  {
                type ipi-sys-update-types:system_container_type_t;
                mandatory true;
                description "Container type";
            }
            leaf upgrade-type  {
                type ipi-sys-update-types:system_container_upgrade_t;
                mandatory true;
                description "Upgrade type";
            }
            leaf file  {
                type string;
                mandatory true;
                description "Container image filename";
            }
        }
    }

    rpc sys-container-uninstall {
        if-feature feature-list:HAVE_PSERVD;
        if-feature feature-list:NOT_HAVE_TIBIT;
        description "Use this RPC to uninstall the container image.";
        input  {
            leaf type  {
                type ipi-sys-update-types:system_container_type_t;
                mandatory true;
                description "Container type";
            }
            leaf un-install  {
                type boolean;
                mandatory true;
                description "Upgrade type";
            }
        }
    }

    rpc sys-container-boot {
        if-feature feature-list:HAVE_PSERVD;
        if-feature feature-list:NOT_HAVE_TIBIT;
        description "Use this RPC to start, stop or restart the container instance.";
        input  {
            leaf type  {
                type ipi-sys-update-types:system_container_type_t;
                mandatory true;
                description "Container type";
            }
            leaf boot-type  {
                type ipi-sys-update-types:system_container_boot_t;
                mandatory true;
                description "Bootup type";
            }
        }
    }

    rpc sys-container-get {
        if-feature feature-list:HAVE_PSERVD;
        if-feature feature-list:NOT_HAVE_TIBIT;
        description "Use this RPC to download container image.";
        input  {
            leaf type  {
                type ipi-sys-update-types:system_container_type_t;
                mandatory true;
                description "Container type";
            }
            leaf url  {
                type string;
                mandatory true;
                description "Installer URL";
            }
            leaf source-interface  {
                type string;
                mandatory true;
                description "Source interface";
            }
        }
    }

    rpc sys-container-remove {
        if-feature feature-list:HAVE_PSERVD;
        if-feature feature-list:NOT_HAVE_TIBIT;
        description "Use this RPC to remove the container image from filesystem.";
        input  {
            leaf type  {
                type ipi-sys-update-types:system_container_type_t;
                mandatory true;
                description "Container type";
            }
            leaf file  {
                type string;
                mandatory true;
                description "Container image filename";
            }
        }
    }

    rpc sys-container-verify {
        if-feature feature-list:HAVE_PSERVD;
        if-feature feature-list:NOT_HAVE_TIBIT;
        description "Use this RPC to verify the container image against the signature file";
        input  {
            leaf type  {
                type ipi-sys-update-types:system_container_type_t;
                mandatory true;
                description "Container type";
            }
            leaf image  {
                type string;
                mandatory true;
                description "Container image filename";
            }
            leaf signature  {
                type string;
                mandatory true;
                description "Container image filename";
            }
        }
    }

    rpc sys-container-cancel-download {
        if-feature feature-list:HAVE_PSERVD;
        if-feature feature-list:NOT_HAVE_TIBIT;
        description "Use this RPC to cancel the download which is running in the
                    background.";
    }

    notification sys-update-installation-status {
        if-feature feature-list:HAVE_PSERVD;
        if-feature feature-list:NOT_HAVE_TIBIT;

        description "This system update event is generated when the software installation starts and ends..";

        leaf severity {
            type cml-data-types:cml_notif_severity_t;
            description "Notification severity level (value: INFO)";
        }

        leaf eventClass {
            type cml-data-types:cml_notif_class_t;
            description "Notification event class (value: MESSAGE)";
        }

        leaf message {
            type string;
            description " alarm message notification";
        }
    }

    notification sys-update-download-status {
        if-feature feature-list:HAVE_PSERVD;
        if-feature feature-list:NOT_HAVE_TIBIT;

        description "Notification sent on successful download operation with INFO severity or on failed download operation with MAJOR severity..";

        leaf severity {
            type cml-data-types:cml_notif_severity_t;
            description "Notification severity level (value: INFO)";
        }

        leaf eventClass {
            type cml-data-types:cml_notif_class_t;
            description "Notification event class (value: MESSAGE)";
        }

        leaf message {
            type string;
            description " alarm message notification";
        }
    }

    notification sys-container-download-status {
        if-feature feature-list:HAVE_PSERVD;
        if-feature feature-list:NOT_HAVE_TIBIT;

        description "Notification sent on successful download operation with INFO severity or on failed download operation with MAJOR severity..";

        leaf severity {
            type cml-data-types:cml_notif_severity_t;
            description "Notification severity level (value: INFO)";
        }

        leaf eventClass {
            type cml-data-types:cml_notif_class_t;
            description "Notification event class (value: MESSAGE)";
        }

        leaf message {
            type string;
            description " alarm message notification";
        }
    }

}
