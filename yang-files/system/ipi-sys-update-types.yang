/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-sys-update-types.yang
*
*/

module ipi-sys-update-types {

    yang-version 1.1;

    namespace   "http://www.ipinfusion.com/yang/ocnos/ipi-sys-update-types";

    prefix "ipi-sys-update-types";

    organization
        "IP Infusion Inc.";

    contact
        "Address: 3965 Freedom Circle, Suite 200, Santa Clara, CA 95054
         Phone: +1 408-400-1900
         E-mail: support@ipinfusion.com
         Web: http://www.ipinfusion.com/";

    description
        "system update data types";


    revision "2022-06-01" {
        description "Updated the yang file with feature";
        reference " 0.2.0.";
    }

    revision "2020-09-10" {
        description "Initial Version";
        reference " 0.1.0.";
    }



    typedef  system_container_upgrade_t {
        type enumeration {
            enum install {
                value 1;
                description "Install container";
            }
            enum update {
                value 2;
                description "Update container";
            }
        }
        description "type definition for SYSTEM_CONTAINER_UPGRADE_T";
    }

    typedef  system_container_boot_t {
        type enumeration {
            enum start {
                value 1;
                description "Start raon container";
            }
            enum stop {
                value 2;
                description "Stop raon container";
            }
            enum restart {
                value 3;
                description "Restart raon container";
            }
        }
        description "type definition for SYSTEM_CONTAINER_BOOT_T";
    }

    typedef  system_container_type_t {
        type enumeration {
            enum raon {
                value 1;
                description "Raon container";
            }
        }
        description "type definition for SYSTEM_CONTAINER_TYPE_T";
    }

}
