/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-logging-cli.yang
*
*/

submodule ipi-logging-cli {

    yang-version 1.1;

    belongs-to  ipi-logging { prefix ipi-logging; }

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "IMI global logging configurations";


    revision "2022-06-01" {
        description "Updated the yang file with feature";
        reference " 0.4.0.";
    }

    revision "2021-09-03" {
        description "Update descriptions of attribute";
        reference "Initial Version";
    }

    revision "2021-01-05" {
        description "Restructured module as per open-config";
        reference " 0.2.0.";
    }

    revision "2018-06-21" {
        description "Initial Version";
        reference " 0.1.0.";
    }

    grouping logging-cli-imi-config {
        description
            "Grouping for logging cli configuration";
        leaf enable-logging  {
            type  empty;
            description "Use this attribute to enable/disable CLI history logs. By default CLI
                        history is enabled.";
        } // END of enable-logging definition.

    } // END of logging-cli-imi-config definition.
    grouping max-session-limit-imi-config {
        description
            "Grouping for maximum session limit configuration";
        leaf max-session-limit  {
            type  uint8 {
                 range "1..40"  {
                    description "1..40: Supported range 1 - 40";
                 }
            }
            description "Use this attribute to set maximum session limit for vty.";
        } // END of max-session-limit definition.

    } // END of max-session-limit-imi-config definition.

    grouping  cli-logging-grouping {
    description
        "Logging cli configurations";
    container cli-logging {
        if-feature feature-list:HAVE_IMI;
        if-feature feature-list:HAVE_SYSLOG;
        description
            "Logging cli configurations";
        container config {
            description
                "Configuration data";
            uses logging-cli-imi-config;
        } // END of config-container definition.
        container state {
            config false;
            description
                "Operational state data";
            uses logging-cli-imi-config;
        } // END of state-container definition.
        container max-session-limit {
            description
                "This container defines max limit Configuration";
            container config {
                description
                    "This container defines max limit Configuration";
                uses max-session-limit-imi-config;
            } // END of config-container definition.
            container state {
                config false;
                description
                    "This container defines max limit state";
                uses max-session-limit-imi-config;
            } // END of state-container definition.
        } // END of max-session-limit-container definition.
    } // END of cli-logging-container definition.
    } // END of cli-logging-grouping definition.


}
