/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-logging-fault-management.yang
*
*/

submodule ipi-logging-fault-management {

    yang-version 1.1;

    belongs-to  ipi-logging { prefix ipi-logging; }

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "Logging control for fault-management";


    revision "2022-03-29" {
        description "Added support for shelve and close alarm RPCs";
        reference " 0.4.0.";
    }

    revision "2021-09-03" {
        description "Update descriptions of attribute";
        reference " 0.3.0.";
    }

    revision "2021-03-30" {
        description "Restructured module as per open-config style";
        reference " 0.2.0.";
    }

    revision "2018-06-21" {
        description "Initial Version";
        reference " 0.1.0.";
    }

    grouping logging-fault-management-config {
        description
            "Grouping for fault-management configuration";
        leaf enable-fault-management  {
            type  empty;
            description "Enable Fault Management System";
        } // END of enable-fault-management definition.

    } // END of logging-fault-management-config definition.

    grouping  fault-management-grouping {
    description
        "Fault management configuration";
    container fault-management {
        if-feature feature-list:HAVE_VLOGD;
        if-feature feature-list:HAVE_FMS;
        description
            "Fault management configuration";
        container config {
            description
                "Configuration data";
            uses logging-fault-management-config;
        } // END of config-container definition.
        container state {
            config false;
            description
                "Operational state data";
            uses logging-fault-management-config;
        } // END of state-container definition.
    } // END of fault-management-container definition.
    } // END of fault-management-grouping definition.


}
