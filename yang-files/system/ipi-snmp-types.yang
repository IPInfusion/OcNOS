/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-snmp-types.yang
*
*/

module ipi-snmp-types {

    yang-version 1.1;

    namespace   "http://www.ipinfusion.com/yang/ocnos/ipi-snmp-types";

    prefix "ipi-snmp-types";

    organization
        "IP Infusion Inc.";

    contact
        "Address: 3965 Freedom Circle, Suite 200, Santa Clara, CA 95054
         Phone: +1 408-400-1900
         E-mail: support@ipinfusion.com
         Web: http://www.ipinfusion.com/";

    description
        "snmp module datatypes";


    revision "2022-08-09" {
        description "Added if-feature in datatype";
        reference " 0.4.1.";
    }

    revision "2022-06-28" {
        description "Enable SNMP trap for PIM and PIM-BSR";
        reference " 0.4.0.";
    }

    revision "2022-06-01" {
        description "Updated the yang file with feature";
        reference " 0.3.0.";
    }

    revision "2022-03-11" {
        description "Updated basetypes for datatype SNMP_TRAP_PROTOCOLS from enum to bits";
        reference " 0.2.0.";
    }

    revision "2021-07-28" {
        description "Initial Version";
        reference " 0.1.0.";
    }



    typedef  snmp_trap_protocols {
        type bits {
            bit snmp-authentication {
                position 5;
                description "Module notifications enable,SNMP authentication trap";
            }
            bit mpls {
                position 6;
                description "mpls notification trap";
            }
            bit pw {
                position 7;
                description "pw notification trap";
            }
            bit pwdelete {
                position 8;
                description "PW delete notification trap";
            }
            bit rsvp {
                position 9;
                description "rsvp notification trap";
            }
            bit ospf {
                position 10;
                description "ospf notification trap";
            }
            bit bgp {
                position 11;
                description "bgp notification trap";
            }
            bit isis {
                position 12;
                description "isis notification trap";
            }
            bit vrrp {
                position 13;
                description "vrrp notification trap";
            }
            bit vxlan {
                position 14;
                description "vxlan notification trap";
            }
            bit ospf6 {
                position 15;
                description "ospf6 notification trap";
            }
            bit mplsl3vpn {
                position 16;
                description "mpls-l3vpn notification trap";
            }
            bit rib {
                position 17;
                description "rib notification trap";
            }
            bit pim {
                position 18;
                description "pim notification trap";
            }
        }
        description "type definition for SNMP_TRAP_PROTOCOLS";
    }

    typedef  snmp_agentx_debug_type_t {
        type bits {
            bit snmp-send {
                position 0;
                description "SNMP  (AgentX or SMUX),Packet send";
            }
            bit snmp-receive {
                position 1;
                description "SNMP  (AgentX or SMUX),Packet receive";
            }
            bit snmp-process {
                position 2;
                description "SNMP  (AgentX or SMUX),Packet process";
            }
            bit snmp-xdump {
                position 3;
                description "SNMP  (AgentX or SMUX),Packet hexa dump";
            }
            bit snmp-error-string {
                position 4;
                description "SNMP  (AgentX or SMUX),Error string display";
            }
            bit snmp-detail {
                position 5;
                description "SNMP  (AgentX or SMUX),Detail debugging";
            }
        }
        description "type definition for SNMP_AGENTX_DEBUG_TYPE_T";
    }

}
