/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-network-services-manager-types.yang
*
*/

module ipi-network-services-manager-types {

    yang-version 1.1;

    namespace   "http://www.ipinfusion.com/yang/ocnos/ipi-network-services-manager-types";

    prefix "ipi-network-services-manager-types";

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "network-services-manager datatypes";


    revision "2022-06-24" {
        description "db-synce issue fix JIRA-58792";
        reference " 0.1.0.";
    }

    revision "2022-06-01" {
        description "Updated the yang file with feature";
        reference "Initial Version";
    }

    revision "2021-09-03" {
        description "Update descriptions of attribute";
        reference "Initial Version";
    }

    revision "2021-07-30" {
        description "Initial Version";
        reference "Initial Version";
    }



    typedef  nsm_debug_type_t {
        type bits {
            bit addressmonitor {
                position 1;
                if-feature feature-list:NOT_PNE_VERSION_3_7;
                if-feature feature-list:NOT_PNE_VERSION_6_9;
                description "Enable Monitor adddress netlink";
            }
            bit bfd {
                position 2;
                if-feature feature-list:HAVE_BFD;
                description "Bidirectional Forwarding Detection (BFD)";
            }
            bit events {
                position 3;
                description "NSM events";
            }
            bit hal-events {
                position 4;
                if-feature feature-list:HAVE_HAL;
                if-feature feature-list:NOT_PNE_VERSION_6_9;
                if-feature feature-list:NOT_HAVE_SWFWDR;
                description " Hardware Abstraction Layer,NSM events";
            }
            bit hal-ipc {
                position 5;
                if-feature feature-list:HAVE_ASYNC;
                description "Hardware Abstraction Layer,Async Debugging";
            }
            bit linkmonitor {
                position 6;
                description "Enable Monitor link netlink";
            }
            bit packet-recv {
                position 9;
                description "NSM packets,NSM receive packets";
            }
            bit packet-recv-detail {
                position 10;
                description "NSM packets,NSM receive packets,Detailed information display";
            }
            bit packet-send {
                position 11;
                description "NSM packets,NSM receive packets";
            }
            bit packet-send-detail {
                position 12;
                description "NSM packets,NSM receive packets,Detailed information display";
            }
            bit ha {
                position 13;
                if-feature feature-list:HAVE_HA;
                description "NSM High Availability";
            }
            bit ha-all {
                position 14;
                if-feature feature-list:HAVE_HA;
                description "NSM High Availability,All NSM High Availability events";
            }
            bit vxlan {
                position 15;
                if-feature feature-list:HAVE_VXLAN;
                description "VXLAN";
            }
            bit trill {
                position 16;
                if-feature feature-list:HAVE_TRILLD;
                description "TRILL";
            }
            bit ipsec {
                position 17;
                if-feature feature-list:HAVE_IPSEC;
                description "IPSEC";
            }
            bit kernel {
                position 18;
                if-feature feature-list:HAVE_SWFWDR;
                description "NSM kernel";
            }
            bit mpls {
                position 19;
                if-feature feature-list:HAVE_MPLS;
                description "NSM mpls";
            }
        }
        description "type definition for NSM_DEBUG_TYPE_T";
    }

    typedef  nsm_pkt_mgr_debug_type_t {
        type bits {
            bit l2-protocol-cfm {
                position 2;
                description "debug pktmgr,layer2,protocol,cfm";
            }
            bit l2-protocol-eapol {
                position 3;
                description "debug pktmgr,layer2,protocol,eapol";
            }
            bit l2-protocol-efm {
                position 4;
                description "debug pktmgr,layer2,protocol,efm";
            }
            bit l2-protocol-igmp-snoop {
                position 5;
                description "debug pktmgr,layer2,protocol,igmp snoop";
            }
            bit l2-protocol-lacp {
                position 6;
                description "debug pktmgr,layer2,protocol,lacp";
            }
            bit l2-protocol-lldp {
                position 7;
                description "debug pktmgr,layer2,protocol,lldp";
            }
            bit l2-protocol-mldp-snoop {
                position 8;
                description "debug pktmgr,layer2,protocol,mldp snoop";
            }
            bit l2-protocol-mstp {
                position 9;
                description "debug pktmgr,layer2,protocol,mstp";
            }
            bit l2-protocol-ptp {
                position 10;
                description "debug pktmgr,layer2,protocol,ptp";
            }
        }
        description "type definition for NSM_PKT_MGR_DEBUG_TYPE_T";
    }

    typedef  nsm_exec_debug_type_t {
        type bits {
            bit addressmonitor {
                position 1;
                if-feature feature-list:NOT_PNE_VERSION_3_7;
                if-feature feature-list:NOT_PNE_VERSION_6_9;
                description "Enable Monitor adddress netlink";
            }
            bit bfd {
                position 2;
                if-feature feature-list:HAVE_BFD;
                description "Bidirectional Forwarding Detection (BFD)";
            }
            bit events {
                position 3;
                description "NSM events";
            }
            bit hal-events {
                position 4;
                if-feature feature-list:HAVE_HAL;
                if-feature feature-list:NOT_PNE_VERSION_6_9;
                if-feature feature-list:NOT_HAVE_SWFWDR;
                description " Hardware Abstraction Layer,NSM events";
            }
            bit hal-ipc {
                position 5;
                if-feature feature-list:HAVE_ASYNC;
                description "Hardware Abstraction Layer,Async Debugging";
            }
            bit linkmonitor {
                position 6;
                description "Enable Monitor link netlink";
            }
            bit packet-recv {
                position 9;
                description "NSM packets,NSM receive packets";
            }
            bit packet-recv-detail {
                position 10;
                description "NSM packets,NSM receive packets,Detailed information display";
            }
            bit packet-send {
                position 11;
                description "NSM packets,NSM receive packets";
            }
            bit packet-send-detail {
                position 12;
                description "NSM packets,NSM receive packets,Detailed information display";
            }
            bit ha {
                position 13;
                if-feature feature-list:HAVE_HA;
                description "NSM High Availability";
            }
            bit ha-all {
                position 14;
                if-feature feature-list:HAVE_HA;
                description "NSM High Availability,All NSM High Availability events";
            }
            bit vxlan {
                position 15;
                if-feature feature-list:HAVE_VXLAN;
                description "VXLAN";
            }
            bit trill {
                position 16;
                if-feature feature-list:HAVE_TRILLD;
                description "TRILL";
            }
            bit ipsec {
                position 17;
                if-feature feature-list:HAVE_IPSEC;
                description "IPSEC";
            }
            bit mpls {
                position 18;
                if-feature feature-list:HAVE_MPLS;
                description "NSM mpls";
            }
        }
        description "type definition for NSM_EXEC_DEBUG_TYPE_T";
    }

    typedef  nsm_pktmgr_statistics_type_t {
        type enumeration {
            enum stats {
                value 1;
                description "STATISTICS";
            }
            enum pkt-errors {
                value 2;
                description "PACKET ERROR STATS";
            }
        }
        description "type definition for NSM_PKTMGR_STATISTICS_TYPE_T";
    }

}
