/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-user-session-management-types.yang
*
*/

module ipi-user-session-management-types {

    yang-version 1.1;

    namespace   "http://www.ipinfusion.com/yang/ocnos/ipi-user-session-management-types";

    prefix "ipi-user-session-management-types";

    organization
        "IP Infusion Inc.";

    contact
        "Address: 3965 Freedom Circle, Suite 200, Santa Clara, CA 95054
         Phone: +1 408-400-1900
         E-mail: support@ipinfusion.com
         Web: http://www.ipinfusion.com/";

    description
        "User Session Management Types";


    revision "2021-11-16" {
        description "Module restructuring";
        reference " 0.2.0.";
    }



    typedef  line_console_id_t {
        type enumeration {
            enum 0 {
                value 0;
                description "First Line Number";
            }
        }
        description "type definition for LINE_CONSOLE_ID_T";
    }

}
