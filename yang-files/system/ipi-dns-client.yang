/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-dns-client.yang
*
*/

module ipi-dns-client {

    yang-version 1.1;

    namespace   "http://www.ipinfusion.com/yang/ocnos/ipi-dns-client";

    prefix "ipi-dns-client";

    import ietf-inet-types {
        prefix inet;
        revision-date 2013-07-15;
    }

    import cml-data-types {
        prefix cml-data-types;
        revision-date 2022-09-30;
    }

    import ipi-network-instance {
        prefix ipi-network-instance;
        revision-date 2022-06-01;
    }

    import ipi-vrf {
        prefix ipi-vrf;
        revision-date 2022-07-13;
    }

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "This module provides user with the possibility to configure the device
                DNS client parameters";


    revision "2022-06-24" {
        description "Added implicit delete for servers and search-domains containers";
        reference " 0.2.2.";
    }

    revision "2022-06-01" {
        description "Updated the yang file with feature";
        reference " 0.2.1.";
    }

    revision "2021-12-15" {
        description "Some if-feature removed from datamodel";
        reference " 0.2.0.";
    }

    revision "2021-11-16" {
        description "Added some if-feature to fix customer SKU compilation";
        reference " 0.1.3.";
    }

    revision "2021-08-23" {
        description "Type changed for attribute domain-lookup";
        reference " 0.1.2.";
    }

    revision "2021-08-18" {
        description "Some checks fixed for domain-list and nameservers";
        reference " 0.1.1.";
    }

    revision "2021-07-30" {
        description "Initial Version";
        reference " 0.1.0.";
    }

    grouping dns-vrf-host-entry-config {
        description
            "dnsCMLSEPvrfCMLSEPhostCMLSEPentryCMLSEPconfig";
        leaf hostname  {
            type  cml-data-types:cml_host_string_t {
                length "1..63";
            }
            description "Configure a static hostname-to-address mappings in DNS.";
        } // END of hostname definition.

        leaf ipv4-address  {
            type  inet:ipv4-address;
            description "Configure a static hostname-to-address IPv4 mapping in DNS.";
        } // END of ipv4-address definition.

        leaf ipv6-address  {
            if-feature feature-list:HAVE_IPV6;
            type  inet:ipv6-address;
            description "Configure a static hostname-to-address IPv6 mapping in DNS.";
        } // END of ipv6-address definition.

    } // END of dns-vrf-host-entry-config definition.
    grouping dns-vrf-host-entries-top {
        description
            "dnsCMLSEPvrfCMLSEPhostCMLSEPentriesCMLSEPtop";
        container host-entries {
            description
                "Static hosts data";

            list host-entry {
                key "hostname";
                description
                    "Static host data";
                leaf hostname  {
                    type  leafref {
                        path  "../config/hostname";
                    }
                    description "Configure a static hostname-to-address mappings in DNS.";
                } // END of hostname definition.

                container config {
                    description
                        "Static host configuration data";
                    uses dns-vrf-host-entry-config;
                } // END of config-container definition.
                container state {
                    config false;
                    description
                        "Static host operational state data";
                    uses dns-vrf-host-entry-config;
                } // END of state-container definition.
            } // End of host-entry-list
        } // END of host-entries-container definition.
    } // END of dns-vrf-host-entries-top definition.
    grouping dns-vrf-search-domain-config {
        description
            "dnsCMLSEPvrfCMLSEPsearchCMLSEPdomainCMLSEPconfig";
        leaf domain-name  {
            type  inet:domain-name {
                pattern "((([a-zA-Z0-9_]([a-zA-Z0-9\\-_]){0,61})?[a-zA-Z0-9]\\.)*([a-zA-Z0-9_]([a-zA-Z0-9\\-_]){0,61})?[a-zA-Z0-9]\\.?)|\\.";
                }
                description "Configure a list of default domain names used to complete unqualified
                            host names. Each domain in the list is to be tried in turn.The ip
                            domain-list command is similar to the ip domain-name command, except
                            that with the ip domain-list command you can define a list of domains,
                            each to be tried in turn.If there is no domain list, the default
                            domain name specified with the ip domain-name command is used. If
                            there is a domain list, the default domain name is not used.";
            } // END of domain-name definition.

    } // END of dns-vrf-search-domain-config definition.
    grouping dns-vrf-search-domains-top {
        description
            "dnsCMLSEPvrfCMLSEPsearchCMLSEPdomainsCMLSEPtop";
        container search-domains {
            description
                "Search domains data";

            list search-domain {
                key "domain-name";
                description
                    "Search domain data";
                leaf domain-name  {
                    type  leafref {
                        path  "../config/domain-name";
                    }
                    description "Use this attribute to define a list of default domain names used to
                                complete unqualified host names. Each domain in the list is to be
                                tried in turn. The ip domain-list command is similar to the ip
                                domain-name command, except that with the ip domain-list command you
                                can define a list of domains, each to be tried in turn.If there is no
                                domain list, the default domain name specified with the ip domain-name
                                command is used. If there is a domain list, the default domain name is
                                not used.";
                } // END of domain-name definition.

                container config {
                    description
                        "Search domain configuration data";
                    uses dns-vrf-search-domain-config;
                } // END of config-container definition.
                container state {
                    config false;
                    description
                        "Search domain operational state data";
                    uses dns-vrf-search-domain-config;
                } // END of state-container definition.
            } // End of search-domain-list
        } // END of search-domains-container definition.
    } // END of dns-vrf-search-domains-top definition.
    grouping dns-vrf-servers-config {
        description
            "dnsCMLSEPvrfCMLSEPserversCMLSEPconfig";
        leaf address  {
            type  inet:ip-address;
            description "Name server address used for name resolution.";
        } // END of address definition.

    } // END of dns-vrf-servers-config definition.
    grouping dns-vrf-servers-top {
        description
            "dnsCMLSEPvrfCMLSEPserversCMLSEPtop";
        container servers {
            description
                "Name servers data";

            list server {
                key "address";
                description
                    "Name server data";
                leaf address  {
                    type  leafref {
                        path  "../config/address";
                    }
                    description "Name server address used for name resolution.";
                } // END of address definition.

                container config {
                    description
                        "Name server configuration data";
                    uses dns-vrf-servers-config;
                } // END of config-container definition.
                container state {
                    config false;
                    description
                        "Server operational state data";
                    uses dns-vrf-servers-config;
                } // END of state-container definition.
            } // End of server-list
        } // END of servers-container definition.
    } // END of dns-vrf-servers-top definition.
    grouping dns-vrf-config {
        description
            "dnsCMLSEPvrfCMLSEPconfig";
        leaf vrf-name  {
            if-feature feature-list:HAVE_VRF;
            type  leafref {
                path  "/ipi-network-instance:network-instances/ipi-network-instance:network-instance/ipi-vrf:vrf/ipi-vrf:config/ipi-vrf:vrf-name";
            }
            description "VRF name associated with this instance.";
        } // END of vrf-name definition.

        leaf lookup-enabled  {
            type  boolean;
            description "Enable DNS translation.";
        } // END of lookup-enabled definition.

        leaf default-domain-name  {
            type  inet:domain-name {
                pattern "((([a-zA-Z0-9_]([a-zA-Z0-9\\-_]){0,61})?[a-zA-Z0-9]\\.)*([a-zA-Z0-9_]([a-zA-Z0-9\\-_]){0,61})?[a-zA-Z0-9]\\.?)|\\.";
                }
                description "Default domain name used to complete unqualified host names (names
                            without a dotted-decimal domain name).";
            } // END of default-domain-name definition.

    } // END of dns-vrf-config definition.
    grouping dns-vrfs-top {
        description
            "dnsCMLSEPvrfsCMLSEPtop";
        container vrfs {
            description
                "VRF list for DNS configuration";

            list vrf {
                key "vrf-name";
                description
                    "VRF list for DNS configuration";
                leaf vrf-name  {
                    type  leafref {
                        path  "../config/vrf-name";
                    }
                    description "VRF name associated with this instance.";
                } // END of vrf-name definition.

                container config {
                    description
                        "DNS configuration";
                    uses dns-vrf-config;
                } // END of config-container definition.
                container state {
                    config false;
                    description
                        "DNS operational state data";
                    uses dns-vrf-config;
                } // END of state-container definition.
                uses dns-vrf-servers-top;
                uses dns-vrf-search-domains-top;
                uses dns-vrf-host-entries-top;
            } // End of vrf-list
        } // END of vrfs-container definition.
    } // END of dns-vrfs-top definition.
    grouping dns-debug-config {
        description
            "dnsCMLSEPdebugCMLSEPconfig";
        leaf debug-status  {
            type  cml-data-types:cml_on_off_t;
            description "DNS client debug.";
        } // END of debug-status definition.

    } // END of dns-debug-config definition.
    grouping dns-debug-terminal-state {
        description
            "dnsCMLSEPdebugCMLSEPterminalCMLSEPstate";
        leaf debug-status  {
            type  cml-data-types:cml_on_off_t;
            description "DNS client debug.";
        } // END of debug-status definition.

    } // END of dns-debug-terminal-state definition.
    grouping dns-debug-terminal-top {
        description
            "dnsCMLSEPdebugCMLSEPterminalCMLSEPtop";
        container terminal {
            description
                "DNS client terminal debugging information";
            container state {
                config false;
                description
                    "DNS client terminal debugging information";
                uses dns-debug-terminal-state;
            } // END of state-container definition.
        } // END of terminal-container definition.
    } // END of dns-debug-terminal-top definition.
    grouping dns-debug-top {
        description
            "dnsCMLSEPdebugCMLSEPtop";
        container debug {
            description
                "DNS client debug data";
            container config {
                description
                    "DNS client debugging configuration";
                uses dns-debug-config;
            } // END of config-container definition.
            container state {
                config false;
                description
                    "DNS client debugging information";
                uses dns-debug-config;
            } // END of state-container definition.
            uses dns-debug-terminal-top;
        } // END of debug-container definition.
    } // END of dns-debug-top definition.

    grouping  dns-grouping {
    description
        "Container for DNS";
    container dns {
        if-feature feature-list:HAVE_DNS_CLIENT;
        description
            "Container for DNS";
        uses dns-vrfs-top;
        uses dns-debug-top;
    } // END of dns-container definition.
    } // END of dns-grouping definition.

    uses dns-grouping;

    rpc dns-client-terminal-debug-on {
        if-feature feature-list:HAVE_DNS_CLIENT;
        description "Enable DNS client debug";
    }

    rpc dns-client-terminal-debug-off {
        if-feature feature-list:HAVE_DNS_CLIENT;
        description "Disable DNS client debug";
    }

}
