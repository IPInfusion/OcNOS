/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : bridge.yang
*
*/

submodule bridge {

    belongs-to  ZebOS { prefix ZebOS; }
    include interface;
            include mstp;
            include vlan;


    import cml_data_types {
        prefix cml_data_types;
    }

    import feature_list {
        prefix feature_list;
    }

    description
        "Layer-2 bridge configurations";


    revision "2017-02-15" {
        description "added staticMac table for fdb entry.";
    }

    revision "2017-02-14" {
        description "adding missing flag for cli generation.";
    }

    revision "2017-02-10" {
        description "disabling trill bridge creation command.";
    }

    revision "2017-01-28" {
        description "adding flag for rpvts bridge.";
    }

    revision "2017-01-12" {
        description "adding support for svlan bridge.";
    }

    revision "2017-01-09" {
        description "default bridge command disabled.";
    }

    revision "2017-01-07" {
        description "change for helpstring in cli.";
    }

    revision "2016-10-13" {
        description "bridge module includes all bridge managed objects.";
    }

    revision "2016-09-12" {
        description "bridge module includes all bridge managed objects.";
    }



    grouping bridge-grouping {
        list bridge {
             
            description
                "bridge";

            config true;
            key "bridgeId";

            
            leaf bridgeId  {
                type  cml_data_types:CML_STRING_T {
                    length "0..255";
                }
            } // END of bridgeId definition.

            leaf bridgeType  {
                mandatory true;
                type  cml_data_types:CML_BRIDGE_PROTOCOL_T;  
            } // END of bridgeType definition.

            leaf isDefault  {
                type  cml_data_types:CML_INT8_T;  
                config false;
            } // END of isDefault definition.

            leaf ageingTime  {
                type  cml_data_types:CML_UINT32_T;  
                config false;
            } // END of ageingTime definition.

            leaf spanningTreeEnable  {
                type  cml_data_types:CML_UINT32_T;  
                config false;
            } // END of spanningTreeEnable definition.

            leaf providerEdge  {
                if-feature feature_list:HAVE_PROVIDER_BRIDGE;
                type  cml_data_types:CML_UINT32_T;  
                config false;
            } // END of providerEdge definition.

            leaf backboneEdge  {
                if-feature feature_list:HAVE_I_BEB;
                if-feature feature_list:HAVE_B_BEB;
                if-feature feature_list:HAVE_UDLD;
                type  cml_data_types:CML_UINT32_T;  
                config false;
            } // END of backboneEdge definition.

            leaf vlanNumDeletes  {
                if-feature feature_list:HAVE_PROVIDER_BRIDGE;
                type  cml_data_types:CML_UINT32_T;  
                config false;
            } // END of vlanNumDeletes definition.

            leaf trafficClassEnabled  {
                if-feature feature_list:HAVE_PROVIDER_BRIDGE;
                type  cml_data_types:CML_UINT32_T;  
                config false;
            } // END of trafficClassEnabled definition.

            leaf topologyType  {
                mandatory true;
                type  cml_data_types:CML_BRIDGE_TOPOLOGY_T;  
            } // END of topologyType definition.

            leaf numCosq  {
                if-feature feature_list:HAVE_QOS;
                type  cml_data_types:CML_UINT32_T;  
                config false;
            } // END of numCosq definition.

            leaf maxMstInstances  {
                type  cml_data_types:CML_UINT16_T;  
                config false;
            } // END of maxMstInstances definition.

            leaf uniTypeMode  {
                type  cml_data_types:CML_UINT16_T;  
                config false;
            } // END of uniTypeMode definition.

            leaf forward  {
                if-feature feature_list:HAVE_SPBD;
                type  cml_data_types:CML_BRIDGE_FORWARDING_SET_T;  
            } // END of forward definition.

            leaf addressFlag  {
                type  cml_data_types:CML_BOOL_T;  
            } // END of addressFlag definition.

            leaf brType  {
                type  cml_data_types:CML_BRIDGE_TYPE_T;  
            } // END of brType definition.

            leaf vlanId  {
                if-feature feature_list:HAVE_PROVIDER_BRIDGE;
                type  cml_data_types:CML_UINT32_T {
                     range "2..4094";
                }
            } // END of vlanId definition.

            leaf edgeProtocol  {
                if-feature feature_list:HAVE_PROVIDER_BRIDGE;
                type  cml_data_types:CML_UINT32_T;  
            } // END of edgeProtocol definition.

            leaf sVlanId  {
                if-feature feature_list:HAVE_PROVIDER_BRIDGE;
                type  cml_data_types:CML_UINT32_T {
                     range "2..4094";
                }
            } // END of sVlanId definition.


            list bridgeStaticFdb {
                 
                description
                    "bridgeStaticFdb";

                config false;
                key "macAddr";

                
                leaf macAddr  {
                    type  cml_data_types:CML_UINT32_T;  
                } // END of macAddr definition.

                leaf snmpStatus  {
                    type  cml_data_types:CML_UINT32_T;  
                } // END of snmpStatus definition.

                leaf timeVal  {
                    type  cml_data_types:CML_UINT32_T;  
                } // END of timeVal definition.

                leaf vid  {
                    type  cml_data_types:CML_UINT32_T;  
                } // END of vid definition.


                list interfaceInfo {
                     
                    description
                        "interfaceInfo";

                    config false;
                    key "ifindex";

                    
                    leaf ifindex  {
                        type  cml_data_types:CML_UINT32_T;  
                    } // END of ifindex definition.

                    leaf isForward  {
                        type  cml_data_types:CML_BOOL_T;  
                    } // END of isForward definition.

                    leaf type  {
                        type  cml_data_types:CML_UINT32_T;  
                    } // END of type definition.

                    leaf ovrMacType  {
                        type  cml_data_types:CML_UINT32_T;  
                    } // END of ovrMacType definition.

                    leaf priority  {
                        type  cml_data_types:CML_UINT32_T;  
                    } // END of priority definition.

                } // End of interfaceInfo-list
            } // End of bridgeStaticFdb-list

            list staticMac {
                 
                description
                    "static forwarding table entry for the bridge";

                config true;
                key "macAddr";

                
                leaf macAddr  {
                    type  cml_data_types:CML_STRING_T {
                        length "0..255";
                    }
                    description "bridge address";
                } // END of macAddr definition.

                leaf discardForward  {
                    type  cml_data_types:CML_DISCARDFORWARD_T;  
                } // END of discardForward definition.

                leaf ifName  {
                    type  cml_data_types:CML_STRING_T {
                        length "0..255";
                    }
                } // END of ifName definition.

            } // End of staticMac-list

            list vipTbllsit {
                                 if-feature feature_list:HAVE_I_BEB;

                description
                    "vipTbllsit";

                config true;
                key "vipSidStart";

                
                leaf vipSidStart  {
                    type  cml_data_types:CML_UINT32_T {
                         range "1..16777214";
                    }
                } // END of vipSidStart definition.

                leaf vipSidEnd  {
                    type  cml_data_types:CML_UINT32_T {
                         range "1..16777214";
                    }
                } // END of vipSidEnd definition.

                leaf srvInstName  {
                    type  cml_data_types:CML_STRING_T {
                        length "0..255";
                    }
                } // END of srvInstName definition.

            } // End of vipTbllsit-list

            list interface {
                 
                description
                    " Group of bridge attribute having interface property";

                config true;
                key "ifName";

                
                leaf ifName  {
                    type  cml_data_types:CML_STRING_T {
                        length "0..255";
                    }
                    description "bridge-group";
                } // END of ifName definition.

                leaf spanningTreeStatus  {
                    mandatory true;
                    type  cml_data_types:CML_SPANNINGTREE_ENABLE_DISABLE_T;  
                    description "bridge-group spanning-tree";
                } // END of spanningTreeStatus definition.

            } // End of interface-list

            list oepmapping {
                 
                description
                    "oepmapping";

                config true;
                key "oepTableName";

                
                leaf oepTableName  {
                    type  cml_data_types:CML_STRING_T {
                        length "0..255";
                    }
                } // END of oepTableName definition.

                leaf oepId  {
                    type  cml_data_types:CML_STRING_T {
                        length "0..255";
                    }
                } // END of oepId definition.

                leaf oepvlanTypeId  {
                    type  cml_data_types:CML_OEP_VLAN_TYPE_T;  
                } // END of oepvlanTypeId definition.

                leaf oepvlanId  {
                    type  cml_data_types:CML_UINT16_T {
                         range "2..4094";
                    }
                } // END of oepvlanId definition.

            } // End of oepmapping-list

            list cvlanRegTab {
                 
                description
                    "cvlanRegTab";

                config true;
                key "cvlanRegTabName";

                
                leaf cvlanRegTabName  {
                    type  cml_data_types:CML_STRING_T {
                        length "0..255";
                    }
                } // END of cvlanRegTabName definition.


                list cvlanRegId {
                                         if-feature feature_list:HAVE_PROVIDER_BRIDGE;

                    description
                        "cvlanRegId";

                    config true;
                    key "cvlanRegId";

                    
                    leaf cvlanRegId  {
                        if-feature feature_list:HAVE_PROVIDER_BRIDGE;
                        type  cml_data_types:CML_STRING_T {
                            length "0..255";
                        }
                    } // END of cvlanRegId definition.

                    leaf svlanRegId  {
                        if-feature feature_list:HAVE_PROVIDER_BRIDGE;
                        type  cml_data_types:CML_UINT16_T;  
                    } // END of svlanRegId definition.

                    leaf cvlanPepConfig  {
                        if-feature feature_list:HAVE_PROVIDER_BRIDGE;
                        type  cml_data_types:CML_CVLAN_CONFIG_T;  
                    } // END of cvlanPepConfig definition.

                } // End of cvlanRegId-list
            } // End of cvlanRegTab-list
            uses bridgeSpanning;
            uses mstp-grouping;
            uses vlan-grouping;
        } // End of bridge-list
    } // END of bridge-grouping definition.


    grouping spanningTree-grouping {
        list spanningTree {
                         if-feature feature_list:HAVE_DEFAULT_BRIDGE;

            description
                "spanningTree";

            config true;
            key "bridgeId";

            
            leaf bridgeId  {
                type  cml_data_types:CML_STRING_T {
                    length "0..255";
                }
            } // END of bridgeId definition.

            leaf spannMode  {
                type  cml_data_types:CML_BRIDGE_SPANMODE_T;  
            } // END of spannMode definition.

            leaf edgeFlag  {
                type  cml_data_types:CML_BOOL_T;  
                default false;
            } // END of edgeFlag definition.


            list spinterface {
                 
                description
                    " Group of bridge attribute having interface property";

                config true;
                key "ifName";

                
                leaf ifName  {
                    type  cml_data_types:CML_STRING_T {
                        length "0..255";
                    }
                    description "bridge-group";
                } // END of ifName definition.

                leaf spanningState  {
                    type  cml_data_types:CML_SPANNINGTREE_ENABLE_DISABLE_T;  
                    default "enable";
                } // END of spanningState definition.

            } // End of spinterface-list
            uses bridgeSpanning;
            uses spanInstance-grouping;
        } // End of spanningTree-list
    } // END of spanningTree-grouping definition.
    grouping bridgeSpanning {
                leaf-list macAddr  {
            type  cml_data_types:CML_STRING_T {
                length "0..255";
            }
            description "bridge address";
        } // END of macAddr definition.

        leaf discardForward  {
            type  cml_data_types:CML_DISCARDFORWARD_T;  
        } // END of discardForward definition.

        leaf learning  {
            type  cml_data_types:CML_BOOL_T;  
            description "bridge acquire";
        } // END of learning definition.

        leaf ifName  {
            type  cml_data_types:CML_STRING_T {
                length "0..255";
            }
        } // END of ifName definition.

        leaf macAddressTableLearning  {
            type  cml_data_types:CML_ENABLE_DISABLE_T;  
            default "enable";
        } // END of macAddressTableLearning definition.

        leaf macLimit  {
            type  cml_data_types:CML_INT32_T;  
        } // END of macLimit definition.

        leaf macLimitRange  {
            type  cml_data_types:CML_INT32_T {
                 range "5..32768";
            }
        } // END of macLimitRange definition.

    } // END of bridgeSpanning definition.


}
