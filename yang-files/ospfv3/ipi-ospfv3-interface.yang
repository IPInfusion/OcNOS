/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-ospfv3-interface.yang
*
*/

submodule ipi-ospfv3-interface {

    yang-version 1.1;

    belongs-to  ipi-ospfv3 { prefix ipi-ospfv3; }

    import feature-list {
        prefix feature-list;
        revision-date 2023-02-21;
    }

    import ietf-inet-types {
        prefix inet;
        revision-date 2013-07-15;
    }

    import ipi-interface {
        prefix ipi-interface;
        revision-date 2022-08-24;
    }

    import ipi-ospfv3-types {
        prefix ipi-ospfv3-types;
        revision-date 2022-06-01;
    }

    import ipi-ipsec {
        prefix ipi-ipsec;
        revision-date 2022-06-27;
    }

    include ipi-ospfv3-interface-state { revision-date 2022-06-01;}
    organization
        "IP Infusion Inc.";

    contact
        "Address: 3965 Freedom Circle, Suite 200, Santa Clara, CA 95054
         Phone: +1 408-400-1900
         E-mail: support@ipinfusion.com
         Web: http://www.ipinfusion.com/";

    description
        "Layer-3 OSPFv3 interface configurations";


    revision "2022-06-27" {
        description "Updated SPI range in ipsec module";
        reference " 0.1.9.";
    }

    revision "2022-06-24" {
        description "Internal fixes handling transform-set from ip-sec module";
        reference " 0.1.8.";
    }

    revision "2022-06-13" {
        description "Removed sa-lifetime attribute from ip-sec module";
        reference " 0.1.7.";
    }

    revision "2022-06-07" {
        description "Changed the dependent module config IPsec Transform-set ESP Configuration data container to a presence container";
        reference " 0.1.6.";
    }

    revision "2022-06-01" {
        description "Updated the yang file with feature";
        reference " 0.1.5.";
    }

    revision "2022-05-04" {
        description "Added authentication-cryptomap attribute for IPSec authentication support of OSPFv3";
        reference " 0.1.4.";
    }

    revision "2021-09-17" {
        description "Added interface-name leaf inside interface/config";
        reference " 0.1.3.";
    }

    revision "2021-09-03" {
        description "Update descriptions of attribute";
        reference " 0.1.2.";
    }

    revision "2021-07-26" {
        description "Notification support";
        reference " 0.1.1.";
    }

    revision "2021-06-17" {
        description "Restructured module in accordance with OpenConfig style";
        reference " 0.1.0.";
    }

    grouping ospfv3-interface-neighbor-static-state {
        description
            "Grouping for OSPFv3 static neighbor state data";
        leaf interface-state  {
            type  string {
                length "1..1965";
                pattern "[^?' =,>|]+";
            }
            description "This attribute returns the interface state value.";
        } // END of interface-state definition.

    } // END of ospfv3-interface-neighbor-static-state definition.
    grouping ospfv3-interface-neighbor-static-config {
        description
            "Grouping for OSPFv3 static neighbor configuration data";
        leaf address  {
            type  inet:ipv6-address;
            description "Static neighbor IPv6 link-local address";
        } // END of address definition.

        leaf cost  {
            type  uint16 {
                 range "1..65535"  {
                    description "1..65535: Supported range 1 - 65535";
                 }
            }
            default "10";
            description "Use this attribute to set the cost of the interface. This parameter
                        does not apply to NBMA networks.";
        } // END of cost definition.

        leaf priority  {
            type  uint8 {
                 range "0..255"  {
                    description "0..255: Supported range 0 - 255";
                 }
            }
            default "0";
            description "Use this attribute to set a neighbor priority. This parameter does not
                        apply to point-to-multipoint interfaces.";
        } // END of priority definition.

        leaf poll-interval  {
            type  uint32 {
                 range "0..4294967295"  {
                    description "0..4294967295: Supported range 0 - 4294967295";
                 }
            }
            units "seconds";
            default "120";
            description "Use this attribute to set the dead neighbor polling interval in
                        seconds. It is recommended to set this value much higher than the
                        hello interval. The default is 120 seconds.";
        } // END of poll-interval definition.

    } // END of ospfv3-interface-neighbor-static-config definition.
    grouping ospfv3-interface-neighbor-static-top {
        description
            "Grouping for OSPFv3 neighbor static";
        container neighbors-static {
            description
                "Configuration data for OSPFv3 static neighbors";

            list neighbor-static {
            when " /ospfv3/interfaces/interface/instances/instance/config/network-type != 'point-to-point' and /ospfv3/interfaces/interface/instances/instance/config/network-type != 'broadcast' ";
                key "address";
                description
                    "List of OSPFv3 static neighbors";
                leaf address  {
                    type  leafref {
                        path  "../config/address";
                    }
                    description "Static neighbor IPv6 link-local address";
                } // END of address definition.

                container config {
                    description
                        "Configuration data for OSPFv3 static neighbor";
                    uses ospfv3-interface-neighbor-static-config;
                } // END of config-container definition.
                container state {
                    config false;
                    description
                        "Operational state data for OSPFv3 static neighbor";
                    uses ospfv3-interface-neighbor-static-config;
                    uses ospfv3-interface-neighbor-static-state;
                } // END of state-container definition.
            } // End of neighbor-static-list
        } // END of neighbors-static-container definition.
    } // END of ospfv3-interface-neighbor-static-top definition.
    grouping ospfv3-interface-timers-config {
        description
            "Grouping for OSPFv3 interface timers configuration data";
        leaf dead-interval  {
            type  uint16 {
                 range "1..65535"  {
                    description "1..65535: Supported range 1 - 65535";
                 }
            }
            units "seconds";
            default "40";
            description "Use this attribute to set the amount of time that the router waits to
                        receive an OSPF hello packet from the neighbor before declaring the
                        neighbor down";
        } // END of dead-interval definition.

        leaf hello-interval  {
            type  uint16 {
                 range "1..65535"  {
                    description "1..65535: Supported range 1 - 65535";
                 }
            }
            units "seconds";
            description "Use this attribute to set the interval between hello packets.";
        } // END of hello-interval definition.

        leaf transmission-delay  {
            type  uint16 {
                 range "1..1800"  {
                    description "1..1800: Supported range 1 - 1800";
                 }
            }
            units "seconds";
            default "1";
            description "Use this attribute to set the estimated time it takes to transmit a
                        Link State Update packet over the interface.";
        } // END of transmission-delay definition.

        leaf retransmission-interval  {
            type  uint16 {
                 range "1..1800"  {
                    description "1..1800: Supported range 1 - 1800";
                 }
            }
            units "seconds";
            default "5";
            description "Use this attibute to set the interval between retransmission of Link
                        State Update packets.";
        } // END of retransmission-interval definition.

    } // END of ospfv3-interface-timers-config definition.
    grouping ospfv3-interface-timers-top {
        description
            "Grouping for OSPFv3 interface timers";
        container timers {
            description
                "Configuration data for OSPFv3 interface timers";
            container config {
                description
                    "Configuration data for OSPFv3 interface timers";
                uses ospfv3-interface-timers-config;
            } // END of config-container definition.
            container state {
                config false;
                description
                    "Operational state data for OSPFv3 interface timers";
                uses ospfv3-interface-timers-config;
            } // END of state-container definition.
        } // END of timers-container definition.
    } // END of ospfv3-interface-timers-top definition.
    grouping ospfv3-interface-router-config {
        description
            "Grouping for OSPFv3 interface router configuration data";
        leaf ospfv3-id  {
            type  ipi-ospfv3-types:ospfv3_string_t;
            default "";
            description "Use this attribute to enable OSPFv3 routing on an interface. Specify
                        the process ID to configure multiple instances of OSPFv3. When running
                        a single instance of OSPFv3, you do not need to specify a instance ID.
                        When OSPFv3 receives a packet, it checks if the instance ID in the
                        packet matches the instance ID of the receiving interface.";
        } // END of ospfv3-id definition.

        leaf area-id  {
            type  ipi-ospfv3-types:ospfv3_area_t;
            description "Use this attribute to enable OSPFv3 routing on an interface. Specify
                        the process ID to configure multiple instances of OSPFv3. When running
                        a single instance of OSPFv3, you do not need to specify a instance ID.
                        When OSPFv3 receives a packet, it checks if the instance ID in the
                        packet matches the instance ID of the receiving interface.";
        } // END of area-id definition.

    } // END of ospfv3-interface-router-config definition.
    grouping ospfv3-interface-router-top {
        description
            "Grouping for OSPFv3 interface router top-level";
        container routers {
            description
                "Configuration data for OSPFv3 interface routers";

            list router {
                key "ospfv3-id area-id";
                max-elements 1;
                description
                    "List of OSPFv3 interface routers";
                leaf ospfv3-id  {
                    type  leafref {
                        path  "../config/ospfv3-id";
                    }
                    description "Use this attribute to enable OSPFv3 routing on an interface. Specify
                                the process ID to configure multiple instances of OSPFv3. When running
                                a single instance of OSPFv3, you do not need to specify a instance ID.
                                When OSPFv3 receives a packet, it checks if the instance ID in the
                                packet matches the instance ID of the receiving interface.";
                } // END of ospfv3-id definition.

                leaf area-id  {
                    type  leafref {
                        path  "../config/area-id";
                    }
                    description "Use this attribute to enable OSPFv3 routing on an interface. Specify
                                the process ID to configure multiple instances of OSPFv3. When running
                                a single instance of OSPFv3, you do not need to specify a instance ID.
                                When OSPFv3 receives a packet, it checks if the instance ID in the
                                packet matches the instance ID of the receiving interface.";
                } // END of area-id definition.

                container config {
                    description
                        "Configuration data for OSPFv3 router";
                    uses ospfv3-interface-router-config;
                } // END of config-container definition.
                container state {
                    config false;
                    description
                        "Operational state data for OSPFv3 router";
                    uses ospfv3-interface-router-config;
                } // END of state-container definition.
            } // End of router-list
        } // END of routers-container definition.
    } // END of ospfv3-interface-router-top definition.
    grouping ospfv3-interface-instance-config {
        description
            "Grouping for OSPFv3 interface instance configuration data";
        leaf instance-id  {
            type  uint8 {
                 range "0..31 | 64..95"  {
                    description "0..31: Supported range 0 - 31,64..95: Supported range 64 - 95";
                 }
            }
            description "Use this attribute to set the interface instance ID. Each Instance
                        ID implies a separate OSPFv3 instance with its own neighbor
                        adjacencies, link state database, protocol data structures, and
                        shortest path first (SPF) computation.";
        } // END of instance-id definition.

        leaf network-type  {
            type  ipi-ospfv3-types:ospfv3_network_type_t;
            description "Use this attribute to set an OSPFv3 network type.";
        } // END of network-type definition.

        leaf cost  {
            type  uint16 {
                 range "1..65535"  {
                    description "1..65535: Supported range 1 - 65535";
                 }
            }
            default "10";
            description "Use this attribute to specify the link-cost described in LSAs.The cost
                        (or metric) of an interface in OSPF indicates the overhead required to
                        send packets across a certain interface. The value is taken to
                        describe Link State information, and used for route calculation.";
        } // END of cost definition.

        leaf priority  {
            type  uint8 {
                 range "0..255"  {
                    description "0..255: Supported range 0 - 255";
                 }
            }
            default "1";
            description "Use this attribute to set the router priority for determining the
                        designated router (DR) for the network. A router with the higher
                        router priority becomes the DR. If the priority is the same for two
                        routers, the router with the higher router ID takes precedence. Only
                        routers with a nonzero priority value are eligible to become the
                        designated or backup designated router. Configure router priority for
                        broadcast or NBMA networks only and not for point-to-point networks.";
        } // END of priority definition.

        leaf traffic-engineering-metric  {
            if-feature feature-list:HAVE_OSPF6_TE;
            type  uint16 {
                 range "1..65535"  {
                    description "1..65535: Supported range 1 - 65535";
                 }
            }
            description "Use this attribute to set the traffic engineering metric for an
                        interface. The traffic engineering metric is used in OSPF-TE Link
                        State Advertisements. If the traffic engineering metric is not set,
                        the ipv6 ospf cost value for an interface is used in OSPF-TE Link
                        State Advertisements.";
        } // END of traffic-engineering-metric definition.

        leaf mtu  {
            type  uint16 {
                 range "1280..65535"  {
                    description "1280..65535: Supported range 1280 - 65535";
                 }
            }
            default "1500";
            description "Use this attribute to set MTU size for OSPFv3 to construct packets
                        based on this value. Whenever OSPFv3 constructs packets, it uses
                        interface MTU size as Maximum IP packet size. this attribute forces
                        OSPFv3 to use the specified value overriding the actual interface MTU
                        size.";
        } // END of mtu definition.

        leaf mtu-ignore  {
            type  empty;
            description "Use this attribute to ignore the MTU size during DD (Database
                        Description) exchange. By default, during the DD exchange process,
                        OSPFv3 checks the MTU size described in DD packets received from its
                        neighbor, and if the MTU size does not match the interface MTU, the
                        neighbor adjacency is not established. Using this command makes OSPFv3
                        ignore this check and allows establishing of adjacency regardless of
                        MTU size in the DD packet.";
        } // END of mtu-ignore definition.

        leaf enable-demand-circuit  {
            if-feature feature-list:HAVE_OSPF6_OD;
            type  empty;
            description "Use this attribute to enable Hello Suppression and LSA Suppression
                        sent on OSPFv3 interface.";
        } // END of enable-demand-circuit definition.

        leaf enable-flood-reduction  {
            if-feature feature-list:HAVE_OSPF6_OD;
            type  empty;
            description "Use this attribute to enable DoNotAge option in LSA sent on an OSPFv3
                        interface.When this command is configured,
                        router can send/receive LSA with DNA option set and process them on
                        the interface.";
        } // END of enable-flood-reduction definition.

        leaf enable-link-lsa-suppression  {
            type  empty;
            description "Use this attribute to enable or disable link LSA (type 8) suppression.
                        A type 8 LSA gives information about link-local addresses and a list
                        of IPv6 addresses on the link. If enabled and the interface type is
                        not broadcast or NBMA, the router does not send type 8 link LSAs. This
                        implies that other routers on the link determine the router's next-hop
                        address using a mechanism other than the type 8 link LSA. This feature
                        is implicitly disabled if the interface type is broadcast or NBMA.";
        } // END of enable-link-lsa-suppression definition.

        leaf enable-bfd  {
            if-feature feature-list:HAVE_BFD;
            type  boolean;
            description "Use this attribute to enable Bidirectional Forwarding Detection (BFD)";
        } // END of enable-bfd definition.

        leaf disable-fast-reroute  {
            if-feature feature-list:HAVE_OSPF6_LFA;
            type  empty;
            description "Use this attribute to prohibit the interface from being used as the
                        next hop in a repair path.";
        } // END of disable-fast-reroute definition.

        leaf authentication-cryptomap  {
            if-feature feature-list:HAVE_IPSEC;
            if-feature feature-list:HAVE_TUNNEL;
            type  leafref {
                path  "/ipi-ipsec:ipsec/ipi-ipsec:crypto-maps/ipi-ipsec:crypto-map/ipi-ipsec:config/ipi-ipsec:name";
            }
            description "Use this attribute to set the Crypto-map used to setup IPsec SA.";
        } // END of authentication-cryptomap definition.

    } // END of ospfv3-interface-instance-config definition.
    grouping ospfv3-interface-instance-top {
        description
            "Grouping for OSPFv3 interface instance";
        container instances {
            description
                "Configuration data for OSPFv3 interface instances";

            list instance {
                key "instance-id";
                description
                    "List of OSPFv3 interface instances";
                leaf instance-id  {
                    type  leafref {
                        path  "../config/instance-id";
                    }
                    description "Use this attribute to set the interface instance ID. Each Instance
                                ID implies a separate OSPFv3 instance with its own neighbor
                                adjacencies, link state database, protocol data structures, and
                                shortest path first (SPF) computation";
                } // END of instance-id definition.

                container config {
                    description
                        "Configuration data for OSPFv3";
                    uses ospfv3-interface-instance-config;
                } // END of config-container definition.
                container state {
                    config false;
                    description
                        "Operational state data for OSPFv3 interface";
                    container statistics {
                        config false;
                        description
                            "OSPFv3 interface status";
                        uses ospfv3-interface-instance-statistics-state;
                    } // END of statistics-container definition.
                    uses ospfv3-interface-instance-config;
                    uses ospfv3-interface-instance-state;
                } // END of state-container definition.
                uses ospfv3-interface-router-top;
                uses ospfv3-interface-timers-top;
                uses ospfv3-interface-neighbor-static-top;
                uses ospfv3-interface-designated-router-state;
                uses ospfv3-interface-backup-designated-router-state;
                uses ospfv3-interface-instance-neighbor-state;
            } // End of instance-list
        } // END of instances-container definition.
    } // END of ospfv3-interface-instance-top definition.
    grouping ospfv3-interface-config {
        description
            "Grouping for OSPFv3 interface configuration data";
        leaf interface-name  {
            type  leafref {
                path  "/ipi-interface:interfaces/ipi-interface:interface/ipi-interface:name";
            }
            description "Interface name for which OSPFv3 is being configured.";
        } // END of interface-name definition.

        leaf shutdown  {
            type  empty;
            description "Use this attribute to shutdown OSPFV3 on the interface";
        } // END of shutdown definition.

    } // END of ospfv3-interface-config definition.
    grouping ospfv3-interface-config-error {
        description
            "ospfv3CMLSEPinterfaceCMLSEPconfigCMLSEPerror";
        container interface-config-error {
            config false;
            description
                "Interface configuration error";
            leaf router-id  {
                type  inet:ipv4-address;
                description "OSPFv3 router ID.";
            } // END of router-id definition.

            leaf interface-index  {
                type  uint32;
                description "Interface index.";
            } // END of interface-index definition.

            leaf interface-instance-id  {
                type  uint8;
                description "Interface instance ID.";
            } // END of interface-instance-id definition.

            leaf error-type  {
                type  ipi-ospfv3-types:ospfv3_config_error_type_t;
                description "Error type.";
            } // END of error-type definition.

            leaf packet-type  {
                type  ipi-ospfv3-types:ospfv3_packet_type_t;
                description "Packet type.";
            } // END of packet-type definition.

        } // END of interface-config-error-container definition.
    } // END of ospfv3-interface-config-error definition.
    grouping ospfv3-interface-state-change {
        description
            "ospfv3CMLSEPinterfaceCMLSEPstateCMLSEPchange";
        container interface-state-change {
            config false;
            description
                "Interface state change notification";
            leaf router-id  {
                type  inet:ipv4-address;
                description "OSPFv3 router ID.";
            } // END of router-id definition.

            leaf interface-index  {
                type  uint32;
                description "Interface index.";
            } // END of interface-index definition.

            leaf interface-instance-id  {
                type  uint8;
                description "Interface instance ID.";
            } // END of interface-instance-id definition.

            leaf interface-state  {
                type  ipi-ospfv3-types:ospfv3_interface_state_t;
                description "Interface state.";
            } // END of interface-state definition.

        } // END of interface-state-change-container definition.
    } // END of ospfv3-interface-state-change definition.
    grouping ospfv3-interface-rx-bad-packet {
        description
            "ospfv3CMLSEPinterfaceCMLSEPrxCMLSEPbadCMLSEPpacket";
        container interface-rx-bad-packet {
            config false;
            description
                "Interface RX bad packet notification";
            leaf router-id  {
                type  inet:ipv4-address;
                description "OSPFv3 router ID.";
            } // END of router-id definition.

            leaf interface-index  {
                type  uint32;
                description "Interface index.";
            } // END of interface-index definition.

            leaf interface-instance-id  {
                type  uint8;
                description "Interface instance ID.";
            } // END of interface-instance-id definition.

            leaf packet-src  {
                type  inet:ipv6-address;
                description "The source IPv6 address";
            } // END of packet-src definition.

            leaf packet-type  {
                type  ipi-ospfv3-types:ospfv3_packet_type_t;
                description "Packet type.";
            } // END of packet-type definition.

        } // END of interface-rx-bad-packet-container definition.
    } // END of ospfv3-interface-rx-bad-packet definition.

    grouping  interfaces-grouping {
    description
        "Configuration data for OSPFv3 interfaces";
    container interfaces {
        if-feature feature-list:HAVE_OSPF6D;
        if-feature feature-list:HAVE_IPV6;
        description
            "Configuration data for OSPFv3 interfaces";

        list interface {
        when " /ospfv3/interfaces/interface/instances  or /ospfv3/interfaces/interface/config/shutdown ";
            key "interface-name";
            description
                "List of OSPFv3 interfaces";
            leaf interface-name  {
                type  leafref {
                    path  "../config/interface-name";
                }
                description "Interface name for which OSPFv3 is being configured.";
            } // END of interface-name definition.

            container config {
                description
                    "Configuration data for OSPFv3 interface";
                uses ospfv3-interface-config;
            } // END of config-container definition.
            container state {
                config false;
                description
                    "Operational state data for OSPFv3 interface";
                uses ospfv3-interface-config;
                uses ospfv3-interface-config-error;
                uses ospfv3-interface-state-change;
                uses ospfv3-interface-rx-bad-packet;
            } // END of state-container definition.
            uses ospfv3-interface-instance-top;
        } // End of interface-list
    } // END of interfaces-container definition.
    } // END of interfaces-grouping definition.


}
