/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-ospfv3-debug.yang
*
*/

submodule ipi-ospfv3-debug {

    yang-version 1.1;

    belongs-to  ipi-ospfv3 { prefix ipi-ospfv3; }

    import feature-list {
        prefix feature-list;
        revision-date 2023-02-21;
    }

    import ipi-ospfv3-types {
        prefix ipi-ospfv3-types;
        revision-date 2022-06-01;
    }

    organization
        "IP Infusion Inc.";

    contact
        "Address: 3965 Freedom Circle, Suite 200, Santa Clara, CA 95054
         Phone: +1 408-400-1900
         E-mail: support@ipinfusion.com
         Web: http://www.ipinfusion.com/";

    description
        "Layer-3 OSPFv3 debug configurations";


    revision "2022-06-01" {
        description "Updated the yang file with feature";
        reference " 0.1.3.";
    }

    revision "2021-09-01" {
        description "Fixed command to enable all debugging after partial configuration";
        reference " 0.1.2.";
    }

    revision "2021-08-13" {
        description "Added container to debug packet";
        reference " 0.1.1.";
    }

    revision "2021-06-17" {
        description "Restructured module in accordance with OpenConfig style";
        reference " 0.1.0.";
    }

    grouping ospfv3-debug-config {
        description
            "Grouping for OSPFv3 debug configuration data";
        leaf bfd  {
            if-feature feature-list:HAVE_BFD;
            type  empty;
            description "Bidirectional Forwarding Detection (BFD)";
        } // END of bfd definition.

        leaf retransmission  {
            type  empty;
            description "OSPFv3 retransmission information";
        } // END of retransmission definition.

        leaf events  {
            type  ipi-ospfv3-types:ospfv3_debug_event_t;
            description "OSPFv3 events information";
        } // END of events definition.

        leaf ifsm  {
            type  ipi-ospfv3-types:ospfv3_debug_ifsm_t;
            description "Use this attribute to enable OSPFv3 Interface State Machine debug";
        } // END of ifsm definition.

        leaf lfa  {
            if-feature feature-list:HAVE_OSPF6_LFA;
            type  empty;
            description "Use this attribute to enable OSPFv3 LFA route install details debug";
        } // END of lfa definition.

        leaf lsa  {
            type  ipi-ospfv3-types:ospfv3_debug_lsa_t;
            description "Use this attribute to enable OSPFv3 Link State Advertisement debug";
        } // END of lsa definition.

        leaf nfsm  {
            type  ipi-ospfv3-types:ospfv3_debug_nfsm_t;
            description "Use this attribute to enable OSPFv3 Neighbor State Machine debug";
        } // END of nfsm definition.

        leaf nsm  {
            type  ipi-ospfv3-types:ospfv3_debug_nsm_t;
            description "Use this attribute to enable OSPFv3 NSM information debug";
        } // END of nsm definition.

        leaf rib  {
            if-feature feature-list:HAVE_RIBD;
            type  ipi-ospfv3-types:ospfv3_debug_rib_t;
            description "Use this attribute to enable OSPFv3 RIB information debug";
        } // END of rib definition.

        leaf route  {
            type  ipi-ospfv3-types:ospfv3_debug_route_t;
            description "Use this attribute to enable OSPFv3 route information debug";
        } // END of route definition.

        container packet {
            description
                "OSPFv3 debug packet";
            leaf hello  {
                type  ipi-ospfv3-types:ospfv3_debug_packet_options_t;
                description "OSPFv3 Hello";
            } // END of hello definition.

            leaf dd  {
                type  ipi-ospfv3-types:ospfv3_debug_packet_options_t;
                description "OSPFv3 Database Description";
            } // END of dd definition.

            leaf ls-request  {
                type  ipi-ospfv3-types:ospfv3_debug_packet_options_t;
                description "OSPFv3 Link State Request";
            } // END of ls-request definition.

            leaf ls-update  {
                type  ipi-ospfv3-types:ospfv3_debug_packet_options_t;
                description "OSPFv3 Link State Update";
            } // END of ls-update definition.

            leaf ls-ack  {
                type  ipi-ospfv3-types:ospfv3_debug_packet_options_t;
                description "OSPFv3 Link State Acknowledgment";
            } // END of ls-ack definition.

        } // END of packet-container definition.
    } // END of ospfv3-debug-config definition.
    grouping ospfv3-debug-terminal-state {
        description
            "Grouping for OSPFv3 debug state for exec mode";
        container terminal-debug {
            config false;
            description
                "Runtime attributes for terminal debug";
            leaf bfd  {
                if-feature feature-list:HAVE_BFD;
                type  empty;
                description "Bidirectional Forwarding Detection (BFD)";
            } // END of bfd definition.

            leaf retransmission  {
                type  empty;
                description "OSPFv3 Debug retransmission information";
            } // END of retransmission definition.

            leaf events  {
                type  ipi-ospfv3-types:ospfv3_debug_event_t;
                description "OSPFv3 events information";
            } // END of events definition.

            leaf ifsm  {
                type  ipi-ospfv3-types:ospfv3_debug_ifsm_t;
                description "Use this attribute to enable OSPFv3 Interface State Machine debug";
            } // END of ifsm definition.

            leaf lfa  {
                if-feature feature-list:HAVE_OSPF6_LFA;
                type  empty;
                description "Use this attribute to enable OSPFv3 LFA route install details debug";
            } // END of lfa definition.

            leaf lsa  {
                type  ipi-ospfv3-types:ospfv3_debug_lsa_t;
                description "Use this attribute to enable OSPFv3 Link State Advertisement debug";
            } // END of lsa definition.

            leaf nfsm  {
                type  ipi-ospfv3-types:ospfv3_debug_nfsm_t;
                description "Use this attribute to enable OSPFv3 Neighbor State Machine debug";
            } // END of nfsm definition.

            leaf nsm  {
                type  ipi-ospfv3-types:ospfv3_debug_nsm_t;
                description "Use this attribute to enable OSPFv3 NSM information debug";
            } // END of nsm definition.

            leaf rib  {
                if-feature feature-list:HAVE_RIBD;
                type  ipi-ospfv3-types:ospfv3_debug_rib_t;
                description "Use this attribute to enable OSPFv3 RIB information debug";
            } // END of rib definition.

            leaf route  {
                type  ipi-ospfv3-types:ospfv3_debug_route_t;
                description "Use this attribute to enable OSPFv3 route information debug";
            } // END of route definition.

            container packet {
                config false;
                description
                    "OSPFv3 debug packet";
                leaf hello  {
                    type  ipi-ospfv3-types:ospfv3_debug_packet_options_t;
                    description "OSPFv3 Hello";
                } // END of hello definition.

                leaf dd  {
                    type  ipi-ospfv3-types:ospfv3_debug_packet_options_t;
                    description "OSPFv3 Database Description";
                } // END of dd definition.

                leaf ls-request  {
                    type  ipi-ospfv3-types:ospfv3_debug_packet_options_t;
                    description "OSPFv3 Link State Request";
                } // END of ls-request definition.

                leaf ls-update  {
                    type  ipi-ospfv3-types:ospfv3_debug_packet_options_t;
                    description "OSPFv3 Link State Update";
                } // END of ls-update definition.

                leaf ls-ack  {
                    type  ipi-ospfv3-types:ospfv3_debug_packet_options_t;
                    description "OSPFv3 Link State Acknowledgment";
                } // END of ls-ack definition.

            } // END of packet-container definition.
        } // END of terminal-debug-container definition.
    } // END of ospfv3-debug-terminal-state definition.
    grouping ospfv3-debug-top {
        description
            "Grouping for OSPFv3 debug";
        container debug {
            description
                "Configuration data for OSPFv3 debug";
            container config {
                description
                    "Configuration data for OSPFv3 debug";
                uses ospfv3-debug-config;
            } // END of config-container definition.
            container state {
                config false;
                description
                    "Operational state data for OSPFv3 debug";
                uses ospfv3-debug-config;
                uses ospfv3-debug-terminal-state;
            } // END of state-container definition.
        } // END of debug-container definition.
    } // END of ospfv3-debug-top definition.


}
