/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-ospfv3-address-family.yang
*
*/

submodule ipi-ospfv3-address-family {

    yang-version 1.1;

    belongs-to  ipi-ospfv3 { prefix ipi-ospfv3; }

    import ietf-inet-types {
        prefix inet;
        revision-date 2013-07-15;
    }

    import ipi-ospfv3-types {
        prefix ipi-ospfv3-types;
        revision-date 2022-06-01;
    }

    include ipi-ospfv3-redistribute { revision-date 2022-06-01;}
    organization
        "IP Infusion Inc.";

    contact
        "Address: 3965 Freedom Circle, Suite 200, Santa Clara, CA 95054
         Phone: +1 408-400-1900
         E-mail: support@ipinfusion.com
         Web: http://www.ipinfusion.com/";

    description
        "Layer-3 OSPFv3 configurations";


    revision "2022-06-01" {
        description "Updated the yang file with feature";
        reference " 0.2.0.";
    }

    revision "2021-09-07" {
        description "Set route-map max length to 63 chars";
        reference " 0.1.1.";
    }

    revision "2021-06-17" {
        description "Restructured module in accordance with OpenConfig style";
        reference " 0.1.0.";
    }

    grouping ospfv3-address-family-default-information-config {
        description
            "Grouping for OSPF default information for ipv4 address family
                        configuration data";
        leaf originate  {
            type  empty;
            description "Use this attribute to create a default external route into an OSPF
                        routing domain. The system acts like an
                        Autonomous System Boundary Router (ASBR) when you use the
                        default-information originate command
                        to redistribute routes into an OSPF routing domain. An ASBR does not
                        by default generate a default
                        route into the OSPF routing domain";
        } // END of originate definition.

        leaf always-advertise-default-route  {
            when " /ospfv3/processes/process/address-family/ipv4/default-information/config/originate ";
            type  empty;
            description "Use this attribute to advertise the default route regardless of
                        whether there is a default route.";
        } // END of always-advertise-default-route definition.

        leaf metric  {
            when " /ospfv3/processes/process/address-family/ipv4/default-information/config/originate ";
            type  uint32 {
                 range "0..16777214"  {
                    description "0..16777214: Supported range 0 - 16777214";
                 }
            }
            default "20";
            description "Use this attribute to set the OSPF area with default metric.";
        } // END of metric definition.

        leaf metric-type  {
            when " /ospfv3/processes/process/address-family/ipv4/default-information/config/originate ";
            type  ipi-ospfv3-types:ospfv3_metric_type_t;
            default "2";
            description "Use this attribute to set the OSPF area default metric type.";
        } // END of metric-type definition.

        leaf route-map  {
            when " /ospfv3/processes/process/address-family/ipv4/default-information/config/originate ";
            type  string {
                length "1..63";
                pattern "[^?' =,>|]+";
            }
            description "Use this attribute to set route-map instance.";
        } // END of route-map definition.

    } // END of ospfv3-address-family-default-information-config definition.
    grouping ospfv3-address-family-default-information-top {
        description
            "Grouping for OSPF default information for ipv4 address family";
        container default-information {
            description
                "Container for OSPF default information";
            container config {
                description
                    "Configuration data for default information";
                uses ospfv3-address-family-default-information-config;
            } // END of config-container definition.
            container state {
                config false;
                description
                    "Operational state data for default information";
                uses ospfv3-address-family-default-information-config;
            } // END of state-container definition.
        } // END of default-information-container definition.
    } // END of ospfv3-address-family-default-information-top definition.
    grouping ospfv3-address-family-summary-address-config {
        description
            "Grouping for OSPFv3 summary address for IPv4 address family
                        configuration data";
        leaf address  {
            type  inet:ipv4-prefix;
            description "Use this attribute to summarize or suppress external routes with the
                        specified address range.";
        } // END of address definition.

        leaf not-advertise  {
            type  empty;
            description "Use this attribute to summarize or suppress external routes with the
                        specified address range.";
        } // END of not-advertise definition.

        leaf tag  {
            type  uint32 {
                 range "0..4294967295"  {
                    description "0..4294967295: Supported range 0 - 4294967295";
                 }
            }
            default "0";
            description "Use this attribute to configure the Tag value to use as a match value
                        for controlling redistribution via route maps.";
        } // END of tag definition.

    } // END of ospfv3-address-family-summary-address-config definition.
    grouping ospfv3-address-family-summary-address-top {
        description
            "Grouping for OSPFv3 summary address for IPv4 address family";
        container summary-addresses {
            description
                "Configuration data for OSPFv3 summary addresses for IPv4 address
                        family";

            list summary-address {
                key "address";
                description
                    "List of OSPFv3 summary addresses for OSPFv3 IPv4 address family";
                leaf address  {
                    type  leafref {
                        path  "../config/address";
                    }
                    description "Use this attribute to summarize or suppress external routes with the
                                specified address range.";
                } // END of address definition.

                container config {
                    description
                        "Configuration data for OSPFv3 summary address for IPv4 address family";
                    uses ospfv3-address-family-summary-address-config;
                } // END of config-container definition.
                container state {
                    config false;
                    description
                        "Operational state data for OSPFv3 summary address for IPv4 address
                                family";
                    uses ospfv3-address-family-summary-address-config;
                } // END of state-container definition.
            } // End of summary-address-list
        } // END of summary-addresses-container definition.
    } // END of ospfv3-address-family-summary-address-top definition.
    grouping ospfv3-address-family-area-range-config {
        description
            "Grouping for OSPFv3 range for IPv4 address family configuration data";
        leaf address  {
            type  inet:ipv4-prefix;
            description "Use this attribute to configure the OSPFv3 address range for IPv4
                        address family.";
        } // END of address definition.

        leaf not-advertise  {
            type  empty;
            description "Use this attribute to Specify to advertise / non-advertise the OSPFv3
                        address range for IPv4 address family.";
        } // END of not-advertise definition.

    } // END of ospfv3-address-family-area-range-config definition.
    grouping ospfv3-address-family-area-range-top {
        description
            "Grouping for OSPFv3 area range for IPv4 address family";
        container address-ranges {
            description
                "Configuration data for OSPFv3 ranges for IPv4 address family";

            list address-range {
                key "address";
                description
                    "List of OSPFv3 ranges for IPv4 address family";
                leaf address  {
                    type  leafref {
                        path  "../config/address";
                    }
                    description "Use this attribute to configure the OSPFv3 address range for IPv4
                                address family.";
                } // END of address definition.

                container config {
                    description
                        "Configuration data for OSPFv3 range for IPv4 address family";
                    uses ospfv3-address-family-area-range-config;
                } // END of config-container definition.
                container state {
                    config false;
                    description
                        "Operational state data for OSPFv3 range for IPv4 address family";
                    uses ospfv3-address-family-area-range-config;
                } // END of state-container definition.
            } // End of address-range-list
        } // END of address-ranges-container definition.
    } // END of ospfv3-address-family-area-range-top definition.
    grouping ospfv3-address-family-area-config {
        description
            "Grouping for OSPFv3 IPv4 address family area configuration data";
        leaf area-id  {
            type  ipi-ospfv3-types:ospfv3_area_t;
            description "Area can be of type IPv4 address or integer.";
        } // END of area-id definition.

    } // END of ospfv3-address-family-area-config definition.
    grouping ospfv3-address-family-area-top {
        description
            "Grouping for OSPFv3 area for address";
        container areas {
            description
                "Configuration data for OSPFv3 areas";

            list area {
            when " /ospfv3/processes/process/address-family/ipv4/areas/area/address-ranges ";
                key "area-id";
                description
                    "List of OSPFv3 areas";
                leaf area-id  {
                    type  leafref {
                        path  "../config/area-id";
                    }
                    description "Area can be of type IPv4 address or integer.";
                } // END of area-id definition.

                container config {
                    description
                        "Configuration data for OSPFv3 IPv4 address family area";
                    uses ospfv3-address-family-area-config;
                } // END of config-container definition.
                container state {
                    config false;
                    description
                        "Operational state data for OSPFv3 IPv4 address family area";
                    uses ospfv3-address-family-area-config;
                } // END of state-container definition.
                uses ospfv3-address-family-area-range-top;
            } // End of area-list
        } // END of areas-container definition.
    } // END of ospfv3-address-family-area-top definition.
    grouping ospfv3-address-family-ipv4-config {
        description
            "Grouping for OSPFv3 IPv4 address family configuration data";
        leaf enable-af  {
            type  empty;
            description "Enable OSPFv3 IPv4 address family config.";
        } // END of enable-af definition.

    } // END of ospfv3-address-family-ipv4-config definition.
    grouping ospfv3-address-family-ipv4-top {
        description
            "Grouping for OSPFv3 IPv4 address family";
        container ipv4 {
            description
                "Configuration data for OSPFv3 IPv4 address family";
            container config {
                description
                    "Configuration data for OSPFv3 IPv4 address family";
                uses ospfv3-address-family-ipv4-config;
            } // END of config-container definition.
            container state {
                config false;
                description
                    "Operational state data for OSPFv3 IPv4 address family";
                uses ospfv3-address-family-ipv4-config;
            } // END of state-container definition.
            uses ospfv3-address-family-area-top;
            uses ospfv3-address-family-summary-address-top;
            uses ospfv3-address-family-default-information-top;
            uses ospfv3-address-family-redistribute-top;
        } // END of ipv4-container definition.
    } // END of ospfv3-address-family-ipv4-top definition.
    grouping ospfv3-address-family-top {
        description
            "Grouping for OSPFv3 IPv4 address family";
        container address-family {
            description
                "Configuration data for OSPFv3 IPv4 address family";
            uses ospfv3-address-family-ipv4-top;
        } // END of address-family-container definition.
    } // END of ospfv3-address-family-top definition.


}
