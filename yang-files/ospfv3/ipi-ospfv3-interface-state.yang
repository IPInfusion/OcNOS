/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-ospfv3-interface-state.yang
*
*/

submodule ipi-ospfv3-interface-state {

    yang-version 1.1;

    belongs-to  ipi-ospfv3 { prefix ipi-ospfv3; }

    import feature-list {
        prefix feature-list;
        revision-date 2023-02-21;
    }

    import ietf-yang-types {
        prefix yang;
        revision-date 2013-07-15;
    }

    import ietf-inet-types {
        prefix inet;
        revision-date 2013-07-15;
    }

    import ipi-ospfv3-types {
        prefix ipi-ospfv3-types;
        revision-date 2022-06-01;
    }

    include ipi-ospfv3-process-state { revision-date 2022-06-01;}
    organization
        "IP Infusion Inc.";

    contact
        "Address: 3965 Freedom Circle, Suite 200, Santa Clara, CA 95054
         Phone: +1 408-400-1900
         E-mail: support@ipinfusion.com
         Web: http://www.ipinfusion.com/";

    description
        "Layer-3 OSPFv3 interface state";


    revision "2022-06-01" {
        description "Updated the yang file with feature";
        reference " 0.1.2.";
    }

    revision "2021-09-03" {
        description "Update descriptions of attribute";
        reference " 0.1.1.";
    }

    revision "2021-06-17" {
        description "Restructured module in accordance with OpenConfig style";
        reference " 0.1.0.";
    }

    grouping ospfv3-interface-instance-neighbor-state-statistics {
        description
            "Grouping for OSPFv3 interface neighbor statistics state attr";
        leaf dead-timer-due-in  {
            type  string {
                length "1..1965";
                pattern "[^?' =,>|]+";
            }
            description "This attribute returns the dead-timer-due-in value.";
        } // END of dead-timer-due-in definition.

        leaf timer-dump  {
            type  string {
                length "1..1965";
                pattern "[^?' =,>|]+";
            }
            description "This attribute returns the timer-dump value.";
        } // END of timer-dump definition.

        leaf state-changes  {
            type  yang:counter64;
            description "This attribute returns the state-changes value.";
        } // END of state-changes definition.

        leaf hello-suppressed  {
            if-feature feature-list:HAVE_OSPF6_OD;
            type  yang:counter64;
            description "This attribute returns the hello-suppressed value.";
        } // END of hello-suppressed definition.

        leaf database-summary-count  {
            type  yang:counter64;
            description "This attribute returns the database-summary-count value.";
        } // END of database-summary-count definition.

        leaf ls-request-count  {
            type  yang:counter64;
            description "This attribute returns the ls-request-count value.";
        } // END of ls-request-count definition.

        leaf ls-retransmissiom-count  {
            type  yang:counter64;
            description "This attribute returns the ls-retransmissiom-count value.";
        } // END of ls-retransmissiom-count definition.

    } // END of ospfv3-interface-instance-neighbor-state-statistics definition.
    grouping ospfv3-interface-instance-neighbor-state-attr {
        description
            "Grouping for OSPFv3 interface neighbor state attr";
        leaf router-id  {
            type  inet:ipv4-address;
            description "This attribute returns the router-id value.";
        } // END of router-id definition.

        leaf address  {
            type  inet:ipv6-address;
            description "This attribute returns the address value.";
        } // END of address definition.

        leaf area-id  {
            type  inet:ipv4-address;
            description "This attribute returns the area-id value.";
        } // END of area-id definition.

        leaf state  {
            type  string {
                length "1..1965";
                pattern "[^?' =,>|]+";
            }
            description "This attribute returns the state value.";
        } // END of state definition.

        leaf state-message  {
            type  string {
                length "1..1965";
                pattern "[^?' =,>|]+";
            }
            description "This attribute returns the state-message value.";
        } // END of state-message definition.

        leaf bfd-enable  {
            if-feature feature-list:HAVE_BFD;
            type  empty;
            description "This attribute returns the bfd-enable value.";
        } // END of bfd-enable definition.

        leaf priority  {
            type  uint8;
            description "This attribute returns the priority value.";
        } // END of priority definition.

        leaf neighbor-options  {
            type  ipi-ospfv3-types:ospfv3_ls_options_t;
            description "This attribute returns the neighbor-options value.";
        } // END of neighbor-options definition.

        leaf designated-router-router-id  {
            type  inet:ipv4-address;
            description "This attribute returns the designated-router-router-id value.";
        } // END of designated-router-router-id definition.

        leaf backup-designated-router-router-id  {
            type  inet:ipv4-address;
            description "This attribute returns the backup-designated-router-router-id value.";
        } // END of backup-designated-router-router-id definition.

    } // END of ospfv3-interface-instance-neighbor-state-attr definition.
    grouping ospfv3-interface-designated-router-state-attr {
        description
            "Grouping for OSPFv3 interface designated router state attr";
        leaf router-id  {
            type  inet:ipv4-address;
            description "This attribute returns the router-id value.";
        } // END of router-id definition.

        leaf address  {
            type  inet:ipv6-address;
            description "This attribute returns the address value.";
        } // END of address definition.

    } // END of ospfv3-interface-designated-router-state-attr definition.
    grouping ospfv3-interface-instance-neighbor-state {
        description
            "Grouping for OSPFv3 interface neighbor state data";

        list neighbor {
            key "router-id";
            config false;
            description
                "List of neighbor for interface state database";
            leaf router-id  {
                type  leafref {
                    path  "../state/router-id";
                }
                description "This attribute returns the router-id value.";
            } // END of router-id definition.

            container state {
                config false;
                description
                    "Operational state data for neighbor of interface state database";
                container statistics {
                    config false;
                    description
                        "OSPFv3 interface neighbor status";
                    uses ospfv3-interface-instance-neighbor-state-statistics;
                } // END of statistics-container definition.
                uses ospfv3-interface-instance-neighbor-state-attr;
            } // END of state-container definition.
            uses ospfv3-route-state;
        } // End of neighbor-list
    } // END of ospfv3-interface-instance-neighbor-state definition.
    grouping ospfv3-interface-backup-designated-router-state {
        description
            "Grouping for OSPFv3 interface backup designated router state";
        container backup-designated-router {
            config false;
            description
                "OSPFv3 interface backup designated router data";
            container state {
                config false;
                description
                    "Operational state data for backup designated router";
                uses ospfv3-interface-designated-router-state-attr;
            } // END of state-container definition.
        } // END of backup-designated-router-container definition.
    } // END of ospfv3-interface-backup-designated-router-state definition.
    grouping ospfv3-interface-designated-router-state {
        description
            "Grouping for OSPFv3 interface designated router state";
        container designated-router {
            config false;
            description
                "OSPFv3 interface designated router data";
            container state {
                config false;
                description
                    "Operational state data for designated router";
                uses ospfv3-interface-designated-router-state-attr;
            } // END of state-container definition.
        } // END of designated-router-container definition.
    } // END of ospfv3-interface-designated-router-state definition.
    grouping ospfv3-interface-instance-statistics-state {
        description
            "Grouping for OSPFv3 interface statistics state data";
        leaf neighbor-count  {
            type  uint32;
            description "This attribute returns the neighbor-count value.";
        } // END of neighbor-count definition.

        leaf adjacent-neighbor-count  {
            type  uint32;
            description "This attribute returns the adjacent-neighbor-count value.";
        } // END of adjacent-neighbor-count definition.

        leaf hello-due-in  {
            type  string {
                length "1..1965";
                pattern "((([0-1]?[0-9])|(2[0-3])):[0-5][0-9]:[0-5][0-9])|([0-9]+d(([0-1][0-9])|(2[0-3]))h[0-5][0-9]m)";
            }
            description "This attribute returns the hello-due-in value.";
        } // END of hello-due-in definition.

        leaf hello-in  {
            type  yang:counter64;
            description "This attribute returns the hello-in value.";
        } // END of hello-in definition.

        leaf hello-out  {
            type  yang:counter64;
            description "This attribute returns the hello-out value.";
        } // END of hello-out definition.

        leaf hello-suppressed  {
            if-feature feature-list:HAVE_OSPF6_OD;
            type  yang:counter64;
            description "This attribute returns the hello-suppressed value.";
        } // END of hello-suppressed definition.

        leaf database-description-in  {
            type  yang:counter64;
            description "This attribute returns the database-description-in value.";
        } // END of database-description-in definition.

        leaf database-description-out  {
            type  yang:counter64;
            description "This attribute returns the database-description-out value.";
        } // END of database-description-out definition.

        leaf ls-request-in  {
            type  yang:counter64;
            description "This attribute returns the ls-request-in value.";
        } // END of ls-request-in definition.

        leaf ls-request-out  {
            type  yang:counter64;
            description "This attribute returns the ls-request-out value.";
        } // END of ls-request-out definition.

        leaf ls-update-in  {
            type  yang:counter64;
            description "This attribute returns the ls-update-in value.";
        } // END of ls-update-in definition.

        leaf ls-update-out  {
            type  yang:counter64;
            description "This attribute returns the ls-update-out value.";
        } // END of ls-update-out definition.

        leaf ls-ack-in  {
            type  yang:counter64;
            description "This attribute returns the ls-ack-in value.";
        } // END of ls-ack-in definition.

        leaf ls-ack-out  {
            type  yang:counter64;
            description "This attribute returns the ls-ack-out value.";
        } // END of ls-ack-out definition.

        leaf ls-ack-discarded  {
            type  yang:counter64;
            description "This attribute returns the ls-ack-discarded value.";
        } // END of ls-ack-discarded definition.

    } // END of ospfv3-interface-instance-statistics-state definition.
    grouping ospfv3-interface-instance-state {
        description
            "Grouping for OSPFv3 interface state data";
        leaf administrative-state  {
            type  ipi-ospfv3-types:ospfv3_interface_admin_state_t;
            description "This attribute returns the administrative-state value.";
        } // END of administrative-state definition.

        leaf interface-index  {
            type  uint32;
            description "This attribute returns the interface-index value.";
        } // END of interface-index definition.

        leaf interface-state  {
            type  ipi-ospfv3-types:ospfv3_interface_state_t;
            description "This attribute returns the interface-instance-state value.";
        } // END of interface-state definition.

        leaf address  {
            type  inet:ipv6-address;
            description "This attribute returns the address value.";
        } // END of address definition.

        leaf link-local-address  {
            type  inet:ipv6-address;
            description "This attribute returns the link-local-address value.";
        } // END of link-local-address definition.

        leaf router-id  {
            type  inet:ipv4-address;
            description "This attribute returns the router-id value.";
        } // END of router-id definition.

    } // END of ospfv3-interface-instance-state definition.


}
