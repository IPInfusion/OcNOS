/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-ospfv3-area-state.yang
*
*/

submodule ipi-ospfv3-area-state {

    yang-version 1.1;

    belongs-to  ipi-ospfv3 { prefix ipi-ospfv3; }

    import ietf-yang-types {
        prefix yang;
        revision-date 2013-07-15;
    }

    import ietf-inet-types {
        prefix inet;
        revision-date 2013-07-15;
    }

    include ipi-ospfv3-process-state { revision-date 2022-06-01;}
    organization
        "IP Infusion Inc.";

    contact
        "Address: 3965 Freedom Circle, Suite 200, Santa Clara, CA 95054
         Phone: +1 408-400-1900
         E-mail: support@ipinfusion.com
         Web: http://www.ipinfusion.com/";

    description
        "Layer-3 OSPFv3 area state";


    revision "2022-06-01" {
        description "Updated the yang file with feature";
        reference " 0.1.2.";
    }

    revision "2021-09-03" {
        description "Update descriptions of attribute";
        reference " 0.1.1.";
    }

    revision "2021-06-17" {
        description "Restructured module in accordance with OpenConfig style";
        reference " 0.1.0.";
    }

    grouping ospfv3-area-vertex-state-attr {
        description
            "Grouping for OSPFv3 area vertex state";
        leaf router-id  {
            type  inet:ipv4-address;
            description "This attribute returns the router-id value.";
        } // END of router-id definition.

        leaf distance  {
            type  uint8;
            description "This attribute returns the distance value.";
        } // END of distance definition.

    } // END of ospfv3-area-vertex-state-attr definition.
    grouping ospfv3-area-vertex-state {
        description
            "Grouping for OSPFv3 area vertex state data";

        list vertex {
            key "router-id";
            config false;
            description
                "List of vertex for area state database";
            leaf router-id  {
                type  leafref {
                    path  "../state/router-id";
                }
                description "This attribute returns the router-id value.";
            } // END of router-id definition.


            list next-hop {
                key "address";
                config false;
                description
                    "List of next hops of area state database";
                leaf address  {
                    type  leafref {
                        path  "../state/address";
                    }
                    description "This attribute returns the address value.";
                } // END of address definition.

                container state {
                    config false;
                    description
                        "Operational state data for area next-hop area state database";
                    uses ospfv3-next-hop-state;
                } // END of state-container definition.
            } // End of next-hop-list
            container state {
                config false;
                description
                    "Operational state data for vertex of area state database";
                uses ospfv3-area-vertex-state-attr;
            } // END of state-container definition.
        } // End of vertex-list
    } // END of ospfv3-area-vertex-state definition.
    grouping ospfv3-area-info-state {
        description
            "Grouping for OSPFv3 ares state info";

        list area-info {
            key "area-id";
            config false;
            description
                "List of areas";
            leaf area-id  {
                type  leafref {
                    path  "../state/area-id";
                }
                description "This attribute returns the area id value.";
            } // END of area-id definition.

            container state {
                config false;
                description
                    "Operational state data for area";
                container statistics {
                    config false;
                    description
                        "OSPFv3 area status";
                    uses ospfv3-area-statistics-state;
                } // END of statistics-container definition.
                uses ospfv3-area-state;
            } // END of state-container definition.
            uses ospfv3-area-vertex-state;
        } // End of area-info-list
    } // END of ospfv3-area-info-state definition.
    grouping ospfv3-area-statistics-state {
        description
            "Grouping for OSPFv3 area statistics state data";
        leaf active-interface-count  {
            type  yang:counter64;
            description "This attribute returns the active-interface-count value.";
        } // END of active-interface-count definition.

        leaf interface-count  {
            type  yang:counter64;
            description "This attribute returns the interface-count value.";
        } // END of interface-count definition.

        leaf spf-algorithm-executed-count  {
            type  yang:counter64;
            description "This attribute returns the spf-algorithm-executed-count value.";
        } // END of spf-algorithm-executed-count definition.

        leaf lsa-count  {
            type  yang:counter64;
            description "This attribute returns the lsa-count value.";
        } // END of lsa-count definition.

        leaf lsa-checksum  {
            type  string {
                length "1..1965";
                pattern "[^?' =,>|]+";
            }
            description "This attribute returns the lsa-checksum value.";
        } // END of lsa-checksum definition.

        leaf unknown-lsa-count  {
            type  yang:counter64;
            description "This attribute returns the unknown-lsa-count value.";
        } // END of unknown-lsa-count definition.

    } // END of ospfv3-area-statistics-state definition.
    grouping ospfv3-area-state {
        description
            "Grouping for OSPFv3 area state data";
        leaf area-id  {
            type  inet:ipv4-address;
            description "This attribute returns the area id value.";
        } // END of area-id definition.

        leaf-list interface-name  {
            type  string {
                length "1..1965";
                pattern "[^?' =,>|]+";
            }
            description "This attribute returns the interface name value.";
        } // END of interface-name definition.

        leaf backbone  {
            type  empty;
            description "This attribute returns the backbone value.";
        } // END of backbone definition.

        leaf active  {
            type  empty;
            description "This attribute returns the active value.";
        } // END of active definition.

        leaf asbr  {
            type  empty;
            description "This attribute returns the asbr value.";
        } // END of asbr definition.

    } // END of ospfv3-area-state definition.


}
