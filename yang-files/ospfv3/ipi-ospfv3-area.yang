/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-ospfv3-area.yang
*
*/

submodule ipi-ospfv3-area {

    yang-version 1.1;

    belongs-to  ipi-ospfv3 { prefix ipi-ospfv3; }

    import feature-list {
        prefix feature-list;
        revision-date 2023-02-21;
    }

    import ietf-yang-types {
        prefix yang;
        revision-date 2013-07-15;
    }

    import ietf-inet-types {
        prefix inet;
        revision-date 2013-07-15;
    }

    import ipi-ospfv3-types {
        prefix ipi-ospfv3-types;
        revision-date 2022-06-01;
    }

    import ipi-ipsec {
        prefix ipi-ipsec;
        revision-date 2022-06-27;
    }

    organization
        "IP Infusion Inc.";

    contact
        "Address: 3965 Freedom Circle, Suite 200, Santa Clara, CA 95054
         Phone: +1 408-400-1900
         E-mail: support@ipinfusion.com
         Web: http://www.ipinfusion.com/";

    description
        "Layer-3 OSPFv3 configurations";


    revision "2022-06-27" {
        description "Updated SPI range in ipsec module";
        reference " 0.1.10.";
    }

    revision "2022-06-24" {
        description "Internal fixes handling transform-set from ip-sec module";
        reference " 0.1.9.";
    }

    revision "2022-06-13" {
        description "Removed sa-lifetime attribute from ip-sec module";
        reference " 0.1.8.";
    }

    revision "2022-06-07" {
        description "Changed the dependent module config IPsec Transform-set ESP Configuration data container to a presence container";
        reference " 0.1.7.";
    }

    revision "2022-06-01" {
        description "Updated the yang file with feature";
        reference " 0.1.6.";
    }

    revision "2022-05-04" {
        description "Added authentication-cryptomap attribute for IPSec authentication support of OSPFv3";
        reference " 0.1.5.";
    }

    revision "2021-10-27" {
        description "Stub and nsssa config container presence, and enable leaf mandatory";
        reference " 0.1.4.";
    }

    revision "2021-10-06" {
        description "Removed area route-map leafref";
        reference " 0.1.3.";
    }

    revision "2021-09-03" {
        description "Update descriptions of attribute";
        reference " 0.1.2.";
    }

    revision "2021-07-26" {
        description "Notification support";
        reference " 0.1.1.";
    }

    revision "2021-06-17" {
        description "Restructured module in accordance with OpenConfig style";
        reference " 0.1.0.";
    }

    grouping ospfv3-common-timers-config {
        description
            "Grouping for OSPFv3 common timers configuration data";
        leaf dead-interval  {
            type  uint16 {
                 range "1..65535"  {
                    description "1..65535: Supported range 1 - 65535";
                 }
            }
            units "seconds";
            default "40";
            description "Use this command to set the amount of time that the router waits to
                        receive an OSPF hello packet from the neighbor before declaring the
                        neighbor down.";
        } // END of dead-interval definition.

        leaf hello-interval  {
            type  uint16 {
                 range "1..65535"  {
                    description "1..65535: Supported range 1 - 65535";
                 }
            }
            units "seconds";
            default "10";
            description "Use this command to set the interval the router waits before it sends
                        a hello packet.";
        } // END of hello-interval definition.

        leaf transmission-delay  {
            type  uint16 {
                 range "1..1800"  {
                    description "1..1800: Supported range 1 - 1800";
                 }
            }
            units "seconds";
            default "1";
            description "Use this command to set the interval the router waits before it
                        transmits a packet.";
        } // END of transmission-delay definition.

        leaf retransmission-interval  {
            type  uint16 {
                 range "1..1800"  {
                    description "1..1800: Supported range 1 - 1800";
                 }
            }
            units "seconds";
            default "5";
            description "Use this command to set the interval the router waits before it sends
                        a hello packet.";
        } // END of retransmission-interval definition.

    } // END of ospfv3-common-timers-config definition.
    grouping ospfv3-common-timers-top {
        description
            "Grouping for OSPFv3 common timers";
        container timers {
            description
                "Configuration data for OSPFv3 link timers";
            container config {
                description
                    "Configuration data for OSPFv3 link timers";
                uses ospfv3-common-timers-config;
            } // END of config-container definition.
            container state {
                config false;
                description
                    "Operational state data for OSPFv3 link timers";
                uses ospfv3-common-timers-config;
            } // END of state-container definition.
        } // END of timers-container definition.
    } // END of ospfv3-common-timers-top definition.
    grouping ospfv3-area-virtual-link-timers-top {
        description
            "Grouping for OSPFv3 virtual link timers";
        uses ospfv3-common-timers-top;
    } // END of ospfv3-area-virtual-link-timers-top definition.
    grouping ospfv3-area-virtual-link-state {
        description
            "Grouping for OSPFv3 virtual link state data";
        leaf name  {
            type  string {
                length "1..1965";
                pattern "[^?' =,>|]+";
            }
            description "This attribute returns the interface name value.";
        } // END of name definition.

        leaf status  {
            type  ipi-ospfv3-types:ospfv3_link_status_t;
            description "This attribute returns the interface status value.";
        } // END of status definition.

        leaf interface-name  {
            type  string {
                length "1..1965";
                pattern "[^?' =,>|]+";
            }
            description "This attribute returns the interface interface name value.";
        } // END of interface-name definition.

        leaf virtual-link-interface-state  {
            type  string {
                length "1..1965";
                pattern "[^?' =,>|]+";
            }
            description "This attribute returns the interface virtual link interface state
                        value.";
        } // END of virtual-link-interface-state definition.

        leaf local-address  {
            type  inet:ipv4-address;
            description "This attribute returns the interface local address value.";
        } // END of local-address definition.

        leaf remote-address  {
            type  inet:ipv4-address;
            description "This attribute returns the interface remote address value.";
        } // END of remote-address definition.

        leaf virtual-link-instance-id  {
            type  uint32;
            description "This attribute returns the interface virtual link instance id value.";
        } // END of virtual-link-instance-id definition.

        leaf hello-suppression-enable  {
            type  empty;
            description "This attribute returns the interface hello suppression enable value.";
        } // END of hello-suppression-enable definition.

        leaf do-not-age-lsa-enable  {
            type  empty;
            description "This attribute returns the interface do not age lsa enable value.";
        } // END of do-not-age-lsa-enable definition.

        leaf hello-due-in  {
            type  yang:date-and-time {
                pattern "\\d{4}-\\d{2}-\\d{2}T\\d{2}:\\d{2}:\\d{2}(\\.\\d+)?(Z|[\\+\\-]\\d{2}:\\d{2})";
                }
                description "This attribute returns the interface hello due in value.";
            } // END of hello-due-in definition.

            leaf adjacency-state  {
                type  string {
                    length "1..1965";
                    pattern "[^?' =,>|]+";
                }
                description "This attribute returns the interface adjacency state value.";
            } // END of adjacency-state definition.

    } // END of ospfv3-area-virtual-link-state definition.
    grouping ospfv3-area-virtual-link-config {
        description
            "Grouping for OSPFv3 virtual link configuration data";
        leaf remote-router-id  {
            type  inet:ipv4-address;
            description "Use this attribute to set the interface IP address of the neighbor.";
        } // END of remote-router-id definition.

        leaf bfd-fall-over  {
            if-feature feature-list:HAVE_BFD;
            type  empty;
            description "Use this attribute to enable BFD on a virtual-link.";
        } // END of bfd-fall-over definition.

        leaf instance-id  {
            type  uint8 {
                 range "0..31 | 64..95"  {
                    description "0..31: Supported range 0 - 31,64..95: Supported range 64 - 95";
                 }
            }
            default "0";
            description "The OSPFv3 instance.";
        } // END of instance-id definition.

        leaf authentication-cryptomap  {
            if-feature feature-list:HAVE_IPSEC;
            if-feature feature-list:HAVE_TUNNEL;
            type  leafref {
                path  "/ipi-ipsec:ipsec/ipi-ipsec:crypto-maps/ipi-ipsec:crypto-map/ipi-ipsec:config/ipi-ipsec:name";
            }
            description "Use this attribute to set the Crypto-map used to setup IPsec SA.";
        } // END of authentication-cryptomap definition.

    } // END of ospfv3-area-virtual-link-config definition.
    grouping ospfv3-area-virtual-link-top {
        description
            "Grouping for OSPFv3 virtual link";
        container virtual-links {
            description
                "Configuration data for OSPFv3 virtual links";

            list virtual-link {
                key "remote-router-id";
                description
                    "List of OSPFv3 virtual links";
                leaf remote-router-id  {
                    type  leafref {
                        path  "../config/remote-router-id";
                    }
                    description "Use this attribute to set the interface IP address of the neighbor.";
                } // END of remote-router-id definition.

                container config {
                    description
                        "Configuration data for OSPFv3 virtual link";
                    uses ospfv3-area-virtual-link-config;
                } // END of config-container definition.
                container state {
                    config false;
                    description
                        "Operational state data for OSPFv3 virtual link";
                    uses ospfv3-area-virtual-link-config;
                    uses ospfv3-area-virtual-link-state;
                    uses ospfv3-virtual-link-config-error;
                    uses ospfv3-virtual-link-state-change;
                    uses ospfv3-virtual-link-neighbor-state-change;
                    uses ospfv3-virtual-link-tx-retransmit;
                    uses ospfv3-virtual-link-rx-bad-packet;
                } // END of state-container definition.
                uses ospfv3-area-virtual-link-timers-top;
            } // End of virtual-link-list
        } // END of virtual-links-container definition.
    } // END of ospfv3-area-virtual-link-top definition.
    grouping ospfv3-area-range-config {
        description
            "Grouping for OSPFv3 area address range configuration data";
        leaf address  {
            type  inet:ipv6-prefix;
            description "Use this attribute to configure the OSPFv3 address range.";
        } // END of address definition.

        leaf not-advertise  {
            type  empty;
            description "Use this attribute to Specify to advertise / non-advertise the OSPFv3
                        address range.";
        } // END of not-advertise definition.

    } // END of ospfv3-area-range-config definition.
    grouping ospfv3-area-range-top {
        description
            "Grouping for OSPFv3 area address range";
        container address-ranges {
            description
                "Configuration data for OSPFv3 ranges";

            list address-range {
                key "address";
                description
                    "List of OSPFv3 ranges";
                leaf address  {
                    type  leafref {
                        path  "../config/address";
                    }
                    description "Use this attribute to configure the OSPFv3 address range.";
                } // END of address definition.

                container config {
                    description
                        "Configuration data for OSPFv3 address range";
                    uses ospfv3-area-range-config;
                } // END of config-container definition.
                container state {
                    config false;
                    description
                        "Operational state data for OSPFv3 address range";
                    uses ospfv3-area-range-config;
                } // END of state-container definition.
            } // End of address-range-list
        } // END of address-ranges-container definition.
    } // END of ospfv3-area-range-top definition.
    grouping ospfv3-area-nssa-config {
        description
            "Grouping for OSPFv3 Not-So-Stubby Area (NSSA) configuration data";
        leaf enable  {
            type  empty;
            mandatory true;
            description "Use this attribute to set an area as a Not-So-Stubby-Area (NSSA).";
        } // END of enable definition.

        leaf no-summary  {
            type  empty;
            description "Use this attribute to do not send summary LSA into NSSA.";
        } // END of no-summary definition.

        leaf stability-interval  {
            when " /ospfv3/processes/process/areas/area/nssa/config/enable ";
            type  uint32 {
                 range "0..2147483647"  {
                    description "0..2147483647: Supported range 0 - 2147483647";
                 }
            }
            units "seconds";
            default "40";
            description "Use this attribute to set stability interval into NSSA.";
        } // END of stability-interval definition.

        leaf translator-role  {
            when " /ospfv3/processes/process/areas/area/nssa/config/enable ";
            type  ipi-ospfv3-types:ospfv3_translator_role_t;
            default "candidate";
            description "Use this attribute to set NSSA-ABR translator role.";
        } // END of translator-role definition.

        leaf no-redistribution  {
            when " /ospfv3/processes/process/areas/area/nssa/config/enable ";
            type  empty;
            description "Use this attribute to set no redistribution into this NSSA area.";
        } // END of no-redistribution definition.

        leaf default-information-originate  {
            when " /ospfv3/processes/process/areas/area/nssa/config/enable ";
            type  empty;
            description "Use this attribute to set originate type 7 default into NSSA area.";
        } // END of default-information-originate definition.

        leaf metric  {
            when " /ospfv3/processes/process/areas/area/nssa/config/default-information-originate ";
            type  uint32 {
                 range "0..16777214"  {
                    description "0..16777214: Supported range 0 - 16777214";
                 }
            }
            default "0";
            description "Use this attribute to inform the value of the metric for OSPFv3
                        default route.";
        } // END of metric definition.

        leaf metric-type  {
            when " /ospfv3/processes/process/areas/area/nssa/config/default-information-originate ";
            type  ipi-ospfv3-types:ospfv3_metric_type_t;
            default "2";
            description "Use this attribute to inform the type of the metric for OSPFv3 default
                        route.";
        } // END of metric-type definition.

        leaf route-map  {
            when " /ospfv3/processes/process/areas/area/nssa/config/default-information-originate ";
            type  string {
                length "1..1965";
                pattern "[^?' =,>|]+";
            }
            description "Use this attributes to import routes from other routing protocols, or
                        from another OSPF instance, into OSPFv3 AS-external-LSAs.";
        } // END of route-map definition.

    } // END of ospfv3-area-nssa-config definition.
    grouping ospfv3-area-nssa-top {
        description
            "Grouping for OSPFv3 Not-So-Stubby Area (NSSA)";
        container nssa {
            if-feature feature-list:HAVE_NSSA;
            description
                "Configuration data for OSPFv3 Not-So-Stubby Area (NSSA)";
            container config {
                presence "yes";
                description
                    "Configuration data for OSPFv3 Not-So-Stubby Area (NSSA)";
                uses ospfv3-area-nssa-config;
            } // END of config-container definition.
            container state {
                config false;
                description
                    "Operational state data for OSPFv3 Not-So-Stubby Area (NSSA)";
                uses ospfv3-area-nssa-config;
            } // END of state-container definition.
        } // END of nssa-container definition.
    } // END of ospfv3-area-nssa-top definition.
    grouping ospfv3-area-stub-config {
        description
            "Grouping for OSPFv3 stub area configuration data";
        leaf enable  {
            type  empty;
            mandatory true;
            description "Use this attribute to define an area as a stub area on all routers.";
        } // END of enable definition.

        leaf no-summary  {
            type  empty;
            description "Use this attribute to do not inject inter-area routes into stub.";
        } // END of no-summary definition.

    } // END of ospfv3-area-stub-config definition.
    grouping ospfv3-area-stub-top {
        description
            "Grouping for OSPFv3 stub area";
        container stub {
            description
                "Configuration data for OSPFv3 stub area";
            container config {
                presence "yes";
                description
                    "Configuration data for OSPFv3 stub area";
                uses ospfv3-area-stub-config;
            } // END of config-container definition.
            container state {
                config false;
                description
                    "Operational state data for OSPFv3 stub area";
                uses ospfv3-area-stub-config;
            } // END of state-container definition.
        } // END of stub-container definition.
    } // END of ospfv3-area-stub-top definition.
    grouping ospfv3-area-config {
        description
            "Grouping for OSPFv3 area configuration data";
        leaf area-id  {
            type  ipi-ospfv3-types:ospfv3_area_t;
            description "Use this attribute to set the OSPFv3 area ID.";
        } // END of area-id definition.

        leaf default-cost  {
            when " /ospfv3/processes/process/areas/area/stub/config/enable  or /ospfv3/processes/process/areas/area/nssa/config/enable ";
            type  uint32 {
                 range "0..16777215"  {
                    description "0..16777215: Supported range 0 - 16777215";
                 }
            }
            default "1";
            description "Use this attribute to set the cost for default summary route sent into
                        a stub area. If an area is configured as a stub, the OSPFv3 router
                        originates one type-3 inter-area-prefix-LSA into the stub area. This
                        attribute changes the metric for this LSA.";
        } // END of default-cost definition.

    } // END of ospfv3-area-config definition.
    grouping ospfv3-area-top {
        description
            "Grouping for OSPFv3 area";
        container areas {
            description
                "Configuration data for OSPFv3 areas";

            list area {
            when " /ospfv3/processes/process/areas/area/stub/config/enable  or /ospfv3/processes/process/areas/area/nssa/config/enable  or /ospfv3/processes/process/areas/area/address-ranges  or /ospfv3/processes/process/areas/area/virtual-links ";
                key "area-id";
                description
                    "List of OSPFv3 areas";
                leaf area-id  {
                    type  leafref {
                        path  "../config/area-id";
                    }
                    description "Use this attribute to set the OSPFv3 area ID.";
                } // END of area-id definition.

                container config {
                    description
                        "Configuration data for OSPFv3 area";
                    uses ospfv3-area-config;
                } // END of config-container definition.
                container state {
                    config false;
                    description
                        "Operational state data for OSPFv3 area";
                    uses ospfv3-area-config;
                } // END of state-container definition.
                uses ospfv3-area-stub-top;
                uses ospfv3-area-nssa-top;
                uses ospfv3-area-virtual-link-top;
                uses ospfv3-area-range-top;
            } // End of area-list
        } // END of areas-container definition.
    } // END of ospfv3-area-top definition.
    grouping ospfv3-virtual-link-config-error {
        description
            "ospfv3CMLSEPvirtualCMLSEPlinkCMLSEPconfigCMLSEPerror";
        container virtual-link-config-error {
            config false;
            description
                "Virtual link configuration error notification";
            leaf router-id  {
                type  inet:ipv4-address;
                description "The originator Router ID.";
            } // END of router-id definition.

            leaf instance-id  {
                type  uint8;
                description "Instance ID.";
            } // END of instance-id definition.

            leaf error-type  {
                type  ipi-ospfv3-types:ospfv3_config_error_type_t;
                description "Error type.";
            } // END of error-type definition.

            leaf packet-type  {
                type  ipi-ospfv3-types:ospfv3_packet_type_t;
                description "Packet type.";
            } // END of packet-type definition.

        } // END of virtual-link-config-error-container definition.
    } // END of ospfv3-virtual-link-config-error definition.
    grouping ospfv3-virtual-link-state-change {
        description
            "ospfv3CMLSEPvirtualCMLSEPlinkCMLSEPstateCMLSEPchange";
        container virtual-link-state-change {
            config false;
            description
                "Virtual link state change notification";
            leaf router-id  {
                type  inet:ipv4-address;
                description "The originator Router ID.";
            } // END of router-id definition.

            leaf instance-id  {
                type  uint8;
                description "Instance ID.";
            } // END of instance-id definition.

            leaf virtual-link-state  {
                type  ipi-ospfv3-types:ospfv3_interface_state_t;
                description "Virtual link state.";
            } // END of virtual-link-state definition.

        } // END of virtual-link-state-change-container definition.
    } // END of ospfv3-virtual-link-state-change definition.
    grouping ospfv3-virtual-link-neighbor-state-change {
        description
            "ospfv3CMLSEPvirtualCMLSEPlinkCMLSEPneighborCMLSEPstateCMLSEPchange";
        container virtual-link-neighbor-state-change {
            config false;
            description
                "Virtual link neighbor state change notification";
            leaf router-id  {
                type  inet:ipv4-address;
                description "The originator Router ID.";
            } // END of router-id definition.

            leaf instance-id  {
                type  uint8;
                description "Instance ID.";
            } // END of instance-id definition.

            leaf neighbor-state  {
                type  ipi-ospfv3-types:ospfv3_interface_state_t;
                description "Neighbor state.";
            } // END of neighbor-state definition.

        } // END of virtual-link-neighbor-state-change-container definition.
    } // END of ospfv3-virtual-link-neighbor-state-change definition.
    grouping ospfv3-virtual-link-rx-bad-packet {
        description
            "ospfv3CMLSEPvirtualCMLSEPlinkCMLSEPrxCMLSEPbadCMLSEPpacket";
        container virtual-link-rx-bad-packet {
            config false;
            description
                "Virtual link RX bad packet notification";
            leaf router-id  {
                type  inet:ipv4-address;
                description "The originator Router ID.";
            } // END of router-id definition.

            leaf instance-id  {
                type  uint8;
                description "Instance ID.";
            } // END of instance-id definition.

            leaf packet-type  {
                type  ipi-ospfv3-types:ospfv3_packet_type_t;
                description "Packet type.";
            } // END of packet-type definition.

        } // END of virtual-link-rx-bad-packet-container definition.
    } // END of ospfv3-virtual-link-rx-bad-packet definition.
    grouping ospfv3-virtual-link-tx-retransmit {
        description
            "ospfv3CMLSEPvirtualCMLSEPlinkCMLSEPtxCMLSEPretransmit";
        container virtual-link-tx-retransmit {
            config false;
            description
                "Virtual link TX retransmit notification";
            leaf router-id  {
                type  inet:ipv4-address;
                description "The originator Router ID.";
            } // END of router-id definition.

            leaf instance-id  {
                type  uint8;
                description "Instance ID.";
            } // END of instance-id definition.

            leaf packet-type  {
                type  ipi-ospfv3-types:ospfv3_packet_type_t;
                description "Packet type.";
            } // END of packet-type definition.

            leaf lsdb-type  {
                type  uint32;
                description "Link state advertisement type.";
            } // END of lsdb-type definition.

            leaf lsdb-lsid  {
                type  uint32;
                description "The Link State ID.";
            } // END of lsdb-lsid definition.

            leaf lsdb-router-id  {
                type  inet:ipv4-address;
                description "LSDB router ID.";
            } // END of lsdb-router-id definition.

        } // END of virtual-link-tx-retransmit-container definition.
    } // END of ospfv3-virtual-link-tx-retransmit definition.


}
