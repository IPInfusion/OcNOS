/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : dhcpc.yang
*
*/

submodule dhcpc {

    belongs-to  ZebOS { prefix ZebOS; }
    include interface;
    include featuredhcp;


    import cml_data_types {
        prefix cml_data_types;
    }

    import feature_list {
        prefix feature_list;
    }

    description
        "dhcp_client_configuration";


    revision "2016-12-27" {
        description "Added snmp oid.";
    }

    revision "2016-10-28" {
        description "Initial version of dhcpc datamodel.";
    }



    grouping DHCPClientInterface-grouping {
        list DHCPClientInterface {
                         if-feature feature_list:HAVE_DHCP_CLIENT;

            description
                "DHCP interface related operations";

            config true;
            key "ifName";

            
            leaf ifName  {
                type  cml_data_types:CML_STRING_T {
                    length "0..255";
                }
            } // END of ifName definition.

            leaf address  {
                type  cml_data_types:CML_BOOL_T;  
            } // END of address definition.

            leaf nameserver  {
                type  cml_data_types:CML_BOOL_T;  
            } // END of nameserver definition.

            leaf logserver  {
                type  cml_data_types:CML_BOOL_T;  
            } // END of logserver definition.

            leaf hostname  {
                type  cml_data_types:CML_BOOL_T;  
            } // END of hostname definition.

            leaf ntpserver  {
                type  cml_data_types:CML_BOOL_T;  
            } // END of ntpserver definition.

            leaf ipv6address  {
                type  cml_data_types:CML_BOOL_T;  
            } // END of ipv6address definition.

            leaf ipv6nameserver  {
                type  cml_data_types:CML_BOOL_T;  
            } // END of ipv6nameserver definition.

        } // End of DHCPClientInterface-list
    } // END of DHCPClientInterface-grouping definition.


}
