/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-evpn-mpls.yang
*
*/

module ipi-evpn-mpls {

    yang-version 1.1;

    namespace   "http://www.ipinfusion.com/yang/ocnos/ipi-evpn-mpls";

    prefix "ipi-evpn-mpls";

    import cml-data-types {
        prefix cml-data-types;
        revision-date 2022-09-30;
    }

    import ietf-inet-types {
        prefix inet;
        revision-date 2013-07-15;
    }

    import ipi-evpn-mpls-types {
        prefix ipi-evpn-mpls-types;
        revision-date 2022-06-01;
    }

    import ipi-vrf {
        prefix ipi-vrf;
        revision-date 2022-07-13;
    }

    import ipi-interface {
        prefix ipi-interface;
        revision-date 2022-08-24;
    }

    import ipi-network-instance {
        prefix ipi-network-instance;
        revision-date 2022-06-01;
    }

    import ietf-yang-types {
        prefix yang;
        revision-date 2013-07-15;
    }

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for EVPN-MPLS protocol";


    revision "2022-09-22" {
        description "Added EVPN-VPWS if-feature flag for xconnect CLI";
        reference " 0.5.2.";
    }

    revision "2022-08-15" {
        description "Changed control-word as optional Argument for EVI";
        reference " 0.5.1.";
    }

    revision "2022-07-07" {
        description "Added dependency for ARP-ND refresh/MAC-ageing timer";
        reference " 0.5.0.";
    }

    revision "2022-06-23" {
        description "Introduced control word CLI option for EVI";
        reference " 0.4.3.";
    }

    revision "2022-06-01" {
        description "Updated the yang file with feature";
        reference " 0.4.2.";
    }

    revision "2022-05-17" {
        description "Addition of when tag,dependency while mapping IRB interface to L2VNID";
        reference " 0.4.1.";
    }

    revision "2022-04-28" {
        description "Addition of EVPN-MPLS IRB CLI";
        reference " 0.4.0.";
    }

    revision "2022-04-22" {
        description "Added dependent object and when tag for global vrf configs";
        reference " 0.3.2.";
    }

    revision "2021-12-10" {
        description "EVPN MPLS Xconnect (ELINE) get-api update";
        reference " 0.3.1.";
    }

    revision "2021-10-13" {
        description "Changes for unification of access clis for vxlan and evpn-mpls";
        reference " 0.3.0.";
    }

    revision "2021-10-11" {
        description "Get-API enhanced to show underlay rsvp-multipath grp-name and ecmp nhlfe_ix";
        reference " 0.2.3.";
    }

    revision "2021-09-01" {
        description "Changed base interface module's switchport attribute name and the datatype from bool to empty";
        reference " 0.2.2.";
    }

    revision "2021-08-18" {
        description "Added dependent object and when tag for access-interface objectlist";
        reference " 0.2.1.";
    }

    revision "2021-08-05" {
        description "Fixed Pyang warnings and ODL issues";
        reference " 0.2.0.";
    }

    revision "2021-05-06" {
        description "Added encapsulation dependency on access interface configuration";
        reference " 0.1.2.";
    }

    revision "2021-03-16" {
        description "Updated leafrefs due to Subinterface data model restructuring";
        reference " 0.1.1.";
    }

    revision "2021-03-04" {
        description "Initial Version";
        reference " 0.1.0.";
    }

    grouping evpn-mpls-global-config {
        description
            "Grouping for global evpn-mpls configuration";
        leaf enable-evpn-mpls  {
            type  empty;
            mandatory true;
            description "Use this attribute to enable EVPN-MPLS module. Without this
                        attribute evpn mpls functionality can not be achieved";
        } // END of enable-evpn-mpls definition.

        leaf vtep-ipv4  {
            when " /ipi-evpn-mpls:evpn-mpls/ipi-evpn-mpls:global/ipi-evpn-mpls:config/ipi-evpn-mpls:enable-evpn-mpls ";
            type  inet:ipv4-address;
            description "Use this attribute to set source vtep global ip address.
                        This will be treated at evpn mpls tunnel source address";
        } // END of vtep-ipv4 definition.

        leaf mac-ageing-timer  {
            when " /ipi-evpn-mpls:evpn-mpls/ipi-evpn-mpls:global/ipi-evpn-mpls:config/ipi-evpn-mpls:enable-evpn-mpls ";
            type  uint32 {
                 range "10..572"  {
                    description "10..572: Supported range 10 - 572";
                 }
            }
            units "seconds";
            description "Use this attribute to set the time till a learned mac
                        address will persist after last update";
        } // END of mac-ageing-timer definition.

    } // END of evpn-mpls-global-config definition.
    grouping evpn-mpls-tenant-top {
        description
            "Grouping for EVPN-MPLS tenant top";

        list mpls-tenant {
        when " /ipi-evpn-mpls:evpn-mpls/ipi-evpn-mpls:global/ipi-evpn-mpls:config ";
            key "tenant-identifier";
            description
                "Tenant configurations for EVPN-MPLS";
            leaf tenant-identifier  {
                type  leafref {
                    path  "../config/tenant-identifier";
                }
                description "Tenant Identifier";
            } // END of tenant-identifier definition.

            container config {
                description
                    "Configuration data";
                uses evpn-mpls-tenant-config;
                uses evpn-mpls-tenant-global-config;
            } // END of config-container definition.
            container state {
                config false;
                description
                    "Operational state data";
                uses evpn-mpls-tenant-config;
                uses evpn-mpls-tenant-global-config;
            } // END of state-container definition.
            container route-count-info {
                config false;
                description
                    "Configuration data for EVPN-MPLS global capability configuration";
                container state {
                    config false;
                    description
                        "Operational state data";
                    uses evpn-mpls-tenant-route-count-state;
                } // END of state-container definition.
            } // END of route-count-info-container definition.
            container xconnect-mapping-info {
                if-feature feature-list:HAVE_EVPN_VPWS;
                config false;
                description
                    "This holds data for EVPN-MPLS xconnect mapping summary";
                container state {
                    config false;
                    description
                        "Operational state data";
                    uses evpn-mpls-tenant-xconnect-mapping-state;
                } // END of state-container definition.
            } // END of xconnect-mapping-info-container definition.
            uses evpn-mpls-tenant-arp-cache-list;
            uses evpn-mpls-tenant-nd-cache-list;
            uses evpn-mpls-tenant-mac-table-list;
            uses evpn-mpls-tenant-access-interface-list;
        } // End of mpls-tenant-list
    } // END of evpn-mpls-tenant-top definition.
    grouping evpn-mpls-tenant-arp-cache-list {
        description
            "Grouping for arp-cache information configuration";

        list arp-cache-info {
            key "host-ip";
            config false;
            description
                "arp-cache information list";
            leaf host-ip  {
                type  leafref {
                    path  "../state/host-ip";
                }
                description "Use this attribute to show Host IP address";
            } // END of host-ip definition.

            container state {
                config false;
                description
                    "Operational state data";
                uses evpn-mpls-tenant-arp-cache-state;
            } // END of state-container definition.
        } // End of arp-cache-info-list
    } // END of evpn-mpls-tenant-arp-cache-list definition.
    grouping evpn-mpls-tenant-nd-cache-list {
        description
            "Grouping for nd-cache information display";

        list nd-cache-info {
            key "host-ip";
            config false;
            description
                "nd-cache information list";
            leaf host-ip  {
                type  leafref {
                    path  "../state/host-ip";
                }
                description "Use this attribute to show Host IP address";
            } // END of host-ip definition.

            container state {
                config false;
                description
                    "Operational state data";
                uses evpn-mpls-tenant-nd-cache-state;
            } // END of state-container definition.
        } // End of nd-cache-info-list
    } // END of evpn-mpls-tenant-nd-cache-list definition.
    grouping evpn-mpls-tenant-mac-table-list {
        description
            "Grouping for mac table information display";

        list mac-table-info {
            key "mac-address";
            config false;
            description
                "mac table display information";
            leaf mac-address  {
                type  leafref {
                    path  "../state/mac-address";
                }
                description "Mac Adress of the host";
            } // END of mac-address definition.

            container state {
                config false;
                description
                    "Operational state data";
                uses evpn-mpls-tenant-mac-table-state;
            } // END of state-container definition.
        } // End of mac-table-info-list
    } // END of evpn-mpls-tenant-mac-table-list definition.
    grouping evpn-mpls-tenant-access-interface-list {
        description
            "Grouping for access interafce information display";

        list access-interface-info {
            key "access-interface-name";
            config false;
            description
                "access interface display information";
            leaf access-interface-name  {
                type  leafref {
                    path  "../state/access-interface-name";
                }
                description "Use this attribute to fetch the access port information mapped to
                            particular tenant";
            } // END of access-interface-name definition.

            container state {
                config false;
                description
                    "Operational state data";
                uses evpn-mpls-tenant-access-interface-state;
            } // END of state-container definition.
        } // End of access-interface-info-list
    } // END of evpn-mpls-tenant-access-interface-list definition.
    grouping evpn-mpls-tunnel-top {
        description
            "Top-Level Grouping for EVPN-MPLS Tunnel";

        list tunnel {
        when " /ipi-evpn-mpls:evpn-mpls/ipi-evpn-mpls:global/ipi-evpn-mpls:config ";
            key "destination-vtep-ip destination-evpn-identifier";
            config false;
            description
                "tunnel related display information";
            leaf destination-vtep-ip  {
                type  leafref {
                    path  "../state/destination-vtep-ip";
                }
                description "Use this attribute to get Tunnel destination IP";
            } // END of destination-vtep-ip definition.

            leaf destination-evpn-identifier  {
                type  leafref {
                    path  "../state/destination-evpn-identifier";
                }
                description "use this attribute to get destination tenant identifier for specific
                            tunnel";
            } // END of destination-evpn-identifier definition.

            container state {
                config false;
                description
                    "Operational state data";
                uses evpn-mpls-tunnel-state;
                uses evpn-mpls-tunnel-counters-state;
            } // END of state-container definition.
        } // End of tunnel-list
    } // END of evpn-mpls-tunnel-top definition.
    grouping evpn-mpls-tenant-global-config {
        description
            "Grouping for EVPN-MPLS tenant global configuration";
        leaf tenant-identifier  {
            type  uint32 {
                 range "1..16777215"  {
                    description "1..16777215: Supported range 1 - 16777215";
                 }
            }
            description "Tenant Identifier";
        } // END of tenant-identifier definition.

        leaf vpws-identifier  {
            if-feature feature-list:HAVE_EVPN_VPWS;
            type  uint32 {
                 range "1..16777215"  {
                    description "1..16777215: Supported range 1 - 16777215";
                 }
            }
            description "Use this attribute to create vpws tenant";
        } // END of vpws-identifier definition.

        leaf control-word  {
            type  boolean;
            description "Use this attribute to set control word for EVI";
        } // END of control-word definition.

    } // END of evpn-mpls-tenant-global-config definition.
    grouping evpn-mpls-tenant-config {
        description
            "Grouping for EVPN-MPLS tenant configuration";
        leaf vrf-name  {
            type  leafref {
                path  "/ipi-network-instance:network-instances/ipi-network-instance:network-instance/ipi-vrf:vrf/ipi-vrf:config/ipi-vrf:vrf-name";
            }
            description "Use this attribute to map vrf to carry EVPN routes";
        } // END of vrf-name definition.

        leaf mac-holdtime  {
            type  int32 {
                 range "-1..300"  {
                    description "-1..300: Supported range -1 - 300";
                 }
            }
            units "seconds";
            default "0";
            description "Use this attribute to set the time a host mac entry will persist after
                        unconfig";
        } // END of mac-holdtime definition.

        leaf tenant-description  {
            type  string {
                length "1..1965";
                pattern "[^?' =,>|]+";
            }
            description "Use this attribute to set evpn-mpls tenant identifier name";
        } // END of tenant-description definition.

        leaf tunnel-policy-name  {
            if-feature feature-list:HAVE_SERVICE_MAPPING;
            type  string {
                length "1..127";
                pattern "[^?' =,>|]+";
            }
            description "Transport Tunnel Selection Policy";
        } // END of tunnel-policy-name definition.

        leaf irb-name  {
            type  leafref {
                path  "/ipi-interface:interfaces/ipi-interface:interface/ipi-interface:name";
            }
            description "Use this attribute to provide default gateway behavior on a VTEP for
                        particular VNID.";
        } // END of irb-name definition.

    } // END of evpn-mpls-tenant-config definition.
    grouping evpn-mpls-tenant-route-count-state {
        description
            "Grouping for evpn-mpls tenant configuration";
        leaf total  {
            type  uint32;
            description "Use this attribute to show count of Total Route Entries";
        } // END of total definition.

        leaf mac-only  {
            type  uint32;
            description "Use this attribute to show count of Mac Only Entries";
        } // END of mac-only definition.

        leaf mac-ipv4  {
            type  uint32;
            description "Use this attribute to show count of Mac Ipv4 Entries";
        } // END of mac-ipv4 definition.

        leaf mac-ipv6  {
            if-feature feature-list:HAVE_IPV6;
            type  uint32;
            description "Use this attribute to show count of Mac Ipv6 Entries";
        } // END of mac-ipv6 definition.

    } // END of evpn-mpls-tenant-route-count-state definition.
    grouping evpn-mpls-tenant-xconnect-mapping-state {
        description
            "Grouping for evpn-mpls xconnect mapping";
        leaf source-tenant-description  {
            type  string {
                length "1..1965";
                pattern "[^?' =,>|]+";
            }
            description "Use this attribute to show name of source tenant";
        } // END of source-tenant-description definition.

        leaf destination-vpws-identifier  {
            type  uint32;
            description "Use this attribute to show the remote vpws id";
        } // END of destination-vpws-identifier definition.

        leaf source-interface  {
            type  string {
                length "1..1965";
                pattern "[^?' =,>|]+";
            }
            description "Use this attribute to show source connection of tunnel";
        } // END of source-interface definition.

        leaf destination-interface  {
            type  string {
                length "1..1965";
                pattern "[^?' =,>|]+";
            }
            description "Use this attribute to show destination connection of tunnel";
        } // END of destination-interface definition.

        leaf vtep-ip-address  {
            type  inet:ipv4-address;
            description "Use this attribute to show tunnel ip address";
        } // END of vtep-ip-address definition.

        leaf connection-type  {
            type  ipi-evpn-mpls-types:evpn_mpls_xconnect_connection_type_t;
            description "Use this attribute to show the type of network connection";
        } // END of connection-type definition.

        leaf connection-status  {
            type  ipi-evpn-mpls-types:evpn_mpls_xconnect_connection_status_t;
            description "Use this attribute to show status of network connection";
        } // END of connection-status definition.

    } // END of evpn-mpls-tenant-xconnect-mapping-state definition.
    grouping evpn-mpls-tenant-arp-cache-state {
        description
            "Grouping for display arp-cache information";
        leaf host-ip  {
            type  inet:ipv4-address;
            description "Use this attribute to show Host IP address";
        } // END of host-ip definition.

        leaf host-mac  {
            type  cml-data-types:cml_mac_addr_t {
                length "1..1965";
            }
            description "Use this attribute to show Host MAC address";
        } // END of host-mac definition.

        leaf host-type  {
            type  ipi-evpn-mpls-types:evpn_mpls_host_t;
            description "Use this attribute to show Host Type";
        } // END of host-type definition.

    } // END of evpn-mpls-tenant-arp-cache-state definition.
    grouping evpn-mpls-tenant-nd-cache-state {
        description
            "Grouping for display nd-cache information";
        leaf host-ip  {
            type  inet:ipv6-address;
            description "Use this attribute to show Host IP address";
        } // END of host-ip definition.

        leaf host-mac  {
            type  cml-data-types:cml_mac_addr_t {
                length "1..1965";
            }
            description "Use this attribute to show Host Mac Address";
        } // END of host-mac definition.

        leaf host-type  {
            type  ipi-evpn-mpls-types:evpn_mpls_host_t;
            description "Use this attribute to show Host Type";
        } // END of host-type definition.

    } // END of evpn-mpls-tenant-nd-cache-state definition.
    grouping evpn-mpls-tenant-mac-table-state {
        description
            "Grouping for display mac table information";
        leaf mac-address  {
            type  cml-data-types:cml_mac_addr_t {
                length "1..1965";
            }
            description "Mac Adress of the host";
        } // END of mac-address definition.

        leaf interface-name  {
            type  leafref {
                path  "/ipi-interface:interfaces/ipi-interface:interface/ipi-interface:name";
            }
            description "interface name";
        } // END of interface-name definition.

        leaf vtep-ip-esi  {
            type  string {
                length "1..1965";
                pattern "[^?' =,>|]+";
            }
            description "VTEP global ip address or ESI";
        } // END of vtep-ip-esi definition.

        leaf host-type  {
            type  ipi-evpn-mpls-types:evpn_mpls_host_t;
            description "Host Type";
        } // END of host-type definition.

        leaf host-status  {
            type  ipi-evpn-mpls-types:evpn_mpls_host_status_t;
            description "Host Status";
        } // END of host-status definition.

        leaf access-port-description  {
            type  string {
                length "1..1965";
                pattern "[^?' =,>|]+";
            }
            description "Description for the port";
        } // END of access-port-description definition.

    } // END of evpn-mpls-tenant-mac-table-state definition.
    grouping evpn-mpls-tenant-access-interface-state {
        description
            "Grouping for display access interface information";
        leaf access-interface-name  {
            type  string {
                length "1..1965";
                pattern "[^?' =,>|]+";
            }
            description "Use this attribute to fetch the access port information mapped to
                        particular tenant";
        } // END of access-interface-name definition.

        leaf tenant-description  {
            type  string {
                length "1..1965";
                pattern "[^?' =,>|]+";
            }
            description "Use this attribute to get evpn-mpls tenant identifier name";
        } // END of tenant-description definition.

        leaf ethernet-segment-id  {
            type  string {
                length "1..1965";
                pattern "[^?' =,>|]+";
            }
            description "This Object is used to get the evpn multi-homed Ethernet Segment
                        Identifier value";
        } // END of ethernet-segment-id definition.

        leaf port-status  {
            type  string {
                length "1..1965";
                pattern "[^?' =,>|]+";
            }
            description "This Object is used to get the DF/Non-DF status value in multihomed
                        environment";
        } // END of port-status definition.

    } // END of evpn-mpls-tenant-access-interface-state definition.
    grouping evpn-mpls-tunnel-state {
        description
            "Grouping for displaying tunnel information";
        leaf destination-vtep-ip  {
            type  inet:ipv4-address;
            description "Use this attribute to set Tunnel destination IP";
        } // END of destination-vtep-ip definition.

        leaf destination-evpn-identifier  {
            type  uint32;
            description "use this attribute to get destination tenant identifier for specific
                        tunnel";
        } // END of destination-evpn-identifier definition.

        leaf source-vtep-ip  {
            type  inet:ipv4-address;
            description "Use this attribute to set Tunnel source IP";
        } // END of source-vtep-ip definition.

        leaf up-down-time  {
            type  yang:timeticks;
            description "Use this attribute to indicate tunnel up/down time";
        } // END of up-down-time definition.

        leaf tunnel-status  {
            type  ipi-evpn-mpls-types:evpn_mpls_tunnel_status_t;
            description "Use this attribute to see the Status of tunnel";
        } // END of tunnel-status definition.

        leaf source-vpws-identifier  {
            type  uint32;
            description "Use this attribute to see the source tenant identifier";
        } // END of source-vpws-identifier definition.

        leaf destination-vpws-identifier  {
            type  uint32;
            description "Use this attribute to see the destination tenant identifier";
        } // END of destination-vpws-identifier definition.

        leaf local-multicast-label  {
            type  uint32;
            description "Use this attribute to see the local multicast label";
        } // END of local-multicast-label definition.

        leaf local-unicast-label  {
            type  uint32;
            description "Use this attribute to see the local unicast label";
        } // END of local-unicast-label definition.

        leaf remote-multicast-label  {
            type  uint32;
            description "Use this attribute to see the remote multicast label";
        } // END of remote-multicast-label definition.

        leaf remote-unicast-label  {
            type  uint32;
            description "Use this attribute to see the remote unicast label";
        } // END of remote-unicast-label definition.

        leaf is_xconnect  {
            type  boolean;
            description "Use this attribute to see xconnect enabled or not";
        } // END of is_xconnect definition.

        leaf rsvp-multipath-grp-name  {
            if-feature feature-list:HAVE_RSVP_MULTIPATH;
            type  string {
                length "1..1965";
                pattern "[^?' =,>|]+";
            }
            description "Use this attribute to see Underlay RSVP-Multipath Group name";
        } // END of rsvp-multipath-grp-name definition.

        leaf rsvp-multipath-nhlfe-ix  {
            if-feature feature-list:HAVE_RSVP_MULTIPATH;
            type  uint32;
            description "Use this attribute to see Underlay RSVP-Multipath NHLFE ix";
        } // END of rsvp-multipath-nhlfe-ix definition.

        leaf tunnel-label  {
            type  uint32;
            description "Use this attribute to see the tunnel label";
        } // END of tunnel-label definition.

        leaf network-interface  {
            type  leafref {
                path  "/ipi-interface:interfaces/ipi-interface:interface/ipi-interface:name";
            }
            description "network interface name";
        } // END of network-interface definition.

    } // END of evpn-mpls-tunnel-state definition.
    grouping evpn-mpls-tunnel-counters-state {
        description
            "Grouping for displaying tunnel counters and statistics.";
        container counters {
            config false;
            description
                "A collection of evpn-mpls network-related statistics";
            leaf out-bum-packets  {
                type  yang:counter64;
                description "This indicates total number of BUM packets sent out from tunnel
                            interface";
            } // END of out-bum-packets definition.

            leaf out-unicast-packets  {
                type  yang:counter64;
                description "This indicates total number of known Unicast packets sent out from
                            tunnel interface";
            } // END of out-unicast-packets definition.

            leaf in-bum-packets  {
                type  yang:counter64;
                description "This indicates total number of BUM packets received on tunnel
                            interface";
            } // END of in-bum-packets definition.

            leaf in-unicast-packets  {
                type  yang:counter64;
                description "This indicates total number of known Unicast packets received on
                            tunnel interface";
            } // END of in-unicast-packets definition.

        } // END of counters-container definition.
    } // END of evpn-mpls-tunnel-counters-state definition.
    grouping arp-nd-global-grouping {
        description
            "Grouping for configuring global ARP-ND configs";
        leaf arp-nd-refresh-time  {
            when " /ipi-evpn-mpls:evpn-mpls/ipi-evpn-mpls:global/ipi-evpn-mpls:config/ipi-evpn-mpls:enable-evpn-mpls ";
            type  uint32 {
                 range "3..190"  {
                    description "3..190: Supported range 3 - 190";
                 }
            }
            units "seconds";
            description "Use this attribute to configure aging out the arp-cache and
                        nd-cache entries";
        } // END of arp-nd-refresh-time definition.

    } // END of arp-nd-global-grouping definition.

    grouping  evpn-mpls-grouping {
    description
        "EVPN-MPLS global level container";
    container evpn-mpls {
        if-feature feature-list:HAVE_NVO;
        if-feature feature-list:HAVE_MPLS;
        if-feature feature-list:HAVE_BGP_EVPN;
        description
            "EVPN-MPLS global level container";
        container global {
            description
                "Configuration data for EVPN-MPLS global capability configuration";
            container config {
                presence "Enable EVPN-MPLS";
                description
                    "Configuration data";
                uses evpn-mpls-global-config;
            } // END of config-container definition.
            container state {
                config false;
                description
                    "Operational state data";
                uses evpn-mpls-global-config;
            } // END of state-container definition.
        } // END of global-container definition.
        container arp-nd-global {
            description
                "ARP-ND global data";
            container config {
                description
                    "ARP-ND global configuration data";
                uses arp-nd-global-grouping;
            } // END of config-container definition.
            container state {
                config false;
                description
                    "Operational state data";
                uses arp-nd-global-grouping;
            } // END of state-container definition.
        } // END of arp-nd-global-container definition.
        uses evpn-mpls-tenant-top;
        uses evpn-mpls-tunnel-top;
    } // END of evpn-mpls-container definition.
    } // END of evpn-mpls-grouping definition.

    uses evpn-mpls-grouping;

    rpc clear-nvo-mpls-dynamic-mac-address-table {
        if-feature feature-list:HAVE_MPLS;
        if-feature feature-list:HAVE_SUBINTERFACE;
        if-feature feature-list:HAVE_NVO;
        if-feature feature-list:HAVE_BGP_EVPN;
        description "Use this RPC to clear the dynamic entries from mac address table";
        input  {
            leaf tenant-identifier  {
                type uint32 {
                    range "1..16777215";
                }
                description "Use this attribute to include a tenant";
            }
        }
    }

    rpc clear-evpn-mpls-egress-counters {
        if-feature feature-list:HAVE_MPLS;
        if-feature feature-list:HAVE_SUBINTERFACE;
        if-feature feature-list:HAVE_NVO;
        if-feature feature-list:HAVE_BGP_EVPN;
        description "Use this RPC to clear the counters";
        input  {
            leaf tenant-identifier  {
                type uint32 {
                    range "1..16777215";
                }
                description "Use this attribute to include a tenant";
            }
            leaf egress-direction  {
                type ipi-evpn-mpls-types:evpn_mpls_egress_dir_t;
                mandatory true;
                description "Use this attribute to include Tunnel direction";
            }
            leaf destination-ip  {
                type inet:ipv4-address;
                description "Use this attribute to include Tunnel destination IP";
            }
        }
    }

    rpc clear-evpn-mpls-ingress-counters {
        if-feature feature-list:HAVE_MPLS;
        if-feature feature-list:HAVE_SUBINTERFACE;
        if-feature feature-list:HAVE_NVO;
        if-feature feature-list:HAVE_BGP_EVPN;
        description "Use this RPC to clear the ingress side counters";
        input  {
            leaf tenant-identifier  {
                type uint32 {
                    range "1..16777215";
                }
                description "Use this attribute to include a tenant";
            }
            leaf ingress-direction  {
                type ipi-evpn-mpls-types:evpn_mpls_ingress_dir_t;
                mandatory true;
                description "Use this attribute to include Tunnel direction";
            }
        }
    }

}
