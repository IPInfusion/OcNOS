/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-evpn-mpls-types.yang
*
*/

module ipi-evpn-mpls-types {

    yang-version 1.1;

    namespace   "http://www.ipinfusion.com/yang/ocnos/ipi-evpn-mpls-types";

    prefix "ipi-evpn-mpls-types";

    organization
        "IP Infusion Inc.";

    contact
        "Address: 3965 Freedom Circle, Suite 200, Santa Clara, CA 95054
         Phone: +1 408-400-1900
         E-mail: support@ipinfusion.com
         Web: http://www.ipinfusion.com/";

    description
        "YANG version of the ipi-evpn-mpls-types";


    revision "2022-06-01" {
        description "Updated the yang file with feature";
        reference " 0.1.3.";
    }

    revision "2021-12-27" {
        description "EVPN MPLS Xconnect git api";
        reference " 0.1.2.";
    }

    revision "2021-09-03" {
        description "Update descriptions of attribute";
        reference " 0.1.1.";
    }

    revision "2021-03-04" {
        description "Initial Version";
        reference " 0.1.0.";
    }



    typedef  evpn_mpls_host_t {
        type enumeration {
            enum Dynamic {
                value 0;
                description "Host type is Dynamic";
            }
            enum Static-Local {
                value 1;
                description "Host type is Static Local";
            }
            enum Remote-Dynamic {
                value 2;
                description "Host type is Evpn Dynamic";
            }
            enum Remote-Static {
                value 3;
                description "Host type is Evpn Static";
            }
            enum Static-Remote {
                value 4;
                description "Host type is Static Remote";
            }
        }
        description "type definition for EVPN_MPLS_HOST_T";
    }

    typedef  evpn_mpls_xconnect_connection_type_t {
        type enumeration {
            enum NA {
                value 0;
                description "Connection type not available";
            }
            enum AC-AC {
                value 1;
                description "Connection type local Xconnect";
            }
            enum AC-NW {
                value 2;
                description "Connection type Xconnect over tunnle";
            }
        }
        description "type definition for EVPN_MPLS_XCONNECT_CONNECTION_TYPE_T";
    }

    typedef  evpn_mpls_xconnect_connection_status_t {
        type enumeration {
            enum NA {
                value 0;
                description "Connection status not available";
            }
            enum NW-SET {
                value 1;
                description "Xconnect network up";
            }
            enum AC-DN-NW-DN {
                value 2;
                description "Access port down - network down";
            }
            enum AC-DN-NW-UP {
                value 3;
                description "Access port down - network up";
            }
            enum AC-UP-NW-DN {
                value 4;
                description "Access port up - network down";
            }
        }
        description "type definition for EVPN_MPLS_XCONNECT_CONNECTION_STATUS_T";
    }

    typedef  evpn_mpls_host_status_t {
        type enumeration {
            enum --- {
                value 0;
                description "Default host status";
            }
            enum Max-Move-conflict {
                value 1;
                description "MAC has moved too many times";
            }
            enum Discard {
                value 2;
                description "MAC is moved to the discard state";
            }
        }
        description "type definition for EVPN_MPLS_HOST_STATUS_T";
    }

    typedef  evpn_mpls_tunnel_status_t {
        type enumeration {
            enum Deleted {
                value 0;
                description "Tunnel is deleted";
            }
            enum Un-Resolved {
                value 1;
                description "Tunnel not established";
            }
            enum Resolved {
                value 2;
                description "Tunnel established but not in hardware";
            }
            enum Installed {
                value 3;
                description "Tunnel established succesfully in hardware";
            }
        }
        description "type definition for EVPN_MPLS_TUNNEL_STATUS_T";
    }

    typedef  evpn_mpls_egress_dir_t {
        type enumeration {
            enum egress {
                value 1;
                description "egress direction";
            }
        }
        description "type definition for EVPN_MPLS_EGRESS_DIR_T";
    }

    typedef  evpn_mpls_ingress_dir_t {
        type enumeration {
            enum ingress {
                value 1;
                description "ingress direction";
            }
        }
        description "type definition for EVPN_MPLS_INGRESS_DIR_T";
    }

}
