/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-dhcpc.yang
*
*/

submodule zebos-dhcpc {

    belongs-to  zebos { prefix zebos; }

    import cml_data_types {
        prefix cml_data_types;
    }

    import feature_list {
        prefix feature_list;
    }

    include zebos-interface;
    include zebos-featuredhcp;
    organization
        "IP Infusion Inc.";

    contact
        "Address: 3965 Freedom Circle, Suite 200, Santa Clara, CA 95054
        Phone: +1 408-400-1900
        E-mail: support@ipinfusion.com
        Web: http://www.ipinfusion.com/";

    description
        "dhcp_client_configuration";


    revision "2016-12-27" {
        description "Added snmp oid.";
    }

    revision "2016-10-28" {
        description "Initial version of dhcpc datamodel.";
    }



    grouping DHCPClientInterface-grouping {
        list DHCPClientInterface {
            if-feature feature_list:HAVE_DHCP_CLIENT;
            key "ifName";
            description
                "DHCP interface related operations";
            leaf ifName  {
                type  cml_data_types:CML_STRING_T {
                    length "0..255";
                }
                description "";
            } // END of ifName definition.

            leaf address  {
                type  cml_data_types:CML_BOOL_T;
                description "";
            } // END of address definition.

            leaf nameserver  {
                type  cml_data_types:CML_BOOL_T;
                description "";
            } // END of nameserver definition.

            leaf logserver  {
                type  cml_data_types:CML_BOOL_T;
                description "";
            } // END of logserver definition.

            leaf hostname  {
                type  cml_data_types:CML_BOOL_T;
                description "";
            } // END of hostname definition.

            leaf ntpserver  {
                type  cml_data_types:CML_BOOL_T;
                description "";
            } // END of ntpserver definition.

            leaf ipv6address  {
                type  cml_data_types:CML_BOOL_T;
                description "";
            } // END of ipv6address definition.

            leaf ipv6nameserver  {
                type  cml_data_types:CML_BOOL_T;
                description "";
            } // END of ipv6nameserver definition.

        } // End of DHCPClientInterface-list
    } // END of DHCPClientInterface-grouping definition.


}
