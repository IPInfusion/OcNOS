/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-mcec.yang
*
*/

submodule zebos-mcec {

    belongs-to  zebos { prefix zebos; }

    import cml_data_types {
        prefix cml_data_types;
    }

    include zebos-interface;
    organization
        "IP Infusion Inc.";

    contact
        "Address: 3965 Freedom Circle, Suite 200, Santa Clara, CA 95054
        Phone: +1 408-400-1900
        E-mail: support@ipinfusion.com
        Web: http://www.ipinfusion.com/";

    description
        "Multi Chassis Ethernet Channel (MCEC)";


    revision "2016-07-02" {
        description "Initial draft version for MCEC module.";
    }


    grouping  mcecMaster-grouping {
    container mcecMaster {
        description
            "mcecMaster";
        leaf mcecDebug  {
            type  cml_data_types:MCEC_DEBUG_T;
            description "";
        } // END of mcecDebug definition.


        list portal {
            key "mlagId";
            config false;
            description
                "struct mcec_portal";
            leaf mlagId  {
                type  cml_data_types:CML_UINT16_T;
                description "";
            } // END of mlagId definition.

            leaf ifName  {
                type  cml_data_types:CML_STRING_T {
                    length "0..255";
                }
                description "";
            } // END of ifName definition.

            leaf homeAggKey  {
                type  cml_data_types:CML_UINT16_T;
                description "";
            } // END of homeAggKey definition.

            leaf homeAdminAggKey  {
                type  cml_data_types:CML_UINT16_T;
                description "";
            } // END of homeAdminAggKey definition.

            leaf homeOperAggKey  {
                type  cml_data_types:CML_UINT16_T;
                description "";
            } // END of homeOperAggKey definition.

            leaf homeOperPartnerAggKey  {
                type  cml_data_types:CML_UINT16_T;
                description "";
            } // END of homeOperPartnerAggKey definition.

            leaf homePartnerSystem  {
                type  cml_data_types:CML_STRING_T {
                    length "0..255";
                }
                description "";
            } // END of homePartnerSystem definition.

            leaf homePartnerSystemPriority  {
                type  cml_data_types:CML_UINT16_T;
                description "";
            } // END of homePartnerSystemPriority definition.

            leaf homeMemberIfBandwidth  {
                type  cml_data_types:CML_UINT64_T;
                description "";
            } // END of homeMemberIfBandwidth definition.

            leaf homePhyPropertiesDigest  {
                type  cml_data_types:CML_STRING_T {
                    length "0..255";
                }
                description "";
            } // END of homePhyPropertiesDigest definition.

            leaf homeMemIfState  {
                type  cml_data_types:CML_UINT8_T;
                description "";
            } // END of homeMemIfState definition.

            leaf homeStpState  {
                type  cml_data_types:CML_UINT8_T;
                description "";
            } // END of homeStpState definition.

            leaf homeMlagSync  {
                type  cml_data_types:CML_UINT8_T;
                description "";
            } // END of homeMlagSync definition.

            leaf idlToMlagFloodEnabled  {
                type  cml_data_types:CML_UINT8_T;
                description "";
            } // END of idlToMlagFloodEnabled definition.

            leaf mlagPortState  {
                type  cml_data_types:CML_UINT8_T;
                description "";
            } // END of mlagPortState definition.

            leaf mlagIfState  {
                type  cml_data_types:CML_UINT8_T;
                description "";
            } // END of mlagIfState definition.

            leaf isAggMapped  {
                type  cml_data_types:CML_UINT8_T;
                description "";
            } // END of isAggMapped definition.

            leaf nttinfopdu  {
                type  cml_data_types:CML_UINT8_T;
                description "";
            } // END of nttinfopdu definition.

            leaf mlagInfoUpdate  {
                type  cml_data_types:CML_UINT8_T;
                description "";
            } // END of mlagInfoUpdate definition.

            leaf differMlagInfo  {
                type  cml_data_types:CML_UINT8_T;
                description "";
            } // END of differMlagInfo definition.

            leaf neighAdminAggKey  {
                type  cml_data_types:CML_UINT16_T;
                description "";
            } // END of neighAdminAggKey definition.

            leaf neighOperPartnerAggKey  {
                type  cml_data_types:CML_UINT16_T;
                description "";
            } // END of neighOperPartnerAggKey definition.

            leaf neighPartnerSystem  {
                type  cml_data_types:CML_STRING_T {
                    length "0..255";
                }
                description "";
            } // END of neighPartnerSystem definition.

            leaf neighPartnerSystemPriority  {
                type  cml_data_types:CML_UINT16_T;
                description "";
            } // END of neighPartnerSystemPriority definition.

            leaf neighMemberIfBandwidth  {
                type  cml_data_types:CML_UINT64_T;
                description "";
            } // END of neighMemberIfBandwidth definition.

            leaf neighPhyPropertiesDigest  {
                type  cml_data_types:CML_STRING_T {
                    length "0..255";
                }
                description "";
            } // END of neighPhyPropertiesDigest definition.

            leaf neighMemIfState  {
                type  cml_data_types:CML_UINT8_T;
                description "";
            } // END of neighMemIfState definition.

            leaf neighStpState  {
                type  cml_data_types:CML_UINT8_T;
                description "";
            } // END of neighStpState definition.

            leaf neighMlagSync  {
                type  cml_data_types:CML_UINT8_T;
                description "";
            } // END of neighMlagSync definition.

            leaf mlagBandwidth  {
                type  cml_data_types:CML_UINT64_T;
                description "";
            } // END of mlagBandwidth definition.

            leaf mcecInfoRcvState  {
                type  cml_data_types:CML_UINT8_T;
                description "";
            } // END of mcecInfoRcvState definition.

            leaf mcecInfoPeriodicTxState  {
                type  cml_data_types:CML_UINT8_T;
                description "";
            } // END of mcecInfoPeriodicTxState definition.

            leaf infoPeriodicTxTimerExpired  {
                type  cml_data_types:CML_UINT8_T;
                description "";
            } // END of infoPeriodicTxTimerExpired definition.

            leaf mcecValidInfoPduRx  {
                type  cml_data_types:CML_UINT32_T;
                description "";
            } // END of mcecValidInfoPduRx definition.

            leaf mcecValidInfoPduTx  {
                type  cml_data_types:CML_UINT32_T;
                description "";
            } // END of mcecValidInfoPduTx definition.

        } // End of portal-list
        container mcecDomain {
            description
                "mcec domain";
            leaf homeDomainSysNumber  {
                type  cml_data_types:CML_UINT8_T {
                     range "1..2";
                }
                description "";
            } // END of homeDomainSysNumber definition.

            leaf confNeighDomainSysNumber  {
                type  cml_data_types:CML_UINT8_T;
                config false;
                description "";
            } // END of confNeighDomainSysNumber definition.

            leaf domainAddress  {
                type  cml_data_types:CML_STRING_T {
                    length "0..255";
                }
                description "";
            } // END of domainAddress definition.

            leaf domainPriority  {
                type  cml_data_types:CML_UINT16_T {
                     range "1..65535";
                }
                default "32768";
                description "";
            } // END of domainPriority definition.

            leaf homeHelloTimeout  {
                type  cml_data_types:CML_MCEC_HELLO_T;
                default "short";
                description "";
            } // END of homeHelloTimeout definition.

            leaf domainSync  {
                type  cml_data_types:CML_UINT8_T;
                config false;
                description "";
            } // END of domainSync definition.

            leaf domainAdjacency  {
                type  cml_data_types:CML_UINT8_T;
                config false;
                description "";
            } // END of domainAdjacency definition.

            leaf domainConfigured  {
                type  cml_data_types:CML_UINT8_T;
                config false;
                description "";
            } // END of domainConfigured definition.

            leaf mcecBegin  {
                type  cml_data_types:CML_UINT8_T;
                config false;
                description "";
            } // END of mcecBegin definition.

            leaf nsmImiSyncUpDone  {
                type  cml_data_types:CML_UINT8_T;
                config false;
                description "";
            } // END of nsmImiSyncUpDone definition.

            leaf portalCount  {
                type  cml_data_types:CML_UINT16_T;
                config false;
                description "";
            } // END of portalCount definition.

            leaf mcecInvalidPduRx  {
                type  cml_data_types:CML_UINT32_T;
                config false;
                description "";
            } // END of mcecInvalidPduRx definition.

        } // END of mcecDomain-container definition.
        container idp {
            description
                "mcec_idp";
            leaf intraDomainLink  {
                type  cml_data_types:CML_STRING_T {
                    length "0..255";
                }
                description "";
            } // END of intraDomainLink definition.

            leaf neighDomainAddr  {
                type  cml_data_types:CML_STRING_T {
                    length "0..255";
                }
                config false;
                description "";
            } // END of neighDomainAddr definition.

            leaf neighDomainPriority  {
                type  cml_data_types:CML_UINT32_T;
                config false;
                description "";
            } // END of neighDomainPriority definition.

            leaf neighDomainSysNumber  {
                type  cml_data_types:CML_UINT16_T;
                config false;
                description "";
            } // END of neighDomainSysNumber definition.

            leaf neighDomainSync  {
                type  cml_data_types:CML_UINT16_T;
                config false;
                description "";
            } // END of neighDomainSync definition.

            leaf neighHelloTimeout  {
                type  cml_data_types:CML_UINT16_T;
                config false;
                description "";
            } // END of neighHelloTimeout definition.

            leaf differDomain  {
                type  cml_data_types:CML_UINT16_T;
                config false;
                description "";
            } // END of differDomain definition.

            leaf ntthellopdu  {
                type  cml_data_types:CML_UINT16_T;
                config false;
                description "";
            } // END of ntthellopdu definition.

            leaf portEnabled  {
                type  cml_data_types:CML_UINT16_T;
                config false;
                description "";
            } // END of portEnabled definition.

            leaf stpState  {
                type  cml_data_types:CML_UINT16_T;
                config false;
                description "";
            } // END of stpState definition.

            leaf helloPeriodicTxTimerExpired  {
                type  cml_data_types:CML_UINT8_T;
                config false;
                description "";
            } // END of helloPeriodicTxTimerExpired definition.

            leaf currentWhileTimerExpired  {
                type  cml_data_types:CML_UINT8_T;
                config false;
                description "";
            } // END of currentWhileTimerExpired definition.

            leaf mcecHelloRcvState  {
                type  cml_data_types:CML_UINT8_T;
                config false;
                description "";
            } // END of mcecHelloRcvState definition.

            leaf mcecHelloPeriodicTxState  {
                type  cml_data_types:CML_UINT8_T;
                config false;
                description "";
            } // END of mcecHelloPeriodicTxState definition.

            leaf mcecValidHelloPduTx  {
                type  cml_data_types:CML_UINT32_T;
                config false;
                description "";
            } // END of mcecValidHelloPduTx definition.

            leaf mcecValidInfoPduTx  {
                type  cml_data_types:CML_UINT32_T;
                config false;
                description "";
            } // END of mcecValidInfoPduTx definition.

            leaf mcecValidMacSyncPduTx  {
                type  cml_data_types:CML_UINT32_T;
                config false;
                description "";
            } // END of mcecValidMacSyncPduTx definition.

            leaf mcecValidHelloPduRx  {
                type  cml_data_types:CML_UINT32_T;
                config false;
                description "";
            } // END of mcecValidHelloPduRx definition.

            leaf mcecValidInfoPduRx  {
                type  cml_data_types:CML_UINT32_T;
                config false;
                description "";
            } // END of mcecValidInfoPduRx definition.

            leaf mcecValidMacSyncPduRx  {
                type  cml_data_types:CML_UINT32_T;
                config false;
                description "";
            } // END of mcecValidMacSyncPduRx definition.

        } // END of idp-container definition.
        container macSync {
            config false;
            description
                "mac_sync *msyncp : mac synchronization structure";
            leaf numberOfEntry  {
                type  cml_data_types:CML_UINT16_T;
                description "";
            } // END of numberOfEntry definition.


            list lmt {
                key "lmtMacAddr";
                config false;
                description
                    "Local MAC Table";
                leaf lmtIsAddEntry  {
                    type  cml_data_types:CML_UINT8_T;
                    description "";
                } // END of lmtIsAddEntry definition.

                leaf lmtIsStaticEntry  {
                    type  cml_data_types:CML_UINT8_T;
                    description "";
                } // END of lmtIsStaticEntry definition.

                leaf lmtVid  {
                    type  cml_data_types:CML_UINT16_T;
                    description "";
                } // END of lmtVid definition.

                leaf lmtMacAddr  {
                    type  cml_data_types:CML_STRING_T {
                        length "0..255";
                    }
                    description "";
                } // END of lmtMacAddr definition.

                leaf lmtOifName  {
                    type  cml_data_types:CML_STRING_T {
                        length "0..255";
                    }
                    description "";
                } // END of lmtOifName definition.

            } // End of lmt-list

            list rmt {
                key "rmtMacAddr";
                config false;
                description
                    "Remote MAC Table";
                leaf rmtIsAddEntry  {
                    type  cml_data_types:CML_UINT8_T;
                    description "";
                } // END of rmtIsAddEntry definition.

                leaf rmtIsStaticEntry  {
                    type  cml_data_types:CML_UINT8_T;
                    description "";
                } // END of rmtIsStaticEntry definition.

                leaf rmtVid  {
                    type  cml_data_types:CML_UINT16_T;
                    description "";
                } // END of rmtVid definition.

                leaf rmtMacAddr  {
                    type  cml_data_types:CML_STRING_T {
                        length "0..255";
                    }
                    description "";
                } // END of rmtMacAddr definition.

                leaf rmtOifName  {
                    type  cml_data_types:CML_STRING_T {
                        length "0..255";
                    }
                    description "";
                } // END of rmtOifName definition.

            } // End of rmt-list
        } // END of macSync-container definition.
        container mcecStpSync {
            config false;
            description
                "stp synchronization structure";
            leaf mcecStpSyncFlags  {
                type  cml_data_types:CML_UINT8_T;
                description "";
            } // END of mcecStpSyncFlags definition.

            leaf bridgePriority  {
                type  cml_data_types:CML_UINT16_T;
                description "";
            } // END of bridgePriority definition.

            leaf pathcostMethod  {
                type  cml_data_types:CML_UINT8_T;
                description "";
            } // END of pathcostMethod definition.

            leaf domainDigest  {
                type  cml_data_types:CML_STRING_T {
                    length "0..255";
                }
                description "";
            } // END of domainDigest definition.

            leaf neighDomainDigest  {
                type  cml_data_types:CML_STRING_T {
                    length "0..255";
                }
                description "";
            } // END of neighDomainDigest definition.

            leaf stpSyncNumberOfEntries  {
                type  cml_data_types:CML_UINT8_T;
                description "";
            } // END of stpSyncNumberOfEntries definition.

            leaf tcnMlagId  {
                type  cml_data_types:CML_UINT16_T;
                description "";
            } // END of tcnMlagId definition.


            list mcecStpMlagIfSyncEntry {
                key "mlagId";
                config false;
                description
                    "mcecStpMlagIfSyncEntry";
                leaf mlagId  {
                    type  cml_data_types:CML_UINT16_T;
                    description "";
                } // END of mlagId definition.

                leaf portPriority  {
                    type  cml_data_types:CML_UINT16_T;
                    description "";
                } // END of portPriority definition.

                leaf pathCost  {
                    type  cml_data_types:CML_UINT32_T;
                    description "";
                } // END of pathCost definition.

                leaf interfaceDigest  {
                    type  cml_data_types:CML_STRING_T {
                        length "0..255";
                    }
                    description "";
                } // END of interfaceDigest definition.

                leaf neighInterfaceDigest  {
                    type  cml_data_types:CML_STRING_T {
                        length "0..255";
                    }
                    description "";
                } // END of neighInterfaceDigest definition.

            } // End of mcecStpMlagIfSyncEntry-list
        } // END of mcecStpSync-container definition.
    } // END of mcecMaster-container definition.
    } // END of mcecMaster-container definition.


}
