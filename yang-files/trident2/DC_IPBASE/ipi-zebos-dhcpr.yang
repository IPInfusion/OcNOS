/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-zebos-dhcpr.yang
*
*/

submodule ipi-zebos-dhcpr {

    belongs-to  ipi-zebos { prefix ipi-zebos; }

    import cml-data-types {
        prefix cml-data-types;
    }

    import feature-list {
        prefix feature-list;
    }

    organization
        "IP Infusion Inc.";

    contact
        "Address: 3965 Freedom Circle, Suite 200, Santa Clara, CA 95054
        Phone: +1 408-400-1900
        E-mail: support@ipinfusion.com
        Web: http://www.ipinfusion.com/";

    description
        "dhcp_relay_configuration";


    revision "2018-06-21" {
        description " Initial Version.";
        reference "";
    }


    grouping  dhcpRelay-grouping {
    description
        "Global DHCP Relay configs";
    container dhcpRelay {
        description
            "Global DHCP Relay configs";
        leaf relay  {
            type  cml-data-types:CML_BOOL_T;
            description "";
        } // END of relay definition.

        leaf relay6  {
            type  cml-data-types:CML_BOOL_T;
            description "";
        } // END of relay6 definition.

    } // END of dhcpRelay-container definition.
    } // END of dhcpRelay-container definition.

    grouping  dhcpRelayVrf-grouping {
    description
        "VRF related DHCPv4 Relay configs";
    container dhcpRelayVrf {
        description
            "VRF related DHCPv4 Relay configs";
        leaf sourceIp  {
            type  cml-data-types:CML_IPV4_ADDR_T;
            description "Enable link selection sub-option (5) in the option-82 in DHCP packet";
        } // END of sourceIp definition.

        leaf option82  {
            type  cml-data-types:CML_BOOL_T;
            description "";
        } // END of option82 definition.

        leaf-list dhcpv4ServerAddress  {
            type  cml-data-types:CML_IPV4_ADDR_T;
            description "IPv4 address of the DHCP server";
        } // END of dhcpv4ServerAddress definition.

        leaf-list dhcpv6ServerAddress  {
            if-feature feature-list:HAVE_IPV6;
            type  cml-data-types:CML_IPV6_ADDR_T;
            description "";
        } // END of dhcpv6ServerAddress definition.

        leaf remoteId  {
            type  cml-data-types:CML_REMOTEID_T {
                pattern "^[a-zA-Z0-9]*";
                }
                description "Remote host identifier. Use option 82 to provide the DHCP server information about the DHCP client";
            } // END of remoteId definition.

    } // END of dhcpRelayVrf-container definition.
    } // END of dhcpRelayVrf-container definition.

    grouping  dhcpRelayInterface-grouping {
    description
        "Interface related DHCP Relay configs";
    container dhcpRelayInterface {
        description
            "Interface related DHCP Relay configs";
        leaf v4RelayInterface  {
            type  cml-data-types:CML_BOOL_T;
            description "Enable relay on Client facing interface";
        } // END of v4RelayInterface definition.

        leaf v4UplinkInterface  {
            type  cml-data-types:CML_BOOL_T;
            description "Specify the interface as an uplink interface(Server facing)";
        } // END of v4UplinkInterface definition.

        leaf v6RelayInterface  {
            if-feature feature-list:HAVE_IPV6;
            type  cml-data-types:CML_BOOL_T;
            description "Enable IPv6 relay on Client facing interface";
        } // END of v6RelayInterface definition.

        leaf v6UplinkInterface  {
            if-feature feature-list:HAVE_IPV6;
            type  cml-data-types:CML_BOOL_T;
            description "Specify the interface as an uplink interface(Server facing)";
        } // END of v6UplinkInterface definition.

    } // END of dhcpRelayInterface-container definition.
    } // END of dhcpRelayInterface-container definition.


}
