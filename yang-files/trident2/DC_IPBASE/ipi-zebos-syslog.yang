/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-zebos-syslog.yang
*
*/

submodule ipi-zebos-syslog {

    belongs-to  ipi-zebos { prefix ipi-zebos; }

    import cml-data-types {
        prefix cml-data-types;
    }

    import feature-list {
        prefix feature-list;
    }

    include ipi-zebos-vrf;
    organization
        "IP Infusion Inc.";

    contact
        "Address: 3965 Freedom Circle, Suite 200, Santa Clara, CA 95054
        Phone: +1 408-400-1900
        E-mail: support@ipinfusion.com
        Web: http://www.ipinfusion.com/";

    description
        "hostp syslog configurations";


    revision "2018-06-21" {
        description " Initial Version.";
        reference "";
    }



    grouping rsyslog-grouping {
    description
        "Remote syslogd related commands";
        list rsyslog {
            key "vrfName";
            description
                "Remote syslogd related commands";
            leaf vrfName  {
                type  cml-data-types:CML_STRING_T;
                description "";
            } // END of vrfName definition.

            leaf featureRsyslog  {
                type  cml-data-types:CML_RSYSLOG_FEATURE_T;
                description "";
            } // END of featureRsyslog definition.


            list syslogServer {
                key "serverAddr";
                description
                    "list of servers";
                leaf serverAddr  {
                    type  cml-data-types:CML_STRING_T {
                        length "1..63";
                    }
                    description "Remote syslog server, maximum 5 servers can be configured ";
                } // END of serverAddr definition.

                leaf serverSeverity  {
                    type  cml-data-types:CML_INT8_T {
                         range "0..7";
                    }
                    default "7";
                    description "";
                } // END of serverSeverity definition.

                leaf serverFacility  {
                    type  cml-data-types:CML_FACILITY_T;
                    default "local7";
                    description "";
                } // END of serverFacility definition.

            } // End of syslogServer-list
        } // End of rsyslog-list
    } // END of rsyslog-grouping definition.

    grouping  hostpSyslog-grouping {
    description
        "rsyslog configurations";
    container hostpSyslog {
        description
            "rsyslog configurations";
        leaf defaultVrfSourceInterface  {
            type  cml-data-types:CML_STRING_T;
            description "";
        } // END of defaultVrfSourceInterface definition.

        leaf mgmtVrfSrcInterface  {
            type  cml-data-types:CML_STRING_T;
            description "";
        } // END of mgmtVrfSrcInterface definition.

        leaf debuglogging  {
            if-feature feature-list:HAVE_DEBUG_MODULE_SEVERITY;
            type  cml-data-types:CML_LEVEL_T;
            description "";
        } // END of debuglogging definition.

        leaf debug  {
            if-feature feature-list:NOT_HAVE_DEBUG_MODULE_SEVERITY;
            type  cml-data-types:CML_BOOL_T;
            description "";
        } // END of debug definition.

    } // END of hostpSyslog-container definition.
    } // END of hostpSyslog-container definition.


}
