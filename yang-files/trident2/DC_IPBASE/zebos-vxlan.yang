/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-vxlan.yang
*
*/

submodule zebos-vxlan {

    belongs-to  zebos { prefix zebos; }

    import cml_data_types {
        prefix cml_data_types;
    }

    import feature_list {
        prefix feature_list;
    }

    include zebos-vrf;
    organization
        "IP Infusion Inc.";

    contact
        "Address: 3965 Freedom Circle, Suite 200, Santa Clara, CA 95054
        Phone: +1 408-400-1900
        E-mail: support@ipinfusion.com
        Web: http://www.ipinfusion.com/";

    description
        "Network Virtualization Overlay functionality";


    revision "2017-08-09" {
        description " Initial Version.";
        reference "";
    }



    grouping nsmipv4prefixroute-grouping {
    description
        "nsm ipv4 prefix route";
        list nsmipv4prefixroute {
            key "vrfName";
            description
                "nsm ipv4 prefix route";
            leaf vrfName  {
                type  cml_data_types:CML_STRING_T;
                description "Mac vrf name";
            } // END of vrfName definition.


            list ipv4VrfDestPrefix {
                key "ipv4DestVrfPrefix";
                description
                    "vrf Ipv4 destination prefix";
                leaf ipv4DestVrfPrefix  {
                    type  cml_data_types:CML_IPV4_PREFIX_T;
                    description "IP destination prefix (e.g. 10.0.0.0/8)";
                } // END of ipv4DestVrfPrefix definition.


                list ipv4VrfGwAddr {
                    key "ipv4VrfGwAddr";
                    description
                        "vrf Ipv4 nexthop address";
                    leaf ipv4VrfGwAddr  {
                        type  cml_data_types:CML_IPV4_ADDR_T;
                        description "IP gateway address";
                    } // END of ipv4VrfGwAddr definition.

                } // End of ipv4VrfGwAddr-list
            } // End of ipv4VrfDestPrefix-list
        } // End of nsmipv4prefixroute-list
    } // END of nsmipv4prefixroute-grouping definition.


    grouping nsmipv6prefixroute-grouping {
    description
        "nsm ipv6 prefix route";
        list nsmipv6prefixroute {
            key "vrfName";
            description
                "nsm ipv6 prefix route";
            leaf vrfName  {
                type  cml_data_types:CML_STRING_T;
                description "Mac vrf name";
            } // END of vrfName definition.


            list ipv6VrfDestPrefix {
                key "ipv6DestVrfPrefix";
                description
                    "vrf Ipv6 destination prefix";
                leaf ipv6DestVrfPrefix  {
                    type  cml_data_types:CML_IPV6_PREFIX_T;
                    description "IPv6 destination prefix (e.g. 3ffe:506::/32)";
                } // END of ipv6DestVrfPrefix definition.


                list ipv6VrfGwAddr {
                    key "ipv6VrfGwAddr";
                    description
                        "vrf Ipv6 nexthop address";
                    leaf ipv6VrfGwAddr  {
                        type  cml_data_types:CML_IPV6_ADDR_T;
                        description "IPv6 gateway address";
                    } // END of ipv6VrfGwAddr definition.

                } // End of ipv6VrfGwAddr-list
            } // End of ipv6VrfDestPrefix-list
        } // End of nsmipv6prefixroute-list
    } // END of nsmipv6prefixroute-grouping definition.


    grouping nvoAccessIfVlanInfo-grouping {
    description
        "VxLAN acess side port-vlan configurations";
        list nvoAccessIfVlanInfo {
            key "vlanId";
            description
                "VxLAN acess side port-vlan configurations";
            leaf vlanId  {
                type  cml_data_types:CML_UINT32_T {
                     range "2..4094";
                }
                description "Vlan on the port for which the access port is created";
            } // END of vlanId definition.

            leaf tpid  {
                type  cml_data_types:CML_STRING_T;
                description "Tpid for the outer vlan";
            } // END of tpid definition.

            leaf arpCacheDisablePortVlan  {
                type  cml_data_types:CML_BOOL_T;
                default false;
                description "Disable arp cache on access interface";
            } // END of arpCacheDisablePortVlan definition.

            leaf ndCacheDisablePortVlan  {
                type  cml_data_types:CML_BOOL_T;
                default false;
                description "Disable ND cache on access interface";
            } // END of ndCacheDisablePortVlan definition.

            leaf DfStatus  {
                type  cml_data_types:CML_VXLAN_DF_STATUS_T;
                config false;
                description "DF flag status";
            } // END of DfStatus definition.

            uses access-info;
            uses vxlan-counters;
        } // End of nvoAccessIfVlanInfo-list
    } // END of nvoAccessIfVlanInfo-grouping definition.


    grouping nvoAccessIfOuterVlanInfo-grouping {
    description
        "VxLAN acess side stacked-vlan configurations";
        list nvoAccessIfOuterVlanInfo {
            key "outerVlanId";
            description
                "VxLAN acess side stacked-vlan configurations";
            leaf outerVlanId  {
                type  cml_data_types:CML_UINT32_T {
                     range "2..4094";
                }
                description "VXLAN access side stacked outer vlan configurations";
            } // END of outerVlanId definition.


            list nvoAccessIfInnerVlanInfo {
                key "innerVlanId";
                description
                    "VxLAN acess side inner-vlan configurations";
                leaf innerVlanId  {
                    type  cml_data_types:CML_UINT32_T {
                         range "2..4094";
                    }
                    description "VxLAN access side inner-vlan configurations";
                } // END of innerVlanId definition.

                leaf tpid  {
                    type  cml_data_types:CML_STRING_T;
                    description "Tpid for the outer vlan";
                } // END of tpid definition.

                leaf arpCacheDisablePortStackedVlan  {
                    type  cml_data_types:CML_BOOL_T;
                    default false;
                    description "Disable arp cache on access interface using inner vlan id";
                } // END of arpCacheDisablePortStackedVlan definition.

                leaf ndCacheDisablePortStackedVlan  {
                    type  cml_data_types:CML_BOOL_T;
                    default false;
                    description "Disable ND cache on access interface";
                } // END of ndCacheDisablePortStackedVlan definition.

                uses access-info;
            } // End of nvoAccessIfInnerVlanInfo-list
        } // End of nvoAccessIfOuterVlanInfo-list
    } // END of nvoAccessIfOuterVlanInfo-grouping definition.
    grouping access-info {
        description
            "accessCMLSEPinfo";
        leaf vnId  {
            type  cml_data_types:CML_UINT32_T {
                 range "1..16777215";
            }
            description "VXLAN Identifier";
        } // END of vnId definition.

        leaf vnIname  {
            type  cml_data_types:CML_STRING_T;
            description "VXLAN Identifier Name";
        } // END of vnIname definition.

        leaf shutdownInterface  {
            type  cml_data_types:CML_BOOL_T;
            default false;
            description "Shutdown access interface";
        } // END of shutdownInterface definition.

        leaf description  {
            type  cml_data_types:CML_LINE_T;
            description "Description of access interface";
        } // END of description definition.

        leaf dynamicLearningDisable  {
            type  cml_data_types:CML_BOOL_T;
            default false;
            description "Disable dynamic learning on access interface";
        } // END of dynamicLearningDisable definition.

        leaf accessMacHoldTime  {
            type  cml_data_types:CML_INT32_T {
                 range "-1..300";
            }
            description "Time a host mac entry will persist after unconfiguring";
        } // END of accessMacHoldTime definition.

        leaf arpFloodSuppress  {
            type  cml_data_types:CML_BOOL_T;
            default false;
            description "Supress arp flooding on access interface";
        } // END of arpFloodSuppress definition.

        leaf GarpGnaEnable  {
            type  cml_data_types:CML_BOOL_T;
            default false;
            description "Enables garp-gna packets";
        } // END of GarpGnaEnable definition.

        leaf cos  {
            if-feature feature_list:HAVE_HQOS;
            type  cml_data_types:CML_UINT8_T {
                 range "0..7";
            }
            description "COS Value";
        } // END of cos definition.

        leaf cosDir  {
            if-feature feature_list:HAVE_HQOS;
            type  cml_data_types:CML_VXLAN_QOS_DIR_T;
            description "COS Dir Mapping";
        } // END of cosDir definition.

        leaf dscp  {
            if-feature feature_list:HAVE_HQOS;
            type  cml_data_types:CML_UINT8_T {
                 range "0..63";
            }
            description "DSCP Value";
        } // END of dscp definition.

        leaf dscpDir  {
            if-feature feature_list:HAVE_HQOS;
            type  cml_data_types:CML_VXLAN_QOS_DIR_T;
            description "DSCP Ingress Dir";
        } // END of dscpDir definition.

        leaf profileDir  {
            if-feature feature_list:HAVE_HQOS;
            type  cml_data_types:CML_VXLAN_QOS_DIR_T;
            description "Profile Dir Mapping";
        } // END of profileDir definition.

        leaf profileId  {
            if-feature feature_list:HAVE_HQOS;
            type  cml_data_types:CML_UINT8_T {
                 range "1..128";
            }
            description "QOS Profile ID";
        } // END of profileId definition.

        leaf-list macAddrOnly  {
            type  cml_data_types:CML_MAC_ADDR_T;
            description "MAC Address of host";
        } // END of macAddrOnly definition.


        list nvoAccessHostInfo {
            key "macAddr";
            description
                "nvo_host_info";
            leaf macAddr  {
                type  cml_data_types:CML_MAC_ADDR_T;
                description "MAC address of host";
            } // END of macAddr definition.

            leaf-list ipAddr  {
                type  cml_data_types:CML_IPV4_ADDR_T;
                description "IPv4 Address of host";
            } // END of ipAddr definition.

            leaf-list ip6Addr  {
                type  cml_data_types:CML_IPV6_ADDR_T;
                description "IPv6 Address of host";
            } // END of ip6Addr definition.

        } // End of nvoAccessHostInfo-list
    } // END of access-info definition.
    grouping vxlan-counters {
        description
            "vxlanCMLSEPcounters";
        leaf out_bytes  {
            type  cml_data_types:CML_UINT64_T;
            description "This indicates total number of bytes sent out from access port";
        } // END of out_bytes definition.

        leaf out_packets  {
            type  cml_data_types:CML_UINT64_T;
            description "This indicates total number of packets sent out from access port";
        } // END of out_packets definition.

        leaf in_bytes  {
            type  cml_data_types:CML_UINT64_T;
            description "This indicates total number of bytes received on access port";
        } // END of in_bytes definition.

        leaf in_packets  {
            type  cml_data_types:CML_UINT64_T;
            description "This indicates total number of packets received on access port";
        } // END of in_packets definition.

    } // END of vxlan-counters definition.

    grouping  anycastGwMac-grouping {
    description
        "anycast-gateway-mac";
    container anycastGwMac {
        description
            "anycast-gateway-mac";
        leaf anycastGwMacAddr  {
            type  cml_data_types:CML_MAC_ADDR_T;
            description "Anycast gateway mac address";
        } // END of anycastGwMacAddr definition.

    } // END of anycastGwMac-container definition.
    } // END of anycastGwMac-container definition.

    grouping  ifAcastGwMac-grouping {
    description
        "IRB interface forwarding for anycast gateway mac";
    container ifAcastGwMac {
        description
            "IRB interface forwarding for anycast gateway mac";
        leaf ifAnycastGwMac  {
            type  cml_data_types:CML_BOOL_T;
            default false;
            description "IRB forwarding for anycast gateway mac";
        } // END of ifAnycastGwMac definition.

    } // END of ifAcastGwMac-container definition.
    } // END of ifAcastGwMac-container definition.

    grouping  esiHoldTime-grouping {
    description
        "Esi Hold-Timer configuration";
    container esiHoldTime {
        description
            "Esi Hold-Timer configuration";
        leaf hold-time  {
            type  cml_data_types:CML_INT32_T {
                 range "10..300";
            }
            description "Time before ESI interface can be made up on enabling EVPN";
        } // END of hold-time definition.

    } // END of esiHoldTime-container definition.
    } // END of esiHoldTime-container definition.

    grouping  nvo-grouping {
    description
        "VxLAN global Configurations";
    container nvo {
        presence "yes";
        description
            "VxLAN global Configurations";
        leaf vxlanEnable  {
            type  cml_data_types:CML_BOOL_T;
            mandatory true;
            description "Enable VXLAN module";
        } // END of vxlanEnable definition.

        leaf irbEnable  {
            type  cml_data_types:CML_BOOL_T;
            description "Enable IRB globally";
        } // END of irbEnable definition.

        leaf vtepIpv4  {
            type  cml_data_types:CML_IPV4_ADDR_T;
            description "VTEP global ip address";
        } // END of vtepIpv4 definition.

        leaf arpndRefreshtimer  {
            type  cml_data_types:CML_UINT32_T {
                 range "3..300000";
            }
            description "Refresh time for dynamic ARP/ND on vxlan access port";
        } // END of arpndRefreshtimer definition.

        leaf macAgeing  {
            type  cml_data_types:CML_UINT32_T {
                 range "10..1000000";
            }
            default "300";
            description "Time a learned mac address will persist";
        } // END of macAgeing definition.

        leaf maxCacheDisableCount  {
            type  cml_data_types:CML_UINT16_T {
                 range "1..200";
            }
            description "Max number of ARP/ND cache disable allowed for port-vlan access-ports";
        } // END of maxCacheDisableCount definition.


        list nvoGlobalQosConfiguration {
            if-feature feature_list:HAVE_HQOS;
            key "globalDir";
            description
                "Qos configuration for mapping direction and profile ID";
            leaf globalDir  {
                type  cml_data_types:CML_VXLAN_QOS_DIR_T;
                description "QoS Global Direction for VxLAN";
            } // END of globalDir definition.

            leaf vxlanQoSMode  {
                if-feature feature_list:HAVE_HQOS;
                type  cml_data_types:CML_VXLAN_QOS_GLOBAL_MODE_T;
                mandatory true;
                description "VXLAN QoS Map Mode - COS or DSCP";
            } // END of vxlanQoSMode definition.

            leaf globalProfileId  {
                type  cml_data_types:CML_UINT8_T {
                     range "65..128";
                }
                description "QOS Profile ID";
            } // END of globalProfileId definition.

        } // End of nvoGlobalQosConfiguration-list

        list nvoTunnelStats {
            key "destIp";
            config false;
            description
                "Tunnel Stats";
            leaf destIp  {
                type  cml_data_types:CML_IPV4_ADDR_T;
                description "Tunnel destination IP";
            } // END of destIp definition.

            leaf sourceIp  {
                type  cml_data_types:CML_IPV4_ADDR_T;
                description "Tunnel source IP";
            } // END of sourceIp definition.

            leaf out_bytes  {
                type  cml_data_types:CML_UINT64_T;
                description "This indicates total number of bytes sent out from tunnel interface";
            } // END of out_bytes definition.

            leaf out_packets  {
                type  cml_data_types:CML_UINT64_T;
                description "This indicates total number of packets sent out from tunnel interface";
            } // END of out_packets definition.

            leaf in_bytes  {
                type  cml_data_types:CML_UINT64_T;
                description "This indicates total number of bytes received on tunnel interface";
            } // END of in_bytes definition.

            leaf in_packets  {
                type  cml_data_types:CML_UINT64_T;
                description "This indicates total number of packets received on tunnel interface";
            } // END of in_packets definition.

            leaf updatetime  {
                type  cml_data_types:CML_TIMETICKS_T;
                description "This indicates the last updated time of a tunnel nexthop";
            } // END of updatetime definition.

            leaf up-downtime  {
                type  cml_data_types:CML_TIMETICKS_T;
                description "This indicates tunnel up/down time";
            } // END of up-downtime definition.

            leaf tunnelStatus  {
                type  cml_data_types:CML_TUNNEL_STATUS_T;
                description "Status of tunnel";
            } // END of tunnelStatus definition.

            leaf txArpDiscardPackets  {
                type  cml_data_types:CML_UINT64_T;
                description "This Object describes Arp Discarded Packets";
            } // END of txArpDiscardPackets definition.

            leaf txNdDiscardPackets  {
                type  cml_data_types:CML_UINT64_T;
                description "This Object describes Nd Discarded Packets";
            } // END of txNdDiscardPackets definition.

            leaf txArpRequestPackets  {
                type  cml_data_types:CML_UINT64_T;
                description "This Object describes Arp request Transmitted Packets";
            } // END of txArpRequestPackets definition.

            leaf txArpReplyPackets  {
                type  cml_data_types:CML_UINT64_T;
                description "This Object describes Arp reply Transmitted Packets";
            } // END of txArpReplyPackets definition.

            leaf txNeighborSolicitationPackets  {
                type  cml_data_types:CML_UINT64_T;
                description "This Object describes Neighbour Solicitation Transmitted Packets";
            } // END of txNeighborSolicitationPackets definition.

            leaf txNeighborAdvertisementPackets  {
                type  cml_data_types:CML_UINT64_T;
                description "This Object describes Neighbour Advertisement Transmitted Packets";
            } // END of txNeighborAdvertisementPackets definition.

            leaf txGarpPackets  {
                type  cml_data_types:CML_UINT64_T;
                description "This Object describes Garp Transmitted Packets";
            } // END of txGarpPackets definition.

            leaf txGnaPackets  {
                type  cml_data_types:CML_UINT64_T;
                description "This Object describes Gna Transmitted Packets";
            } // END of txGnaPackets definition.

        } // End of nvoTunnelStats-list

        list dynamicMacMovement {
            key "dynamicMacMovement";
            description
                "VxLAN dynamic-learning Configurations";
            leaf dynamicMacMovement  {
                type  cml_data_types:CML_BOOL_T;
                description "Dynamic Mac Movement enable";
            } // END of dynamicMacMovement definition.

        } // End of dynamicMacMovement-list

        list nvoTenant {
            if-feature feature_list:HAVE_NVO;
            key "nvoId";
            description
                "Tunnel Side Configurations including tenant information";
            leaf nvoId  {
                type  cml_data_types:CML_UINT32_T {
                     range "1..16777215";
                }
                description "Tenant Identifier";
            } // END of nvoId definition.

            leaf is_multicast  {
                type  cml_data_types:CML_BOOL_T;
                description "Configure multicast tunnel";
            } // END of is_multicast definition.

            leaf ingRepl  {
                type  cml_data_types:CML_BOOL_T;
                default false;
                description "Enable ingress replication";
            } // END of ingRepl definition.

            leaf innerVidDisabled  {
                type  cml_data_types:CML_BOOL_T;
                default false;
                description "Carry the inner-vlan ID over the tunnel or not";
            } // END of innerVidDisabled definition.

            leaf vrfName  {
                type  cml_data_types:CML_STRING_T {
                    length "1..32";
                }
                description "vrf to carry EVPN routes ";
            } // END of vrfName definition.

            leaf map-network  {
                type  cml_data_types:CML_STRING_T;
                description "Tunnel name";
            } // END of map-network definition.

            leaf macHoldTime  {
                type  cml_data_types:CML_INT32_T {
                     range "-1..300";
                }
                default "0";
                description "Time a host mac entry will persist after unconfig";
            } // END of macHoldTime definition.

            leaf vxlanName  {
                type  cml_data_types:CML_STRING_T;
                description "VXLAN identifier name";
            } // END of vxlanName definition.

            leaf ifName  {
                type  cml_data_types:CML_STRING_T;
                description "IRB interface name";
            } // END of ifName definition.


            list nvoStatic {
                key "macAddr";
                description
                    "Tunnel Side Configurations including tenant information";
                leaf macAddr  {
                    type  cml_data_types:CML_MAC_ADDR_T;
                    description "Mac address of the host";
                } // END of macAddr definition.

                leaf remoteVtepIp  {
                    type  cml_data_types:CML_IPV4_ADDR_T;
                    description "Destination IP Address";
                } // END of remoteVtepIp definition.

            } // End of nvoStatic-list

            list nvoArpCacheInfo {
                key "hostIp";
                config false;
                description
                    "ArpCache Entries";
                leaf hostIp  {
                    type  cml_data_types:CML_IPV4_ADDR_T;
                    description "Host IP address";
                } // END of hostIp definition.

                leaf hostMac  {
                    type  cml_data_types:CML_MAC_ADDR_T;
                    description "Host Mac Address";
                } // END of hostMac definition.

                leaf hostType  {
                    type  cml_data_types:CML_VXLAN_HOST_T;
                    description "Host Type";
                } // END of hostType definition.

                leaf ifindex  {
                    type  cml_data_types:CML_UINT32_T;
                    description "Interface Index";
                } // END of ifindex definition.

            } // End of nvoArpCacheInfo-list

            list nvoNdCacheInfo {
                key "hostIp";
                config false;
                description
                    "NdCache Entries";
                leaf hostIp  {
                    type  cml_data_types:CML_IPV6_ADDR_T;
                    description "Host IP address";
                } // END of hostIp definition.

                leaf hostMac  {
                    type  cml_data_types:CML_MAC_ADDR_T;
                    description "Host Mac Address";
                } // END of hostMac definition.

                leaf hostType  {
                    type  cml_data_types:CML_VXLAN_HOST_T;
                    description "Host Type";
                } // END of hostType definition.

                leaf ifindex  {
                    type  cml_data_types:CML_UINT32_T;
                    description "Interface Index";
                } // END of ifindex definition.

            } // End of nvoNdCacheInfo-list

            list nvoMacTable {
                key "macAddr";
                config false;
                description
                    "Host Mac Addresses Table";
                leaf macAddr  {
                    type  cml_data_types:CML_MAC_ADDR_T;
                    description "Mac Adress of the host";
                } // END of macAddr definition.

                leaf interface  {
                    type  cml_data_types:CML_STRING_T;
                    description "interface name";
                } // END of interface definition.

                leaf vlanId  {
                    type  cml_data_types:CML_UINT32_T;
                    description "vlan id";
                } // END of vlanId definition.

                leaf innerVlanId  {
                    type  cml_data_types:CML_UINT32_T;
                    description "Inner vlan Id";
                } // END of innerVlanId definition.

                leaf vtepIpEsi  {
                    type  cml_data_types:CML_STRING_T;
                    description "VTEP global ip address or ESI";
                } // END of vtepIpEsi definition.

                leaf hostType  {
                    type  cml_data_types:CML_VXLAN_HOST_T;
                    description "Host Type";
                } // END of hostType definition.

                leaf hostStatus  {
                    type  cml_data_types:CML_STRING_T;
                    description "Host Status";
                } // END of hostStatus definition.

                leaf accessPortDesc  {
                    type  cml_data_types:CML_STRING_T;
                    description "Description for the port";
                } // END of accessPortDesc definition.

            } // End of nvoMacTable-list

            list nvoMacMapping {
                key "macAddr";
                config false;
                description
                    "FDB table";
                leaf macAddr  {
                    type  cml_data_types:CML_MAC_ADDR_T;
                    description "Mac address of the host";
                } // END of macAddr definition.

                leaf prefix  {
                    type  cml_data_types:CML_IPV4_ADDR_T;
                    description "IP address of the host";
                } // END of prefix definition.

                leaf type  {
                    type  cml_data_types:CML_UINT8_T;
                    description "Type";
                } // END of type definition.

                leaf sticky  {
                    type  cml_data_types:CML_BOOL_T;
                    description "Static mac or Dynamic";
                } // END of sticky definition.

            } // End of nvoMacMapping-list
            container nvoRouteCount {
                config false;
                description
                    "Total Route Count Entries";
                leaf Total  {
                    type  cml_data_types:CML_UINT32_T;
                    description "Total Route Entries";
                } // END of Total definition.

                leaf MACONLY  {
                    type  cml_data_types:CML_UINT32_T;
                    description "Mac Only Entries";
                } // END of MACONLY definition.

                leaf MACIPv4  {
                    type  cml_data_types:CML_UINT32_T;
                    description "Mac Ipv4 Entries";
                } // END of MACIPv4 definition.

                leaf MACIPv6  {
                    type  cml_data_types:CML_UINT32_T;
                    description "Mac Ipv6 Entries";
                } // END of MACIPv6 definition.

            } // END of nvoRouteCount-container definition.
        } // End of nvoTenant-list

        list nvoStaticHostSt {
            key "macAddr";
            config false;
            description
                "nvo vxlan static host state";
            leaf macAddr  {
                type  cml_data_types:CML_MAC_ADDR_T;
                description "Mac Adress of the host";
            } // END of macAddr definition.

            leaf staticHostSt  {
                type  cml_data_types:CML_VXLAN_STATIC_HOST_STATE_T;
                description "static host state";
            } // END of staticHostSt definition.

            leaf vnId  {
                type  cml_data_types:CML_UINT32_T;
                description "nvo id";
            } // END of vnId definition.

            leaf hostIpv4  {
                type  cml_data_types:CML_IPV4_ADDR_T;
                description "Host IP Adress ipv4";
            } // END of hostIpv4 definition.

            leaf hostIpv6  {
                type  cml_data_types:CML_IPV6_ADDR_T;
                description "Host IP Adress ipv6";
            } // END of hostIpv6 definition.

        } // End of nvoStaticHostSt-list
    } // END of nvo-container definition.
    } // END of nvo-container definition.

    grouping  nvoAccessIfInfo-grouping {
    description
        "VxLAN Access side configurations ";
    container nvoAccessIfInfo {
        presence "yes";
        description
            "VxLAN Access side configurations ";
        leaf port  {
            type  cml_data_types:CML_VXLAN_PORT_T;
            mandatory true;
            description "Physical Port in which access-port is created";
        } // END of port definition.

        leaf arpCacheDisable  {
            type  cml_data_types:CML_BOOL_T;
            default false;
            description "Disable arp cache on access interface";
        } // END of arpCacheDisable definition.

        leaf ndCacheDisable  {
            type  cml_data_types:CML_BOOL_T;
            default false;
            description "Disable ND cache on access interface";
        } // END of ndCacheDisable definition.

        leaf DfStatus  {
            type  cml_data_types:CML_VXLAN_DF_STATUS_T;
            config false;
            description "DF flag status";
        } // END of DfStatus definition.

        uses access-info;
        uses vxlan-counters;
    } // END of nvoAccessIfInfo-container definition.
    } // END of nvoAccessIfInfo-container definition.


}
