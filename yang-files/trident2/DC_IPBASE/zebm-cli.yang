/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebm-cli.yang
*
*/



module zebm-cli {
    namespace "http://ipinfusion.com/ns/zebmcli";

    prefix zebm-cli;

    import cml-data-types {
        prefix cml-data-types;
    }
    organization
        "IP Infusion Inc.";

    contact
        "3965 Freedom Circle, Suite 200
        Santa Clara, CA 95054 +1 408-400-1900
        E-mail: support@ipinfusion.com
        Web: http://www.ipinfusion.com/";

    description "List of RPCs used for CML actions";


    revision "2015-10-15" {
        description "initial version: revisied on 2015-10-15.";
        reference "";}

    rpc rollback-transaction {

        description "This RPC will toggle the state of machine based on savepoint identifier";
        input {
            leaf savepointName {
                type cml-data-types:CML_STRING_T;
                mandatory true;
                description "Rollback save-point identifier";
            }
        }
    }

    rpc create-savepoint {

        description "This RPC will store snapshot of current system state with mentioned identifier.";
        input {
            leaf savepointName {
                type cml-data-types:CML_STRING_T;
                mandatory true;
                description "Save-point identifier";
            }
        }
    }

    rpc force-unlock {

        description "This RPC allows user to forcefully unlock the config-store";
        input {
            leaf target {
                type enumeration {
                    enum running {
                    description "running config-store";
                     }
                }
                mandatory true;
                description "Type of config store";
            }
            leaf after {
                type cml-data-types:CML_UINT32_T {
                    range "0..600";
                }
                description "Number of seconds";
            }
        }
    }

    rpc delete-savepoint {

        description "This RPC will delete the mentioned system snapshot identifier.";
        input {
            leaf savepointName {
                type cml-data-types:CML_STRING_T;
                mandatory true;
                description " Delete save-point identifier";
            }
        }
    }

    rpc set-transaction-limit {

        description "This RPC will allow user to set number of transactions allowed per commit";
        input {
            leaf transaction-limit {
                type cml-data-types:CML_UINT32_T {
                    range "10..50000";
                }
                mandatory true;
                description "Number of transactions";
            }
        }
    }

    rpc show-savepoint {
        description "This RPC will display the list of save-points";
        output {
            leaf-list savepoint {
                type string;
                description "List of sabe-point identifiers";
            }
        }
    }

    notification warning-notification {

        description "This RPC will display warning messages";
        leaf warningMsg {
            type string;
            mandatory true;
            description "warning string";
        }
    }

    rpc show-transaction-limit {
        description "This RPC will display the transaction limit per commit";
        output {
            leaf transaction-limit {
                type string;
                description " Displays number of transaction-limit";
            }
        }
    }

    rpc show-auto-config-sync-state {
        description "This RPC will display whether auto config sync is enabled or disabled.";
        output {
            leaf auto-config-sync-state {
                type string;
                description "Shows if auto config sync is enabled or disabled";
            }
        }
    }

    rpc auto-config-sync {
        description "This RPC will allow the user to enable or disable auto config sync";
        input {
            leaf status {
                type enumeration {
                    enum disable {
                        description "disable config auto sync";
                    }
                    enum enable {
                        description "enable config auto sync";
                    }
                }
                description "Enable or disable auto config sync. Once enabled config sync operation will be started whenever any configuration is performed";
            }
        }
    }

    rpc sys-shutdown {
        description "Perform system shutdown";
        input {
            leaf save-config {
                type boolean;
                mandatory true;
                description "Copy running-config to startup-config";
            }
        }
    }

    rpc sys-reload {
        description "Halt and perform a cold restart";
        input {
            leaf save-config {
                type boolean;
                mandatory true;
                description "Copy running-config to startup-config";
            }
        }
    }

    rpc sync-running-config {
        description "This RPC will synchronize the database state with the running config";
    }

    rpc set-default-handling-basic-mode {
        description "Setting the server with-defaults retrieval mode";
        input {
            leaf mode {
                type enumeration {
                    enum explicit {
                        description "explicit mode";
                    }
                    enum trim {
                        description "trim mode";
                    }
                }
                mandatory true;
                description "Explicit or Trim is supported now. Default server retrieval mode will be set based on input.";
            }
        }
    }

}
