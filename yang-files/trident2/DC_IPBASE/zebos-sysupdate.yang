/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-sysupdate.yang
*
*/

submodule zebos-sysupdate {

    belongs-to  zebos { prefix zebos; }

    import cml_data_types {
        prefix cml_data_types;
    }

    organization
        "IP Infusion Inc.";

    description
        "System update feature provides an option for user to upgrade/downgrade the OcNOS image in a router";


    revision "2018-02-19" {
        description " Initial Version.";
        reference "";
    }


    grouping  installers-grouping {
    description
        "Installer list";
    container installers {
        config false;
        description
            "Installer list";
        leaf-list installer  {
            type  cml_data_types:CML_STRING_T;
            description "Installer image available in device";
        } // END of installer definition.

    } // END of installers-container definition.
    } // END of installers-container definition.


}
