/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-vxlan.yang
*
*/

submodule zebos-vxlan {

    belongs-to  zebos { prefix zebos; }

    import cml_data_types {
        prefix cml_data_types;
    }

    import feature_list {
        prefix feature_list;
    }

    include zebos-vrf;
    organization
        "IP Infusion Inc.";

    contact
        "Address: 3965 Freedom Circle, Suite 200, Santa Clara, CA 95054
        Phone: +1 408-400-1900
        E-mail: support@ipinfusion.com
        Web: http://www.ipinfusion.com/";

    description
        "Network Virtualization Overlay functionality";


    revision "2017-08-09" {
        description " Intial Version.";
    }



    grouping nvoAccessIfVlanInfo-grouping {
        list nvoAccessIfVlanInfo {
            key "vlanId";
            description
                "VxLAN acess side port-vlan configurations";
            leaf vlanId  {
                type  cml_data_types:CML_UINT32_T {
                     range "2..4094";
                }
                description "";
            } // END of vlanId definition.

            leaf tpid  {
                type  cml_data_types:CML_STRING_T {
                    length "0..255";
                }
                description "";
            } // END of tpid definition.

            leaf arpCacheDisable  {
                type  cml_data_types:CML_BOOL_T;
                default false;
                description "Disable arp cache on access interface";
            } // END of arpCacheDisable definition.

            leaf ndCacheDisable  {
                type  cml_data_types:CML_BOOL_T;
                default false;
                description "Disable ND cache on access interface";
            } // END of ndCacheDisable definition.

            uses access-info;
            uses vxlan-counters;
        } // End of nvoAccessIfVlanInfo-list
    } // END of nvoAccessIfVlanInfo-grouping definition.


    grouping nvoAccessIfOuterVlanInfo-grouping {
        list nvoAccessIfOuterVlanInfo {
            key "outerVlanId";
            description
                "VxLAN acess side stacked-vlan configurations";
            leaf outerVlanId  {
                type  cml_data_types:CML_UINT32_T {
                     range "2..4094";
                }
                description "";
            } // END of outerVlanId definition.


            list nvoAccessIfInnerVlanInfo {
                key "innerVlanId";
                description
                    "VxLAN acess side inner-vlan configurations";
                leaf innerVlanId  {
                    type  cml_data_types:CML_UINT32_T {
                         range "2..4094";
                    }
                    description "";
                } // END of innerVlanId definition.

                leaf tpid  {
                    type  cml_data_types:CML_STRING_T {
                        length "0..255";
                    }
                    description "";
                } // END of tpid definition.

                leaf arpCacheDisable  {
                    type  cml_data_types:CML_BOOL_T;
                    default false;
                    description "Disable arp cache on access interface";
                } // END of arpCacheDisable definition.

                leaf ndCacheDisable  {
                    type  cml_data_types:CML_BOOL_T;
                    default false;
                    description "Disable ND cache on access interface";
                } // END of ndCacheDisable definition.

                uses access-info;
            } // End of nvoAccessIfInnerVlanInfo-list
        } // End of nvoAccessIfOuterVlanInfo-list
    } // END of nvoAccessIfOuterVlanInfo-grouping definition.
    grouping access-info {
        description
            "accessCMLSEPinfo";
        leaf vnId  {
            type  cml_data_types:CML_UINT32_T {
                 range "1..16777215";
            }
            description "";
        } // END of vnId definition.

        leaf shutdownInterface  {
            type  cml_data_types:CML_BOOL_T;
            default false;
            description "";
        } // END of shutdownInterface definition.

        leaf description  {
            type  cml_data_types:CML_LINE_T;
            description "";
        } // END of description definition.

        leaf dynamicLearningDisable  {
            type  cml_data_types:CML_BOOL_T;
            default false;
            description "";
        } // END of dynamicLearningDisable definition.

        leaf arpFloodSuppress  {
            type  cml_data_types:CML_BOOL_T;
            default false;
            description "";
        } // END of arpFloodSuppress definition.

        leaf cos  {
            if-feature feature_list:HAVE_QOS;
            type  cml_data_types:CML_UINT8_T {
                 range "0..7";
            }
            description "";
        } // END of cos definition.

        leaf cosDir  {
            if-feature feature_list:HAVE_QOS;
            type  cml_data_types:CML_VXLAN_QOS_DIR_T;
            description "";
        } // END of cosDir definition.

        leaf dscp  {
            if-feature feature_list:HAVE_QOS;
            type  cml_data_types:CML_UINT8_T {
                 range "0..63";
            }
            description "";
        } // END of dscp definition.

        leaf dscpDir  {
            if-feature feature_list:HAVE_QOS;
            type  cml_data_types:CML_VXLAN_QOS_DIR_T;
            description "";
        } // END of dscpDir definition.

        leaf profileDir  {
            if-feature feature_list:HAVE_QOS;
            type  cml_data_types:CML_VXLAN_QOS_DIR_T;
            description "";
        } // END of profileDir definition.

        leaf profileId  {
            if-feature feature_list:HAVE_QOS;
            type  cml_data_types:CML_UINT8_T {
                 range "1..128";
            }
            description "";
        } // END of profileId definition.

        leaf-list macAddrOnly  {
            type  cml_data_types:CML_MAC_ADDR_T;
            description "";
        } // END of macAddrOnly definition.


        list nvoAccessHostInfo {
            key "macAddr";
            description
                "nvo_host_info";
            leaf macAddr  {
                type  cml_data_types:CML_MAC_ADDR_T;
                description "";
            } // END of macAddr definition.

            leaf-list ipAddr  {
                type  cml_data_types:CML_IPV4_ADDR_T;
                description "";
            } // END of ipAddr definition.

            leaf-list ip6Addr  {
                type  cml_data_types:CML_IPV6_ADDR_T;
                description "";
            } // END of ip6Addr definition.

        } // End of nvoAccessHostInfo-list
    } // END of access-info definition.
    grouping vxlan-counters {
        description
            "vxlanCMLSEPcounters";
        leaf out_bytes  {
            type  cml_data_types:CML_UINT64_T;
            description "This indicates total number of bytes sent out from access port";
        } // END of out_bytes definition.

        leaf out_packets  {
            type  cml_data_types:CML_UINT64_T;
            description "This indicates total number of packets sent out from access port";
        } // END of out_packets definition.

        leaf in_bytes  {
            type  cml_data_types:CML_UINT64_T;
            description "This indicates total number of bytes recieved on access port";
        } // END of in_bytes definition.

        leaf in_packets  {
            type  cml_data_types:CML_UINT64_T;
            description "This indicates total number of packets recieved on access port";
        } // END of in_packets definition.

    } // END of vxlan-counters definition.

    grouping  nvo-grouping {
    container nvo {
        presence "yes";
        description
            "VxLAN global Configurations";
        leaf vxlanEnable  {
            type  cml_data_types:CML_BOOL_T;
            mandatory true;
            description "";
        } // END of vxlanEnable definition.

        leaf vtepIpv4  {
            type  cml_data_types:CML_IPV4_ADDR_T;
            description "";
        } // END of vtepIpv4 definition.

        leaf vxlanQoSMode  {
            if-feature feature_list:HAVE_QOS;
            type  cml_data_types:CML_VXLAN_QOS_GLOBAL_MODE_T;
            description "";
        } // END of vxlanQoSMode definition.

        leaf globalDir  {
            if-feature feature_list:HAVE_QOS;
            type  cml_data_types:CML_VXLAN_QOS_DIR_T;
            description "";
        } // END of globalDir definition.

        leaf globalProfileId  {
            if-feature feature_list:HAVE_QOS;
            type  cml_data_types:CML_UINT8_T {
                 range "65..128";
            }
            description "";
        } // END of globalProfileId definition.

        leaf macAgeing  {
            type  cml_data_types:CML_UINT32_T {
                 range "10..1000000";
            }
            default "300";
            description "";
        } // END of macAgeing definition.

        leaf maxCacheDisableCount  {
            type  cml_data_types:CML_UINT16_T {
                 range "1..200";
            }
            description "Max number of ARP/ND cache disable allowed for port-vlan access-ports";
        } // END of maxCacheDisableCount definition.


        list nvoTunnelStats {
            key "dest-ip";
            config false;
            description
                "Tunnel Stats";
            leaf dest-ip  {
                type  cml_data_types:CML_IPV4_ADDR_T;
                description "Tunnel destination IP";
            } // END of dest-ip definition.

            leaf source-ip  {
                type  cml_data_types:CML_IPV4_ADDR_T;
                description "Tunnel source IP";
            } // END of source-ip definition.

            leaf out_bytes  {
                type  cml_data_types:CML_UINT64_T;
                description "This indicates total number of bytes sent out from tunnel interface";
            } // END of out_bytes definition.

            leaf out_packets  {
                type  cml_data_types:CML_UINT64_T;
                description "This indicates total number of packets sent out from tunnel interface";
            } // END of out_packets definition.

            leaf in_bytes  {
                type  cml_data_types:CML_UINT64_T;
                description "This indicates total number of bytes recieved on tunnel interface";
            } // END of in_bytes definition.

            leaf in_packets  {
                type  cml_data_types:CML_UINT64_T;
                description "This indicates total number of packets recieved on tunnel interface";
            } // END of in_packets definition.

            leaf updatetime  {
                type  cml_data_types:CML_UINT32_T;
                description "This indicates the last updated time of a tunnel nexthop";
            } // END of updatetime definition.

            leaf up-downtime  {
                type  cml_data_types:CML_UINT32_T;
                description "This indicates tunnel up/down time";
            } // END of up-downtime definition.

            leaf status  {
                type  cml_data_types:CML_TUNNEL_STATUS_T;
                description "Status of tunnel";
            } // END of status definition.

        } // End of nvoTunnelStats-list

        list nvoTenant {
            if-feature feature_list:HAVE_NVO;
            key "nvoId";
            description
                "Tunnel Side Configurations including tenant information";
            leaf nvoId  {
                type  cml_data_types:CML_UINT32_T {
                     range "1..16777215";
                }
                description "";
            } // END of nvoId definition.

            leaf type  {
                type  cml_data_types:CML_BOOL_T;
                description "";
            } // END of type definition.

            leaf mcastIp  {
                type  cml_data_types:CML_IPV4_ADDR_T;
                description "";
            } // END of mcastIp definition.

            leaf ingRepl  {
                type  cml_data_types:CML_BOOL_T;
                default false;
                description "";
            } // END of ingRepl definition.

            leaf innerVidDisabled  {
                type  cml_data_types:CML_BOOL_T;
                default false;
                description "";
            } // END of innerVidDisabled definition.

            leaf vrfName  {
                type  cml_data_types:CML_STRING_T {
                    length "0..255";
                }
                description "";
            } // END of vrfName definition.

            leaf map-network  {
                type  cml_data_types:CML_STRING_T {
                    length "0..255";
                }
                description "";
            } // END of map-network definition.

            leaf macHoldTime  {
                type  cml_data_types:CML_INT32_T {
                     range "-1..300";
                }
                description "";
            } // END of macHoldTime definition.


            list nvoStatic {
                key "macAddr";
                description
                    "Tunnel Side Configurations including tenant information";
                leaf macAddr  {
                    type  cml_data_types:CML_MAC_ADDR_T;
                    description "Mac Adress of the host";
                } // END of macAddr definition.

                leaf remoteVtepIp  {
                    type  cml_data_types:CML_IPV4_ADDR_T;
                    description "";
                } // END of remoteVtepIp definition.

            } // End of nvoStatic-list

            list nvoArpCacheInfo {
                key "hostIp";
                config false;
                description
                    "ArpCache Entries";
                leaf hostIp  {
                    type  cml_data_types:CML_IPV4_ADDR_T;
                    description "Host IP Adress";
                } // END of hostIp definition.

                leaf hostMac  {
                    type  cml_data_types:CML_MAC_ADDR_T;
                    description "Host Mac Address";
                } // END of hostMac definition.

                leaf hostType  {
                    type  cml_data_types:CML_UINT8_T;
                    description "Host Type";
                } // END of hostType definition.

                leaf ifindex  {
                    type  cml_data_types:CML_UINT32_T;
                    description "Interface Index";
                } // END of ifindex definition.

            } // End of nvoArpCacheInfo-list

            list nvoMacMapping {
                key "macAddr";
                config false;
                description
                    "FDB table";
                leaf macAddr  {
                    type  cml_data_types:CML_MAC_ADDR_T;
                    description "Mac Adress of the host";
                } // END of macAddr definition.

                leaf prefix  {
                    type  cml_data_types:CML_IPV4_ADDR_T;
                    description "IP Adress of the host";
                } // END of prefix definition.

                leaf type  {
                    type  cml_data_types:CML_UINT8_T;
                    description "Type";
                } // END of type definition.

                leaf sticky  {
                    type  cml_data_types:CML_BOOL_T;
                    description "Static mac or Dynamic";
                } // END of sticky definition.

            } // End of nvoMacMapping-list
        } // End of nvoTenant-list
    } // END of nvo-container definition.
    } // END of nvo-container definition.

    grouping  nvoAccessIfInfo-grouping {
    container nvoAccessIfInfo {
        presence "yes";
        description
            "VxLAN Access side configurations ";
        leaf port  {
            type  cml_data_types:CML_VXLAN_PORT_T;
            mandatory true;
            description "";
        } // END of port definition.

        leaf arpCacheDisable  {
            type  cml_data_types:CML_BOOL_T;
            default false;
            description "Disable arp cache on access interface";
        } // END of arpCacheDisable definition.

        leaf ndCacheDisable  {
            type  cml_data_types:CML_BOOL_T;
            default false;
            description "Disable ND cache on access interface";
        } // END of ndCacheDisable definition.

        uses access-info;
        uses vxlan-counters;
    } // END of nvoAccessIfInfo-container definition.
    } // END of nvoAccessIfInfo-container definition.


}
