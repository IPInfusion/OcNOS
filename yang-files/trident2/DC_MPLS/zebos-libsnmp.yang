/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-libsnmp.yang
*
*/

submodule zebos-libsnmp {

    belongs-to  zebos { prefix zebos; }

    import cml_data_types {
        prefix cml_data_types;
    }

    import feature_list {
        prefix feature_list;
    }

    include zebos-vrf;
    organization
        "IP Infusion Inc.";

    contact
        "Address: 3965 Freedom Circle, Suite 200, Santa Clara, CA 95054
        Phone: +1 408-400-1900
        E-mail: support@ipinfusion.com
        Web: http://www.ipinfusion.com/";

    description
        "snmp configurations";


    revision "2018-06-21" {
        description " Initial Version.";
        reference "";
    }


    grouping  snmpVrfName-grouping {
    description
        "snmp-server configuration common for all modules";
    container snmpVrfName {
        if-feature feature_list:HAVE_SNMP_AGENT;
        description
            "snmp-server configuration common for all modules";
        leaf vrfName  {
            type  cml_data_types:CML_STRING_T {
                length "0..255";
            }
            description "";
        } // END of vrfName definition.

        leaf-list traps  {
            type  cml_data_types:SNMP_TRAP_OPTIONS_T;
            description "";
        } // END of traps definition.

    } // END of snmpVrfName-container definition.
    } // END of snmpVrfName-container definition.

    grouping  debugAgentx-grouping {
    description
        "debugging for agentx";
    container debugAgentx {
        if-feature feature_list:HAVE_AGENTX;
        description
            "debugging for agentx";
        leaf debug  {
            type  cml_data_types:CML_AGENTX_DEBUG_TYPE_T;
            description "";
        } // END of debug definition.

    } // END of debugAgentx-container definition.
    } // END of debugAgentx-container definition.


}
