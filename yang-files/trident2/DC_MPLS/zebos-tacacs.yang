/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-tacacs.yang
*
*/

submodule zebos-tacacs {

    belongs-to  zebos { prefix zebos; }

    import cml_data_types {
        prefix cml_data_types;
    }

    import feature_list {
        prefix feature_list;
    }

    include zebos-vrf;
    organization
        "IP Infusion Inc.";

    contact
        "Address: 3965 Freedom Circle, Suite 200, Santa Clara, CA 95054
        Phone: +1 408-400-1900
        E-mail: support@ipinfusion.com
        Web: http://www.ipinfusion.com/";

    description
        "Layer-3 tacacs configurations";


    revision "2017-06-08" {
        description "Uplifted the changes from linx branch.";
    }

    revision "2017-06-07" {
        description "Removed tacacs timeout attr and cli sequence. added objectUpdate for 'feature tacacs+ vrf management' command.";
    }

    revision "2017-05-16" {
        description "Updated to hide tacacs timeout.";
    }

    revision "2017-05-11" {
        description "Removed key attr. Updated notif for key.";
    }

    revision "2016-12-27" {
        description "Added snmp oid and documentation tag.";
    }

    revision "2016-10-28" {
        description "Initial version of TAcacs datamodel.";
    }


    grouping  tacacs-grouping {
    container tacacs {
        presence "yes";
        description
            "tacacs related operations";
        leaf vrfName  {
            type  cml_data_types:CML_STRING_T {
                length "0..255";
            }
            description "";
        } // END of vrfName definition.

        leaf featureTacacs  {
            type  cml_data_types:CML_BOOL_T;
            mandatory true;
            description "";
        } // END of featureTacacs definition.

        leaf tacacsKeyEnable  {
            if-feature feature_list:HAVE_HOSTPD;
            if-feature feature_list:HAVE_AAA;
            if-feature feature_list:HAVE_TACACS_CLIENT;
            type  cml_data_types:CML_HOSTP_KEY_TYPE_T;
            default "0";
            description "";
        } // END of tacacsKeyEnable definition.

        leaf tacacsKeyWord  {
            if-feature feature_list:HAVE_HOSTPD;
            if-feature feature_list:HAVE_AAA;
            if-feature feature_list:HAVE_TACACS_CLIENT;
            type  cml_data_types:CML_STRING_T {
                length "0..255";
            }
            description "";
        } // END of tacacsKeyWord definition.

        leaf debugtacacs  {
            if-feature feature_list:HAVE_HOSTPD;
            if-feature feature_list:HAVE_AAA;
            if-feature feature_list:HAVE_TACACS_CLIENT;
            type  cml_data_types:CML_BOOL_T;
            description "";
        } // END of debugtacacs definition.

        leaf debugtacacsConfig  {
            if-feature feature_list:HAVE_HOSTPD;
            if-feature feature_list:HAVE_AAA;
            if-feature feature_list:HAVE_TACACS_CLIENT;
            type  cml_data_types:CML_BOOL_T;
            description "";
        } // END of debugtacacsConfig definition.


        list tacacshost {
            key "hostAddr";
            description
                "tacacshost";
            leaf vrfName  {
                type  cml_data_types:CML_STRING_T {
                    length "0..255";
                }
                description "";
            } // END of vrfName definition.

            leaf hostAddr  {
                type  cml_data_types:CML_HOSTPNAME_T;
                description "";
            } // END of hostAddr definition.

            leaf keyEnable  {
                if-feature feature_list:HAVE_HOSTPD;
                if-feature feature_list:HAVE_AAA;
                if-feature feature_list:HAVE_TACACS_CLIENT;
                type  cml_data_types:CML_HOSTP_KEY_TYPE_T;
                default "0";
                description "";
            } // END of keyEnable definition.

            leaf keyWord  {
                if-feature feature_list:HAVE_HOSTPD;
                if-feature feature_list:HAVE_AAA;
                if-feature feature_list:HAVE_TACACS_CLIENT;
                type  cml_data_types:CML_STRING_T {
                    length "0..255";
                }
                description "";
            } // END of keyWord definition.

            leaf port  {
                if-feature feature_list:HAVE_HOSTPD;
                if-feature feature_list:HAVE_AAA;
                if-feature feature_list:HAVE_TACACS_CLIENT;
                type  cml_data_types:CML_UINT32_T {
                     range "1025..65535";
                }
                description "";
            } // END of port definition.

        } // End of tacacshost-list
    } // END of tacacs-container definition.
    } // END of tacacs-container definition.


}
