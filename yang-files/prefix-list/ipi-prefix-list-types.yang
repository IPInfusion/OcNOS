/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-prefix-list-types.yang
*
*/

module ipi-prefix-list-types {

    yang-version 1.1;

    namespace   "http://www.ipinfusion.com/yang/ocnos/ipi-prefix-list-types";

    prefix "ipi-prefix-list-types";

    import ietf-inet-types {
        prefix inet;
        revision-date 2013-07-15;
    }

    organization
        "IP Infusion Inc.";

    contact
        "Address: 3965 Freedom Circle, Suite 200, Santa Clara, CA 95054
         Phone: +1 408-400-1900
         E-mail: support@ipinfusion.com
         Web: http://www.ipinfusion.com/";

    description
        "YANG version of the ipi-prefix-list-types";


    revision "2022-06-01" {
        description "Updated the yang file with feature";
        reference " 0.4.0.";
    }

    revision "2021-09-03" {
        description "Update descriptions of attribute";
        reference " 0.3.0.";
    }

    revision "2020-12-15" {
        description "Change to have data-types in lower case instead of camel case";
        reference " 0.2.0.";
    }

    revision "2020-06-23" {
        description "Initial Version";
        reference " 0.1.0.";
    }



    typedef  prefix_list_type_t {
        type enumeration {
            enum ip {
                value 1;
                description "Prefix-list type ipv4";
            }
            enum ipv6 {
                value 2;
                description "Prefix-list type ipv6";
            }
        }
        description "type definition for PREFIX_LIST_TYPE_T";
    }

    typedef  prefix_list_action_t {
        type enumeration {
            enum deny {
                value 1;
                description "Specify packets to reject";
            }
            enum permit {
                value 2;
                description "Specify packets to forward";
            }
        }
        description "type definition for PREFIX_LIST_ACTION_T";
    }

    typedef  prefix_list_any_t {
        type enumeration {
            enum any {
                value 1;
                description "Any prefix match. Same as 0.0.0.0/0 le 32 ";
            }
        }
        description "type definition for PREFIX_LIST_ANY_T";
    }

    typedef  prefix_list_ipv4_network_t {
        type union {
            type prefix_list_any_t {

            }
            type inet:ipv4-prefix {

            }
        }
        description "type definition for PREFIX_LIST_IPV4_NETWORK_T";
    }

    typedef  prefix_list_ipv6_network_t {
        type union {
            type prefix_list_any_t {

            }
            type inet:ipv6-prefix {

            }
        }
        description "type definition for PREFIX_LIST_IPV6_NETWORK_T";
    }

}
