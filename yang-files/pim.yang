/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : pim.yang
*
*/

submodule pim {

    belongs-to  ZebOS { prefix ZebOS; }
    include vrf;


    import cml_data_types {
        prefix cml_data_types;
    }


    revision "2017-02-02" {
        description "Fix for JIRA-13119 (implicit delete).";
    }

    revision "2017-01-03" {
        description "commands supported for both pim ipv4 and ipv6.";
    }



    grouping pimDebug-grouping {
        list pimDebug {
             
            description
                "pimDebug";

            config true;
            key "vrfName";

            
            leaf vrfName  {
                type  cml_data_types:CML_STRING_T {
                    length "0..255";
                }
            } // END of vrfName definition.

            leaf debugall  {
                type  cml_data_types:CML_BOOL_T;  
                description "debug pim all";
            } // END of debugall definition.

        } // End of pimDebug-list
    } // END of pimDebug-grouping definition.


    grouping pimTermDebug-grouping {
        list pimTermDebug {
             
            description
                "pimTermDebug";

            config true;
            key "vrfName";

            
            leaf vrfName  {
                type  cml_data_types:CML_STRING_T {
                    length "0..255";
                }
            } // END of vrfName definition.

            leaf debugtermall  {
                type  cml_data_types:CML_BOOL_T;  
                description "debug pim all";
            } // END of debugtermall definition.

        } // End of pimTermDebug-list
    } // END of pimTermDebug-grouping definition.


}
