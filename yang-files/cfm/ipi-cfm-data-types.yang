/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-cfm-data-types.yang
*
*/

module ipi-cfm-data-types {

    yang-version 1.1;

    namespace   "http://www.ipinfusion.com/yang/ocnos/ipi-cfm-data-types";

    prefix "ipi-cfm-data-types";

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "This module defines data types related to the CFM model";


    revision "2022-06-01" {
        description "Updated the yang file with feature";
        reference " 0.3.2.";
    }

    revision "2022-05-31" {
        description "Added support for CFM msg intervals of 1-min and 10-mins";
        reference " 0.3.2.";
    }

    revision "2022-05-09" {
        description "Updation of MPLS flags for CFM and debug CFM CLI";
        reference " 0.3.1.";
    }

    revision "2022-04-29" {
        description "Restructure CFM and Y.1731 over MPLS components to OpenConfig style and enable NETCONF support";
        reference " 0.3.0.";
    }

    revision "2022-04-05" {
        description "Added support for Client Signal Fail (CSF) feature";
        reference " 0.2.1.";
    }

    revision "2022-03-10" {
        description "Restructure LB, LT and CFM Y.1731 L2 bridge dependent CLIs to OpenConfig style";
        reference " 0.2.0.";
    }

    revision "2018-12-06" {
        description "Initial version drafted by referring MEF 38 and IEEE standards";
        reference " 0.1.0.";
    }



    typedef  cfm_mpls_svc_type_t {
        type enumeration {
            enum vpws {
                value 1;
                description "Identifying string for VPWS instance";
            }
            enum evpn {
                value 2;
                description "Identifying string for EVPN instance";
            }
        }
        description "type definition for CFM_MPLS_SVC_TYPE_T";
    }

    typedef  cfm_rmep_mac_addr_t {
        type string {
            pattern "[0-9a-fA-F]{4}.[0-9a-fA-F]{4}.[0-9a-fA-F]{4}";
        }
        description "type definition for CFM_RMEP_MAC_ADDR_T";
    }

    typedef  cfm_rmep_type_t {
        type union {
            type cfm_rmep_mac_addr_t {

            }
            type uint16 {
                range "1..8191";

            }
        }
        description "type definition for CFM_RMEP_TYPE_T";
    }

    typedef  cfm_mip_creation_mode_t {
        type enumeration {
            enum none {
                value 1;
                description "No MIPs can be created for this VID";
            }
            enum default {
                value 2;
                description "MIP can be created if no lower active level or MEP at next lower active level";
            }
            enum explicit {
                value 3;
                description "MEP is needed at the next lower active level";
            }
        }
        description "type definition for CFM_MIP_CREATION_MODE_T";
    }

    typedef  cfm_md_type_t {
        type enumeration {
            enum no-name {
                value 1;
                description "No Maintenace Domain Name. MA type must be integer or ITU-T Carrier code (ICC) based format defined by ITU-T Y.1731";
            }
            enum character-string {
                value 4;
                description "MD name type is Character string. MA type must be string only";
            }
        }
        description "type definition for CFM_MD_TYPE_T";
    }

    typedef  cfm_ma_type_t {
        type enumeration {
            enum string {
                value 2;
                description "Character string as the ma-name. MD type should be string";
            }
            enum integer {
                value 3;
                description "Integer as ma-name. MD type should be no-name";
            }
            enum itu-t {
                value 32;
                description "ITU-T Carrier code (ICC) based format defined by ITU-T Y.1731. MD type should be no-name";
            }
        }
        description "type definition for CFM_MA_TYPE_T";
    }

    typedef  cfm_ma_mip_creation_mode_t {
        type enumeration {
            enum none {
                value 1;
                description "No MIPs can be created for this VID";
            }
            enum default {
                value 2;
                description "MIPs can be created if no lower active level or MEP at next lower active level";
            }
            enum explicit {
                value 3;
                description "MEP is needed at the next lower active level";
            }
            enum defer {
                value 4;
                description "Use the MIP creation permissions of the MD to which this MA belongs to";
            }
        }
        description "type definition for CFM_MA_MIP_CREATION_MODE_T";
    }

    typedef  cfm_ma_status_t {
        type enumeration {
            enum Unknown {
                value 0;
                description "MA connectivity status is unknown";
            }
            enum Active {
                value 1;
                description "MA connectivity status is active";
            }
            enum Partially-Active {
                value 2;
                description "MA connectivity status is partially active";
            }
            enum Not-Active {
                value 3;
                description "MA connectivity status is not active";
            }
            enum Error {
                value 4;
                description "MA connectivity status has some error";
            }
        }
        description "type definition for CFM_MA_STATUS_T";
    }

    typedef  cfm_mep_direction_t {
        type enumeration {
            enum down {
                value 1;
                description "Down MEP";
            }
            enum up {
                value 2;
                description "Up MEP";
            }
        }
        description "type definition for CFM_MEP_DIRECTION_T";
    }

    typedef  cfm_mep_state_t {
        type enumeration {
            enum false {
                value 0;
                description "MEP to cease functioning";
            }
            enum true {
                value 1;
                description "MEP to function normally";
            }
        }
        description "type definition for CFM_MEP_STATE_T";
    }

    typedef  cfm_mep_connectivity_status_t {
        type enumeration {
            enum Fully-Connected {
                value 1;
                description "MEP connectivity status is Fully Connected";
            }
            enum Partially-Connected {
                value 2;
                description "MEP connectivity status is Partially-Connected";
            }
            enum Isolated {
                value 3;
                description "MEP connectivity status is Isolated";
            }
        }
        description "type definition for CFM_MEP_CONNECTIVITY_STATUS_T";
    }

    typedef  cfm_msg_interval_t {
        type enumeration {
            enum 3ms {
                value 1;
                if-feature feature-list:CCM_HW_OFFLOAD;
                description "CC Interval 3 millisecond";
            }
            enum 10ms {
                value 2;
                description "CC Interval 10 millisecond";
            }
            enum 100ms {
                value 3;
                description "CC Interval 100 millisecond";
            }
            enum 1s {
                value 4;
                description "CC Interval 1 second(default)";
            }
            enum 10s {
                value 5;
                description "CC Interval 10 second";
            }
            enum 1min {
                value 6;
                description "CC Interval 1 minute";
            }
            enum 10min {
                value 7;
                description "CC Interval 10 minute";
            }
        }
        description "type definition for CFM_MSG_INTERVAL_T";
    }

    typedef  cfm_mep_lck_t {
        type enumeration {
            enum unlock {
                value 0;
                description "Disable administrative locking state(default)";
            }
            enum lock {
                value 1;
                description "Enable administrative locking state";
            }
        }
        description "type definition for CFM_MEP_LCK_T";
    }

    typedef  cfm_mep_lowest_fault_priority_t {
        type enumeration {
            enum defRDICCM {
                value 1;
                description "DefRDICCM";
            }
            enum defMACstatus {
                value 2;
                description "DefMACstatus(default)";
            }
            enum defRemoteCCM {
                value 3;
                description "DefRemoteCCM";
            }
            enum defErrorCCM {
                value 4;
                description "DefErrorCCM";
            }
            enum defXconCCM {
                value 5;
                description "DefXconCCM";
            }
        }
        description "type definition for CFM_MEP_LOWEST_FAULT_PRIORITY_T";
    }

    typedef  cfm_mep_highest_fault_defect_t {
        type enumeration {
            enum none {
                value 1;
                description "No defects since FNG_RESET";
            }
            enum defRDICCM {
                value 2;
                description "DefRDICCM";
            }
            enum defMACstatus {
                value 3;
                description "DefMACstatus";
            }
            enum defRemoteCCM {
                value 4;
                description "DefRemoteCCM";
            }
            enum defErrorCCM {
                value 5;
                description "DefErrorCCM";
            }
            enum defXconCCM {
                value 6;
                description "DefXconCCM";
            }
        }
        description "type definition for CFM_MEP_HIGHEST_FAULT_DEFECT_T";
    }

    typedef  cfm_received_ccm_defect_t {
        type bits {
            bit defRDICCM {
                position 0;
                description "A remote MEP is reported the RDI bit set in its last CCM";
            }
            bit defMACstatus {
                position 1;
                description "One or more of the remote MEPs is reporting a failure in its Port Status TLV or Interface Status TLV";
            }
            bit defRemoteCCM {
                position 2;
                description "Atleast one of the MEP is not receiving valid CCMs from one of the its remote MEP";
            }
            bit defErrorCCM {
                position 3;
                description "The MEP has received at least one invalid CCM whose CCM Interval has not yet timed out";
            }
            bit defXconCCM {
                position 4;
                description "The MEP has received at least one CCM from either another MAID or a lower MD Level whose CCM Interval has not yet timed out";
            }
            bit none {
                position 5;
                description "No defects in last CCM PDU";
            }
        }
        description "type definition for CFM_RECEIVED_CCM_DEFECT_T";
    }

    typedef  cfm_start_time_immediate_t {
        type enumeration {
            enum immediate {
                value 1;
                description "Start the measurement session immediately";
            }
        }
        description "type definition for CFM_START_TIME_IMMEDIATE_T";
    }

    typedef  cfm_stop_time_none_t {
        type enumeration {
            enum none {
                value 0;
                description "Never end the measurement session";
            }
        }
        description "type definition for CFM_STOP_TIME_NONE_T";
    }

    typedef  cfm_absolute_time_t {
        type enumeration {
            enum absolute {
                value 3;
                description "This object specifies the scheduled start/stop date/time to perform the on-demand Performance Monitoring OAM operations";
            }
        }
        description "type definition for CFM_ABSOLUTE_TIME_T";
    }

    typedef  cfm_relative_time_t {
        type enumeration {
            enum relative {
                value 2;
                description "This object specifies the relative start/stop time from the current system time to perform on-demand Performance Monitoring OAM operations";
            }
        }
        description "type definition for CFM_RELATIVE_TIME_T";
    }

    typedef  cfm_lm_measurement_type_t {
        type enumeration {
            enum lmm {
                value 1;
                description "LMM SOAM PDU generated and received LMR responses tracked";
            }
            enum slm {
                value 2;
                description "SLM SOAM PDU generated and received SLR responses tracked(default)";
            }
            enum ccm {
                value 3;
                description "CCM SOAM PDU generated and received CCM PDUs tracked";
            }
        }
        description "type definition for CFM_LM_MEASUREMENT_TYPE_T";
    }

    typedef  cfm_dm_measurement_type_t {
        type enumeration {
            enum dmm {
                value 1;
                description "DMM SOAM PDU generated. DMR responses received";
            }
        }
        description "type definition for CFM_DM_MEASUREMENT_TYPE_T";
    }

    typedef  cfm_lm_reply_type_t {
        type enumeration {
            enum lmm {
                value 1;
                description "LMM SOAM PDU generated and received LMR responses tracked";
            }
            enum slm {
                value 2;
                description "SLM SOAM PDU generated and received SLR responses tracked(default)";
            }
        }
        description "type definition for CFM_LM_REPLY_TYPE_T";
    }

    typedef  cfm_y1731_tx_interval_t {
        type enumeration {
            enum 1s {
                value 1;
                description "PDU transmit interval is one second(default)";
            }
            enum 1min {
                value 60;
                description "PDU transmit interval is one minute";
            }
        }
        description "type definition for CFM_Y1731_TX_INTERVAL_T";
    }

    typedef  cfm_ebn_rate_unit_t {
        type enumeration {
            enum kbps {
                value 2;
                description "Specifies the unit of kilobits per second";
            }
            enum mbps {
                value 3;
                description "Specifies the unit of megabits per second";
            }
            enum gbps {
                value 4;
                description "Specifies the unit of gigabits per second";
            }
        }
        description "type definition for CFM_EBN_RATE_UNIT_T";
    }

    typedef  cfm_ebn_rate_unit_extended_t {
        type enumeration {
            enum kbps {
                value 2;
                description "Specifies the unit of kilobits per second";
            }
            enum mbps {
                value 3;
                description "Specifies the unit of megabits per second";
            }
            enum gbps {
                value 4;
                description "Specifies the unit of gigabits per second";
            }
            enum percent {
                value 6;
                description "Specifies the unit in percentage";
            }
        }
        description "type definition for CFM_EBN_RATE_UNIT_EXTENDED_T";
    }

    typedef  cfm_relay_action_t {
        type enumeration {
            enum unknown {
                value 0;
                description "Unknown Relay action";
            }
            enum hit {
                value 1;
                description "Indicates the LTM reached an MP whose MAC address matches the target MAC address";
            }
            enum filtering-database {
                value 2;
                description "Indicates the Egress Port was determined by consulting the Filtering Database";
            }
            enum mip-ccm-database {
                value 3;
                description "Indicates the Egress Port was determined by consulting the MIP CCM Database";
            }
        }
        description "type definition for CFM_RELAY_ACTION_T";
    }

    typedef  cfm_dm_measurement_bin_type_t {
        type enumeration {
            enum frame-delay {
                value 1;
                description "Indicates a measurement bin for two-way Frame Delay";
            }
            enum inter-frame-delay-variation {
                value 4;
                description "Indicates a measurement bin for two-way Inter-frame Delay Variation";
            }
        }
        description "type definition for CFM_DM_MEASUREMENT_BIN_TYPE_T";
    }

    typedef  cfm_debug_t {
        type bits {
            bit events {
                position 0;
                description "Enable event debugs";
            }
            bit rx {
                position 1;
                description "Enable receive debugs";
            }
            bit tx {
                position 2;
                description "Enable transmit debugs";
            }
            bit loopback {
                position 3;
                description "Enable loopback debugs";
            }
            bit traceroute {
                position 4;
                description "Enable traceroute debugs";
            }
        }
        description "type definition for CFM_DEBUG_T";
    }

    typedef  cfm_test_type_t {
        type enumeration {
            enum in-service {
                value 0;
                description "This indicates the ETH-Test is in-service and normal client service traffic is not interrupted(default)";
            }
            enum out-of-service {
                value 1;
                description "This indicates the ETH-Test is out-of-service and normal client service traffic is disrupted";
            }
        }
        description "type definition for CFM_TEST_TYPE_T";
    }

    typedef  cfm_test_pattern_type_t {
        type enumeration {
            enum null-sig {
                value 1;
                description "This test pattern is a Null signal without CRC-32(default)";
            }
            enum null-sig-crc32 {
                value 2;
                description "This test pattern is a Null signal with CRC-32";
            }
            enum prbs {
                value 3;
                description "This test pattern is a PRBS 2^31-1 without CRC-32";
            }
            enum prbs-crc32 {
                value 4;
                description "This test pattern is a PRBS 2^31-1 with CRC-32";
            }
        }
        description "type definition for CFM_TEST_PATTERN_TYPE_T";
    }

    typedef  cfm_test_mode_t {
        type enumeration {
            enum generator {
                value 1;
                description "The node will act as a ETH-TST Frame Generator";
            }
            enum receiver {
                value 2;
                description "The node will act as a ETH-TST Frame Receiver(default)";
            }
            enum both {
                value 3;
                description "The node will act as both ETH-TST Frame Generator and Receiver";
            }
        }
        description "type definition for CFM_TEST_MODE_T";
    }

    typedef  cfm_bn_csf_signal_state_t {
        type bits {
            bit SIGNAL_DEGRADED {
                position 0;
                description "Signal is degraded";
            }
            bit SIGNAL_NORMAL {
                position 1;
                description "Signal is normal";
            }
            bit SIGNAL_PENDING {
                position 2;
                description "Signal is pending";
            }
        }
        description "type definition for CFM_BN_CSF_SIGNAL_STATE_T";
    }

    typedef  cfm_tst_session_status_t {
        type enumeration {
            enum In-progress {
                value 1;
                description "The session is on-going";
            }
            enum Completed {
                value 2;
                description "The session is completed";
            }
        }
        description "type definition for CFM_TST_SESSION_STATUS_T";
    }

    typedef  cfm_lb_mac_addr_t {
        type string {
            pattern "[0-9a-fA-F]{4}.[0-9a-fA-F]{4}.[0-9a-fA-F]{4}";
        }
        description "type definition for CFM_LB_MAC_ADDR_T";
    }

    typedef  cfm_pm_session_status_t {
        type enumeration {
            enum not-active {
                value 0;
                description "Indicates the measurement instance is not active";
            }
            enum active {
                value 1;
                description "Indicates the measurement instance is active";
            }
        }
        description "type definition for CFM_PM_SESSION_STATUS_T";
    }

}
