/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-cfm-mpls.yang
*
*/

submodule ipi-cfm-mpls {

    yang-version 1.1;

    belongs-to  ipi-cfm { prefix ipi-cfm; }

    import feature-list {
        prefix feature-list;
        revision-date 2023-02-21;
    }

    import ipi-cfm-data-types {
        prefix ipi-cfm-data-types;
        revision-date 2022-06-01;
    }

    include ipi-cfm-common { revision-date 2022-06-01;}
    include ipi-cfm-mpls-y1731 { revision-date 2022-06-01;}
    organization
        "IP Infusion Inc.";

    contact
        "Address: 3965 Freedom Circle, Suite 200, Santa Clara, CA 95054
         Phone: +1 408-400-1900
         E-mail: support@ipinfusion.com
         Web: http://www.ipinfusion.com/";

    description
        "Data model for IPI CFM Configuration and Operational state on MPLS
                L2VPN service";


    revision "2022-06-01" {
        description "Updated the yang file with feature";
        reference " 0.2.0.";
    }

    revision "2022-05-21" {
        description "Corrected grouping name for cfm-mep-common-state and cfm-mep-common-config";
        reference " 0.1.2.";
    }

    revision "2022-05-09" {
        description "Updation of MPLS flags for CFM and debug CFM CLI";
        reference " 0.1.1.";
    }

    revision "2022-04-29" {
        description "Initial Version";
        reference " 0.1.0.";
    }

    grouping cfm-mep-mpls-config {
        description
            "Configuration data definitions related to Maintenance Endpoint which
                        are MPLS L2VPN service specific";
        leaf vpws-vc-name  {
            when " not(/cfm/mpls/services/service/maintenance-domains/maintenance-domain/maintenance-associations/maintenance-association/maintenance-end-points/maintenance-end-point/config/evpn-id) ";
            type  string {
                length "1..30";
                pattern "[^?' =,>|]+";
            }
            description "This attribute uniquely identifies a VPWS circuit";
        } // END of vpws-vc-name definition.

        leaf evpn-id  {
            when " not(/cfm/mpls/services/service/maintenance-domains/maintenance-domain/maintenance-associations/maintenance-association/maintenance-end-points/maintenance-end-point/config/vpws-vc-name) ";
            type  uint32 {
                 range "1..16777215"  {
                    description "1..16777215: Supported range 1 - 16777215";
                 }
            }
            description "EVPN-MPLS Circuit";
        } // END of evpn-id definition.

    } // END of cfm-mep-mpls-config definition.
    grouping cfm-mpls-service-config {
        description
            "Configuration data definitions related to traceroute MPLS L2VPN
                        service specific";
        leaf service-type  {
            type  ipi-cfm-data-types:cfm_mpls_svc_type_t;
            description "MPLS service type whether it's Virtual Private Wire Service(VPWS) or
                        Ethernet VPN(EVPN)";
        } // END of service-type definition.

        leaf linktrace-cache-enable  {
            type  empty;
            description "This attribute enables linktrace cache for the given MPLS service";
        } // END of linktrace-cache-enable definition.

        leaf linktrace-cache-size  {
            when " ../linktrace-cache-enable ";
            type  uint32 {
                 range "1..4095"  {
                    description "1..4095: Supported range 1 - 4095";
                 }
            }
            default "100";
            description "This attribute specifies the cache size";
        } // END of linktrace-cache-size definition.

    } // END of cfm-mpls-service-config definition.
    grouping cfm-ma-mpls-config {
        description
            "Configuration data definitions related to Maintenance Association
                        which are MPLS L2VPN service";
        leaf mip-creation  {
            type  ipi-cfm-data-types:cfm_ma_mip_creation_mode_t;
            mandatory true;
            description "This parameter indicates whether the management entity can create MIPs
                        for this MA";
        } // END of mip-creation definition.

    } // END of cfm-ma-mpls-config definition.
    grouping cfm-mpls-mep-ccm-top {
        description
            "Grouping for MPLS CFM MEP Continuity Check Messages";
        container continuity-check {
            description
                "Enclosing container for the list of CFM MEP Continuity Check Messages";
            container config {
                description
                    "Configuration data for CFM MEP Continuity Check Message";
                uses cfm-mep-ccm-config;
            } // END of config-container definition.
            container state {
                config false;
                description
                    "Operational data for CFM MEP Continuity Check Message";
                uses cfm-mep-ccm-config;
                uses cfm-mep-ccm-state;
            } // END of state-container definition.
            uses cfm-remote-meps-top;
        } // END of continuity-check-container definition.
    } // END of cfm-mpls-mep-ccm-top definition.
    grouping cfm-mpls-meps-top {
        description
            "Grouping for MPLS CFM Maintenence End Points";
        container maintenance-end-points {
            description
                "Enclosing container for the list of Maintenence End Points";

            list maintenance-end-point {
            when " /cfm/mpls/services/service/maintenance-domains/maintenance-domain/maintenance-associations/maintenance-association/maintenance-end-points/maintenance-end-point/config/vpws-vc-name  or /cfm/mpls/services/service/maintenance-domains/maintenance-domain/maintenance-associations/maintenance-association/maintenance-end-points/maintenance-end-point/config/evpn-id ";
                key "mep-id";
                description
                    "List of Maintenence End Points";
                leaf mep-id  {
                    type  leafref {
                        path  "../config/mep-id";
                    }
                    description "Integer that is unique among all the MEPs in the same MA. Other
                                definition is: a small integer, unique over a given Maintenance
                                Association, identifying a specific Maintenance association End Point";
                } // END of mep-id definition.

                container config {
                    description
                        "Configuration data for Maintenence End Point";
                    uses cfm-mep-common-config;
                    uses cfm-mep-mpls-config;
                } // END of config-container definition.
                container state {
                    config false;
                    description
                        "Operational data for Maintenence End Point";
                    uses cfm-mep-common-config;
                    uses cfm-mep-mpls-config;
                    uses cfm-mep-common-state;
                } // END of state-container definition.
                uses cfm-mep-mpls-config;
                uses cfm-mpls-mep-ccm-top;
                uses cfm-loopback-last-result-top;
                uses cfm-linktrace-database-state;
                uses mpls-y1731-responders-grouping;
                uses mpls-ethernet-loss-measurements-grouping;
                uses mpls-ethernet-delay-measurements-grouping;
            } // End of maintenance-end-point-list
        } // END of maintenance-end-points-container definition.
    } // END of cfm-mpls-meps-top definition.
    grouping cfm-mpls-mas-top {
        description
            "Grouping for MPLS CFM Maintenence Assosiations";
        container maintenance-associations {
            description
                "Enclosing container for the list of Maintenence associations";

            list maintenance-association {
                key "ma-name";
                description
                    "List of Maintenence associations";
                leaf ma-name  {
                    type  leafref {
                        path  "../config/ma-name";
                    }
                    description "The value union for the Maintenance Association Name.";
                } // END of ma-name definition.

                container config {
                    description
                        "Configuration data for Maintenence association";
                    uses cfm-ma-common-config;
                    uses cfm-ma-mpls-config;
                } // END of config-container definition.
                container state {
                    config false;
                    description
                        "Operational data for CFM over MPLS Maintenence association";
                    uses cfm-ma-common-config;
                    uses cfm-ma-mpls-config;
                } // END of state-container definition.
                uses cfm-mpls-meps-top;
            } // End of maintenance-association-list
        } // END of maintenance-associations-container definition.
    } // END of cfm-mpls-mas-top definition.
    grouping cfm-mpls-mds-top {
        description
            "Grouping for MPLS CFM Maintenence Domains";
        container maintenance-domains {
            description
                "Enclosing container for the list of CFM Maintenence Domains over MPLS
                        L2VPN service";

            list maintenance-domain {
                key "md-name";
                description
                    "List of CFM Maintenence Domains over MPLS L2VPN service";
                leaf md-name  {
                    type  leafref {
                        path  "../config/md-name";
                    }
                    description "A unique identifier of a Maintenance Domain";
                } // END of md-name definition.

                container config {
                    description
                        "Configuration data for CFM Maintenence Domains over MPLS L2VPN service";
                    uses cfm-md-common-config;
                } // END of config-container definition.
                container state {
                    config false;
                    description
                        "Operational data for CFM Maintenence Domains over MPLS L2VPN service";
                    uses cfm-md-common-config;
                } // END of state-container definition.
                uses cfm-mpls-mas-top;
            } // End of maintenance-domain-list
        } // END of maintenance-domains-container definition.
    } // END of cfm-mpls-mds-top definition.
    grouping cfm-mpls-service-top {
        description
            "Grouping for CFM over MPLS L2VPN service";
        container services {
            description
                "Enclosing container for the list of CFM over MPLS L2VPN service";

            list service {
                key "service-type";
                description
                    "List of CFM over MPLS L2VPN service";
                leaf service-type  {
                    type  leafref {
                        path  "../config/service-type";
                    }
                    description "MPLS service type whether it's Virtual Private Wire Service(VPWS) or
                                Ethernet VPN(EVPN)";
                } // END of service-type definition.

                container config {
                    description
                        "Configuration data for CFM MPLS L2VPN service";
                    uses cfm-mpls-service-config;
                } // END of config-container definition.
                container state {
                    config false;
                    description
                        "Operational data for Maintenence Domain";
                    uses cfm-mpls-service-config;
                } // END of state-container definition.
                uses cfm-mpls-mds-top;
            } // End of service-list
        } // END of services-container definition.
    } // END of cfm-mpls-service-top definition.

    grouping  mpls-grouping {
    description
        "Augments to support the CFM over MPLS functionality";
    container mpls {
        if-feature feature-list:HAVE_MPLS;
        if-feature feature-list:HAVE_CFM;
        if-feature feature-list:HAVE_ONMD;
        description
            "Augments to support the CFM over MPLS functionality";
        uses cfm-mpls-service-top;
    } // END of mpls-container definition.
    } // END of mpls-grouping definition.


}
