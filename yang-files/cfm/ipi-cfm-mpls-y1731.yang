/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-cfm-mpls-y1731.yang
*
*/

submodule ipi-cfm-mpls-y1731 {

    yang-version 1.1;

    belongs-to  ipi-cfm { prefix ipi-cfm; }

    import feature-list {
        prefix feature-list;
        revision-date 2023-02-21;
    }

    include ipi-cfm-common { revision-date 2022-06-01;}
    organization
        "IP Infusion Inc.";

    contact
        "Address: 3965 Freedom Circle, Suite 200, Santa Clara, CA 95054
         Phone: +1 408-400-1900
         E-mail: support@ipinfusion.com
         Web: http://www.ipinfusion.com/";

    description
        "Data model for IPI Y.1731 CFM Configuration and Operational state on
                MPLS services";


    revision "2022-06-01" {
        description "Updated the yang file with feature";
        reference " 0.2.0.";
    }

    revision "2022-05-26" {
        description "Added support to make rmep parameter for ETH-LM to take RMEPID or RMAC as input as per MEF";
        reference " 0.1.1.";
    }

    revision "2022-04-29" {
        description "Initial Version";
        reference " 0.1.0.";
    }


    grouping  mpls-y1731-responders-grouping {
    description
        "Augments to support a node as PM responder";
    container mpls-y1731-responders {
        if-feature feature-list:HAVE_CFM_Y1731;
        if-feature feature-list:Y1731_HW_OFFLOAD;
        if-feature feature-list:HAVE_MPLS_VC;
        if-feature feature-list:HAVE_CFM;
        if-feature feature-list:HAVE_ONMD;
        description
            "Augments to support a node as PM responder";
        container config {
            description
                "Configuration data for Y.1731 PM responders";
            uses y1731-responder-parameters-config;
        } // END of config-container definition.
        container state {
            config false;
            description
                "State data for Y.1731 PM responders";
            uses y1731-responder-parameters-config;
        } // END of state-container definition.
    } // END of mpls-y1731-responders-container definition.
    } // END of mpls-y1731-responders-grouping definition.

    grouping  mpls-ethernet-loss-measurements-grouping {
    description
        "Enclosing container for the list of Loss Measurements";
    container mpls-ethernet-loss-measurements {
        if-feature feature-list:Y1731_HW_OFFLOAD;
        if-feature feature-list:HAVE_MPLS_VC;
        if-feature feature-list:HAVE_CFM;
        if-feature feature-list:HAVE_CFM_Y1731;
        if-feature feature-list:HAVE_ONMD;
        config false;
        description
            "Enclosing container for the list of Loss Measurements";
        uses cfm-current-loss-measurement-top;
        uses cfm-historic-loss-measurements-top;
    } // END of mpls-ethernet-loss-measurements-container definition.
    } // END of mpls-ethernet-loss-measurements-grouping definition.

    grouping  mpls-ethernet-delay-measurements-grouping {
    description
        "Enclosing container for the list of Delay Measurements";
    container mpls-ethernet-delay-measurements {
        if-feature feature-list:Y1731_HW_OFFLOAD;
        if-feature feature-list:HAVE_MPLS_VC;
        if-feature feature-list:HAVE_CFM;
        if-feature feature-list:HAVE_CFM_Y1731;
        if-feature feature-list:HAVE_ONMD;
        config false;
        description
            "Enclosing container for the list of Delay Measurements";
        uses cfm-current-delay-measurement-top;
        uses cfm-historic-delay-measurements-top;
    } // END of mpls-ethernet-delay-measurements-container definition.
    } // END of mpls-ethernet-delay-measurements-grouping definition.


}
