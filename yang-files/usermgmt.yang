/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : usermgmt.yang
*
*/

submodule usermgmt {

    belongs-to  ZebOS { prefix ZebOS; }


    import cml_data_types {
        prefix cml_data_types;
    }

    description
        "Layer-3 usermgmt configurations";


    revision "2017-01-19" {
        description "User not created properly-[jira-12851].";
    }

    revision "2016-12-27" {
        description "Added snmp oid and documentation tag.";
    }

    revision "2016-10-28" {
        description "Initial version of USERMGMT datamodel.";
    }



    grouping usermgmt-grouping {
        list usermgmt {
             
            description
                "usermgmt";

            config true;
            key "username";

            
            leaf username  {
                type  cml_data_types:CML_STRING_T {
                    length "0..255";
                }
                description "Login name of the user";
            } // END of username definition.

            leaf encryptPassword  {
                type  cml_data_types:CML_STRING_T {
                    length "26..106";
                }
            } // END of encryptPassword definition.

            leaf password  {
                type  cml_data_types:CML_STRING_T {
                    length "8..32";
                }
                description "username";
            } // END of password definition.

            leaf role  {
                type  cml_data_types:USER_MGMT_ROLE_OPTIONS_T;  
                default "network-user";
                description "username with role";
            } // END of role definition.

        } // End of usermgmt-list
    } // END of usermgmt-grouping definition.

    grouping  userDebug-grouping {
    container userDebug {
                config true;

        description
            "userDebug";

        leaf debuguser  {
            type  cml_data_types:CML_BOOL_T;  
            description "debug user-mgmt";
        } // END of debuguser definition.

    } // END of userDebug-container definition.
    } // END of userDebug-container definition.


}
