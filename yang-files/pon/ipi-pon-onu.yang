/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-pon-onu.yang
*
*/

submodule ipi-pon-onu {

    yang-version 1.1;

    belongs-to  ipi-pon { prefix ipi-pon; }

    import feature-list {
        prefix feature-list;
        revision-date 2023-02-21;
    }

    import ipi-pon-types {
        prefix ipi-pon-types;
        revision-date 2022-06-01;
    }

    import ietf-yang-types {
        prefix yang;
        revision-date 2013-07-15;
    }

    organization
        "IP Infusion Inc.";

    contact
        "Address: 3965 Freedom Circle, Suite 200, Santa Clara, CA 95054
         Phone: +1 408-400-1900
         E-mail: support@ipinfusion.com
         Web: http://www.ipinfusion.com/";

    description
        "This module defines a data model for optical network unit(ONU)
                configuration for passive optical network";


    revision "2022-06-01" {
        description "Updated the yang file with feature";
        reference " 0.6.0.";
    }

    revision "2021-10-14" {
        description "Update isolate ONU port description";
        reference " 0.5.0.";
    }

    revision "2021-09-03" {
        description "Update descriptions of attribute";
        reference " 0.3.0.";
    }

    revision "2021-02-15" {
        description "Added support for state container corresponding to config containers";
        reference " 0.2.0.";
    }

    revision "2020-11-13" {
        description "Initial Version";
        reference "Initial Version";
    }

    grouping onu-id-config {
        description
            "Grouping for ONU identity configuration";
        leaf onu-id  {
            type  uint32 {
                 range "0..4095"  {
                    description "0..4095: Supported range 0 - 4095";
                 }
            }
            description "This is the logical ONU identity in the system. The ONU identity is
                        from 0 to 4095";
        } // END of onu-id definition.

    } // END of onu-id-config definition.
    grouping onu-global-config {
        description
            "Grouping for ONU global configuration";
        leaf administrative-state  {
            type  ipi-pon-types:pon_lock_unlock_t;
            default "unlock";
            description "The ONU lock/unlock control. This is identical to the ITU OMCI ONU-G
                        administrative unlock/lock state. The administrative state can be
                        either locked or unlocked. By default it's unlocked";
        } // END of administrative-state definition.

        leaf encryption  {
            if-feature feature-list:NOT_HAVE_TIBIT;
            type  ipi-pon-types:pon_gem_encryption_t;
            default "off";
            description "The on or off state of PON communication encryption per ONU for
                        non-Tibit OLT. By default encryption is off";
        } // END of encryption definition.

        leaf us-fec  {
            if-feature feature-list:NOT_HAVE_TIBIT;
            type  ipi-pon-types:pon_fec_t;
            default "on";
            description "The on or off state of PON upstream FEC per ONU for non-Tibit OLT.
                        Default value is on";
        } // END of us-fec definition.

    } // END of onu-global-config definition.
    grouping onu-registry-base-config {
        description
            "Grouping for ONU registry base configuration";
        leaf olt-id  {
            when " /pon/pon-instance/onu-management/onus/onu/onu-registry/config/pon-port-name  and /pon/pon-instance/onu-management/onus/onu/onu-registry/config/serial-number ";
            type  uint32 {
                 range "0..65535"  {
                    description "0..65535:Feature : HAVE_TIBIT Supported range 0 - 63Not Feature :
                            HAVE_TIBIT  Supported range 0 - 65535";
                 }
            }
            description "This is the logical OLT identity in the system. The OLT identity in
                        Tibit is 0 to 63 while the identity in other system is from 0 to 65535";
        } // END of olt-id definition.

        leaf pon-port-name  {
            when " /pon/pon-instance/onu-management/onus/onu/onu-registry/config/olt-id  and /pon/pon-instance/onu-management/onus/onu/onu-registry/config/serial-number ";
            type  string {
                length "4..64";
                pattern "[^?' =,>|]+";
            }
            description "PON port name starting with 'pon' on which ONU will be presented";
        } // END of pon-port-name definition.

        leaf serial-number  {
            when " /pon/pon-instance/onu-management/onus/onu/onu-registry/config/olt-id  and /pon/pon-instance/onu-management/onus/onu/onu-registry/config/pon-port-name ";
            type  string {
                length "1..64";
                pattern "[^?' =,>|]+";
            }
            description "ONU serial number which can be full hexadecimal string or staring with
                        manufacturer alphabet ID";
        } // END of serial-number definition.

        leaf onu-profile-name  {
            type  string {
                length "1..64";
                pattern "[^?' =,>|]+";
            }
            mandatory true;
            description "The ONU profile be applied to the ONU configuration. The predefined
                        default_onu_profile is provided";
        } // END of onu-profile-name definition.

    } // END of onu-registry-base-config definition.
    grouping onu-registry-applied-profile-name {
        description
            "Grouping for applied ONU profile name";
        leaf operational-onu-profile-name  {
            type  ipi-pon-types:pon_info_string_t {
                length "1..1965";
            }
            config false;
            description "Indicate the ONU profile name which is applied to the ONU currently";
        } // END of operational-onu-profile-name definition.

    } // END of onu-registry-applied-profile-name definition.
    grouping uni-port-id-config {
        description
            "Grouping for ONU UNI identity configuration";
        leaf uni-port-id  {
            type  uint32 {
                 range "0..255"  {
                    description "0..255: Supported range 0 - 255";
                 }
            }
            description "This is the UNI port ID in the ONU. The ID can be between 0 and 255
                        depending on the ONU UNI capability";
        } // END of uni-port-id definition.

    } // END of uni-port-id-config definition.
    grouping uni-operation-config {
        description
            "Grouping for ONU UNI operation configuration";
        leaf administrative-state  {
            type  ipi-pon-types:pon_lock_unlock_t;
            default "lock";
            description "Control UNI port to be locked or unlocked. The value can be either
                        lock or unlock.By default, the UNI port state is 'lock'";
        } // END of administrative-state definition.

        leaf mtu  {
            type  uint16 {
                 range "576..8986"  {
                    description "576..8986: Supported range 576 - 8986";
                 }
            }
            default "1518";
            description "The size of maximum transmission unit for the UNI port. The size range
                        is between 576 and 8986. Default size is 1518";
        } // END of mtu definition.

        leaf dhcp  {
            type  ipi-pon-types:pon_dhcp_on_off_t;
            default "on";
            description "The on or off state for DHCP relay function on UNI port. By default
                        the relay is on";
        } // END of dhcp definition.

        leaf trust  {
            type  ipi-pon-types:pon_trust_on_off_t;
            default "off";
            description "The on or off state for trusting UNI port. By default the state is off";
        } // END of trust definition.

    } // END of uni-operation-config definition.
    grouping onu-rogue-detect-config {
        description
            "Grouping for rogue ONU detection configuration";
        leaf-list pon-port-name  {
            type  ipi-pon-types:pon_info_string_t {
                length "4..64";
            }
            description "The PON port name to enable the rogue ONU detection. The port name
                        should start with 'pon'";
        } // END of pon-port-name definition.

    } // END of onu-rogue-detect-config definition.
    grouping onu-mib-audit-config {
        description
            "Grouping for ONU MIB Audit configuration";
        leaf audit-on-off  {
            type  ipi-pon-types:pon_onu_mib_audit_on_off_t;
            default "on";
            description "Enable/Disable ONU MIB Audit mechanism";
        } // END of audit-on-off definition.

        leaf audit-interval  {
            type  uint32 {
                 range "1..1000000"  {
                    description "1..1000000: Supported range 1 - 1000000";
                 }
            }
            units "seconds";
            default "300";
            description "Set ONU MIB Audit interval";
        } // END of audit-interval definition.

    } // END of onu-mib-audit-config definition.
    grouping uni-ports-config {
        description
            "Grouping for ONU UNI ports configuration";
        container uni-ports {
            description
                "ONU UNI port list";

            list uni-port {
                key "uni-port-id";
                description
                    "ONU UNI port";
                leaf uni-port-id  {
                    type  leafref {
                        path  "../config/uni-port-id";
                    }
                    description "This is the UNI port ID in the ONU. The ID can be between 0 and 255
                                depending on the ONU UNI capability";
                } // END of uni-port-id definition.

                container config {
                    description
                        "configuration data for ONU UNI configuration";
                    uses uni-operation-config;
                    uses uni-port-id-config;
                } // END of config-container definition.
                container state {
                    config false;
                    description
                        "ONU UNI state";
                    uses uni-operation-config;
                    uses uni-port-id-config;
                } // END of state-container definition.
            } // End of uni-port-list
        } // END of uni-ports-container definition.
    } // END of uni-ports-config definition.
    grouping auto-provisioned-uni-ports-states {
        description
            "Grouping for auto-provisioned ONU UNI ports states";
        container uni-ports {
            config false;
            description
                "ONU UNI port list";

            list uni-port {
                key "uni-port-id";
                config false;
                description
                    "ONU UNI port";
                leaf uni-port-id  {
                    type  leafref {
                        path  "../state/uni-port-id";
                    }
                    description "Indicate UNI port ID on the ONU";
                } // END of uni-port-id definition.

                container state {
                    config false;
                    description
                        "ONU UNI state";
                    uses uni-port-id-config;
                    uses uni-operation-config;
                } // END of state-container definition.
            } // End of uni-port-list
        } // END of uni-ports-container definition.
    } // END of auto-provisioned-uni-ports-states definition.
    grouping onu-global-info {
        description
            "Grouping for the ONU global info";
        leaf operational-status  {
            type  ipi-pon-types:pon_info_string_t {
                length "1..1965";
            }
            description "Indicate ONU operational status";
        } // END of operational-status definition.

        leaf operational-down-reason  {
            type  ipi-pon-types:pon_info_string_t {
                length "1..1965";
            }
            description "Indicate ONU operational down reason";
        } // END of operational-down-reason definition.

        leaf total-uni-ports  {
            type  uint16;
            description "Indicate the total number of UNI ports supported by the ONU";
        } // END of total-uni-ports definition.

        leaf upstream-priority-queues  {
            type  uint16;
            description "Indicate the total number of upstream priority queues supported by the
                        ONU";
        } // END of upstream-priority-queues definition.

        leaf downstream-priority-queues  {
            type  uint16;
            description "Indicate the total number of downstream priority queues supported by
                        the ONU";
        } // END of downstream-priority-queues definition.

        leaf pon-port-rx-power-level  {
            type  decimal64 {
                 fraction-digits 3;            }
            units "dBm";
            description "The receive power level in dBm for the ONU at the PON port";
        } // END of pon-port-rx-power-level definition.

    } // END of onu-global-info definition.
    grouping onu-tcont-mapping-info {
        description
            "Grouping for the ONU T-CONT mapping info";
        leaf alloc-id  {
            type  uint32;
            description "Indicate the T-CONT allocation ID";
        } // END of alloc-id definition.

        leaf tcont-name  {
            type  ipi-pon-types:pon_info_string_t {
                length "1..1965";
            }
            description "Indicate the T-CONT name";
        } // END of tcont-name definition.

        leaf pon-port-name  {
            type  ipi-pon-types:pon_info_string_t {
                length "1..1965";
            }
            description "Indicate the PON port name on which the ONU is presented";
        } // END of pon-port-name definition.

    } // END of onu-tcont-mapping-info definition.
    grouping onu-gem-mapping-info {
        description
            "Grouping for the ONU GEM port mapping info";
        leaf gem-port-id  {
            type  uint32;
            description "Indicate the GEM port ID";
        } // END of gem-port-id definition.

        leaf gem-port-name  {
            type  ipi-pon-types:pon_info_string_t {
                length "1..1965";
            }
            description "Indicate the GEM port name";
        } // END of gem-port-name definition.

        leaf tcont-name  {
            type  ipi-pon-types:pon_info_string_t {
                length "1..1965";
            }
            description "Indicate the T-CONT name";
        } // END of tcont-name definition.

        leaf pon-port-name  {
            type  ipi-pon-types:pon_info_string_t {
                length "1..1965";
            }
            description "Indicate the PON port name on which the ONU is presented";
        } // END of pon-port-name definition.

    } // END of onu-gem-mapping-info definition.
    grouping onu-flow-info {
        description
            "Grouping for the info of the flow owned by the ONU";
        leaf flow-id  {
            type  uint16;
            description "Indicate the flow ID which owned by the ONU";
        } // END of flow-id definition.

        leaf operational-status  {
            type  ipi-pon-types:pon_up_down_status_t;
            description "Indicate the operational status of the flow";
        } // END of operational-status definition.

        leaf operational-down-reason  {
            type  ipi-pon-types:pon_info_string_t {
                length "1..1965";
            }
            description "Indicate the reason when flow is down";
        } // END of operational-down-reason definition.

    } // END of onu-flow-info definition.
    grouping onu-upstream-fec-stats {
        description
            "Grouping for ONU upstream FEC statistics";
        leaf codewords  {
            type  yang:counter64;
            description "Indicate the FEC codewords";
        } // END of codewords definition.

        leaf corrected-bytes  {
            type  yang:counter64;
            description "Indicate the FEC corrected bytes";
        } // END of corrected-bytes definition.

        leaf corrected-codewords  {
            type  yang:counter64;
            description "Indicate the FEC corrected codewords";
        } // END of corrected-codewords definition.

        leaf uncorrectable-codewords  {
            type  yang:counter64;
            description "Indicate the FEC uncorrectable codewords";
        } // END of uncorrectable-codewords definition.

    } // END of onu-upstream-fec-stats definition.
    grouping onu-upstream-encrypt-stats {
        description
            "Grouping for ONU upstream encryption statistics";
        leaf encrypted-bytes  {
            type  yang:counter64;
            description "Indicate the encrypted bytes";
        } // END of encrypted-bytes definition.

        leaf encrypted-packets  {
            type  yang:counter64;
            description "Indicate the encrypted packets";
        } // END of encrypted-packets definition.

        leaf plain-bytes  {
            type  yang:counter64;
            description "Indicate the plain bytes";
        } // END of plain-bytes definition.

        leaf plain-packets  {
            type  yang:counter64;
            description "Indicate the plain packets";
        } // END of plain-packets definition.

    } // END of onu-upstream-encrypt-stats definition.
    grouping onu-tcont-mapping-state {
        description
            "Grouping for T-CONT mapping states";
        container tcont-mapping {
            config false;
            description
                "T-CONT mapping";

            list tcont {
                key "alloc-id tcont-name pon-port-name";
                config false;
                description
                    "T-CONT mapping info";
                leaf alloc-id  {
                    type  leafref {
                        path  "../state/alloc-id";
                    }
                    description "Indicate the T-CONT allocation ID";
                } // END of alloc-id definition.

                leaf tcont-name  {
                    type  leafref {
                        path  "../state/tcont-name";
                    }
                    description "Indicate the T-CONT name";
                } // END of tcont-name definition.

                leaf pon-port-name  {
                    type  leafref {
                        path  "../state/pon-port-name";
                    }
                    description "Indicate the PON port name on which the ONU is presented";
                } // END of pon-port-name definition.

                container state {
                    config false;
                    description
                        "state";
                    uses onu-tcont-mapping-info;
                } // END of state-container definition.
            } // End of tcont-list
        } // END of tcont-mapping-container definition.
    } // END of onu-tcont-mapping-state definition.
    grouping onu-gem-mapping-state {
        description
            "Grouping for GEM mapping states";
        container gem-port-mapping {
            config false;
            description
                "GEM port mapping";

            list gem-port {
                key "gem-port-id gem-port-name tcont-name pon-port-name";
                config false;
                description
                    "GEM mapping state";
                leaf gem-port-id  {
                    type  leafref {
                        path  "../state/gem-port-id";
                    }
                    description "Indicate the GEM port ID";
                } // END of gem-port-id definition.

                leaf gem-port-name  {
                    type  leafref {
                        path  "../state/gem-port-name";
                    }
                    description "Indicate the GEM port name";
                } // END of gem-port-name definition.

                leaf tcont-name  {
                    type  leafref {
                        path  "../state/tcont-name";
                    }
                    description "Indicate the T-CONT name";
                } // END of tcont-name definition.

                leaf pon-port-name  {
                    type  leafref {
                        path  "../state/pon-port-name";
                    }
                    description "Indicate the PON port name on which the ONU is presented";
                } // END of pon-port-name definition.

                container state {
                    config false;
                    description
                        "state";
                    uses onu-gem-mapping-info;
                } // END of state-container definition.
            } // End of gem-port-list
        } // END of gem-port-mapping-container definition.
    } // END of onu-gem-mapping-state definition.
    grouping onu-flow-state {
        description
            "Grouping for flow states owned by the ONU";
        container flow-list {
            config false;
            description
                "Flow list owned by the ONU";

            list flow {
                key "flow-id";
                config false;
                description
                    "Flow state";
                leaf flow-id  {
                    type  leafref {
                        path  "../state/flow-id";
                    }
                    description "Indicate the flow ID which owned by the ONU";
                } // END of flow-id definition.

                container state {
                    config false;
                    description
                        "state";
                    uses onu-flow-info;
                } // END of state-container definition.
            } // End of flow-list
        } // END of flow-list-container definition.
    } // END of onu-flow-state definition.
    grouping onu-transport-state {
        description
            "Grouping for transport info of the ONU";
        container transport-info {
            config false;
            description
                "Transport info of the ONU";
            uses onu-tcont-mapping-state;
            uses onu-gem-mapping-state;
            uses onu-flow-state;
        } // END of transport-info-container definition.
    } // END of onu-transport-state definition.
    grouping onu-counters {
        description
            "Grouping for ONU related statistics";
        container counters {
            config false;
            description
                "ONU related statistics";
            container upstream-fec {
                config false;
                description
                    "Upstream FEC counters";
                uses onu-upstream-fec-stats;
            } // END of upstream-fec-container definition.
            container upstream-encryption {
                if-feature feature-list:HAVE_TIBIT;
                config false;
                description
                    "Aggregated upstream encryption counters on the related PON port";
                uses onu-upstream-encrypt-stats;
            } // END of upstream-encryption-container definition.
        } // END of counters-container definition.
    } // END of onu-counters definition.
    grouping auto-provisioned-onus-states {
        description
            "Grouping for auto-provisioned ONUs";

        list onu {
            key "onu-id";
            config false;
            description
                "auto-provisioned ONU state";
            leaf onu-id  {
                type  leafref {
                    path  "../state/onu-id";
                }
                description "This is the logical ONU identity in the system. The ONU identity is
                            from 0 to 4095";
            } // END of onu-id definition.

            container state {
                config false;
                description
                    "ONU global state";
                uses onu-id-config;
                uses onu-global-config;
                uses onu-global-info;
                uses onu-counters;
            } // END of state-container definition.
            container onu-registry {
                config false;
                description
                    "ONU Registry";
                container state {
                    config false;
                    description
                        "ONU registry state";
                    uses onu-registry-base-config;
                    uses onu-registry-applied-profile-name;
                } // END of state-container definition.
            } // END of onu-registry-container definition.
            uses onu-transport-state;
            uses auto-provisioned-uni-ports-states;
        } // End of onu-list
    } // END of auto-provisioned-onus-states definition.
    grouping onu-config {
        description
            "Grouping for ONU configuration";

        list onu {
            key "onu-id";
            description
                "ONU configuration";
            leaf onu-id  {
                type  leafref {
                    path  "../config/onu-id";
                }
                description "This is the logical ONU identity in the system. The ONU identity is
                            from 0 to 4095";
            } // END of onu-id definition.

            container config {
                description
                    "configuration data for ONU configuration";
                uses onu-id-config;
                uses onu-global-config;
            } // END of config-container definition.
            container state {
                config false;
                description
                    "ONU global state";
                uses onu-id-config;
                uses onu-global-config;
                uses onu-global-info;
                uses onu-counters;
            } // END of state-container definition.
            container onu-registry {
                description
                    "ONU Registry";
                container config {
                    description
                        "ONU registry configuration";
                    uses onu-registry-base-config;
                } // END of config-container definition.
                container state {
                    config false;
                    description
                        "ONU registry state";
                    uses onu-registry-base-config;
                    uses onu-registry-applied-profile-name;
                } // END of state-container definition.
            } // END of onu-registry-container definition.
            uses onu-transport-state;
            uses uni-ports-config;
        } // End of onu-list
    } // END of onu-config definition.
    grouping onu-rogue-detect-all {
        description
            "Grouping for all rogue ONU detection configuration";
        container config {
            description
                "Rogue ONU detection configuration";
            uses onu-rogue-detect-config;
        } // END of config-container definition.
        container state {
            config false;
            description
                "Rogue ONU detection state";
            uses onu-rogue-detect-config;
        } // END of state-container definition.
    } // END of onu-rogue-detect-all definition.
    grouping onu-mib-audit-all {
        description
            "Grouping for all ONU MIB audit configuration";
        container config {
            description
                "ONU MIB audit configuration";
            uses onu-mib-audit-config;
        } // END of config-container definition.
        container state {
            config false;
            description
                "ONU MIB audit state";
            uses onu-mib-audit-config;
        } // END of state-container definition.
    } // END of onu-mib-audit-all definition.
    grouping onu-supported-info {
        description
            "Grouping for supported ONU info";
        leaf type  {
            type  ipi-pon-types:pon_info_string_t {
                length "1..1965";
            }
            description "Indicate the ONU device type";
        } // END of type definition.

        leaf vendor  {
            type  ipi-pon-types:pon_info_string_t {
                length "1..1965";
            }
            description "Indicate the ONU vendor";
        } // END of vendor definition.

        leaf model-number  {
            type  ipi-pon-types:pon_info_string_t {
                length "1..1965";
            }
            description "Indicate the ONU model number";
        } // END of model-number definition.

    } // END of onu-supported-info definition.
    grouping onu-unprovisioned-info {
        description
            "Grouping for ONU unprovisioned info";
        leaf serial-number  {
            type  ipi-pon-types:pon_info_string_t {
                length "1..1965";
            }
            description "Indicate the ONU serial number";
        } // END of serial-number definition.

        leaf olt-id  {
            type  uint32;
            description "Indicate the OLT ID on which the ONU is presented";
        } // END of olt-id definition.

        leaf pon-port-name  {
            type  ipi-pon-types:pon_info_string_t {
                length "1..1965";
            }
            description "Indicate the PON port name on which the ONU is presented";
        } // END of pon-port-name definition.

    } // END of onu-unprovisioned-info definition.
    grouping onu-rogue-suspect-info {
        description
            "Grouping for ONU rogue suspect info";
        leaf serial-number  {
            type  ipi-pon-types:pon_info_string_t {
                length "1..1965";
            }
            description "Indicate the identifiable rogue ONU serial number in the format of
                        hexadecimal-string(verdor).
                        It will show '-' if ONU is unidentified";
        } // END of serial-number definition.

        leaf pon-port-name  {
            type  ipi-pon-types:pon_info_string_t {
                length "1..1965";
            }
            description "Indicate the PON port name on which the ONU rogue is detected";
        } // END of pon-port-name definition.

        leaf detected-counter  {
            type  uint32;
            description "Indicate the total number that ONU rogue has been detected on such ONU
                        or PON port";
        } // END of detected-counter definition.

    } // END of onu-rogue-suspect-info definition.
    grouping onu-isolate-info {
        description
            "Grouping for ONU isolation info";
        leaf serial-number  {
            type  ipi-pon-types:pon_info_string_t {
                length "1..1965";
            }
            description "Indicate the ONU with the serial number is or will be isolated";
        } // END of serial-number definition.

        leaf pon-port-name  {
            type  ipi-pon-types:pon_info_string_t {
                length "1..1965";
            }
            description "Indicate the name of PON port from which ONU was or will be isolated.
                        '-' to indicate the ignorance of port name";
        } // END of pon-port-name definition.

    } // END of onu-isolate-info definition.
    grouping onu-supported-state {
        description
            "Grouping for supported ONUs";
        container supported-onu-devices {
            config false;
            description
                "Supported ONU devices";

            list device {
                key "type vendor model-number";
                config false;
                description
                    "Supported ONU device";
                leaf type  {
                    type  leafref {
                        path  "../state/type";
                    }
                    description "Indicate the ONU device type";
                } // END of type definition.

                leaf vendor  {
                    type  leafref {
                        path  "../state/vendor";
                    }
                    description "Indicate the ONU vendor";
                } // END of vendor definition.

                leaf model-number  {
                    type  leafref {
                        path  "../state/model-number";
                    }
                    description "Indicate the ONU model number";
                } // END of model-number definition.

                container state {
                    config false;
                    description
                        "state";
                    uses onu-supported-info;
                } // END of state-container definition.
            } // End of device-list
        } // END of supported-onu-devices-container definition.
    } // END of onu-supported-state definition.
    grouping onu-unprovisioned-state {
        description
            "Grouping for unprovisioned ONUs";
        container unprovisioned-onus {
            config false;
            description
                "Unprovisioned ONUs";

            list onu {
                key "serial-number olt-id pon-port-name";
                config false;
                description
                    "Unprovisioned ONU";
                leaf serial-number  {
                    type  leafref {
                        path  "../state/serial-number";
                    }
                    description "Indicate the ONU serial number";
                } // END of serial-number definition.

                leaf olt-id  {
                    type  leafref {
                        path  "../state/olt-id";
                    }
                    description "Indicate the OLT ID on which the ONU is presented";
                } // END of olt-id definition.

                leaf pon-port-name  {
                    type  leafref {
                        path  "../state/pon-port-name";
                    }
                    description "Indicate the PON port name on which the ONU is presented";
                } // END of pon-port-name definition.

                container state {
                    config false;
                    description
                        "state";
                    uses onu-unprovisioned-info;
                } // END of state-container definition.
            } // End of onu-list
        } // END of unprovisioned-onus-container definition.
    } // END of onu-unprovisioned-state definition.
    grouping onu-rogue-suspect-state {
        description
            "Grouping for rogue suspected ONUs";
        container rogue-suspects {
            config false;
            description
                "ONU rogue suspects";

            list suspect {
                key "serial-number pon-port-name detected-counter";
                config false;
                description
                    "Rogue suspect";
                leaf serial-number  {
                    type  leafref {
                        path  "../state/serial-number";
                    }
                    description "Indicate the rogue suspected ONU serial number. It will show - if ONU
                                is unidentified";
                } // END of serial-number definition.

                leaf pon-port-name  {
                    type  leafref {
                        path  "../state/pon-port-name";
                    }
                    description "Indicate the PON port name on which the ONU rogue is detected";
                } // END of pon-port-name definition.

                leaf detected-counter  {
                    type  leafref {
                        path  "../state/detected-counter";
                    }
                    description "Indicate the number that ONU rogue has been detected";
                } // END of detected-counter definition.

                container state {
                    config false;
                    description
                        "state";
                    uses onu-rogue-suspect-info;
                } // END of state-container definition.
            } // End of suspect-list
        } // END of rogue-suspects-container definition.
    } // END of onu-rogue-suspect-state definition.
    grouping onu-isolate-state {
        description
            "Grouping for isolated ONUs";
        container isolated-onus {
            config false;
            description
                "Isolated ONUs";

            list onu {
                key "serial-number pon-port-name";
                config false;
                description
                    "Isolated ONU";
                leaf serial-number  {
                    type  leafref {
                        path  "../state/serial-number";
                    }
                    description "Indicate the ONU with the serial number is or will be isolated";
                } // END of serial-number definition.

                leaf pon-port-name  {
                    type  leafref {
                        path  "../state/pon-port-name";
                    }
                    description "Indicate the name of PON port from which ONU was or will be isolated";
                } // END of pon-port-name definition.

                container state {
                    config false;
                    description
                        "state";
                    uses onu-isolate-info;
                } // END of state-container definition.
            } // End of onu-list
        } // END of isolated-onus-container definition.
    } // END of onu-isolate-state definition.

    grouping  onu-management-grouping {
    description
        "ONU management";
    container onu-management {
        if-feature feature-list:HAVE_POND;
        description
            "ONU management";
        container onu-rogue-detection-ports {
            description
                "ONU rogue detection port";
            uses onu-rogue-detect-all;
        } // END of onu-rogue-detection-ports-container definition.
        container onu-mib-audit {
            description
                "ONU MIB audit";
            uses onu-mib-audit-all;
        } // END of onu-mib-audit-container definition.
        container onus {
            description
                "All ONU configuration";
            uses onu-config;
        } // END of onus-container definition.
        container auto-provisioned-onus {
            config false;
            description
                "Auto-provisioned ONUs can have same states in onus";
            uses auto-provisioned-onus-states;
        } // END of auto-provisioned-onus-container definition.
        uses onu-supported-state;
        uses onu-unprovisioned-state;
        uses onu-rogue-suspect-state;
        uses onu-isolate-state;
    } // END of onu-management-container definition.
    } // END of onu-management-grouping definition.


}
