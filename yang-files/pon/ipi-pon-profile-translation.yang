/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-pon-profile-translation.yang
*
*/

submodule ipi-pon-profile-translation {

    yang-version 1.1;

    belongs-to  ipi-pon { prefix ipi-pon; }

    import feature-list {
        prefix feature-list;
        revision-date 2023-02-21;
    }

    import ipi-pon-types {
        prefix ipi-pon-types;
        revision-date 2022-06-01;
    }

    organization
        "IP Infusion Inc.";

    contact
        "Address: 3965 Freedom Circle, Suite 200, Santa Clara, CA 95054
         Phone: +1 408-400-1900
         E-mail: support@ipinfusion.com
         Web: http://www.ipinfusion.com/";

    description
        "This module defines a data model for translationprofile configuration
                for passive optical network";


    revision "2022-06-01" {
        description "Updated the yang file with feature";
        reference " 0.4.0.";
    }

    revision "2021-09-03" {
        description "Update descriptions of attribute";
        reference " 0.3.0.";
    }

    revision "2021-02-15" {
        description "Added support for state container corresponding to config containers";
        reference " 0.2.0.";
    }

    revision "2020-11-13" {
        description "Initial Version";
        reference "Initial Version";
    }

    grouping translation-profile-name-config {
        description
            "Grouping for translation profile name";
        leaf profile-name  {
            type  string {
                length "1..64";
                pattern "[^?' =,>|]+";
            }
            description "The attribute is to have unique translation profile name";
        } // END of profile-name definition.

    } // END of translation-profile-name-config definition.
    grouping translation-profile-ready-state {
        description
            "Grouping for translation profile ready state";
        leaf ready-status  {
            type  ipi-pon-types:pon_ready_status_t;
            description "The attribute is to show profile ready status";
        } // END of ready-status definition.

    } // END of translation-profile-ready-state definition.
    grouping tp-input-mode-config {
        description
            "Grouping for translation profile input mode";
        leaf instance-id  {
            type  ipi-pon-types:pon_tp_input_instance_t;
            mandatory true;
            description "It's to have TP input mode switch command for command terminal.
                        Netconf will simply set the value as classification";
        } // END of instance-id definition.

    } // END of tp-input-mode-config definition.
    grouping tp-input-tagged-config {
        description
            "Grouping for tagged VLAN of input translation profile configuration";
        leaf tagged-vlan  {
            type  ipi-pon-types:pon_input_vlan_tagged_t;
            description "It has VLAN tagged.";
        } // END of tagged-vlan definition.

        leaf input-vlan-id  {
            type  uint32 {
                 range "2..4094"  {
                    description "2..4094: Supported range 2 - 4094";
                 }
            }
            description "The translation input VLAN ID is from 2 to 4094";
        } // END of input-vlan-id definition.

        leaf p-bits  {
            type  uint8 {
                 range "0..7"  {
                    description "0..7: Supported range 0 - 7";
                 }
            }
            description "3-bit IEEE 802.1p class of service";
        } // END of p-bits definition.

    } // END of tp-input-tagged-config definition.
    grouping tp-input-priority-tagged-config {
        description
            "Grouping for priority tagged VLAN of input translation profile
                        configuration";
        leaf priority-tagged-vlan  {
            type  ipi-pon-types:pon_input_vlan_ptagged_t;
            description "It has priority tagged VLAN.";
        } // END of priority-tagged-vlan definition.

        leaf p-bits  {
            type  uint8 {
                 range "0..7"  {
                    description "0..7: Supported range 0 - 7";
                 }
            }
            description "3-bit IEEE 802.1p class of service";
        } // END of p-bits definition.

    } // END of tp-input-priority-tagged-config definition.
    grouping tp-input-untagged-config {
        description
            "Grouping for untagged input translation profile configuration";
        leaf untagged-vlan  {
            type  ipi-pon-types:pon_input_vlan_untagged_t;
            description "It has no VLAN tagged.";
        } // END of untagged-vlan definition.

    } // END of tp-input-untagged-config definition.
    grouping tp-input-config-instance {
        description
            "Grouping for input translation profile instance";
        container instance {
            presence "Instance";
            description
                "Input translation instance";
            container config {
                presence "Instance";
                description
                    "Input translation instance configuration";
                uses tp-input-mode-config;
            } // END of config-container definition.
            container state {
                config false;
                description
                    "Input translation instance state";
                uses tp-input-mode-config;
            } // END of state-container definition.
        } // END of instance-container definition.
    } // END of tp-input-config-instance definition.
    grouping tp-input-config-all {
        description
            "Grouping for input translation profile configuration";
        choice detail {
            description
                "Input translation profile detail";
            case tagged-input {

                description
                    "Tagged input translation profile";


                list tagged {
                    key "tagged-vlan input-vlan-id p-bits";
                    max-elements 1;
                    description
                        "Tagged VLAN for input of translation profile configuration";
                    leaf tagged-vlan  {
                        type  leafref {
                            path  "../config/tagged-vlan";
                        }
                        description "It has VLAN tagged.";
                    } // END of tagged-vlan definition.

                    leaf input-vlan-id  {
                        type  leafref {
                            path  "../config/input-vlan-id";
                        }
                        description "The translation input VLAN ID is from 2 to 4094";
                    } // END of input-vlan-id definition.

                    leaf p-bits  {
                        type  leafref {
                            path  "../config/p-bits";
                        }
                        description "3-bit IEEE 802.1p class of service";
                    } // END of p-bits definition.

                    container config {
                        description
                            "Tagged VLAN for input of translation profile configuration";
                        uses tp-input-tagged-config;
                    } // END of config-container definition.
                    container state {
                        config false;
                        description
                            "Tagged VLAN state for input of translation profile";
                        uses tp-input-tagged-config;
                    } // END of state-container definition.
                } // End of tagged-list
            }
            case priority-tagged-input {

                description
                    "Priority tagged input translation profile";


                list priority-tagged {
                    key "priority-tagged-vlan p-bits";
                    max-elements 1;
                    description
                        "Priority tagged VLAN for input of translation profile";
                    leaf priority-tagged-vlan  {
                        type  leafref {
                            path  "../config/priority-tagged-vlan";
                        }
                        description "It has priority tagged VLAN.";
                    } // END of priority-tagged-vlan definition.

                    leaf p-bits  {
                        type  leafref {
                            path  "../config/p-bits";
                        }
                        description "3-bit IEEE 802.1p class of service";
                    } // END of p-bits definition.

                    container config {
                        description
                            "Priority tagged VLAN for input of translation profile configuration";
                        uses tp-input-priority-tagged-config;
                    } // END of config-container definition.
                    container state {
                        config false;
                        description
                            "Priority tagged VLAN state for input of translation profile";
                        uses tp-input-priority-tagged-config;
                    } // END of state-container definition.
                } // End of priority-tagged-list
            }
            case untagged-input {

                description
                    "Untagged input translation profile";


                list untagged {
                    key "untagged-vlan";
                    max-elements 1;
                    description
                        "Untagged VLAN for input of translation profile";
                    leaf untagged-vlan  {
                        type  leafref {
                            path  "../config/untagged-vlan";
                        }
                        description "It has no VLAN tagged.";
                    } // END of untagged-vlan definition.

                    container config {
                        description
                            "Untagged VLAN for input of translation profile configuration";
                        uses tp-input-untagged-config;
                    } // END of config-container definition.
                    container state {
                        config false;
                        description
                            "Untagged tagged VLAN state for input of translation profile";
                        uses tp-input-untagged-config;
                    } // END of state-container definition.
                } // End of untagged-list
            }
        } // END of detail-choice definition.
    } // END of tp-input-config-all definition.
    grouping tp-output-mode-config {
        description
            "Grouping for translation profile output mode";
        leaf instance-id  {
            type  ipi-pon-types:pon_tp_output_instance_t;
            mandatory true;
            description "It's to have TP output mode switch command for command terminal.
                        Netconf will simply set the value as treatment";
        } // END of instance-id definition.

    } // END of tp-output-mode-config definition.
    grouping tp-output-config {
        description
            "Grouping for output translation profile configuration";
        leaf p-bits  {
            type  uint8 {
                 range "0..7"  {
                    description "0..7: Supported range 0 - 7";
                 }
            }
            description "3-bit IEEE 802.1p class of service";
        } // END of p-bits definition.

        leaf action  {
            type  ipi-pon-types:pon_service_operation_t;
            description "Either untouch the VLAN or remove the VLAN";
        } // END of action definition.

    } // END of tp-output-config definition.
    grouping tp-output-config-instance {
        description
            "Grouping for output translation profile instance";
        container instance {
            presence "Instance";
            description
                "Output translation instance";
            container config {
                presence "Instance";
                description
                    "Output translation instance configuration";
                uses tp-output-mode-config;
            } // END of config-container definition.
            container state {
                config false;
                description
                    "Output translation instance state";
                uses tp-output-mode-config;
            } // END of state-container definition.
        } // END of instance-container definition.
    } // END of tp-output-config-instance definition.
    grouping tp-output-config-all {
        description
            "Grouping for output translation profile configuration";

        list vlan-operation {
        when " /pon/pon-instance/profiles/translation-profiles/translation-profile/tp-input/tagged/config/tagged-vlan  or /pon/pon-instance/profiles/translation-profiles/translation-profile/tp-input/priority-tagged/config/priority-tagged-vlan  or /pon/pon-instance/profiles/translation-profiles/translation-profile/tp-input/untagged/config/untagged-vlan ";
            key "p-bits action";
            max-elements 1;
            description
                "VLAN operation for output of translation profile";
            leaf p-bits  {
                type  leafref {
                    path  "../config/p-bits";
                }
                description "3-bit IEEE 802.1p class of service";
            } // END of p-bits definition.

            leaf action  {
                type  leafref {
                    path  "../config/action";
                }
                description "Either untouch the VLAN or remove the VLAN";
            } // END of action definition.

            container config {
                description
                    "VLAN operation for output of translation profile configuration";
                uses tp-output-config;
            } // END of config-container definition.
            container state {
                config false;
                description
                    "VLAN operation state for output of translation profil";
                uses tp-output-config;
            } // END of state-container definition.
        } // End of vlan-operation-list
    } // END of tp-output-config-all definition.
    grouping translation-default-profile-state {
        description
            "Grouping for translation default profile state";
        container default-profile {
            config false;
            description
                "translation default profile";
            container state {
                config false;
                description
                    "translation default profile state";
                uses translation-profile-name-config;
                uses translation-profile-ready-state;
            } // END of state-container definition.
            container tp-input {
                config false;
                description
                    "Translation input profile";
                container tagged {
                    config false;
                    description
                        "Tagged VLAN for translation input profile";
                    container state {
                        config false;
                        description
                            "Classification state";
                        uses tp-input-tagged-config;
                    } // END of state-container definition.
                } // END of tagged-container definition.
                container priority-tagged {
                    config false;
                    description
                        "Priority Tagged VLAN for translation input profile";
                    container state {
                        config false;
                        description
                            "Classification state";
                        uses tp-input-priority-tagged-config;
                    } // END of state-container definition.
                } // END of priority-tagged-container definition.
                container untagged {
                    config false;
                    description
                        "Untagged VLAN for translation input profile";
                    container state {
                        config false;
                        description
                            "Classification state";
                        uses tp-input-untagged-config;
                    } // END of state-container definition.
                } // END of untagged-container definition.
            } // END of tp-input-container definition.
            container tp-output {
                config false;
                description
                    "Translation output profile";
                container vlan-operation {
                    config false;
                    description
                        "VLAN operation for output of translation profile";
                    container state {
                        config false;
                        description
                            "Treatment state";
                        uses tp-output-config;
                    } // END of state-container definition.
                } // END of vlan-operation-container definition.
            } // END of tp-output-container definition.
        } // END of default-profile-container definition.
    } // END of translation-default-profile-state definition.

    grouping  translation-profiles-grouping {
    description
        "Translation profiles";
    container translation-profiles {
        if-feature feature-list:HAVE_POND;
        description
            "Translation profiles";

        list translation-profile {
            key "profile-name";
            description
                "Translation profile";
            leaf profile-name  {
                type  leafref {
                    path  "../config/profile-name";
                }
                description "The attribute is to have unique translation profile name";
            } // END of profile-name definition.

            container config {
                description
                    "Translation profile name configuration";
                uses translation-profile-name-config;
            } // END of config-container definition.
            container state {
                config false;
                description
                    "Translation profile state";
                uses translation-profile-name-config;
                uses translation-profile-ready-state;
            } // END of state-container definition.
            container tp-input {
                description
                    "Translation input profile";
                uses tp-input-config-instance;
                uses tp-input-config-all;
            } // END of tp-input-container definition.
            container tp-output {
                description
                    "Output translation profile";
                uses tp-output-config-instance;
                uses tp-output-config-all;
            } // END of tp-output-container definition.
        } // End of translation-profile-list
        uses translation-default-profile-state;
    } // END of translation-profiles-container definition.
    } // END of translation-profiles-grouping definition.


}
