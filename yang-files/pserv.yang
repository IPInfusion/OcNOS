/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : pserv.yang
*
*/

submodule pserv {

    belongs-to  ZebOS { prefix ZebOS; }


    import cml_data_types {
        prefix cml_data_types;
    }

    import feature_list {
        prefix feature_list;
    }

    description
        "pserv configurations";


    revision "2016-12-27" {
        description "Added snmp oid and documentation tag.";
    }

    revision "2016-10-28" {
        description "Initial version of PSERV datamodel.";
    }


    grouping  pservd-grouping {
    container pservd {
                config true;

        description
            "pservd";

        leaf featuresoftware_watchdog  {
            if-feature feature_list:HAVE_PSERVD;
            type  cml_data_types:CML_BOOL_T;  
            description "feature software-watchdog";
        } // END of featuresoftware_watchdog definition.

        leaf keepalivetime  {
            if-feature feature_list:HAVE_PSERVD;
            type  cml_data_types:CML_UINT32_T {
                 range "30..1800";
            }
            description "software-watchdog keep-alive-time";
        } // END of keepalivetime definition.


        list watchdog {
             
            description
                "watchdog";

            config true;
            key "enablesoftware_watchdog";

            
            leaf enablesoftware_watchdog  {
                type  cml_data_types:CML_STRING_T {
                    length "0..255";
                }
                description "software-watchdog";
            } // END of enablesoftware_watchdog definition.

            leaf pservglobals  {
                type  cml_data_types:CML_STRING_T {
                    length "0..255";
                }
                config false;
                description "protocol status";
            } // END of pservglobals definition.

        } // End of watchdog-list
    } // END of pservd-container definition.
    } // END of pservd-container definition.


}
