/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-sbfd-types.yang
*
*/

module ipi-sbfd-types {

    yang-version 1.1;

    namespace   "http://www.ipinfusion.com/yang/ocnos/ipi-sbfd-types";

    prefix "ipi-sbfd-types";

    organization
        "IP Infusion Inc.";

    contact
        "Address: 3965 Freedom Circle, Suite 200, Santa Clara, CA 95054
         Phone: +1 408-400-1900
         E-mail: support@ipinfusion.com
         Web: http://www.ipinfusion.com/";

    description
        "seamless bfd data types";


    revision "2022-06-01" {
        description "Updated the yang file with feature";
        reference " 0.2.0.";
    }

    revision "2022-03-23" {
        description "Initital Version";
        reference " 0.1.0.";
    }



    typedef  sbfd_sr_type_t {
        type enumeration {
            enum sr {
                value 3;
                description "SR type LSP";
            }
        }
        description "type definition for SBFD_SR_TYPE_T";
    }

}
