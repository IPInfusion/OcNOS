/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-port-mirror.yang
*
*/

module ipi-port-mirror {

    yang-version 1.1;

    namespace   "http://www.ipinfusion.com/yang/ocnos/ipi-port-mirror";

    prefix "ipi-port-mirror";

    import ietf-inet-types {
        prefix inet;
        revision-date 2013-07-15;
    }

    import ietf-yang-types {
        prefix yang;
        revision-date 2013-07-15;
    }

    import cml-data-types {
        prefix cml-data-types;
        revision-date 2022-09-30;
    }

    import ipi-port-mirror-types {
        prefix ipi-port-mirror-types;
        revision-date 2022-06-01;
    }

    import ipi-interface {
        prefix ipi-interface;
        revision-date 2022-08-24;
    }

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "This module provides Port Mirroring configuration";


    revision "2022-07-20" {
        description "Added utils function port_monitor_filter_convert_known_frame_type";
        reference " 0.6.0.";
    }

    revision "2022-06-27" {
        description "Updated when expressions in yang file";
        reference " 0.5.0.";
    }

    revision "2022-06-01" {
        description "Updated the yang file with feature";
        reference " 0.4.0.";
    }

    revision "2022-01-13" {
        description "Modified sub module";
        reference " 0.3.0.";
    }

    revision "2021-11-16" {
        description "Module restructuring";
        reference " 0.2.0.";
    }

    revision "2018-06-21" {
        description "Initial Version";
        reference " 0.1.0.";
    }

    grouping pmirror-interface-config {
        description
            "Port mirror interface configuration";
        leaf name  {
            type  leafref {
                path  "/ipi-interface:interfaces/ipi-interface:interface/ipi-interface:name";
            }
            description "Use this attribute to specify the interface name that will be used for
                        receive mirror packets.";
        } // END of name definition.

        leaf source-interface-name  {
            type  leafref {
                path  "/ipi-interface:interfaces/ipi-interface:interface/ipi-interface:name";
            }
            description "Use this attribute to specify the source interface name in port
                        mirror.";
        } // END of source-interface-name definition.

        leaf direction  {
            type  ipi-port-mirror-types:pmirror_alt_dir_t;
            mandatory true;
            description "Use this attribute to specify the direction in interface port mirror.";
        } // END of direction definition.

    } // END of pmirror-interface-config definition.
    grouping pmirror-interface-top {
        description
            "Port mirror interface top level configuration";
        container interfaces {
            description
                "Port mirror interfaces configuration";

            list interface {
                if-feature feature-list:NOT_HAVE_ADVANCE_MIRROR;
                key "name source-interface-name";
                description
                    "Port mirror interface list";
                leaf name  {
                    type  leafref {
                        path  "../config/name";
                    }
                    description "Use this attribute  to specify the interface name that will be used
                                for receive mirror packets.";
                } // END of name definition.

                leaf source-interface-name  {
                    type  leafref {
                        path  "../config/source-interface-name";
                    }
                    description "Use this attribute to specify the source interface name in port
                                mirror.";
                } // END of source-interface-name definition.

                container config {
                    presence "yes";
                    description
                        "Configuration data for port mirror interface";
                    uses pmirror-interface-config;
                } // END of config-container definition.
                container state {
                    config false;
                    description
                        "Operational state data for port mirror interface";
                    uses pmirror-interface-config;
                } // END of state-container definition.
            } // End of interface-list
        } // END of interfaces-container definition.
    } // END of pmirror-interface-top definition.
    grouping pmirror-filters-dst-mac-config {
        description
            "Port mirror filter destination MAC configuration";
        choice destination-mac-options {
            description
                "destination-mac-options";
            case host-mac {

                description
                    "host-mac";

                leaf destination-mac-address-host  {
                    type  ipi-port-mirror-types:pmirror_mac_addr_t {
                        length "1..1965";
                    }
                    description "Use this attribute to set host destination MAC address.";
                } // END of destination-mac-address-host definition.

            }
            case mac-with-mask {

                description
                    "mac-with-mask";

                leaf destination-mac-address  {
                    when " ../destination-mac-mask ";
                    type  ipi-port-mirror-types:pmirror_mac_addr_t {
                        length "1..1965";
                    }
                    description "Use this attribute to set destination MAC address.";
                } // END of destination-mac-address definition.

                leaf destination-mac-mask  {
                    when " ../destination-mac-address ";
                    type  ipi-port-mirror-types:pmirror_mac_addr_t {
                        length "1..1965";
                    }
                    description "Use this attribute to set destination MAC mask address.";
                } // END of destination-mac-mask definition.

            }
        } // END of destination-mac-options-choice definition.
    } // END of pmirror-filters-dst-mac-config definition.
    grouping pmirror-filters-src-mac-config {
        description
            "Port mirror filter source MAC configuration";
        choice source-mac-options {
            description
                "source-mac-options";
            case host-mac {

                description
                    "host-mac";

                leaf source-mac-address-host  {
                    type  ipi-port-mirror-types:pmirror_mac_addr_t {
                        length "1..1965";
                    }
                    description "Use this attribute to set host source MAC address.";
                } // END of source-mac-address-host definition.

            }
            case mac-with-mask {

                description
                    "mac-with-mask";

                leaf source-mac-address  {
                    when " ../source-mac-mask ";
                    type  ipi-port-mirror-types:pmirror_mac_addr_t {
                        length "1..1965";
                    }
                    description "Use this attribute to set source MAC address.";
                } // END of source-mac-address definition.

                leaf source-mac-mask  {
                    when " ../source-mac-address ";
                    type  ipi-port-mirror-types:pmirror_mac_addr_t {
                        length "1..1965";
                    }
                    description "Use this attribute to set source MAC mask address.";
                } // END of source-mac-mask definition.

            }
        } // END of source-mac-options-choice definition.
    } // END of pmirror-filters-src-mac-config definition.
    grouping pmirror-filters-global-config {
        description
            "Port mirror filter global configuration";
        leaf frame-type  {
            type  ipi-port-mirror-types:pmirror_ethertype_t;
            description "Use this attribute to set ethertype.";
        } // END of frame-type definition.

        leaf arp-type  {
            when " ../frame-type='arp' ";
            type  ipi-port-mirror-types:pmirror_arp_type_t;
            description "Use this attribute to set ARP packet type.";
        } // END of arp-type definition.

        leaf sender-ip-address  {
            when " ../frame-type='arp' ";
            type  inet:ipv4-address;
            description "Use this attribute to set sender IP Address.";
        } // END of sender-ip-address definition.

        leaf target-ip-address  {
            when " ../frame-type='arp' ";
            type  inet:ipv4-address;
            description "Use this attribute to set target IP Address.";
        } // END of target-ip-address definition.

        leaf cos  {
            type  uint8 {
                 range "0..7"  {
                    description "0..7: Supported range 0 - 7";
                 }
            }
            description "Use this attribute to set cos.";
        } // END of cos definition.

        leaf vlan  {
            type  uint16 {
                 range "2..4094"  {
                    description "2..4094: Supported range 2 - 4094";
                 }
            }
            description "Use this attribute to set VLAN.";
        } // END of vlan definition.

        leaf source-ipv4-address  {
            when " ../frame-type='ipv4' ";
            type  cml-data-types:cml_ipv4_addr_or_prefix_t;
            description "Use this attribute to set source IPv4 address.";
        } // END of source-ipv4-address definition.

        leaf destination-ipv4-address  {
            when " ../frame-type='ipv4' ";
            type  cml-data-types:cml_ipv4_addr_or_prefix_t;
            description "Use this attribute to set destination IPv4 address.";
        } // END of destination-ipv4-address definition.

        leaf source-ipv6-address  {
            when " ../frame-type='ipv6' ";
            type  inet:ipv6-prefix;
            description "Use this attribute to set source IPv6 address.";
        } // END of source-ipv6-address definition.

        leaf destination-ipv6-address  {
            when " ../frame-type='ipv6' ";
            type  inet:ipv6-prefix;
            description "Use this attribute to set destination IPv6 address.";
        } // END of destination-ipv6-address definition.

    } // END of pmirror-filters-global-config definition.
    grouping pmirror-filters-global-top {
        description
            "Port mirror filter global top level configuration";
        container filters {
            description
                "Port mirror filters configuration";
            container config {
                description
                    "Configuration data for";
                uses pmirror-filters-dst-mac-config;
                uses pmirror-filters-global-config;
                uses pmirror-filters-src-mac-config;
            } // END of config-container definition.
            container state {
                config false;
                description
                    "Operational state data for";
                uses pmirror-filters-dst-mac-config;
                uses pmirror-filters-global-config;
                uses pmirror-filters-src-mac-config;
            } // END of state-container definition.
        } // END of filters-container definition.
    } // END of pmirror-filters-global-top definition.
    grouping pmirror-filters-config {
        description
            "Port mirror filter configuration";
        leaf seq-id  {
            type  uint32 {
                 range "1..4294967295"  {
                    description "1..4294967295:Feature : HAVE_CUSTOM1_ACL Supported range 1 -
                            268435453Feature : HAVE_CUSTOM2_ACL Supported range 1 - 268435453Not
                            Feature : HAVE_CUSTOM1_ACL,HAVE_CUSTOM2_ACL  Supported range 1 -
                            4294967295";
                 }
            }
            description "The sequence id determines the order in which ACL entries are applied.
                        The sequence id must be unique for each entry in an filter set.";
        } // END of seq-id definition.

    } // END of pmirror-filters-config definition.
    grouping pmirror-filters-top {
        description
            "Port mirror filter top level configuration";
        container session-filters {
            description
                "Port mirror filters configuration";

            list session-filter {
                key "seq-id";
                description
                    "Port mirror filter list";
                leaf seq-id  {
                    type  leafref {
                        path  "../config/seq-id";
                    }
                    description "The sequence id determines the order in which ACL entries are applied.
                                The sequence id must be unique for each entry in an filter set.";
                } // END of seq-id definition.

                container config {
                    // when " ipi-port-mirror:port-mirror/sessions/session/session-filters/session-filter/filters/config  ";
                    description
                        "Configuration data for port mirror filter";
                    uses pmirror-filters-config;
                } // END of config-container definition.
                container state {
                    config false;
                    description
                        "Operational state data for port mirror filter";
                    uses pmirror-filters-config;
                } // END of state-container definition.
                uses pmirror-filters-global-top;
            } // End of session-filter-list
        } // END of session-filters-container definition.
    } // END of pmirror-filters-top definition.
    grouping pmirror-src-itf-config {
        description
            "Port mirror source interface configuration";
        leaf name  {
            type  leafref {
                path  "/ipi-interface:interfaces/ipi-interface:interface/ipi-interface:name";
            }
            description "Source interface name";
        } // END of name definition.

        leaf direction  {
            type  ipi-port-mirror-types:pmirror_dir_t;
            mandatory true;
            description "Source interface direction";
        } // END of direction definition.

    } // END of pmirror-src-itf-config definition.
    grouping pmirror-src-itf-top {
        description
            "Port mirror source interface top level configuration";
        container source-interfaces {
            description
                "Port mirror source interfaces";

            list source-interface {
                key "name";
                description
                    "Port mirror source interface";
                leaf name  {
                    type  leafref {
                        path  "../config/name";
                    }
                    description "Source interface name";
                } // END of name definition.

                container config {
                    presence "yes";
                    description
                        "Configuration data for port mirror source interface";
                    uses pmirror-src-itf-config;
                } // END of config-container definition.
                container state {
                    config false;
                    description
                        "Operational state data for port mirror source interface";
                    uses pmirror-src-itf-config;
                } // END of state-container definition.
            } // End of source-interface-list
        } // END of source-interfaces-container definition.
    } // END of pmirror-src-itf-top definition.
    grouping pmirror-destination-remote-config {
        description
            "Port mirror destination remote configuration";
        leaf vlan-id  {
            type  uint16 {
                 range "2..4094"  {
                    description "2..4094: Supported range 2 - 4094";
                 }
            }
            mandatory true;
            description "Use this attribute to configure port mirror remote vlan-id";
        } // END of vlan-id definition.

        leaf reflector-interface-name  {
            type  leafref {
                path  "/ipi-interface:interfaces/ipi-interface:interface/ipi-interface:name";
            }
            mandatory true;
            description "Use this attribute to configure port mirror remote reflector interface";
        } // END of reflector-interface-name definition.

    } // END of pmirror-destination-remote-config definition.
    grouping pmirror-destination-remote-top {
        description
            "Port mirror destination remote top level configuration";
        container remote {
            when " ../../config/type='remote' ";
            description
                "Port mirror destination remote configuration";
            container config {
                presence "yes";
                description
                    "Configuration data for port-mirror remote";
                uses pmirror-destination-remote-config;
            } // END of config-container definition.
            container state {
                config false;
                description
                    "Operational state data for port-mirror remote";
                uses pmirror-destination-remote-config;
            } // END of state-container definition.
        } // END of remote-container definition.
    } // END of pmirror-destination-remote-top definition.
    grouping pmirror-destination-local-config {
        description
            "Port mirror destination local configuration";
        leaf interface-name  {
            type  leafref {
                path  "/ipi-interface:interfaces/ipi-interface:interface/ipi-interface:name";
            }
            description "Use this attribute to configure port mirror local interface";
        } // END of interface-name definition.

    } // END of pmirror-destination-local-config definition.
    grouping pmirror-destination-local-top {
        description
            "Port mirror destination local top level configuration";
        container local {
            when " ../../config/type='local' ";
            description
                "Port mirror destination local configuration";
            container config {
                description
                    "Configuration data for port mirror local";
                uses pmirror-destination-local-config;
            } // END of config-container definition.
            container state {
                config false;
                description
                    "Operational state data for port mirror local";
                uses pmirror-destination-local-config;
            } // END of state-container definition.
        } // END of local-container definition.
    } // END of pmirror-destination-local-top definition.
    grouping pmirror-destination-top {
        description
            "Port mirror destination top configuration";
        container destination {
            description
                "Port mirror session destination configuration";
            uses pmirror-destination-local-top;
            uses pmirror-destination-remote-top;
        } // END of destination-container definition.
    } // END of pmirror-destination-top definition.
    grouping pmirror-counters {
        description
            "Port mirror counters";
        leaf filter-count  {
            type  yang:counter32;
            description "Port mirror session filter count";
        } // END of filter-count definition.

        leaf tx-source-count  {
            type  yang:counter32;
            description "Port mirror session tx source count";
        } // END of tx-source-count definition.

    } // END of pmirror-counters definition.
    grouping pmirror-config {
        description
            "Port mirror configuration";
        leaf id  {
            type  uint32 {
                 range "1..18"  {
                    description "1..18: Supported range 1 - 18";
                 }
            }
            description "Port mirror session index";
        } // END of id definition.

        leaf type  {
            type  ipi-port-mirror-types:pmirror_sess_type_t;
            mandatory true;
            description "Port mirror session type. The default is local";
        } // END of type definition.

        leaf enabled  {
            type  empty;
            description "Use this attribute to shut/unshut a port-mirror session";
        } // END of enabled definition.

        leaf description  {
            type  cml-data-types:cml_line_t {
                length "1..32";
            }
            description "Use this attribute to add a description to port-mirror session";
        } // END of description definition.

        leaf source-vlan  {
            type  cml-data-types:cml_range_t;
            description "";
        } // END of source-vlan definition.

    } // END of pmirror-config definition.
    grouping pmirror-top {
        description
            "Port mirror top level configuration";
        container sessions {
            description
                "All port-mirror sessions configuration";

            list session {
                if-feature feature-list:HAVE_ADVANCE_MIRROR;
                key "id";
                description
                    "port-mirror session list";
                leaf id  {
                    type  leafref {
                        path  "../config/id";
                    }
                    description "Port mirror session index";
                } // END of id definition.

                container config {
                    description
                        "Configuration data for port-mirror session";
                    uses pmirror-config;
                } // END of config-container definition.
                container state {
                    config false;
                    description
                        "Operational state data for port-mirror session";
                    container counters {
                        config false;
                        description
                            "port-mirror session counters";
                        uses pmirror-counters;
                    } // END of counters-container definition.
                    uses pmirror-config;
                } // END of state-container definition.
                uses pmirror-destination-top;
                uses pmirror-src-itf-top;
                uses pmirror-filters-top;
            } // End of session-list
        } // END of sessions-container definition.
    } // END of pmirror-top definition.

    grouping  port-mirror-grouping {
    description
        "Container for all port-mirror configuration";
    container port-mirror {
        if-feature feature-list:HAVE_L2;
        description
            "Container for all port-mirror configuration";
        uses pmirror-top;
        uses pmirror-interface-top;
    } // END of port-mirror-container definition.
    } // END of port-mirror-grouping definition.

    uses port-mirror-grouping;

}
