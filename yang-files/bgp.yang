/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : bgp.yang
*
*/

submodule bgp {

    belongs-to  ZebOS { prefix ZebOS; }
    include interface;
    include vrf;


    import cml_data_types {
        prefix cml_data_types;
    }

    import feature_list {
        prefix feature_list;
    }


    revision "2016-09-15" {
        description "Revisied on 2016-09-15.";
    }



    grouping bgp-grouping {
        list bgp {
             
            description
                "bgp";

            config true;
            key "bgpAs";

            
            leaf vrId  {
                type  cml_data_types:CML_UINT32_T;  
            } // END of vrId definition.

            leaf bgpAs  {
                type  cml_data_types:CML_UINT32_T {
                     range "1..4294967295";
                }
            } // END of bgpAs definition.

            leaf bgpTableVersion  {
                type  cml_data_types:CML_INT32_T;  
                config false;
            } // END of bgpTableVersion definition.

            leaf ntwkPrefixCount  {
                type  cml_data_types:CML_INT32_T;  
                config false;
            } // END of ntwkPrefixCount definition.

            leaf routerIpAddr  {
                type  cml_data_types:CML_IPV4_ADDR_T;  
            } // END of routerIpAddr definition.

            leaf routerRunIpAddr  {
                type  cml_data_types:CML_STRING_T {
                    length "0..255";
                }
                config false;
            } // END of routerRunIpAddr definition.

            leaf clusterId  {
                type  cml_data_types:CML_CLUSTER_ID_T;  
            } // END of clusterId definition.

            leaf confedId  {
                type  cml_data_types:CML_INT32_T {
                     range "1..65535";
                }
            } // END of confedId definition.

            leaf keepAlive  {
                type  cml_data_types:CML_UINT16_T {
                     range "0..65535";
                }
                default "30";
            } // END of keepAlive definition.

            leaf holdTime  {
                type  cml_data_types:CML_UINT16_T {
                     range "0..65535";
                }
                default "90";
                description "holdtime";
            } // END of holdTime definition.

            leaf localPref  {
                type  cml_data_types:CML_UINT32_T {
                     range "0..4294967295";
                }
                default "100";
            } // END of localPref definition.

            leaf setGshutCapable  {
                type  cml_data_types:CML_BOOL_T;  
            } // END of setGshutCapable definition.

            leaf setGshut  {
                type  cml_data_types:CML_BOOL_T;  
            } // END of setGshut definition.

            leaf gshutLocalPref  {
                type  cml_data_types:CML_UINT32_T {
                     range "0..4294967295";
                }
                default "0";
            } // END of gshutLocalPref definition.

            leaf setInboundRouteFilter  {
                if-feature feature_list:HAVE_VRF;
                type  cml_data_types:CML_BOOL_T;  
            } // END of setInboundRouteFilter definition.

            leaf setLogNbrChanges  {
                type  cml_data_types:CML_BOOL_T;  
            } // END of setLogNbrChanges definition.

            leaf scanInterval  {
                type  cml_data_types:CML_UINT32_T {
                     range "0..60";
                }
                default "60";
            } // END of scanInterval definition.

            leaf distance  {
                type  cml_data_types:CML_UINT8_T {
                     range "1..255";
                }
            } // END of distance definition.

            leaf distanceSrcIp  {
                type  cml_data_types:CML_IPV4_PREFIX_T;  
                description "administrative distance for ip source prefix";
            } // END of distanceSrcIp definition.

            leaf distanceACLName  {
                type  cml_data_types:CML_STRING_T {
                    length "0..255";
                }
                description "administrative distance with access list name";
            } // END of distanceACLName definition.

            leaf setMplsResolution  {
                if-feature feature_list:HAVE_MPLS;
                type  cml_data_types:CML_BOOL_T;  
                description "mpls lsp resolution";
            } // END of setMplsResolution definition.

            leaf restartTime  {
                if-feature feature_list:HAVE_RESTART;
                type  cml_data_types:CML_UINT32_T {
                     range "1..3600";
                }
                default "90";
            } // END of restartTime definition.

            leaf stalepathTime  {
                if-feature feature_list:HAVE_RESTART;
                type  cml_data_types:CML_UINT32_T {
                     range "1..3600";
                }
                default "360";
            } // END of stalepathTime definition.

            leaf deferTime  {
                if-feature feature_list:HAVE_RESTART;
                type  cml_data_types:CML_UINT32_T {
                     range "1..3600";
                }
                default "120";
            } // END of deferTime definition.

            leaf bestpathDontCompareOriginator  {
                type  cml_data_types:CML_BOOL_T;  
            } // END of bestpathDontCompareOriginator definition.

            leaf bestpathTieBreak  {
                type  cml_data_types:CML_BOOL_T;  
            } // END of bestpathTieBreak definition.

            leaf ipv4Unicast  {
                type  cml_data_types:CML_BOOL_T;  
            } // END of ipv4Unicast definition.

            leaf deterministicMed  {
                type  cml_data_types:CML_BOOL_T;  
            } // END of deterministicMed definition.

            leaf compareMed  {
                type  cml_data_types:CML_BOOL_T;  
            } // END of compareMed definition.

            leaf bestpathAspath  {
                type  cml_data_types:CML_BOOL_T;  
                description "bgp bestpath as-path ignore";
            } // END of bestpathAspath definition.

            leaf bestpathCompareConfed  {
                type  cml_data_types:CML_BOOL_T;  
            } // END of bestpathCompareConfed definition.

            leaf bestpathCompareRouterId  {
                type  cml_data_types:CML_BOOL_T;  
            } // END of bestpathCompareRouterId definition.

            leaf enforceFirst  {
                type  cml_data_types:CML_BOOL_T;  
            } // END of enforceFirst definition.

            leaf externalFailover  {
                type  cml_data_types:CML_BOOL_T;  
            } // END of externalFailover definition.

            leaf ebgpMaxPath  {
                type  cml_data_types:CML_INT32_T {
                     range "2..64";
                }
                default "2";
                description "multipath ecmp numbers for ebgp";
            } // END of ebgpMaxPath definition.

            leaf ibgpMaxPath  {
                type  cml_data_types:CML_INT32_T {
                     range "2..64";
                }
                default "2";
                description "multipath ecmp numbers for ibgp";
            } // END of ibgpMaxPath definition.

            leaf bgpShowTypeStr  {
                type  cml_data_types:CML_STRING_T {
                    length "0..255";
                }
                config false;
            } // END of bgpShowTypeStr definition.

            leaf autoSummary  {
                type  cml_data_types:CML_BOOL_T;  
            } // END of autoSummary definition.

            leaf setSyncFlag  {
                type  cml_data_types:CML_BOOL_T;  
            } // END of setSyncFlag definition.

            leaf setNwSyncFlag  {
                type  cml_data_types:CML_BOOL_T;  
            } // END of setNwSyncFlag definition.

            leaf localAsCount  {
                type  cml_data_types:CML_UINT8_T {
                     range "2..64";
                }
                description "bgp as-local-count";
            } // END of localAsCount definition.

            leaf grstSet  {
                if-feature feature_list:HAVE_RESTART;
                type  cml_data_types:CML_BOOL_T;  
            } // END of grstSet definition.

            leaf setClientReflect  {
                type  cml_data_types:CML_BOOL_T;  
            } // END of setClientReflect definition.

            leaf setDampeningFlag  {
                type  cml_data_types:CML_BOOL_T;  
            } // END of setDampeningFlag definition.

            leaf halfLife  {
                type  cml_data_types:CML_UINT32_T {
                     range "1..45";
                }
                default "15";
                description "bgp route dampening reachability half-life time";
            } // END of halfLife definition.

            leaf reusePenalty  {
                type  cml_data_types:CML_UINT32_T {
                     range "1..20000";
                }
            } // END of reusePenalty definition.

            leaf suppressPenalty  {
                type  cml_data_types:CML_UINT32_T {
                     range "1..20000";
                }
            } // END of suppressPenalty definition.

            leaf maxSuppress  {
                type  cml_data_types:CML_UINT32_T {
                     range "1..255";
                }
                description "bgp route dampening to start suppressing a route";
            } // END of maxSuppress definition.

            leaf unreachHalfLife  {
                type  cml_data_types:CML_UINT32_T {
                     range "1..45";
                }
                description "BGP route dampening Un-reachability Half-life time";
            } // END of unreachHalfLife definition.

            leaf dampeningRmapName  {
                type  cml_data_types:CML_STRING_T {
                    length "0..255";
                }
                default "NULL";
            } // END of dampeningRmapName definition.

            leaf rfdMaxPenaltyCeil  {
                type  cml_data_types:CML_INT32_T;  
                default "0";
                config false;
            } // END of rfdMaxPenaltyCeil definition.

            leaf rfdMinPenaltyFloor  {
                type  cml_data_types:CML_INT32_T;  
                default "0";
                config false;
            } // END of rfdMinPenaltyFloor definition.

            leaf dampeningStr  {
                type  cml_data_types:CML_INT32_T;  
                config false;
            } // END of dampeningStr definition.

            leaf rfdCbStr  {
                type  cml_data_types:CML_INT32_T;  
                config false;
            } // END of rfdCbStr definition.

            leaf medType  {
                type  cml_data_types:CML_BGP_MED_TYPE_T;  
            } // END of medType definition.

            leaf medConfedMissingAsWorst  {
                type  cml_data_types:CML_BOOL_T;  
                description "bgp bestpath med confed missing-as-worst";
            } // END of medConfedMissingAsWorst definition.

            leaf medMissingAsWorstConfed  {
                type  cml_data_types:CML_BOOL_T;  
            } // END of medMissingAsWorstConfed definition.

            leaf gracefulReset  {
                type  cml_data_types:CML_BOOL_T;  
            } // END of gracefulReset definition.

            leaf distanceEbgp  {
                type  cml_data_types:CML_UINT8_T {
                     range "1..255";
                }
                default "20";
            } // END of distanceEbgp definition.

            leaf distanceIbgp  {
                type  cml_data_types:CML_UINT8_T {
                     range "1..255";
                }
                default "200";
            } // END of distanceIbgp definition.

            leaf distanceLocal  {
                type  cml_data_types:CML_UINT8_T {
                     range "1..255";
                }
                default "200";
                description "distance bgp";
            } // END of distanceLocal definition.

            leaf multipathRelax  {
                type  cml_data_types:CML_BOOL_T;  
            } // END of multipathRelax definition.

            leaf tableMap  {
                if-feature feature_list:HAVE_BGP_TABLE_MAP;
                type  cml_data_types:CML_STRING_T {
                    length "0..255";
                }
                description "bgp table-map";
            } // END of tableMap definition.

            leaf tableMapFilter  {
                if-feature feature_list:HAVE_BGP_TABLE_MAP;
                type  cml_data_types:CML_BOOL_T;  
                description "bgp table-map filter";
            } // END of tableMapFilter definition.

            leaf additionalPaths  {
                if-feature feature_list:HAVE_BGP_ADD_PATH;
                type  cml_data_types:BGP_ADDITIONAL_PATH_TYPE_T;  
                description "additional paths";
            } // END of additionalPaths definition.

            leaf addPathSelectAll  {
                if-feature feature_list:HAVE_BGP_ADD_PATH;
                type  cml_data_types:CML_BOOL_T;  
                description "select all path";
            } // END of addPathSelectAll definition.

            leaf bestCount  {
                if-feature feature_list:HAVE_BGP_ADD_PATH;
                type  cml_data_types:CML_UINT8_T {
                     range "2..3";
                }
                description "select best path";
            } // END of bestCount definition.


            list bgpConfed {
                 
                description
                    "bgpConfed";

                config true;
                key "peerConfedId";

                
                leaf peerConfedId  {
                    type  cml_data_types:CML_INT32_T {
                         range "1..65535";
                    }
                } // END of peerConfedId definition.

            } // End of bgpConfed-list

            list bgpNetworkList {
                 
                description
                    "bgpNetworkList";

                config true;
                key "localAddr";

                
                leaf localAddr  {
                    type  cml_data_types:CML_STRING_T {
                        length "0..255";
                    }
                } // END of localAddr definition.

                leaf networkRmapName  {
                    type  cml_data_types:CML_STRING_T {
                        length "0..255";
                    }
                } // END of networkRmapName definition.

                leaf backdoor  {
                    type  cml_data_types:CML_BOOL_T;  
                    default false;
                    description "network address with backdoor";
                } // END of backdoor definition.

                leaf ntwkPathCountRoute  {
                    type  cml_data_types:CML_INT32_T;  
                    config false;
                } // END of ntwkPathCountRoute definition.

                leaf noAdvertiseRoute  {
                    type  cml_data_types:CML_STRING_T {
                        length "0..255";
                    }
                    config false;
                } // END of noAdvertiseRoute definition.

                leaf noExportRoute  {
                    type  cml_data_types:CML_STRING_T {
                        length "0..255";
                    }
                    config false;
                } // END of noExportRoute definition.

                leaf localAsRoute  {
                    type  cml_data_types:CML_STRING_T {
                        length "0..255";
                    }
                    config false;
                } // END of localAsRoute definition.

                leaf suppressRoute  {
                    type  cml_data_types:CML_STRING_T {
                        length "0..255";
                    }
                    config false;
                } // END of suppressRoute definition.

                leaf ntwkBestPathCountRoute  {
                    type  cml_data_types:CML_INT32_T;  
                    config false;
                } // END of ntwkBestPathCountRoute definition.

                leaf defIPRoutingTbl  {
                    type  cml_data_types:CML_STRING_T {
                        length "0..255";
                    }
                    config false;
                } // END of defIPRoutingTbl definition.

                leaf advPeerAddrRoute  {
                    type  cml_data_types:CML_STRING_T {
                        length "0..255";
                    }
                    config false;
                } // END of advPeerAddrRoute definition.

                leaf advPeerGroupNameRoute  {
                    type  cml_data_types:CML_STRING_T {
                        length "0..255";
                    }
                    config false;
                } // END of advPeerGroupNameRoute definition.

                leaf advAnyPeer  {
                    type  cml_data_types:CML_STRING_T {
                        length "0..255";
                    }
                    config false;
                } // END of advAnyPeer definition.


                list nextHop {
                     
                    description
                        "nextHop";

                    config false;
                    key "nextHopAddr";

                    
                    leaf nextHopAddr  {
                        type  cml_data_types:CML_STRING_T {
                            length "0..255";
                        }
                    } // END of nextHopAddr definition.

                    uses nextHopRunTimeAttr;
                } // End of nextHop-list
            } // End of bgpNetworkList-list

            list bgpAggregateAddrList {
                 
                description
                    "bgpAggregateAddrList";

                config true;
                key "aggregateAddr";

                
                leaf aggregateAddr  {
                    type  cml_data_types:CML_IPV4_PREFIX_T;  
                    description "aggregate prefix";
                } // END of aggregateAddr definition.

                leaf aggregateAsSet  {
                    mandatory true;
                    type  cml_data_types:CML_BOOL_T;  
                } // END of aggregateAsSet definition.

                leaf aggregateSummOnly  {
                    mandatory true;
                    type  cml_data_types:CML_BOOL_T;  
                    description "aggregate-address summary-only";
                } // END of aggregateSummOnly definition.

            } // End of bgpAggregateAddrList-list

            list bgpRedistList {
                 
                description
                    "bgpRedistList";

                config true;
                key "redistType";

                
                leaf redistType  {
                    type  cml_data_types:CML_BGP_REDISTRIBUTE_TYPE_T;  
                } // END of redistType definition.


                list bgpRmap {
                     
                    description
                        "bgpRmap";

                    config true;
                    key "redistRmapName";

                    
                    leaf redistRmapName  {
                        type  cml_data_types:CML_STRING_T {
                            length "0..255";
                        }
                        description "redistribute route map reference";
                    } // END of redistRmapName definition.

                } // End of bgpRmap-list
            } // End of bgpRedistList-list

            list bgpRedistOspf {
                 
                description
                    "bgpRedistOspf";

                config true;
                key "redistOspf";

                
                leaf redistOspf  {
                    type  cml_data_types:CML_BOOL_T;  
                    description "redistribute with ospf";
                } // END of redistOspf definition.


                list bgpRmap {
                     
                    description
                        "bgpRmap";

                    config true;
                    key "redistRmapName";

                    
                    leaf redistRmapName  {
                        type  cml_data_types:CML_STRING_T {
                            length "0..255";
                        }
                        description "redistribute with route map reference";
                    } // END of redistRmapName definition.

                } // End of bgpRmap-list
            } // End of bgpRedistOspf-list

            list bgpRedistOspfNo {
                 
                description
                    "bgpRedistOspfNo";

                config true;
                key "redistOspfNo";

                
                leaf redistOspfNo  {
                    type  cml_data_types:CML_UINT32_T {
                         range "0..65535";
                    }
                    description "redistribute with ospf proc Id";
                } // END of redistOspfNo definition.


                list bgpRmap {
                     
                    description
                        "bgpRmap";

                    config true;
                    key "redistOspfRmap";

                    
                    leaf redistOspfRmap  {
                        type  cml_data_types:CML_STRING_T {
                            length "0..255";
                        }
                        description "redistribute with ospf proc Id and route map reference";
                    } // END of redistOspfRmap definition.

                } // End of bgpRmap-list
            } // End of bgpRedistOspfNo-list

            list bgpPeerGroup {
                 
                description
                    "bgpPeerGroup";

                config true;
                key "peerGroupName";

                
                leaf peerGroupName  {
                    type  cml_data_types:CML_STRING_T {
                        length "0..255";
                    }
                    description "neighbor peer-group";
                } // END of peerGroupName definition.

            } // End of bgpPeerGroup-list

            list bgpAddressFamily {
                 
                description
                    "bgpAddressFamily";

                config true;
                key "afi";

                
                leaf afi  {
                    type  cml_data_types:CML_AFI_TYPE_T;  
                } // END of afi definition.


                list bgpSubAddressFamily {
                     
                    description
                        "bgpSubAddressFamily";

                    config true;
                    key "safi";

                    
                    leaf safi  {
                        type  cml_data_types:CML_SAFI_TYPE_T;  
                    } // END of safi definition.


                    list vrfAf {
                         
                        description
                            "vrfAf";

                        config true;
                        key "vrfName";

                        
                        leaf vrfName  {
                            type  cml_data_types:CML_STRING_T {
                                length "0..255";
                            }
                        } // END of vrfName definition.

                    } // End of vrfAf-list
                } // End of bgpSubAddressFamily-list
            } // End of bgpAddressFamily-list

            list vrfAddressFamily {
                 
                description
                    "vrfAddressFamily";

                config true;
                key "afi";

                
                leaf afi  {
                    type  cml_data_types:CML_VRF_AFI_TYPE_T;  
                } // END of afi definition.


                list vrfSubAddressFamily {
                     
                    description
                        "vrfSubAddressFamily";

                    config true;
                    key "safi";

                    
                    leaf safi  {
                        type  cml_data_types:CML_VRF_SAFI_TYPE_T;  
                    } // END of safi definition.


                    list afVrfObj {
                         
                        description
                            "afVrfObj";

                        config true;
                        key "vrfName";

                        
                        leaf vrfName  {
                            type  cml_data_types:CML_STRING_T {
                                length "0..255";
                            }
                        } // END of vrfName definition.


                        list vrfPeer {
                             
                            description
                                "vrfPeer";

                            config true;
                            key "peerAddr";

                            
                            leaf peerAddr  {
                                type  cml_data_types:CML_STRING_T {
                                    length "0..255";
                                }
                                description "neighbor";
                            } // END of peerAddr definition.

                            leaf peerAsAf  {
                                mandatory true;
                                type  cml_data_types:CML_UINT32_T {
                                     range "1..4294967295";
                                }
                                description "neighbor autonomous system number (ASN)  for address family";
                            } // END of peerAsAf definition.

                            leaf sourceIdAf  {
                                type  cml_data_types:CML_STRING_T {
                                    length "0..255";
                                }
                                default "NULL";
                                description "neighbor update-source for address-family";
                            } // END of sourceIdAf definition.

                            leaf peerLocalAsAf  {
                                type  cml_data_types:CML_UINT32_T {
                                     range "1..4294967295";
                                }
                                description "neighbor local-as for address family";
                            } // END of peerLocalAsAf definition.

                            leaf sendLabelAf  {
                                type  cml_data_types:CML_BOOL_T;  
                                description "neighbor send-label for address-family";
                            } // END of sendLabelAf definition.

                            leaf sendLabelExplicitNullAf  {
                                type  cml_data_types:CML_BOOL_T;  
                                description "neighbor send-label explicit-null for address-family";
                            } // END of sendLabelExplicitNullAf definition.

                            leaf bgpVersionAf  {
                                type  cml_data_types:CML_UINT8_T;  
                                default "4";
                                description "neighbor version for Address Family";
                            } // END of bgpVersionAf definition.

                            leaf peerConnectIntervalAf  {
                                type  cml_data_types:CML_UINT32_T {
                                     range "1..65535";
                                }
                                default "1";
                                description "neighbor timers for address-family";
                            } // END of peerConnectIntervalAf definition.

                            leaf peerKeepAliveAf  {
                                type  cml_data_types:CML_UINT16_T {
                                     range "0..65535";
                                }
                                default "30";
                            } // END of peerKeepAliveAf definition.

                            leaf peerHoldTimeAf  {
                                type  cml_data_types:CML_UINT16_T {
                                     range "0..65535";
                                }
                                default "90";
                                description "neighbor Keepalive and Holdtime for address-family";
                            } // END of peerHoldTimeAf definition.

                            leaf enforceMultihopAf  {
                                type  cml_data_types:CML_BOOL_T;  
                                description "neighbor enforce-multihop for address-family";
                            } // END of enforceMultihopAf definition.

                            leaf peerShutdownAf  {
                                type  cml_data_types:CML_BOOL_T;  
                                description "neighbor shutdown for address-family";
                            } // END of peerShutdownAf definition.

                            leaf peerGroupStrAf  {
                                type  cml_data_types:CML_BOOL_T;  
                                description "neighbor peer-group for address family";
                            } // END of peerGroupStrAf definition.

                            leaf passwordAf  {
                                type  cml_data_types:CML_STRING_T {
                                    length "0..255";
                                }
                                default "NULL";
                                description "neighbor password for address-family";
                            } // END of passwordAf definition.

                            leaf transportConnectionPassiveAf  {
                                type  cml_data_types:CML_BOOL_T;  
                                description "neighbor passive for address-family";
                            } // END of transportConnectionPassiveAf definition.

                            leaf maxHopCountAf  {
                                type  cml_data_types:CML_UINT8_T {
                                     range "1..255";
                                }
                                default "255";
                                description "neighbor max ebgp-multihop for address-family";
                            } // END of maxHopCountAf definition.

                            leaf timeToLiveAf  {
                                type  cml_data_types:CML_BOOL_T;  
                                description "neighbor ebgp-multihop for address-family";
                            } // END of timeToLiveAf definition.

                            leaf dontCapabilityNegotiateAf  {
                                type  cml_data_types:CML_BOOL_T;  
                                description "neighbor dont-capability-negotiate for address-family";
                            } // END of dontCapabilityNegotiateAf definition.

                            leaf connRetryIntervalAf  {
                                type  cml_data_types:CML_INT32_T {
                                     range "1..65535";
                                }
                                default "120";
                                description "neighbor connection-retry-time for address-family";
                            } // END of connRetryIntervalAf definition.

                            leaf dynamicCapabilityAf  {
                                type  cml_data_types:CML_BOOL_T;  
                                description "neighbor capability dynamic for address-family";
                            } // END of dynamicCapabilityAf definition.

                            leaf peerRaIntervalAf  {
                                type  cml_data_types:CML_UINT32_T {
                                     range "0..65535";
                                }
                                default "0";
                                description "neighbor advertisement-interval for address-family";
                            } // END of peerRaIntervalAf definition.

                            leaf peerAsorigIntervalAf  {
                                type  cml_data_types:CML_UINT32_T {
                                     range "1..65535";
                                }
                                default "1";
                                description "neighbor as-origination-interval for address-family";
                            } // END of peerAsorigIntervalAf definition.

                            leaf neighborAsOverrideAf  {
                                type  cml_data_types:CML_BOOL_T;  
                                description "neighbor asoverride for address family";
                            } // END of neighborAsOverrideAf definition.

                            leaf peerIfNameAf  {
                                if-feature feature_list:HAVE_VRF;
                                type  cml_data_types:CML_STRING_T {
                                    length "0..255";
                                }
                                description "neighbor interface for address family";
                            } // END of peerIfNameAf definition.

                            leaf peerDescAf  {
                                type  cml_data_types:CML_STRING_T {
                                    length "0..255";
                                }
                                description "neighbor description for address family";
                            } // END of peerDescAf definition.

                            leaf peerRestartTimeAf  {
                                if-feature feature_list:HAVE_RESTART;
                                if-feature feature_list:HAVE_VRF;
                                type  cml_data_types:CML_UINT32_T {
                                     range "1..3600";
                                }
                                description "neighbor restart-time for address-family";
                            } // END of peerRestartTimeAf definition.

                            leaf siteOriginIdAf  {
                                if-feature feature_list:HAVE_VRF;
                                type  cml_data_types:CML_STRING_T {
                                    length "0..255";
                                }
                                description "neighbor site of origin for address family";
                            } // END of siteOriginIdAf definition.

                            leaf setGracefulShutAf  {
                                type  cml_data_types:CML_BOOL_T;  
                                description "neighbor g-shut for address-family";
                            } // END of setGracefulShutAf definition.

                            leaf gshutTimerAf  {
                                type  cml_data_types:CML_UINT32_T {
                                     range "10..65535";
                                }
                                description "neighbor g-shut-timer for address-family";
                            } // END of gshutTimerAf definition.


                            list peerAdjInRoute {
                                 
                                description
                                    "peerAdjInRoute";

                                config false;
                                key "networkAddr";

                                
                                leaf networkAddr  {
                                    type  cml_data_types:CML_STRING_T {
                                        length "0..255";
                                    }
                                } // END of networkAddr definition.


                                list nextHop {
                                     
                                    description
                                        "nextHop";

                                    config false;
                                    key "nextHopAddr";

                                    
                                    leaf nextHopAddr  {
                                        type  cml_data_types:CML_STRING_T {
                                            length "0..255";
                                        }
                                    } // END of nextHopAddr definition.

                                    uses nextHopRunTimeAttr;
                                } // End of nextHop-list
                            } // End of peerAdjInRoute-list

                            list peerAdjOutRoute {
                                 
                                description
                                    "peerAdjOutRoute";

                                config false;
                                key "networkAddr";

                                
                                leaf networkAddr  {
                                    type  cml_data_types:CML_STRING_T {
                                        length "0..255";
                                    }
                                } // END of networkAddr definition.


                                list nextHop {
                                     
                                    description
                                        "nextHop";

                                    config false;
                                    key "nextHopAddr";

                                    
                                    leaf nextHopAddr  {
                                        type  cml_data_types:CML_STRING_T {
                                            length "0..255";
                                        }
                                    } // END of nextHopAddr definition.

                                    uses nextHopRunTimeAttr;
                                } // End of nextHop-list
                            } // End of peerAdjOutRoute-list
                            uses peerVrfAttrs;
                            uses peerRuntimeAttr;
                        } // End of vrfPeer-list
                    } // End of afVrfObj-list
                } // End of vrfSubAddressFamily-list
            } // End of vrfAddressFamily-list

            list bgpPeer {
                 
                description
                    "bgpPeer";

                config true;
                key "peerAddr";

                
                leaf peerAddr  {
                    type  cml_data_types:CML_STRING_T {
                        length "0..255";
                    }
                    description "neighbor";
                } // END of peerAddr definition.

                leaf peerAs  {
                    mandatory true;
                    type  cml_data_types:CML_UINT32_T {
                         range "1..4294967295";
                    }
                    description "Neighbors AS number";
                } // END of peerAs definition.

                leaf peerAdditionalPaths  {
                    if-feature feature_list:HAVE_BGP_ADD_PATH;
                    type  cml_data_types:BGP_PEER_ADDITIONAL_PATH_TYPE_T;  
                    description "additional paths";
                } // END of peerAdditionalPaths definition.

                leaf peerAddPathSelectAll  {
                    if-feature feature_list:HAVE_BGP_ADD_PATH;
                    type  cml_data_types:CML_BOOL_T;  
                    description "Advertise additional path";
                } // END of peerAddPathSelectAll definition.

                leaf peerBestCount  {
                    if-feature feature_list:HAVE_BGP_ADD_PATH;
                    type  cml_data_types:CML_UINT8_T {
                         range "2..3";
                    }
                    description "Advertise best additional path";
                } // END of peerBestCount definition.

                leaf setGracefulShut  {
                    type  cml_data_types:CML_BOOL_T;  
                    description "neighbor g-shut";
                } // END of setGracefulShut definition.

                leaf bgpPeerBfd  {
                    type  cml_data_types:CML_BOOL_T;  
                    description "fall-over detection";
                } // END of bgpPeerBfd definition.

                leaf peerBfdMh  {
                    type  cml_data_types:CML_BOOL_T;  
                    description "bfd multihop";
                } // END of peerBfdMh definition.

                leaf gshutTimer  {
                    type  cml_data_types:CML_UINT32_T {
                         range "10..65535";
                    }
                    description "neighbor g-shut-timer";
                } // END of gshutTimer definition.

                leaf peerRestartTime  {
                    if-feature feature_list:HAVE_RESTART;
                    type  cml_data_types:CML_UINT32_T {
                         range "1..3600";
                    }
                    description "neighbor restart-time";
                } // END of peerRestartTime definition.

                leaf peerLocalAs  {
                    type  cml_data_types:CML_UINT32_T {
                         range "1..4294967295";
                    }
                    description "neighbor local-as";
                } // END of peerLocalAs definition.

                leaf neighborAttrUnchanged  {
                    type  cml_data_types:CML_ATTRIBUTE_UNCHANGED_TYPE_T;  
                    description "neighbor attribute-unchanged";
                } // END of neighborAttrUnchanged definition.

                leaf neighborCapabilityGrst  {
                    if-feature feature_list:HAVE_RESTART;
                    type  cml_data_types:CML_BOOL_T;  
                    description "neighbor capability graceful-restart";
                } // END of neighborCapabilityGrst definition.

                leaf peerRemovePvtAs  {
                    type  cml_data_types:CML_BOOL_T;  
                    description "neighbor remove-private-AS";
                } // END of peerRemovePvtAs definition.

                leaf sendCommunity  {
                    type  cml_data_types:CML_BOOL_T;  
                    description "neighbor send-community";
                } // END of sendCommunity definition.

                leaf sendCommunityType  {
                    type  cml_data_types:CML_BGP_SEND_COMMU_TYPE_T;  
                    description "neighbor send-community attribute";
                } // END of sendCommunityType definition.

                leaf neighborRouteServerClient  {
                    type  cml_data_types:CML_BOOL_T;  
                    description "neighbor route-server-client";
                } // END of neighborRouteServerClient definition.

                leaf peerRouteReflector  {
                    type  cml_data_types:CML_BOOL_T;  
                    description "neighbor route-reflector-client";
                } // END of peerRouteReflector definition.

                leaf peerAdminFlag  {
                    type  cml_data_types:CML_INT32_T;  
                } // END of peerAdminFlag definition.

                leaf connRetryInterval  {
                    type  cml_data_types:CML_INT32_T {
                         range "1..65535";
                    }
                    default "120";
                    description "neighbor connection-retry-time";
                } // END of connRetryInterval definition.

                leaf peerDesc  {
                    type  cml_data_types:CML_STRING_T {
                        length "0..255";
                    }
                    description "neighbor description";
                } // END of peerDesc definition.

                leaf transparentAs  {
                    type  cml_data_types:CML_BOOL_T;  
                    description "neighbor transparent-as";
                } // END of transparentAs definition.

                leaf transparentNexthop  {
                    type  cml_data_types:CML_BOOL_T;  
                    description "neighbor transparent-nexthop";
                } // END of transparentNexthop definition.

                leaf sendLabel  {
                    type  cml_data_types:CML_BOOL_T;  
                    description "neighbor send-label";
                } // END of sendLabel definition.

                leaf sendLabelExplicitNull  {
                    type  cml_data_types:CML_BOOL_T;  
                    description "neighbor send-label explicit-null";
                } // END of sendLabelExplicitNull definition.

                leaf timeToLive  {
                    type  cml_data_types:CML_BOOL_T;  
                    description "neighbor ebgp-multihop";
                } // END of timeToLive definition.

                leaf maxHopCount  {
                    type  cml_data_types:CML_UINT8_T {
                         range "1..255";
                    }
                    default "255";
                    description "neighbor ebgp-multihop maximum hop count";
                } // END of maxHopCount definition.

                leaf peerConnectInterval  {
                    type  cml_data_types:CML_UINT32_T {
                         range "1..65535";
                    }
                    default "1";
                    description "neighbor timers";
                } // END of peerConnectInterval definition.

                leaf peerAsorigInterval  {
                    type  cml_data_types:CML_UINT32_T {
                         range "1..65535";
                    }
                    default "1";
                    description "neighbor as-origination-interval";
                } // END of peerAsorigInterval definition.

                leaf peerRaInterval  {
                    type  cml_data_types:CML_UINT32_T {
                         range "0..65535";
                    }
                    default "0";
                    description "neighbor advertisement-interval";
                } // END of peerRaInterval definition.

                leaf password  {
                    if-feature feature_list:HAVE_TCP_MD5SIG;
                    type  cml_data_types:CML_STRING_T {
                        length "0..255";
                    }
                    default "NULL";
                    description "neighbor password";
                } // END of password definition.

                leaf dynamicCapability  {
                    type  cml_data_types:CML_BOOL_T;  
                    description "neighbor capability dynamic";
                } // END of dynamicCapability definition.

                leaf collideEstablished  {
                    type  cml_data_types:CML_BOOL_T;  
                    description "neighbor collide-established";
                } // END of collideEstablished definition.

                leaf sourceId  {
                    type  cml_data_types:CML_STRING_T {
                        length "0..255";
                    }
                    default "NULL";
                    description "neighbor update-source";
                } // END of sourceId definition.

                leaf enforceMultihop  {
                    type  cml_data_types:CML_BOOL_T;  
                    description "neighbor enforce-multihop";
                } // END of enforceMultihop definition.

                leaf neighborOverrideCapability  {
                    type  cml_data_types:CML_BOOL_T;  
                    description "neighbor override-capability";
                } // END of neighborOverrideCapability definition.

                leaf neighborStrictCapability  {
                    type  cml_data_types:CML_BOOL_T;  
                    description "neighbor strict-capability-match";
                } // END of neighborStrictCapability definition.

                leaf disallowHoldtimer  {
                    type  cml_data_types:CML_BOOL_T;  
                    description "neighbor disallow-infinite-holdtime";
                } // END of disallowHoldtimer definition.

                leaf dontCapabilityNegotiate  {
                    type  cml_data_types:CML_BOOL_T;  
                    description "neighbor dont-capability-negotiate";
                } // END of dontCapabilityNegotiate definition.

                leaf transportConnectionPassive  {
                    type  cml_data_types:CML_BOOL_T;  
                    description "neighbor passive";
                } // END of transportConnectionPassive definition.

                leaf peerShutdown  {
                    type  cml_data_types:CML_BOOL_T;  
                    description "neighbor shutdown";
                } // END of peerShutdown definition.

                leaf bgpPort  {
                    type  cml_data_types:CML_UINT16_T {
                         range "0..65535";
                    }
                    default "179";
                    description "neighbor port";
                } // END of bgpPort definition.

                leaf bgpVersion  {
                    type  cml_data_types:CML_UINT8_T;  
                    default "4";
                    description "neighbor version";
                } // END of bgpVersion definition.

                leaf peerIfName  {
                    type  cml_data_types:CML_STRING_T {
                        length "0..255";
                    }
                    description "neighbor interface";
                } // END of peerIfName definition.

                leaf softReconfigInbound  {
                    type  cml_data_types:CML_BOOL_T;  
                    description "neighbor soft-reconfiguration inbound";
                } // END of softReconfigInbound definition.

                leaf weight  {
                    type  cml_data_types:CML_UINT16_T {
                         range "0..65535";
                    }
                    default "0";
                    description "neighbor weight";
                } // END of weight definition.

                leaf maxPrefixes  {
                    type  cml_data_types:CML_UINT32_T {
                         range "1..4294967295";
                    }
                    description "neighbor maximum-prefix";
                } // END of maxPrefixes definition.

                leaf stopUpdate  {
                    type  cml_data_types:CML_BOOL_T;  
                    description "neighbor maximum-prefix stop-update";
                } // END of stopUpdate definition.

                leaf maxPrefixeWarning  {
                    type  cml_data_types:CML_BOOL_T;  
                    description "neighbor maximum-prefix warning";
                } // END of maxPrefixeWarning definition.

                leaf threshold  {
                    type  cml_data_types:CML_UINT8_T {
                         range "1..100";
                    }
                    default "75";
                    description "neighbor maximum-prefix threshold value percent";
                } // END of threshold definition.

                leaf warning  {
                    type  cml_data_types:CML_BOOL_T;  
                    description "neighbor maximum-prefix threshold warning";
                } // END of warning definition.

                leaf allowAsNum  {
                    type  cml_data_types:CML_UINT32_T {
                         range "1..10";
                    }
                    default "3";
                    description "neighbor allowas-in";
                } // END of allowAsNum definition.

                leaf aclInfo  {
                    type  cml_data_types:CML_STRING_T {
                        length "0..255";
                    }
                } // END of aclInfo definition.

                leaf distributeListDirection  {
                    type  cml_data_types:CML_BGP_DISTRIBUTE_LIST_ACTION_T;  
                    description "neighbor distribute-list";
                } // END of distributeListDirection definition.

                leaf prefixListAclInfo  {
                    type  cml_data_types:CML_STRING_T {
                        length "0..255";
                    }
                } // END of prefixListAclInfo definition.

                leaf prefixListDirection  {
                    type  cml_data_types:CML_BGP_DISTRIBUTE_LIST_ACTION_T;  
                    description "neighbor prefix-list";
                } // END of prefixListDirection definition.

                leaf asListAclInfo  {
                    type  cml_data_types:CML_STRING_T {
                        length "0..255";
                    }
                } // END of asListAclInfo definition.

                leaf asListDirection  {
                    type  cml_data_types:CML_BGP_DISTRIBUTE_LIST_ACTION_T;  
                    description "neighbor filter-list";
                } // END of asListDirection definition.

                leaf peerGroupTag  {
                    type  cml_data_types:CML_STRING_T {
                        length "0..255";
                    }
                    description "to add a neighbor to an existing peer-group";
                } // END of peerGroupTag definition.

                leaf peerActivate  {
                    type  cml_data_types:CML_BOOL_T;  
                    description "neighbor activate";
                } // END of peerActivate definition.

                leaf unSuppressAclInfo  {
                    type  cml_data_types:CML_STRING_T {
                        length "0..255";
                    }
                    description "neighbor unsuppress-map";
                } // END of unSuppressAclInfo definition.

                leaf peerRmapOriName  {
                    type  cml_data_types:CML_STRING_T {
                        length "0..255";
                    }
                    description "neighbor default-originate router-map";
                } // END of peerRmapOriName definition.

                leaf defaultPeerRmapName  {
                    type  cml_data_types:CML_BOOL_T;  
                    description "neighbor default-originate";
                } // END of defaultPeerRmapName definition.

                leaf orfPrefixOpt  {
                    type  cml_data_types:CML_BGP_ORF_PREFIX_TYPE_T;  
                } // END of orfPrefixOpt definition.

                leaf setNcpFlag  {
                    type  cml_data_types:CML_BOOL_T;  
                    description "neighbor orf prefix-list";
                } // END of setNcpFlag definition.

                leaf peerRmapName  {
                    type  cml_data_types:CML_STRING_T {
                        length "0..255";
                    }
                } // END of peerRmapName definition.

                leaf peerRmapDirection  {
                    type  cml_data_types:CML_BGP_DISTRIBUTE_LIST_ACTION_T;  
                    description "neighbor route-map";
                } // END of peerRmapDirection definition.

                leaf peerKeepAlive  {
                    type  cml_data_types:CML_UINT16_T {
                         range "0..65535";
                    }
                    default "30";
                } // END of peerKeepAlive definition.

                leaf peerHoldTime  {
                    type  cml_data_types:CML_UINT16_T {
                         range "0..65535";
                    }
                    default "90";
                    description "neighbor Keepalive and Holdtime";
                } // END of peerHoldTime definition.

                leaf nextHopSelf  {
                    type  cml_data_types:CML_BOOL_T;  
                    description "neighbor next-hop-self";
                } // END of nextHopSelf definition.


                list peerAdjInRoute {
                     
                    description
                        "peerAdjInRoute";

                    config false;
                    key "networkAddr";

                    
                    leaf networkAddr  {
                        type  cml_data_types:CML_STRING_T {
                            length "0..255";
                        }
                    } // END of networkAddr definition.


                    list nextHop {
                         
                        description
                            "nextHop";

                        config false;
                        key "nextHopAddr";

                        
                        leaf nextHopAddr  {
                            type  cml_data_types:CML_STRING_T {
                                length "0..255";
                            }
                        } // END of nextHopAddr definition.

                        uses nextHopRunTimeAttr;
                    } // End of nextHop-list
                } // End of peerAdjInRoute-list

                list peerAdjOutRoute {
                     
                    description
                        "peerAdjOutRoute";

                    config false;
                    key "networkAddr";

                    
                    leaf networkAddr  {
                        type  cml_data_types:CML_STRING_T {
                            length "0..255";
                        }
                    } // END of networkAddr definition.


                    list nextHop {
                         
                        description
                            "nextHop";

                        config false;
                        key "nextHopAddr";

                        
                        leaf nextHopAddr  {
                            type  cml_data_types:CML_STRING_T {
                                length "0..255";
                            }
                        } // END of nextHopAddr definition.

                        uses nextHopRunTimeAttr;
                    } // End of nextHop-list
                } // End of peerAdjOutRoute-list

                list bgpPeerAddressFamily {
                     
                    description
                        "bgpPeerAddressFamily";

                    config true;
                    key "afi";

                    
                    leaf afi  {
                        type  cml_data_types:CML_AFI_TYPE_T;  
                    } // END of afi definition.


                    list bgpPeerSubAddressFamily {
                         
                        description
                            "bgpPeerSubAddressFamily";

                        config true;
                        key "safi";

                        
                        leaf safi  {
                            type  cml_data_types:CML_SAFI_TYPE_T;  
                        } // END of safi definition.

                        leaf peerAdditionalPathsAf  {
                            if-feature feature_list:HAVE_BGP_ADD_PATH;
                            type  cml_data_types:BGP_PEER_ADDITIONAL_PATH_TYPE_T;  
                            description "additional paths for address-family";
                        } // END of peerAdditionalPathsAf definition.

                        leaf peerAddPathSelectAllAf  {
                            if-feature feature_list:HAVE_BGP_ADD_PATH;
                            type  cml_data_types:CML_BOOL_T;  
                            description "Advertise additional path for address-family";
                        } // END of peerAddPathSelectAllAf definition.

                        leaf peerBestCountAf  {
                            if-feature feature_list:HAVE_BGP_ADD_PATH;
                            type  cml_data_types:CML_UINT8_T {
                                 range "2..3";
                            }
                            description "Advertise best additional path for address-family";
                        } // END of peerBestCountAf definition.

                        leaf neighborRouteServerClientAf  {
                            type  cml_data_types:CML_BOOL_T;  
                            description "neighbor route-server-client for address family";
                        } // END of neighborRouteServerClientAf definition.

                        leaf nextHopSelfAf  {
                            type  cml_data_types:CML_BOOL_T;  
                            description "neighbor next-hop-self for address family";
                        } // END of nextHopSelfAf definition.


                        list peerAdjInRoute {
                             
                            description
                                "peerAdjInRoute";

                            config false;
                            key "networkAddr";

                            
                            leaf networkAddr  {
                                type  cml_data_types:CML_STRING_T {
                                    length "0..255";
                                }
                            } // END of networkAddr definition.


                            list nextHop {
                                 
                                description
                                    "nextHop";

                                config false;
                                key "nextHopAddr";

                                
                                leaf nextHopAddr  {
                                    type  cml_data_types:CML_STRING_T {
                                        length "0..255";
                                    }
                                } // END of nextHopAddr definition.

                                uses nextHopRunTimeAttr;
                            } // End of nextHop-list
                        } // End of peerAdjInRoute-list

                        list peerAdjOutRoute {
                             
                            description
                                "peerAdjOutRoute";

                            config false;
                            key "networkAddr";

                            
                            leaf networkAddr  {
                                type  cml_data_types:CML_STRING_T {
                                    length "0..255";
                                }
                            } // END of networkAddr definition.


                            list nextHop {
                                 
                                description
                                    "nextHop";

                                config false;
                                key "nextHopAddr";

                                
                                leaf nextHopAddr  {
                                    type  cml_data_types:CML_STRING_T {
                                        length "0..255";
                                    }
                                } // END of nextHopAddr definition.

                                uses nextHopRunTimeAttr;
                            } // End of nextHop-list
                        } // End of peerAdjOutRoute-list
                        uses peerVrfAttrs;
                        uses peerRuntimeAttr;
                    } // End of bgpPeerSubAddressFamily-list
                } // End of bgpPeerAddressFamily-list
                uses peerRuntimeAttr;
            } // End of bgpPeer-list

            list addrFamily {
                 
                description
                    "addrFamily";

                config true;
                key "afi";

                
                leaf afi  {
                    type  cml_data_types:CML_AFI_TYPE_T;  
                } // END of afi definition.


                list subAddrFamily {
                     
                    description
                        "subAddrFamily";

                    config true;
                    key "safi";

                    
                    leaf safi  {
                        type  cml_data_types:CML_SAFI_TYPE_T;  
                    } // END of safi definition.

                    leaf additionalPathsAf  {
                        if-feature feature_list:HAVE_BGP_ADD_PATH;
                        type  cml_data_types:BGP_ADDITIONAL_PATH_TYPE_T;  
                        description "additional paths for address-family";
                    } // END of additionalPathsAf definition.

                    leaf addPathSelectAllAf  {
                        if-feature feature_list:HAVE_BGP_ADD_PATH;
                        type  cml_data_types:CML_BOOL_T;  
                        description "select all path for address-family";
                    } // END of addPathSelectAllAf definition.

                    leaf bestCountAf  {
                        if-feature feature_list:HAVE_BGP_ADD_PATH;
                        type  cml_data_types:CML_UINT8_T {
                             range "2..3";
                        }
                        description "select best path for address-family";
                    } // END of bestCountAf definition.

                    leaf setClientReflectAf  {
                        type  cml_data_types:CML_BOOL_T;  
                        description "bgp client-to-client reflection for address-family";
                    } // END of setClientReflectAf definition.

                    leaf ntwkPrefixCountAf  {
                        type  cml_data_types:CML_INT32_T;  
                        config false;
                    } // END of ntwkPrefixCountAf definition.

                    leaf ntwkRouterIpAddrAf  {
                        type  cml_data_types:CML_INT32_T;  
                        config false;
                    } // END of ntwkRouterIpAddrAf definition.

                    leaf bgpTableVersionAf  {
                        type  cml_data_types:CML_INT32_T;  
                        config false;
                    } // END of bgpTableVersionAf definition.


                    list bgpAddressFamilyAggregateAddrList {
                         
                        description
                            "bgpAddressFamilyAggregateAddrList";

                        config true;
                        key "aggregateAddrAf";

                        
                        leaf aggregateAddrAf  {
                            type  cml_data_types:CML_STRING_T {
                                length "0..255";
                            }
                            description "aggregate-address for address-family";
                        } // END of aggregateAddrAf definition.

                        leaf aggregateTypeAf  {
                            type  cml_data_types:CML_BGP_AGGREGATE_ADDR_TYPE_T;  
                            description "aggregate-address-type for address-family";
                        } // END of aggregateTypeAf definition.

                        leaf aggregateAsSetAf  {
                            type  cml_data_types:CML_BOOL_T;  
                            description "redistribute as-set for address family";
                        } // END of aggregateAsSetAf definition.

                        leaf aggregateSummOnlyAf  {
                            type  cml_data_types:CML_BOOL_T;  
                            description "redistribute summary-only for address family";
                        } // END of aggregateSummOnlyAf definition.

                    } // End of bgpAddressFamilyAggregateAddrList-list

                    list vrfobj {
                         
                        description
                            "vrfobj";

                        config true;
                        key "vrfName";

                        
                        leaf vrfName  {
                            type  cml_data_types:CML_STRING_T {
                                length "0..255";
                            }
                        } // END of vrfName definition.

                        leaf autoSummaryAf  {
                            type  cml_data_types:CML_BOOL_T;  
                            description "auto-summary for address-family";
                        } // END of autoSummaryAf definition.

                        leaf setNwSyncFlagAf  {
                            type  cml_data_types:CML_BOOL_T;  
                            description "network synchronization for address-family";
                        } // END of setNwSyncFlagAf definition.

                        leaf halfLifeAf  {
                            type  cml_data_types:CML_UINT32_T {
                                 range "1..45";
                            }
                            default "15";
                            description "bgp route dampening reachability half-life time for address family";
                        } // END of halfLifeAf definition.

                        leaf reusePenaltyAf  {
                            type  cml_data_types:CML_UINT32_T {
                                 range "1..20000";
                            }
                        } // END of reusePenaltyAf definition.

                        leaf suppressPenaltyAf  {
                            type  cml_data_types:CML_UINT32_T {
                                 range "1..20000";
                            }
                        } // END of suppressPenaltyAf definition.

                        leaf maxSuppressAf  {
                            type  cml_data_types:CML_UINT32_T {
                                 range "1..255";
                            }
                            description "bgp route dampening to start suppressing a route for address family";
                        } // END of maxSuppressAf definition.

                        leaf unreachHalfLifeAf  {
                            type  cml_data_types:CML_UINT32_T {
                                 range "1..45";
                            }
                            description "bgp route dampening Un-reachability Half-life time for address family";
                        } // END of unreachHalfLifeAf definition.

                        leaf dampeningRmapNameAf  {
                            type  cml_data_types:CML_STRING_T {
                                length "0..255";
                            }
                            description "bgp dampening route-map for address-family";
                        } // END of dampeningRmapNameAf definition.

                        leaf tableMapAf  {
                            if-feature feature_list:HAVE_BGP_TABLE_MAP;
                            type  cml_data_types:CML_STRING_T {
                                length "0..255";
                            }
                            description "bgp table-map for address-family";
                        } // END of tableMapAf definition.

                        leaf tableMapFilterAf  {
                            if-feature feature_list:HAVE_BGP_TABLE_MAP;
                            type  cml_data_types:CML_BOOL_T;  
                            description "bgp table-map filter for address-family";
                        } // END of tableMapFilterAf definition.

                        leaf setDampeningFlagAf  {
                            type  cml_data_types:CML_BOOL_T;  
                            description "bgp dampening for address-family";
                        } // END of setDampeningFlagAf definition.

                        leaf distanceEbgpAf  {
                            type  cml_data_types:CML_UINT8_T {
                                 range "1..255";
                            }
                            default "20";
                        } // END of distanceEbgpAf definition.

                        leaf distanceIbgpAf  {
                            type  cml_data_types:CML_UINT8_T {
                                 range "1..255";
                            }
                            default "200";
                        } // END of distanceIbgpAf definition.

                        leaf distanceLocalAf  {
                            type  cml_data_types:CML_UINT8_T {
                                 range "1..255";
                            }
                            default "200";
                            description "administrative distance for address-family";
                        } // END of distanceLocalAf definition.

                        leaf setSyncFlagAf  {
                            type  cml_data_types:CML_BOOL_T;  
                            description "synchronization for address-family";
                        } // END of setSyncFlagAf definition.

                        leaf ebgpMaxPathAf  {
                            type  cml_data_types:CML_INT32_T {
                                 range "2..64";
                            }
                            default "2";
                            description "multipath ECMP numbers for eBGP address family";
                        } // END of ebgpMaxPathAf definition.

                        leaf ibgpMaxPathAf  {
                            type  cml_data_types:CML_INT32_T {
                                 range "2..64";
                            }
                            default "2";
                            description "multipath ECMP numbers for iBGP address family";
                        } // END of ibgpMaxPathAf definition.

                        leaf setGshutAf  {
                            type  cml_data_types:CML_BOOL_T;  
                            description "bgp g-shut for address family";
                        } // END of setGshutAf definition.

                        leaf setGshutCapableAf  {
                            type  cml_data_types:CML_BOOL_T;  
                            description "bgp g-shut-capable for address-family";
                        } // END of setGshutCapableAf definition.

                        leaf gshutLocalPrefAf  {
                            type  cml_data_types:CML_UINT32_T {
                                 range "0..4294967295";
                            }
                            default "0";
                            description "bgp g-shut-local-preference for address-family";
                        } // END of gshutLocalPrefAf definition.

                        leaf confedIdAf  {
                            type  cml_data_types:CML_INT32_T {
                                 range "1..65535";
                            }
                            description "bgp confederation identifier in digits for address-family";
                        } // END of confedIdAf definition.


                        list bgpConfed {
                             
                            description
                                "bgpConfed";

                            config true;
                            key "peerConfedIdAf";

                            
                            leaf peerConfedIdAf  {
                                type  cml_data_types:CML_INT32_T {
                                     range "1..65535";
                                }
                                description "bgp confederation peers for address-family";
                            } // END of peerConfedIdAf definition.

                        } // End of bgpConfed-list

                        list bgpAddressFamilyNetworkList {
                             
                            description
                                "bgpAddressFamilyNetworkList";

                            config true;
                            key "localAddrAf";

                            
                            leaf localAddrAf  {
                                type  cml_data_types:CML_STRING_T {
                                    length "0..255";
                                }
                            } // END of localAddrAf definition.

                            leaf localAddrMaskAf  {
                                type  cml_data_types:CML_IPV4_ADDR_T;  
                                description "network address with mask for address family";
                            } // END of localAddrMaskAf definition.

                            leaf networkRmapNameAf  {
                                type  cml_data_types:CML_STRING_T {
                                    length "0..255";
                                }
                            } // END of networkRmapNameAf definition.

                            leaf backdoorAf  {
                                type  cml_data_types:CML_BOOL_T;  
                                default false;
                                description "network address with backdoor for address family";
                            } // END of backdoorAf definition.

                            leaf ntwkPathCountRouteAf  {
                                type  cml_data_types:CML_INT32_T;  
                                config false;
                            } // END of ntwkPathCountRouteAf definition.

                            leaf noAdvertiseRouteAf  {
                                type  cml_data_types:CML_STRING_T {
                                    length "0..255";
                                }
                                config false;
                            } // END of noAdvertiseRouteAf definition.

                            leaf noExportRouteAf  {
                                type  cml_data_types:CML_STRING_T {
                                    length "0..255";
                                }
                                config false;
                            } // END of noExportRouteAf definition.

                            leaf localAsRouteAf  {
                                type  cml_data_types:CML_STRING_T {
                                    length "0..255";
                                }
                                config false;
                            } // END of localAsRouteAf definition.

                            leaf suppressRouteAf  {
                                type  cml_data_types:CML_STRING_T {
                                    length "0..255";
                                }
                                config false;
                            } // END of suppressRouteAf definition.

                            leaf ntwkBestPathCountRouteAf  {
                                type  cml_data_types:CML_INT32_T;  
                                config false;
                            } // END of ntwkBestPathCountRouteAf definition.

                            leaf defIPRoutingTblAf  {
                                type  cml_data_types:CML_STRING_T {
                                    length "0..255";
                                }
                                config false;
                            } // END of defIPRoutingTblAf definition.

                            leaf advPeerAddrRouteAf  {
                                type  cml_data_types:CML_STRING_T {
                                    length "0..255";
                                }
                                config false;
                            } // END of advPeerAddrRouteAf definition.

                            leaf advPeerGroupNameRouteAf  {
                                type  cml_data_types:CML_STRING_T {
                                    length "0..255";
                                }
                                config false;
                            } // END of advPeerGroupNameRouteAf definition.

                            leaf advAnyPeerAf  {
                                type  cml_data_types:CML_STRING_T {
                                    length "0..255";
                                }
                                config false;
                            } // END of advAnyPeerAf definition.


                            list nextHopAf {
                                 
                                description
                                    "nextHopAf";

                                config false;
                                key "nextHopAddrAf";

                                
                                leaf nextHopAddrAf  {
                                    type  cml_data_types:CML_STRING_T {
                                        length "0..255";
                                    }
                                } // END of nextHopAddrAf definition.

                                leaf rfdFlapCountAf  {
                                    type  cml_data_types:CML_INT32_T;  
                                } // END of rfdFlapCountAf definition.

                                leaf dampInfoTimesAf  {
                                    type  cml_data_types:CML_STRING_T {
                                        length "0..255";
                                    }
                                } // END of dampInfoTimesAf definition.

                                leaf peerNtwkWeightAf  {
                                    type  cml_data_types:CML_INT32_T;  
                                } // END of peerNtwkWeightAf definition.

                                leaf flapTimeReuseListAf  {
                                    type  cml_data_types:CML_STRING_T {
                                        length "0..255";
                                    }
                                } // END of flapTimeReuseListAf definition.

                                leaf flapRecordDurationAf  {
                                    type  cml_data_types:CML_STRING_T {
                                        length "0..255";
                                    }
                                } // END of flapRecordDurationAf definition.

                                leaf dampTimeToReuseAf  {
                                    type  cml_data_types:CML_STRING_T {
                                        length "0..255";
                                    }
                                } // END of dampTimeToReuseAf definition.

                                leaf bgpInfoFlagAf  {
                                    type  cml_data_types:CML_STRING_T {
                                        length "0..255";
                                    }
                                } // END of bgpInfoFlagAf definition.

                                leaf bgpAttrNextHopAf  {
                                    type  cml_data_types:CML_STRING_T {
                                        length "0..255";
                                    }
                                } // END of bgpAttrNextHopAf definition.

                                leaf bgpAttrNextHopLenAf  {
                                    type  cml_data_types:CML_STRING_T {
                                        length "0..255";
                                    }
                                } // END of bgpAttrNextHopLenAf definition.

                                leaf bgpUpTimeAf  {
                                    type  cml_data_types:CML_STRING_T {
                                        length "0..255";
                                    }
                                } // END of bgpUpTimeAf definition.

                                leaf medFlagTypeAf  {
                                    type  cml_data_types:CML_STRING_T {
                                        length "0..255";
                                    }
                                } // END of medFlagTypeAf definition.

                                leaf bgpMedValAf  {
                                    type  cml_data_types:CML_INT32_T;  
                                } // END of bgpMedValAf definition.

                                leaf bgpAsPathStrAf  {
                                    type  cml_data_types:CML_STRING_T {
                                        length "0..255";
                                    }
                                } // END of bgpAsPathStrAf definition.

                                leaf bgpAsPath4BStrAf  {
                                    type  cml_data_types:CML_STRING_T {
                                        length "0..255";
                                    }
                                } // END of bgpAsPath4BStrAf definition.

                                leaf bgpAsPathOriginAf  {
                                    type  cml_data_types:CML_STRING_T {
                                        length "0..255";
                                    }
                                } // END of bgpAsPathOriginAf definition.

                                leaf bgpAsPath4BOriginAf  {
                                    type  cml_data_types:CML_STRING_T {
                                        length "0..255";
                                    }
                                } // END of bgpAsPath4BOriginAf definition.

                                leaf ibgpMetricRouteAf  {
                                    type  cml_data_types:CML_INT32_T;  
                                } // END of ibgpMetricRouteAf definition.

                                leaf aggregateAsRouteAf  {
                                    type  cml_data_types:CML_INT32_T;  
                                } // END of aggregateAsRouteAf definition.

                                leaf aggregatorAddrRouteAf  {
                                    type  cml_data_types:CML_STRING_T {
                                        length "0..255";
                                    }
                                } // END of aggregatorAddrRouteAf definition.

                                leaf networkRemoteAddrRouteAf  {
                                    type  cml_data_types:CML_STRING_T {
                                        length "0..255";
                                    }
                                } // END of networkRemoteAddrRouteAf definition.

                                leaf originatorIdRouteAf  {
                                    type  cml_data_types:CML_STRING_T {
                                        length "0..255";
                                    }
                                } // END of originatorIdRouteAf definition.

                                leaf routePeerAddrRouteAf  {
                                    type  cml_data_types:CML_STRING_T {
                                        length "0..255";
                                    }
                                } // END of routePeerAddrRouteAf definition.

                                leaf routeLocalPrefRouteAf  {
                                    type  cml_data_types:CML_INT32_T;  
                                } // END of routeLocalPrefRouteAf definition.

                                leaf briLabelRouteAf  {
                                    type  cml_data_types:CML_INT32_T;  
                                } // END of briLabelRouteAf definition.

                                leaf routeCommNameRouteAf  {
                                    type  cml_data_types:CML_STRING_T {
                                        length "0..255";
                                    }
                                } // END of routeCommNameRouteAf definition.

                                leaf clusterListRouteAf  {
                                    type  cml_data_types:CML_STRING_T {
                                        length "0..255";
                                    }
                                } // END of clusterListRouteAf definition.

                                leaf routeGetPenaltyRouteAf  {
                                    type  cml_data_types:CML_INT32_T;  
                                } // END of routeGetPenaltyRouteAf definition.

                                leaf routeGetFlapCountRouteAf  {
                                    type  cml_data_types:CML_INT32_T;  
                                } // END of routeGetFlapCountRouteAf definition.

                                leaf lastUpdateRouteAf  {
                                    type  cml_data_types:CML_STRING_T {
                                        length "0..255";
                                    }
                                } // END of lastUpdateRouteAf definition.

                                leaf reflectorClientRouteAf  {
                                    type  cml_data_types:CML_STRING_T {
                                        length "0..255";
                                    }
                                } // END of reflectorClientRouteAf definition.

                                leaf routeDampeningFlagRouteAf  {
                                    type  cml_data_types:CML_STRING_T {
                                        length "0..255";
                                    }
                                } // END of routeDampeningFlagRouteAf definition.

                                leaf historyRouteAf  {
                                    type  cml_data_types:CML_STRING_T {
                                        length "0..255";
                                    }
                                } // END of historyRouteAf definition.

                                leaf nhopValidRouteAf  {
                                    type  cml_data_types:CML_STRING_T {
                                        length "0..255";
                                    }
                                } // END of nhopValidRouteAf definition.

                                leaf routeMedFlagTypeRouteAf  {
                                    type  cml_data_types:CML_STRING_T {
                                        length "0..255";
                                    }
                                } // END of routeMedFlagTypeRouteAf definition.

                                leaf routeValidStateRouteAf  {
                                    type  cml_data_types:CML_STRING_T {
                                        length "0..255";
                                    }
                                } // END of routeValidStateRouteAf definition.

                                leaf bgpInfoStaleRouteAf  {
                                    type  cml_data_types:CML_STRING_T {
                                        length "0..255";
                                    }
                                } // END of bgpInfoStaleRouteAf definition.

                                leaf routePeerLocalAsRouteAf  {
                                    type  cml_data_types:CML_STRING_T {
                                        length "0..255";
                                    }
                                } // END of routePeerLocalAsRouteAf definition.

                                leaf bgpConfedPeerRouteAf  {
                                    type  cml_data_types:CML_STRING_T {
                                        length "0..255";
                                    }
                                } // END of bgpConfedPeerRouteAf definition.

                                leaf bgpInfoTypeRouteAf  {
                                    type  cml_data_types:CML_STRING_T {
                                        length "0..255";
                                    }
                                } // END of bgpInfoTypeRouteAf definition.

                                leaf ecmpMultiCandidateRouteAf  {
                                    type  cml_data_types:CML_STRING_T {
                                        length "0..255";
                                    }
                                } // END of ecmpMultiCandidateRouteAf definition.

                                leaf multiInstalledRouteAf  {
                                    type  cml_data_types:CML_INT32_T;  
                                } // END of multiInstalledRouteAf definition.

                                leaf routeSyncFlagRouteAf  {
                                    type  cml_data_types:CML_BOOL_T;  
                                } // END of routeSyncFlagRouteAf definition.

                                leaf atomicAggregateRouteAf  {
                                    type  cml_data_types:CML_STRING_T {
                                        length "0..255";
                                    }
                                } // END of atomicAggregateRouteAf definition.

                                leaf bgpInfoSelectedRouteAf  {
                                    type  cml_data_types:CML_STRING_T {
                                        length "0..255";
                                    }
                                } // END of bgpInfoSelectedRouteAf definition.

                            } // End of nextHopAf-list
                        } // End of bgpAddressFamilyNetworkList-list

                        list bgpAddressFamilyRedistListOspf {
                             
                            description
                                "bgpAddressFamilyRedistListOspf";

                            config true;
                            key "redistOspfAf";

                            
                            leaf redistOspfAf  {
                                type  cml_data_types:CML_BOOL_T;  
                                description "redistribute for address-family";
                            } // END of redistOspfAf definition.


                            list bgpRmapAf {
                                 
                                description
                                    "bgpRmapAf";

                                config true;
                                key "redistRmapNameAf";

                                
                                leaf redistRmapNameAf  {
                                    type  cml_data_types:CML_STRING_T {
                                        length "0..255";
                                    }
                                    description "redistribute route map reference for address family";
                                } // END of redistRmapNameAf definition.

                            } // End of bgpRmapAf-list
                        } // End of bgpAddressFamilyRedistListOspf-list

                        list bgpAddressFamilyRedistList {
                             
                            description
                                "bgpAddressFamilyRedistList";

                            config true;
                            key "redistTypeAf";

                            
                            leaf redistTypeAf  {
                                type  cml_data_types:CML_BGP_REDISTRIBUTE_TYPE_T;  
                                description "redistribute for address-family";
                            } // END of redistTypeAf definition.


                            list bgpRmapAf {
                                 
                                description
                                    "bgpRmapAf";

                                config true;
                                key "redistRmapNameAf";

                                
                                leaf redistRmapNameAf  {
                                    type  cml_data_types:CML_STRING_T {
                                        length "0..255";
                                    }
                                    description "redistribute route map reference for address family";
                                } // END of redistRmapNameAf definition.

                            } // End of bgpRmapAf-list
                        } // End of bgpAddressFamilyRedistList-list

                        list bgpRedistOspfAf {
                             
                            description
                                "bgpRedistOspfAf";

                            config true;
                            key "redistOspfNoAf";

                            
                            leaf redistOspfNoAf  {
                                type  cml_data_types:CML_UINT32_T {
                                     range "0..65535";
                                }
                                description "redistribute with ospf proc Id for address family";
                            } // END of redistOspfNoAf definition.


                            list bgpRmapAf {
                                 
                                description
                                    "bgpRmapAf";

                                config true;
                                key "redistOspfRmapAf";

                                
                                leaf redistOspfRmapAf  {
                                    type  cml_data_types:CML_STRING_T {
                                        length "0..255";
                                    }
                                    description "redistribute with ospf proc Id and route map reference for address family";
                                } // END of redistOspfRmapAf definition.

                            } // End of bgpRmapAf-list
                        } // End of bgpRedistOspfAf-list
                    } // End of vrfobj-list
                } // End of subAddrFamily-list
            } // End of addrFamily-list
        } // End of bgp-list
    } // END of bgp-grouping definition.


    grouping bgpGlobal-grouping {
        list bgpGlobal {
             
            description
                "BGP global commands";

            config true;
            key "vrId";

            
            leaf vrId  {
                type  cml_data_types:CML_UINT32_T;  
            } // END of vrId definition.

            leaf snmpRestart  {
                if-feature feature_list:HAVE_SNMP;
                type  cml_data_types:CML_BOOL_T;  
                description "snmp restart bgp";
            } // END of snmpRestart definition.

            leaf aggNexthop  {
                type  cml_data_types:CML_BOOL_T;  
                description "bgp aggregate-nexthop-check";
            } // END of aggNexthop definition.

            leaf pathSelect  {
                type  cml_data_types:CML_BOOL_T;  
                description "bgp rfc1771-path-select";
            } // END of pathSelect definition.

            leaf setDisableAdjOut  {
                type  cml_data_types:CML_BOOL_T;  
                description "bgp disable-adj-out";
            } // END of setDisableAdjOut definition.

            leaf setExtAsnCap  {
                if-feature feature_list:HAVE_EXT_CAP_ASN;
                type  cml_data_types:CML_BOOL_T;  
                description "bgp extended-asn-cap";
            } // END of setExtAsnCap definition.

            leaf setNexthopTriggerEnable  {
                type  cml_data_types:CML_BOOL_T;  
                description "bgp nexthop-trigger enable";
            } // END of setNexthopTriggerEnable definition.

            leaf delayInterval  {
                type  cml_data_types:CML_UINT8_T {
                     range "1..100";
                }
                default "5";
                description "bgp nexthop-trigger delay";
            } // END of delayInterval definition.

            leaf rfc1771StrictSet  {
                type  cml_data_types:CML_BOOL_T;  
                description "bgp rfc1771-strict";
            } // END of rfc1771StrictSet definition.

            leaf multiInstance  {
                type  cml_data_types:CML_BOOL_T;  
                description "bgp multiple-instance";
            } // END of multiInstance definition.

            leaf allowSamePeer  {
                type  cml_data_types:CML_BOOL_T;  
                description "bgp multiple-instance allow-same-peer";
            } // END of allowSamePeer definition.

            leaf configType  {
                type  cml_data_types:CML_STRING_T {
                    length "0..255";
                }
                description "bgp config-type";
            } // END of configType definition.


            list communityList {
                 
                description
                    "communityList";

                config true;
                key "commListName";

                
                leaf commListName  {
                    type  cml_data_types:CML_STRING_T {
                        length "0..255";
                    }
                } // END of commListName definition.


                list commListAction {
                     
                    description
                        "commListAction";

                    config true;
                    key "action";

                    
                    leaf action  {
                        type  cml_data_types:CML_BGP_COMMUNITY_LIST_ACTION_T;  
                    } // END of action definition.


                    list commListVal {
                         
                        description
                            "commListVal";

                        config true;
                        key "commListValue";

                        
                        leaf commListValue  {
                            type  cml_data_types:CML_STRING_T {
                                length "0..255";
                            }
                            description "community-list";
                        } // END of commListValue definition.

                    } // End of commListVal-list
                } // End of commListAction-list
            } // End of communityList-list

            list communityListNo {
                 
                description
                    "communityListNo";

                config true;
                key "commListStandNo";

                
                leaf commListStandNo  {
                    type  cml_data_types:CML_UINT32_T {
                         range "1..99";
                    }
                } // END of commListStandNo definition.


                list commListAction {
                     
                    description
                        "commListAction";

                    config true;
                    key "action";

                    
                    leaf action  {
                        type  cml_data_types:CML_BGP_COMMUNITY_LIST_ACTION_T;  
                        description "action type for community-list number";
                    } // END of action definition.


                    list commListVal {
                         
                        description
                            "commListVal";

                        config true;
                        key "commListValue";

                        
                        leaf commListValue  {
                            type  cml_data_types:CML_STRING_T {
                                length "0..255";
                            }
                            description "community-list number";
                        } // END of commListValue definition.

                    } // End of commListVal-list
                } // End of commListAction-list
            } // End of communityListNo-list

            list communityListStand {
                 
                description
                    "communityListStand";

                config true;
                key "commListName";

                
                leaf commListName  {
                    type  cml_data_types:CML_STRING_T {
                        length "0..255";
                    }
                } // END of commListName definition.


                list commListAction {
                     
                    description
                        "commListAction";

                    config true;
                    key "action";

                    
                    leaf action  {
                        type  cml_data_types:CML_BGP_COMMUNITY_LIST_ACTION_T;  
                        description "action type for standard community name";
                    } // END of action definition.


                    list commListVal {
                         
                        description
                            "commListVal";

                        config true;
                        key "commListValue";

                        
                        leaf commListValue  {
                            type  cml_data_types:CML_STRING_T {
                                length "0..255";
                            }
                            description "standard community name";
                        } // END of commListValue definition.

                    } // End of commListVal-list
                } // End of commListAction-list
            } // End of communityListStand-list

            list communityListExp {
                 
                description
                    "communityListExp";

                config true;
                key "commListNo";

                
                leaf commListNo  {
                    type  cml_data_types:CML_UINT32_T {
                         range "100..500";
                    }
                } // END of commListNo definition.


                list commListAction {
                     
                    description
                        "commListAction";

                    config true;
                    key "action";

                    
                    leaf action  {
                        type  cml_data_types:CML_BGP_COMMUNITY_LIST_ACTION_T;  
                    } // END of action definition.


                    list commListVal {
                         
                        description
                            "commListVal";

                        config true;
                        key "regExpList";

                        
                        leaf regExpList  {
                            type  cml_data_types:CML_STRING_T {
                                length "0..255";
                            }
                            description "expanded community-list number";
                        } // END of regExpList definition.

                    } // End of commListVal-list
                } // End of commListAction-list
            } // End of communityListExp-list

            list communityListExpand {
                 
                description
                    "communityListExpand";

                config true;
                key "commListExpName";

                
                leaf commListExpName  {
                    type  cml_data_types:CML_STRING_T {
                        length "0..255";
                    }
                } // END of commListExpName definition.


                list commListAction {
                     
                    description
                        "commListAction";

                    config true;
                    key "action";

                    
                    leaf action  {
                        type  cml_data_types:CML_BGP_COMMUNITY_LIST_ACTION_T;  
                    } // END of action definition.


                    list commListVal {
                         
                        description
                            "commListVal";

                        config true;
                        key "regExpList";

                        
                        leaf regExpList  {
                            type  cml_data_types:CML_STRING_T {
                                length "0..255";
                            }
                            description "community-list expanded";
                        } // END of regExpList definition.

                    } // End of commListVal-list
                } // End of commListAction-list
            } // End of communityListExpand-list

            list extCommuListNo {
                 
                description
                    "extCommuListNo";

                config true;
                key "extCommListStandNo";

                
                leaf extCommListStandNo  {
                    type  cml_data_types:CML_UINT32_T {
                         range "1..99";
                    }
                } // END of extCommListStandNo definition.


                list extCommListAction {
                     
                    description
                        "extCommListAction";

                    config true;
                    key "extAction";

                    
                    leaf extAction  {
                        type  cml_data_types:CML_BGP_COMMUNITY_LIST_ACTION_T;  
                    } // END of extAction definition.


                    list extCommListVal {
                         
                        description
                            "extCommListVal";

                        config true;
                        key "extCommListValue";

                        
                        leaf extCommListValue  {
                            type  cml_data_types:CML_STRING_T {
                                length "0..255";
                            }
                            description "standard extended community list number";
                        } // END of extCommListValue definition.

                    } // End of extCommListVal-list
                } // End of extCommListAction-list
            } // End of extCommuListNo-list

            list extCommListStand {
                 
                description
                    "extCommListStand";

                config true;
                key "extCommListName";

                
                leaf extCommListName  {
                    type  cml_data_types:CML_STRING_T {
                        length "0..255";
                    }
                } // END of extCommListName definition.

                leaf delExcomm  {
                    mandatory true;
                    type  cml_data_types:CML_STRING_T {
                        length "0..255";
                    }
                } // END of delExcomm definition.


                list extCommListAction {
                     
                    description
                        "extCommListAction";

                    config true;
                    key "extAction";

                    
                    leaf extAction  {
                        type  cml_data_types:CML_BGP_COMMUNITY_LIST_ACTION_T;  
                    } // END of extAction definition.


                    list routeTargetSoo {
                         
                        description
                            "routeTargetSoo";

                        config true;
                        key "rtSoo";

                        
                        leaf rtSoo  {
                            type  cml_data_types:CML_STRING_T {
                                length "0..255";
                            }
                        } // END of rtSoo definition.


                        list extCommListVal {
                             
                            description
                                "extCommListVal";

                            config true;
                            key "extCommListValue";

                            
                            leaf extCommListValue  {
                                type  cml_data_types:CML_STRING_T {
                                    length "0..255";
                                }
                                description "standard extended-community list for rt or soo";
                            } // END of extCommListValue definition.

                        } // End of extCommListVal-list
                    } // End of routeTargetSoo-list
                } // End of extCommListAction-list
            } // End of extCommListStand-list

            list extCommunityListExp {
                 
                description
                    "extCommunityListExp";

                config true;
                key "extCommListNo";

                
                leaf extCommListNo  {
                    type  cml_data_types:CML_UINT32_T {
                         range "100..500";
                    }
                } // END of extCommListNo definition.


                list extCommListAction {
                     
                    description
                        "extCommListAction";

                    config true;
                    key "extAction";

                    
                    leaf extAction  {
                        type  cml_data_types:CML_BGP_COMMUNITY_LIST_ACTION_T;  
                    } // END of extAction definition.


                    list extCommListVal {
                         
                        description
                            "extCommListVal";

                        config true;
                        key "extCommListValue";

                        
                        leaf extCommListValue  {
                            type  cml_data_types:CML_STRING_T {
                                length "0..255";
                            }
                            description "extended community list number";
                        } // END of extCommListValue definition.

                    } // End of extCommListVal-list
                } // End of extCommListAction-list
            } // End of extCommunityListExp-list

            list extCommListExpand {
                 
                description
                    "extCommListExpand";

                config true;
                key "extCommListExpName";

                
                leaf extCommListExpName  {
                    type  cml_data_types:CML_STRING_T {
                        length "0..255";
                    }
                } // END of extCommListExpName definition.


                list extCommListAction {
                     
                    description
                        "extCommListAction";

                    config true;
                    key "extAction";

                    
                    leaf extAction  {
                        type  cml_data_types:CML_BGP_COMMUNITY_LIST_ACTION_T;  
                    } // END of extAction definition.


                    list extCommListVal {
                         
                        description
                            "extCommListVal";

                        config true;
                        key "extCommListValue";

                        
                        leaf extCommListValue  {
                            type  cml_data_types:CML_STRING_T {
                                length "0..255";
                            }
                            description "expanded community list number";
                        } // END of extCommListValue definition.

                    } // End of extCommListVal-list
                } // End of extCommListAction-list
            } // End of extCommListExpand-list

            list accessList {
                 
                description
                    "accessList";

                config true;
                key "accessListName";

                
                leaf accessListName  {
                    type  cml_data_types:CML_STRING_T {
                        length "0..255";
                    }
                } // END of accessListName definition.


                list accessListDirection {
                     
                    description
                        "accessListDirection";

                    config true;
                    key "accessListDirection";

                    
                    leaf accessListDirection  {
                        type  cml_data_types:CML_BGP_COMMUNITY_LIST_ACTION_T;  
                    } // END of accessListDirection definition.


                    list bgpRegExp {
                         
                        description
                            "bgpRegExp";

                        config true;
                        key "bgpRegExp";

                        
                        leaf bgpRegExp  {
                            type  cml_data_types:CML_STRING_T {
                                length "0..255";
                            }
                            description "ip as-path access-list";
                        } // END of bgpRegExp definition.

                    } // End of bgpRegExp-list
                } // End of accessListDirection-list
            } // End of accessList-list
        } // End of bgpGlobal-list
    } // END of bgpGlobal-grouping definition.


    grouping bgpDebug-grouping {
        list bgpDebug {
             
            description
                "bgpDebug";

            config true;
            key "vrId";

            
            leaf vrId  {
                type  cml_data_types:CML_UINT32_T;  
            } // END of vrId definition.

            leaf debugFlag  {
                type  cml_data_types:CML_BGP_DEBUG_TYPE_T;  
                default "all";
            } // END of debugFlag definition.

            leaf undebugFlag  {
                type  cml_data_types:CML_BGP_DEBUG_TYPE_T;  
                default "all";
            } // END of undebugFlag definition.

            leaf debugUpdateFlag  {
                type  cml_data_types:CML_BGP_UPDATE_DEBUG_TYPE_T;  
            } // END of debugUpdateFlag definition.

        } // End of bgpDebug-list
    } // END of bgpDebug-grouping definition.


    grouping hashTableSize-grouping {
        list hashTableSize {
             
            description
                "hashTableSize";

            config false;
            key "hashSize";

            
            leaf hashSize  {
                type  cml_data_types:CML_INT32_T;  
            } // END of hashSize definition.

            container hashTableInfo {
                                config false;

                description
                    "hashTableInfo";

                leaf hashBacket  {
                    type  cml_data_types:CML_STRING_T {
                        length "0..255";
                    }
                } // END of hashBacket definition.

                leaf hashRefCnt  {
                    type  cml_data_types:CML_INT32_T;  
                } // END of hashRefCnt definition.

                leaf hashAsStr  {
                    type  cml_data_types:CML_STRING_T {
                        length "0..255";
                    }
                } // END of hashAsStr definition.

                leaf hashComStr  {
                    type  cml_data_types:CML_STRING_T {
                        length "0..255";
                    }
                } // END of hashComStr definition.

            } // END of hashTableInfo-container definition.
        } // End of hashTableSize-list
    } // END of hashTableSize-grouping definition.


    grouping vrfTable-grouping {
        list vrfTable {
             
            description
                "vrfTable";

            config true;
            key "vrfName";

            
            leaf vrfName  {
                type  cml_data_types:CML_STRING_T {
                    length "0..255";
                }
            } // END of vrfName definition.

            leaf importMap  {
                type  cml_data_types:CML_STRING_T {
                    length "0..255";
                }
            } // END of importMap definition.

            leaf rdStr  {
                type  cml_data_types:CML_STRING_T {
                    length "0..255";
                }
                description "route distinguisher";
            } // END of rdStr definition.


            list routeTarget {
                 
                description
                    "routeTarget";

                config true;
                key "rtRdStr";

                
                leaf direct  {
                    mandatory true;
                    type  cml_data_types:CML_RT_T;  
                } // END of direct definition.

                leaf rtRdStr  {
                    type  cml_data_types:CML_STRING_T {
                        length "0..255";
                    }
                    description "route distinguisher";
                } // END of rtRdStr definition.

            } // End of routeTarget-list
        } // End of vrfTable-list
    } // END of vrfTable-grouping definition.
    grouping peerRuntimeAttr {
                leaf maxPathIbgp  {
            type  cml_data_types:CML_INT32_T;  
            config false;
        } // END of maxPathIbgp definition.

        leaf asLocalCount  {
            type  cml_data_types:CML_INT32_T;  
            default "1";
            config false;
        } // END of asLocalCount definition.

        leaf cfgMaxPathEbgp  {
            type  cml_data_types:CML_INT32_T;  
            config false;
        } // END of cfgMaxPathEbgp definition.

        leaf maxPathEbgp  {
            type  cml_data_types:CML_INT32_T;  
            config false;
        } // END of maxPathEbgp definition.

        leaf cfgMaxPathIbgp  {
            type  cml_data_types:CML_INT32_T;  
            config false;
        } // END of cfgMaxPathIbgp definition.

        leaf bgpCommunityCount  {
            type  cml_data_types:CML_INT32_T;  
            config false;
        } // END of bgpCommunityCount definition.

        leaf peerConfedIdCheck  {
            type  cml_data_types:CML_STRING_T {
                length "0..255";
            }
            config false;
        } // END of peerConfedIdCheck definition.

        leaf peerAdvExtAsnCap  {
            type  cml_data_types:CML_STRING_T {
                length "0..255";
            }
            config false;
        } // END of peerAdvExtAsnCap definition.

        leaf peerAndExtAsnCap  {
            type  cml_data_types:CML_STRING_T {
                length "0..255";
            }
            config false;
        } // END of peerAndExtAsnCap definition.

        leaf peerRecvExtAsnCap  {
            type  cml_data_types:CML_STRING_T {
                length "0..255";
            }
            config false;
        } // END of peerRecvExtAsnCap definition.

        leaf addFamilystring  {
            type  cml_data_types:CML_STRING_T {
                length "0..255";
            }
            config false;
        } // END of addFamilystring definition.

        leaf keepAliveIn  {
            type  cml_data_types:CML_INT32_T;  
            config false;
        } // END of keepAliveIn definition.

        leaf keepAliveOut  {
            type  cml_data_types:CML_INT32_T;  
            config false;
        } // END of keepAliveOut definition.

        leaf openMsgIn  {
            type  cml_data_types:CML_INT32_T;  
            config false;
        } // END of openMsgIn definition.

        leaf openMsgOut  {
            type  cml_data_types:CML_INT32_T;  
            config false;
        } // END of openMsgOut definition.

        leaf bgpAsPathCount  {
            type  cml_data_types:CML_INT32_T;  
            config false;
        } // END of bgpAsPathCount definition.

        leaf bgpAsPath4BCount  {
            type  cml_data_types:CML_INT32_T;  
            config false;
        } // END of bgpAsPath4BCount definition.

        leaf updateMsgIn  {
            type  cml_data_types:CML_INT32_T;  
            default "0";
            config false;
        } // END of updateMsgIn definition.

        leaf updateMsgOut  {
            type  cml_data_types:CML_INT32_T;  
            default "0";
            config false;
        } // END of updateMsgOut definition.

        leaf nextHopGlobal  {
            type  cml_data_types:CML_STRING_T {
                length "0..255";
            }
            config false;
        } // END of nextHopGlobal definition.

        leaf nextHopLocal  {
            type  cml_data_types:CML_STRING_T {
                length "0..255";
            }
            config false;
        } // END of nextHopLocal definition.

        leaf peerRemotePort  {
            type  cml_data_types:CML_INT32_T;  
            config false;
        } // END of peerRemotePort definition.

        leaf peerRemoteAddr  {
            type  cml_data_types:CML_STRING_T {
                length "0..255";
            }
            config false;
        } // END of peerRemoteAddr definition.

        leaf peerLocalHost  {
            type  cml_data_types:CML_STRING_T {
                length "0..255";
            }
            config false;
        } // END of peerLocalHost definition.

        leaf nextHop  {
            type  cml_data_types:CML_STRING_T {
                length "0..255";
            }
            config false;
        } // END of nextHop definition.

        leaf peerLocalPort  {
            type  cml_data_types:CML_INT32_T;  
            config false;
        } // END of peerLocalPort definition.

        leaf prefixListCount  {
            type  cml_data_types:CML_INT32_T;  
            config false;
        } // END of prefixListCount definition.

        leaf defInfoOri  {
            type  cml_data_types:CML_STRING_T {
                length "0..255";
            }
            config false;
        } // END of defInfoOri definition.

        leaf InboundPathPolicy  {
            type  cml_data_types:CML_STRING_T {
                length "0..255";
            }
            config false;
        } // END of InboundPathPolicy definition.

        leaf OutboundPathPolicy  {
            type  cml_data_types:CML_STRING_T {
                length "0..255";
            }
            config false;
        } // END of OutboundPathPolicy definition.

        leaf defOriInfoSent  {
            type  cml_data_types:CML_STRING_T {
                length "0..255";
            }
            config false;
        } // END of defOriInfoSent definition.

        leaf orfPrefixStr  {
            type  cml_data_types:CML_STRING_T {
                length "0..255";
            }
            config false;
        } // END of orfPrefixStr definition.

        leaf orfPrefixSend  {
            type  cml_data_types:CML_STRING_T {
                length "0..255";
            }
            config false;
        } // END of orfPrefixSend definition.

        leaf orfPrefixCount  {
            type  cml_data_types:CML_STRING_T {
                length "0..255";
            }
            config false;
        } // END of orfPrefixCount definition.

        leaf orfWaitRefresh  {
            type  cml_data_types:CML_STRING_T {
                length "0..255";
            }
            config false;
        } // END of orfWaitRefresh definition.

        leaf grstRestart  {
            type  cml_data_types:CML_STRING_T {
                length "0..255";
            }
            config false;
        } // END of grstRestart definition.

        leaf afDependentCap  {
            type  cml_data_types:CML_STRING_T {
                length "0..255";
            }
            config false;
        } // END of afDependentCap definition.

        leaf peerAfTableVersion  {
            type  cml_data_types:CML_INT32_T;  
            config false;
        } // END of peerAfTableVersion definition.

        leaf peerBgpAfTableVersion  {
            type  cml_data_types:CML_INT32_T;  
            config false;
        } // END of peerBgpAfTableVersion definition.

        leaf peerIndex  {
            type  cml_data_types:CML_INT32_T;  
            config false;
        } // END of peerIndex definition.

        leaf peerOffset  {
            type  cml_data_types:CML_INT32_T;  
            config false;
        } // END of peerOffset definition.

        leaf peerMask  {
            type  cml_data_types:CML_STRING_T {
                length "0..255";
            }
            config false;
        } // END of peerMask definition.

        leaf fwdStatusPreserve  {
            type  cml_data_types:CML_STRING_T {
                length "0..255";
            }
            config false;
        } // END of fwdStatusPreserve definition.

        leaf orfTypePrefix  {
            type  cml_data_types:CML_STRING_T {
                length "0..255";
            }
            config false;
        } // END of orfTypePrefix definition.

        leaf orfTypePrefixSendMode  {
            type  cml_data_types:CML_STRING_T {
                length "0..255";
            }
            config false;
        } // END of orfTypePrefixSendMode definition.

        leaf orfTypePrefixRecvMode  {
            type  cml_data_types:CML_STRING_T {
                length "0..255";
            }
            config false;
        } // END of orfTypePrefixRecvMode definition.

        leaf orfTypePrefixOld  {
            type  cml_data_types:CML_STRING_T {
                length "0..255";
            }
            config false;
        } // END of orfTypePrefixOld definition.

        leaf orfTypePrefixSendModeOld  {
            type  cml_data_types:CML_STRING_T {
                length "0..255";
            }
            config false;
        } // END of orfTypePrefixSendModeOld definition.

        leaf orfTypePrefixRecvModeOld  {
            type  cml_data_types:CML_STRING_T {
                length "0..255";
            }
            config false;
        } // END of orfTypePrefixRecvModeOld definition.

        leaf peerPrefixCount  {
            type  cml_data_types:CML_INT32_T;  
            config false;
        } // END of peerPrefixCount definition.

        leaf peerSendPrefixCount  {
            type  cml_data_types:CML_INT32_T;  
            config false;
        } // END of peerSendPrefixCount definition.

        leaf peerFlagShutDown  {
            type  cml_data_types:CML_STRING_T {
                length "0..255";
            }
            config false;
        } // END of peerFlagShutDown definition.

        leaf peerCount  {
            type  cml_data_types:CML_INT32_T;  
            config false;
        } // END of peerCount definition.

        leaf brdAs  {
            type  cml_data_types:CML_INT32_T;  
            config false;
        } // END of brdAs definition.

        leaf brdAsNum  {
            type  cml_data_types:CML_INT32_T;  
            config false;
        } // END of brdAsNum definition.

        leaf brdAs4  {
            type  cml_data_types:CML_INT32_T;  
            config false;
        } // END of brdAs4 definition.

        leaf brdAsNum4  {
            type  cml_data_types:CML_INT32_T;  
            config false;
        } // END of brdAsNum4 definition.

        leaf brdIp  {
            type  cml_data_types:CML_STRING_T {
                length "0..255";
            }
            config false;
        } // END of brdIp definition.

        leaf brdIpNum  {
            type  cml_data_types:CML_INT32_T;  
            config false;
        } // END of brdIpNum definition.

        leaf peerNotifyInfo  {
            type  cml_data_types:CML_INT32_T;  
            config false;
        } // END of peerNotifyInfo definition.

        leaf peerNotifyDirect  {
            type  cml_data_types:CML_STRING_T {
                length "0..255";
            }
            config false;
        } // END of peerNotifyDirect definition.

        leaf peerNotifyLastReset  {
            type  cml_data_types:CML_STRING_T {
                length "0..255";
            }
            config false;
        } // END of peerNotifyLastReset definition.

        leaf notifyCodeStr  {
            type  cml_data_types:CML_STRING_T {
                length "0..255";
            }
            config false;
        } // END of notifyCodeStr definition.

        leaf bgpConnection  {
            type  cml_data_types:CML_STRING_T {
                length "0..255";
            }
            config false;
        } // END of bgpConnection definition.

        leaf nextConnectTimer  {
            type  cml_data_types:CML_INT32_T;  
            config false;
        } // END of nextConnectTimer definition.

        leaf conEstCount  {
            type  cml_data_types:CML_INT32_T;  
            config false;
        } // END of conEstCount definition.

        leaf conDroppedCount  {
            type  cml_data_types:CML_INT32_T;  
            config false;
        } // END of conDroppedCount definition.

        leaf peerPrefixOverflow  {
            type  cml_data_types:CML_STRING_T {
                length "0..255";
            }
            config false;
        } // END of peerPrefixOverflow definition.

        leaf peerGstatusAcceptGrst  {
            type  cml_data_types:CML_STRING_T {
                length "0..255";
            }
            config false;
        } // END of peerGstatusAcceptGrst definition.

        leaf peerGrstRestart  {
            type  cml_data_types:CML_INT32_T;  
            config false;
        } // END of peerGrstRestart definition.

        leaf bpfEstUpTime  {
            type  cml_data_types:CML_STRING_T {
                length "0..255";
            }
            config false;
        } // END of bpfEstUpTime definition.

        leaf lastReadTime  {
            type  cml_data_types:CML_STRING_T {
                length "0..255";
            }
            config false;
        } // END of lastReadTime definition.

        leaf bpfState  {
            type  cml_data_types:CML_STRING_T {
                length "0..255";
            }
            config false;
        } // END of bpfState definition.

        leaf peerLinkType  {
            type  cml_data_types:CML_STRING_T {
                length "0..255";
            }
            config false;
        } // END of peerLinkType definition.

        leaf hopAwayCount  {
            type  cml_data_types:CML_INT32_T;  
            config false;
        } // END of hopAwayCount definition.

        leaf peerRouterId  {
            type  cml_data_types:CML_STRING_T {
                length "0..255";
            }
            config false;
        } // END of peerRouterId definition.

        leaf recvPacketCount  {
            type  cml_data_types:CML_INT32_T;  
            config false;
        } // END of recvPacketCount definition.

        leaf notificationIn  {
            type  cml_data_types:CML_INT32_T;  
            config false;
        } // END of notificationIn definition.

        leaf notificationOut  {
            type  cml_data_types:CML_INT32_T;  
            config false;
        } // END of notificationOut definition.

        leaf pktInQue  {
            type  cml_data_types:CML_INT32_T;  
            config false;
        } // END of pktInQue definition.

        leaf sentPacketCount  {
            type  cml_data_types:CML_INT32_T;  
            config false;
        } // END of sentPacketCount definition.

        leaf refreshRecvPacketCount  {
            type  cml_data_types:CML_INT32_T;  
            config false;
        } // END of refreshRecvPacketCount definition.

        leaf refreshSentPacketCount  {
            type  cml_data_types:CML_INT32_T;  
            config false;
        } // END of refreshSentPacketCount definition.

        leaf advertisementInterval  {
            type  cml_data_types:CML_INT32_T;  
            config false;
        } // END of advertisementInterval definition.

        leaf peerHoldTimeRun  {
            type  cml_data_types:CML_INT32_T;  
            config false;
        } // END of peerHoldTimeRun definition.

        leaf peerKeepAliveRun  {
            type  cml_data_types:CML_INT32_T;  
            config false;
        } // END of peerKeepAliveRun definition.

        leaf neighborCap  {
            type  cml_data_types:CML_STRING_T {
                length "0..255";
            }
            config false;
        } // END of neighborCap definition.

        leaf advertisedCapability  {
            type  cml_data_types:CML_STRING_T {
                length "0..255";
            }
            config false;
        } // END of advertisedCapability definition.

        leaf advCapabilityRefresh  {
            type  cml_data_types:CML_STRING_T {
                length "0..255";
            }
            config false;
        } // END of advCapabilityRefresh definition.

        leaf noIfBinding  {
            type  cml_data_types:CML_STRING_T {
                length "0..255";
            }
            config false;
        } // END of noIfBinding definition.


        list peerPrefix {
             
            description
                "peerPrefix";

            config false;
            key "prefixEntrySeq";

            
            leaf prefixEntrySeq  {
                type  cml_data_types:CML_INT32_T;  
            } // END of prefixEntrySeq definition.

            leaf prefixEntryType  {
                type  cml_data_types:CML_STRING_T {
                    length "0..255";
                }
            } // END of prefixEntryType definition.

            leaf prefixEntryGe  {
                type  cml_data_types:CML_INT32_T;  
            } // END of prefixEntryGe definition.

            leaf prefixEntryLe  {
                type  cml_data_types:CML_INT32_T;  
            } // END of prefixEntryLe definition.

            leaf peerPrefixLen  {
                type  cml_data_types:CML_INT32_T;  
            } // END of peerPrefixLen definition.

        } // End of peerPrefix-list
    } // END of peerRuntimeAttr definition.
    grouping nextHopRunTimeAttr {
                leaf rfdFlapCount  {
            type  cml_data_types:CML_INT32_T;  
            config false;
        } // END of rfdFlapCount definition.

        leaf dampInfoTimes  {
            type  cml_data_types:CML_STRING_T {
                length "0..255";
            }
            config false;
        } // END of dampInfoTimes definition.

        leaf peerNtwkWeight  {
            type  cml_data_types:CML_INT32_T;  
            config false;
        } // END of peerNtwkWeight definition.

        leaf flapTimeReuseList  {
            type  cml_data_types:CML_STRING_T {
                length "0..255";
            }
            config false;
        } // END of flapTimeReuseList definition.

        leaf flapRecordDuration  {
            type  cml_data_types:CML_STRING_T {
                length "0..255";
            }
            config false;
        } // END of flapRecordDuration definition.

        leaf dampTimeToReuse  {
            type  cml_data_types:CML_STRING_T {
                length "0..255";
            }
            config false;
        } // END of dampTimeToReuse definition.

        leaf checkCidr  {
            type  cml_data_types:CML_INT32_T;  
            config false;
        } // END of checkCidr definition.

        leaf bgpInfoFlag  {
            type  cml_data_types:CML_STRING_T {
                length "0..255";
            }
            config false;
        } // END of bgpInfoFlag definition.

        leaf bgpAttrMpNexthopGlobalIn  {
            type  cml_data_types:CML_STRING_T {
                length "0..255";
            }
            config false;
        } // END of bgpAttrMpNexthopGlobalIn definition.

        leaf bgpAttrNextHop  {
            type  cml_data_types:CML_STRING_T {
                length "0..255";
            }
            config false;
        } // END of bgpAttrNextHop definition.

        leaf bgpAttrMpNexthopGlobal  {
            type  cml_data_types:CML_STRING_T {
                length "0..255";
            }
            config false;
        } // END of bgpAttrMpNexthopGlobal definition.

        leaf bgpAttrNextHopLen  {
            type  cml_data_types:CML_STRING_T {
                length "0..255";
            }
            config false;
        } // END of bgpAttrNextHopLen definition.

        leaf bgpAttrMpNexthopLocal  {
            type  cml_data_types:CML_STRING_T {
                length "0..255";
            }
            config false;
        } // END of bgpAttrMpNexthopLocal definition.

        leaf bgpUpTime  {
            type  cml_data_types:CML_STRING_T {
                length "0..255";
            }
            config false;
        } // END of bgpUpTime definition.

        leaf medFlagType  {
            type  cml_data_types:CML_STRING_T {
                length "0..255";
            }
            config false;
        } // END of medFlagType definition.

        leaf bgpMedVal  {
            type  cml_data_types:CML_INT32_T;  
            config false;
        } // END of bgpMedVal definition.

        leaf bgpAsPathStr  {
            type  cml_data_types:CML_STRING_T {
                length "0..255";
            }
            config false;
        } // END of bgpAsPathStr definition.

        leaf bgpAsPath4BStr  {
            type  cml_data_types:CML_STRING_T {
                length "0..255";
            }
            config false;
        } // END of bgpAsPath4BStr definition.

        leaf bgpAsPathOrigin  {
            type  cml_data_types:CML_STRING_T {
                length "0..255";
            }
            config false;
        } // END of bgpAsPathOrigin definition.

        leaf bgpAsPath4BOrigin  {
            type  cml_data_types:CML_STRING_T {
                length "0..255";
            }
            config false;
        } // END of bgpAsPath4BOrigin definition.

        leaf ibgpMetricRoute  {
            type  cml_data_types:CML_INT32_T;  
            config false;
        } // END of ibgpMetricRoute definition.

        leaf aggregateAsRoute  {
            type  cml_data_types:CML_INT32_T;  
            config false;
        } // END of aggregateAsRoute definition.

        leaf aggregatorAddrRoute  {
            type  cml_data_types:CML_STRING_T {
                length "0..255";
            }
            config false;
        } // END of aggregatorAddrRoute definition.

        leaf networkRemoteAddrRoute  {
            type  cml_data_types:CML_STRING_T {
                length "0..255";
            }
            config false;
        } // END of networkRemoteAddrRoute definition.

        leaf originatorIdRoute  {
            type  cml_data_types:CML_STRING_T {
                length "0..255";
            }
            config false;
        } // END of originatorIdRoute definition.

        leaf routePeerAddrRoute  {
            type  cml_data_types:CML_STRING_T {
                length "0..255";
            }
            config false;
        } // END of routePeerAddrRoute definition.

        leaf routeLocalPrefRoute  {
            type  cml_data_types:CML_INT32_T;  
            config false;
        } // END of routeLocalPrefRoute definition.

        leaf briLabelRoute  {
            type  cml_data_types:CML_INT32_T;  
            config false;
        } // END of briLabelRoute definition.

        leaf routeCommNameRoute  {
            type  cml_data_types:CML_STRING_T {
                length "0..255";
            }
            config false;
        } // END of routeCommNameRoute definition.

        leaf clusterListRoute  {
            type  cml_data_types:CML_STRING_T {
                length "0..255";
            }
            config false;
        } // END of clusterListRoute definition.

        leaf routeGetPenaltyRoute  {
            type  cml_data_types:CML_INT32_T;  
            config false;
        } // END of routeGetPenaltyRoute definition.

        leaf routeGetFlapCountRoute  {
            type  cml_data_types:CML_INT32_T;  
            config false;
        } // END of routeGetFlapCountRoute definition.

        leaf lastUpdateRoute  {
            type  cml_data_types:CML_STRING_T {
                length "0..255";
            }
            config false;
        } // END of lastUpdateRoute definition.

        leaf reflectorClientRoute  {
            type  cml_data_types:CML_STRING_T {
                length "0..255";
            }
            config false;
        } // END of reflectorClientRoute definition.

        leaf routeDampeningFlagRoute  {
            type  cml_data_types:CML_STRING_T {
                length "0..255";
            }
            config false;
        } // END of routeDampeningFlagRoute definition.

        leaf historyRoute  {
            type  cml_data_types:CML_STRING_T {
                length "0..255";
            }
            config false;
        } // END of historyRoute definition.

        leaf nhopValidRoute  {
            type  cml_data_types:CML_STRING_T {
                length "0..255";
            }
            config false;
        } // END of nhopValidRoute definition.

        leaf routeMedFlagTypeRoute  {
            type  cml_data_types:CML_STRING_T {
                length "0..255";
            }
            config false;
        } // END of routeMedFlagTypeRoute definition.

        leaf routeValidStateRoute  {
            type  cml_data_types:CML_STRING_T {
                length "0..255";
            }
            config false;
        } // END of routeValidStateRoute definition.

        leaf bgpInfoStaleRoute  {
            type  cml_data_types:CML_STRING_T {
                length "0..255";
            }
            config false;
        } // END of bgpInfoStaleRoute definition.

        leaf routePeerLocalAsRoute  {
            type  cml_data_types:CML_STRING_T {
                length "0..255";
            }
            config false;
        } // END of routePeerLocalAsRoute definition.

        leaf bgpConfedPeerRoute  {
            type  cml_data_types:CML_STRING_T {
                length "0..255";
            }
            config false;
        } // END of bgpConfedPeerRoute definition.

        leaf bgpInfoTypeRoute  {
            type  cml_data_types:CML_STRING_T {
                length "0..255";
            }
            config false;
        } // END of bgpInfoTypeRoute definition.

        leaf ecmpMultiCandidateRoute  {
            type  cml_data_types:CML_STRING_T {
                length "0..255";
            }
            config false;
        } // END of ecmpMultiCandidateRoute definition.

        leaf multiInstalledRoute  {
            type  cml_data_types:CML_INT32_T;  
            config false;
        } // END of multiInstalledRoute definition.

        leaf routeSyncFlagRoute  {
            type  cml_data_types:CML_BOOL_T;  
            config false;
        } // END of routeSyncFlagRoute definition.

        leaf atomicAggregateRoute  {
            type  cml_data_types:CML_STRING_T {
                length "0..255";
            }
            config false;
        } // END of atomicAggregateRoute definition.

        leaf bgpInfoSelectedRoute  {
            type  cml_data_types:CML_STRING_T {
                length "0..255";
            }
            config false;
        } // END of bgpInfoSelectedRoute definition.

    } // END of nextHopRunTimeAttr definition.
    grouping peerVrfAttrs {
                leaf bgpPortAf  {
            type  cml_data_types:CML_UINT16_T {
                 range "0..65535";
            }
            default "179";
            description "neighbor port for address-family";
        } // END of bgpPortAf definition.

        leaf peerActivateAf  {
            type  cml_data_types:CML_BOOL_T;  
            description "neighbor activate for address family";
        } // END of peerActivateAf definition.

        leaf defaultPeerRmapNameAf  {
            type  cml_data_types:CML_BOOL_T;  
            description "neighbor default-originate for address family";
        } // END of defaultPeerRmapNameAf definition.

        leaf peerRmapOriNameAf  {
            type  cml_data_types:CML_STRING_T {
                length "0..255";
            }
            description "neighbor default-originate router-map for address-family";
        } // END of peerRmapOriNameAf definition.

        leaf softReconfigInboundAf  {
            type  cml_data_types:CML_BOOL_T;  
            description "neighbor soft-reconfiguration inbound for address family";
        } // END of softReconfigInboundAf definition.

        leaf weightAf  {
            type  cml_data_types:CML_UINT16_T {
                 range "0..65535";
            }
            default "0";
            description "neighbor weight for address family";
        } // END of weightAf definition.

        leaf peerRouteReflectorAf  {
            type  cml_data_types:CML_BOOL_T;  
            description "neighbor route-reflector-client for address family";
        } // END of peerRouteReflectorAf definition.

        leaf peerRemovePvtAsAf  {
            type  cml_data_types:CML_BOOL_T;  
            description "neighbor remove-private-AS for address family";
        } // END of peerRemovePvtAsAf definition.

        leaf sendCommunityAf  {
            type  cml_data_types:CML_BOOL_T;  
            description "neighbor send-community for address family";
        } // END of sendCommunityAf definition.

        leaf sendCommunityTypeAf  {
            type  cml_data_types:CML_BGP_SEND_COMMU_TYPE_T;  
            description "neighbor send-community attribute for address family";
        } // END of sendCommunityTypeAf definition.

        leaf neighborAttrUnchangedAf  {
            type  cml_data_types:CML_ATTRIBUTE_UNCHANGED_TYPE_T;  
            description "neighbor attribute-unchanged for address family";
        } // END of neighborAttrUnchangedAf definition.

        leaf orfPrefixOptAf  {
            type  cml_data_types:CML_BGP_ORF_PREFIX_TYPE_T;  
            description "orf prefix-list ";
        } // END of orfPrefixOptAf definition.

        leaf setNcpFlagAf  {
            type  cml_data_types:CML_BOOL_T;  
            description "neighbor orf prefix-list for address family";
        } // END of setNcpFlagAf definition.

        leaf peerAllowEbgpVpnAf  {
            if-feature feature_list:HAVE_VRF;
            type  cml_data_types:CML_BOOL_T;  
            description "neighbor allow-ebgp-vpn for address family";
        } // END of peerAllowEbgpVpnAf definition.

        leaf allowAsNumAf  {
            type  cml_data_types:CML_UINT32_T {
                 range "1..10";
            }
            default "3";
            description "neighbor allowas-in for address family";
        } // END of allowAsNumAf definition.

        leaf neighborCapabilityGrstAf  {
            type  cml_data_types:CML_BOOL_T;  
            description "neighbor capability graceful-restart for address family";
        } // END of neighborCapabilityGrstAf definition.

        leaf aclInfoAf  {
            type  cml_data_types:CML_STRING_T {
                length "0..255";
            }
        } // END of aclInfoAf definition.

        leaf distributeListDirectionAf  {
            type  cml_data_types:CML_BGP_DISTRIBUTE_LIST_ACTION_T;  
            description "neighbor distribute-list for address family";
        } // END of distributeListDirectionAf definition.

        leaf asListAclInfoAf  {
            type  cml_data_types:CML_STRING_T {
                length "0..255";
            }
        } // END of asListAclInfoAf definition.

        leaf asListDirectionAf  {
            type  cml_data_types:CML_BGP_DISTRIBUTE_LIST_ACTION_T;  
            description "neighbor filter-list for address family";
        } // END of asListDirectionAf definition.

        leaf peerGroupTagAf  {
            type  cml_data_types:CML_STRING_T {
                length "0..255";
            }
            description "to add a neighbor to an existing peer-group for address family";
        } // END of peerGroupTagAf definition.

        leaf prefixListAclInfoAf  {
            type  cml_data_types:CML_STRING_T {
                length "0..255";
            }
        } // END of prefixListAclInfoAf definition.

        leaf prefixListDirectionAf  {
            type  cml_data_types:CML_BGP_DISTRIBUTE_LIST_ACTION_T;  
            description "neighbor prefix-list for address family";
        } // END of prefixListDirectionAf definition.

        leaf peerRmapNameAf  {
            type  cml_data_types:CML_STRING_T {
                length "0..255";
            }
        } // END of peerRmapNameAf definition.

        leaf peerRmapDirectionAf  {
            type  cml_data_types:CML_BGP_DISTRIBUTE_LIST_ACTION_T;  
            description "neighbor route-map for address family";
        } // END of peerRmapDirectionAf definition.

        leaf maxPrefixesAf  {
            type  cml_data_types:CML_UINT32_T {
                 range "1..4294967295";
            }
            description "neighbor maximum-prefix for address-family";
        } // END of maxPrefixesAf definition.

        leaf stopUpdateAf  {
            type  cml_data_types:CML_BOOL_T;  
            description "neighbor maximum-prefix stop-update for address-family";
        } // END of stopUpdateAf definition.

        leaf maxPrefixeWarningAf  {
            type  cml_data_types:CML_BOOL_T;  
            description "neighbor maximum-prefix warning for address-family";
        } // END of maxPrefixeWarningAf definition.

        leaf thresholdAf  {
            type  cml_data_types:CML_UINT8_T {
                 range "1..100";
            }
            default "75";
            description "neighbor maximum-prefix threshold for address-family";
        } // END of thresholdAf definition.

        leaf warningAf  {
            type  cml_data_types:CML_BOOL_T;  
            description "neighbor maximum-prefix threshold warning for address-family";
        } // END of warningAf definition.

        leaf unSuppressAclInfoAf  {
            type  cml_data_types:CML_STRING_T {
                length "0..255";
            }
            description "neighbor unsuppress-map for address-family";
        } // END of unSuppressAclInfoAf definition.

    } // END of peerVrfAttrs definition.


}
