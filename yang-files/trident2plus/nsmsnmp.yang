/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : nsmsnmp.yang
*
*/

submodule nsmsnmp {

    belongs-to  ZebOS { prefix ZebOS; }

    import cml_data_types {
        prefix cml_data_types;
    }

    import feature_list {
        prefix feature_list;
    }

    include vrf;
    organization
        "IP Infusion Inc.";

    contact
        "Address: 3965 Freedom Circle, Suite 200, Santa Clara, CA 95054
        Phone: +1 408-400-1900
        E-mail: support@ipinfusion.com
        Web: http://www.ipinfusion.com/";

    description
        "Simple Network Management Protocol";


    revision "2017-05-20" {
        description "Added auto-populate custom tag.";
    }

    revision "2017-02-20" {
        description "Initial version of SNMP datamodel.";
    }


    grouping  nsmsnmp-grouping {
    container nsmsnmp {
        description
            "snmp  related operations";
        leaf vrfName  {
            type  cml_data_types:CML_STRING_T {
                length "0..255";
            }
        } // END of vrfName definition.

        leaf enabled  {
            type  cml_data_types:CML_BOOL_T;
            description "enable snmp-server";
        } // END of enabled definition.

        leaf syscontact  {
            if-feature feature_list:HAVE_SNMP_AGENT;
            type  cml_data_types:CML_LINE_T;
        } // END of syscontact definition.

        leaf syslocation  {
            if-feature feature_list:HAVE_SNMP_AGENT;
            type  cml_data_types:CML_LINE_T;
        } // END of syslocation definition.

    } // END of nsmsnmp-container definition.
    } // END of nsmsnmp-container definition.


}
