/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : acl.yang
*
*/

submodule acl {

    belongs-to  ZebOS { prefix ZebOS; }

    import cml_data_types {
        prefix cml_data_types;
    }

    import feature_list {
        prefix feature_list;
    }

    organization
        "IP Infusion Inc.";

    contact
        "Address: 3965 Freedom Circle, Suite 200, Santa Clara, CA 95054
        Phone: +1 408-400-1900
        E-mail: support@ipinfusion.com
        Web: http://www.ipinfusion.com/";

    description
        "Access List Related Configurations";


    revision "2017-05-23" {
        description " Intial Version.";
    }

    grouping accessListAttr {
        description
            "accessListAttr";
        leaf remark  {
            type  cml_data_types:CML_STRING_T {
                length "0..255";
            }
        } // END of remark definition.

        leaf startSeqNum  {
            type  cml_data_types:CML_UINT32_T;
        } // END of startSeqNum definition.

        leaf increment  {
            type  cml_data_types:CML_UINT64_T;
        } // END of increment definition.

        leaf filterTypeDF  {
            type  cml_data_types:CML_ACL_FILTER_ACTION_T;
            default "deny-all";
        } // END of filterTypeDF definition.

        leaf logDF  {
            if-feature feature_list:HAVE_SFLOW;
            type  cml_data_types:CML_BOOL_T;
        } // END of logDF definition.

        leaf sampleDF  {
            if-feature feature_list:HAVE_SFLOW;
            type  cml_data_types:CML_BOOL_T;
        } // END of sampleDF definition.


        list filterList {
            key "accessNumFL";
            description
                "filterList";
            leaf accessNumFL  {
                type  cml_data_types:CML_UINT32_T {
                     range "1..268435453";
                }
            } // END of accessNumFL definition.

            leaf filterTypeFL  {
                type  cml_data_types:CML_ACL_FILTER_ACTION_T;
            } // END of filterTypeFL definition.

            leaf logFL  {
                if-feature feature_list:HAVE_SFLOW;
                type  cml_data_types:CML_BOOL_T;
            } // END of logFL definition.

            leaf sampleFL  {
                if-feature feature_list:HAVE_SFLOW;
                type  cml_data_types:CML_BOOL_T;
            } // END of sampleFL definition.

            leaf packetFormatFM  {
                type  cml_data_types:CML_ACL_ETHER_TYPE_T;
            } // END of packetFormatFM definition.

            leaf cosFM  {
                type  cml_data_types:CML_INT32_T {
                     range "0..7";
                }
            } // END of cosFM definition.

            leaf vlanFM  {
                type  cml_data_types:CML_INT32_T {
                     range "1..4094";
                }
            } // END of vlanFM definition.

            leaf sMacFM  {
                type  cml_data_types:CML_STRING_T {
                    length "0..255";

                    pattern "[0-9a-fA-F]{1,4}\.[0-9a-fA-F]{1,4}\.[0-9a-fA-F]{1,4}|[0-9a-fA-F]{2}\-[0-9a-fA-F]{2}\-[0-9a-fA-F]{2}\-[0-9a-fA-F]{2}\-[0-9a-fA-F]{2}\-[0-9a-fA-F]{2}|[0-9a-fA-F]{2}:[0-9a-fA-F]{2}:[0-9a-fA-F]{2}:[0-9a-fA-F]{2}:[0-9a-fA-F]{2}:[0-9a-fA-F]{2}|any";
                }
            } // END of sMacFM definition.

            leaf sMacMaskFM  {
                type  cml_data_types:CML_STRING_T {
                    length "0..255";

                    pattern "[0-9a-fA-F]{1,4}\.[0-9a-fA-F]{1,4}\.[0-9a-fA-F]{1,4}|[0-9a-fA-F]{2}\-[0-9a-fA-F]{2}\-[0-9a-fA-F]{2}\-[0-9a-fA-F]{2}\-[0-9a-fA-F]{2}\-[0-9a-fA-F]{2}|[0-9a-fA-F]{2}:[0-9a-fA-F]{2}:[0-9a-fA-F]{2}:[0-9a-fA-F]{2}:[0-9a-fA-F]{2}:[0-9a-fA-F]{2}";
                }
            } // END of sMacMaskFM definition.

            leaf dMacFM  {
                type  cml_data_types:CML_STRING_T {
                    length "0..255";

                    pattern "[0-9a-fA-F]{1,4}\.[0-9a-fA-F]{1,4}\.[0-9a-fA-F]{1,4}|[0-9a-fA-F]{2}\-[0-9a-fA-F]{2}\-[0-9a-fA-F]{2}\-[0-9a-fA-F]{2}\-[0-9a-fA-F]{2}\-[0-9a-fA-F]{2}|[0-9a-fA-F]{2}:[0-9a-fA-F]{2}:[0-9a-fA-F]{2}:[0-9a-fA-F]{2}:[0-9a-fA-F]{2}:[0-9a-fA-F]{2}|any";
                }
            } // END of dMacFM definition.

            leaf dMacMaskFM  {
                type  cml_data_types:CML_STRING_T {
                    length "0..255";

                    pattern "[0-9a-fA-F]{1,4}\.[0-9a-fA-F]{1,4}\.[0-9a-fA-F]{1,4}|[0-9a-fA-F]{2}\-[0-9a-fA-F]{2}\-[0-9a-fA-F]{2}\-[0-9a-fA-F]{2}\-[0-9a-fA-F]{2}\-[0-9a-fA-F]{2}|[0-9a-fA-F]{2}:[0-9a-fA-F]{2}:[0-9a-fA-F]{2}:[0-9a-fA-F]{2}:[0-9a-fA-F]{2}:[0-9a-fA-F]{2}";
                }
            } // END of dMacMaskFM definition.

            leaf sIpFC  {
                type  cml_data_types:CML_ACL_ANY_IPV4_ADDR_T;
            } // END of sIpFC definition.

            leaf dIpFC  {
                type  cml_data_types:CML_ACL_ANY_IPV4_ADDR_T;
            } // END of dIpFC definition.

            leaf protocolFC  {
                type  cml_data_types:CML_ACL_IP_PROTO_T;
            } // END of protocolFC definition.

            leaf srcPortMinFC  {
                type  cml_data_types:CML_UINT16_T {
                     range "0..65535";
                }
            } // END of srcPortMinFC definition.

            leaf srcPortMaxFC  {
                type  cml_data_types:CML_UINT16_T {
                     range "0..65535";
                }
            } // END of srcPortMaxFC definition.

            leaf srcPortUdpFC  {
                type  cml_data_types:CML_ACL_UDP_KEYWORD_T;
            } // END of srcPortUdpFC definition.

            leaf srcPortTcpFC  {
                type  cml_data_types:CML_ACL_TCP_KEYWORD_T;
            } // END of srcPortTcpFC definition.

            leaf srcPortOperFC  {
                type  cml_data_types:CML_ACL_PORT_OPERATIONS_T;
            } // END of srcPortOperFC definition.

            leaf destPortMinFC  {
                type  cml_data_types:CML_UINT16_T {
                     range "0..65535";
                }
            } // END of destPortMinFC definition.

            leaf destPortMaxFC  {
                type  cml_data_types:CML_UINT16_T {
                     range "0..65535";
                }
            } // END of destPortMaxFC definition.

            leaf destPortUdpFC  {
                type  cml_data_types:CML_ACL_UDP_KEYWORD_T;
            } // END of destPortUdpFC definition.

            leaf destPortTcpFC  {
                type  cml_data_types:CML_ACL_TCP_KEYWORD_T;
            } // END of destPortTcpFC definition.

            leaf destPortOperFC  {
                type  cml_data_types:CML_ACL_PORT_OPERATIONS_T;
            } // END of destPortOperFC definition.

            leaf dscpFC  {
                type  cml_data_types:CML_ACL_DSCP_T;
            } // END of dscpFC definition.

            leaf precedenceFC  {
                type  cml_data_types:CML_ACL_PRECEDENCE_T;
            } // END of precedenceFC definition.

            leaf fragmentsFC  {
                type  cml_data_types:CML_INT32_T;
            } // END of fragmentsFC definition.

            leaf tcpFlagFC  {
                type  cml_data_types:CML_ACL_TCP_FLAGS_T;
            } // END of tcpFlagFC definition.

            leaf icmpMsgFC  {
                type  cml_data_types:CML_ACL_ICMP_OPTIONS_T;
            } // END of icmpMsgFC definition.

            leaf icmpTypeFC  {
                type  cml_data_types:CML_UINT8_T {
                     range "0..255";
                }
            } // END of icmpTypeFC definition.

            leaf icmpCodeFC  {
                type  cml_data_types:CML_UINT8_T {
                     range "0..255";
                }
            } // END of icmpCodeFC definition.

            leaf protocolFZE  {
                type  cml_data_types:CML_ACL_IPV6_PROTO_T;
            } // END of protocolFZE definition.

            leaf srcAddrFZE  {
                type  cml_data_types:CML_ACL_ANY_IPV6_ADDR_T;
            } // END of srcAddrFZE definition.

            leaf srcPortOperFZE  {
                type  cml_data_types:CML_ACL_PORT_OPERATIONS_T;
            } // END of srcPortOperFZE definition.

            leaf srcPortMaxFZE  {
                type  cml_data_types:CML_UINT16_T {
                     range "0..65535";
                }
            } // END of srcPortMaxFZE definition.

            leaf srcPortMinFZE  {
                type  cml_data_types:CML_UINT16_T {
                     range "0..65535";
                }
            } // END of srcPortMinFZE definition.

            leaf srcPortUdpFZE  {
                type  cml_data_types:CML_ACL_UDP_KEYWORD_T;
            } // END of srcPortUdpFZE definition.

            leaf srcPortTcpFZE  {
                type  cml_data_types:CML_ACL_TCP_KEYWORD_T;
            } // END of srcPortTcpFZE definition.

            leaf destAddrFZE  {
                type  cml_data_types:CML_ACL_ANY_IPV6_ADDR_T;
            } // END of destAddrFZE definition.

            leaf destPortOperFZE  {
                type  cml_data_types:CML_ACL_PORT_OPERATIONS_T;
            } // END of destPortOperFZE definition.

            leaf destPortMaxFZE  {
                type  cml_data_types:CML_UINT16_T {
                     range "0..65535";
                }
            } // END of destPortMaxFZE definition.

            leaf destPortMinFZE  {
                type  cml_data_types:CML_UINT16_T {
                     range "0..65535";
                }
            } // END of destPortMinFZE definition.

            leaf destPortUdpFZE  {
                type  cml_data_types:CML_ACL_UDP_KEYWORD_T;
            } // END of destPortUdpFZE definition.

            leaf destPortTcpFZE  {
                type  cml_data_types:CML_ACL_TCP_KEYWORD_T;
            } // END of destPortTcpFZE definition.

            leaf icmpMsgFZE  {
                type  cml_data_types:CML_ACL_ICMPV6_OPTIONS_T;
            } // END of icmpMsgFZE definition.

            leaf icmpTypeFZE  {
                type  cml_data_types:CML_UINT8_T {
                     range "0..255";
                }
            } // END of icmpTypeFZE definition.

            leaf icmpCodeFZE  {
                type  cml_data_types:CML_UINT8_T {
                     range "0..255";
                }
            } // END of icmpCodeFZE definition.

            leaf flowLabelFZE  {
                type  cml_data_types:CML_INT32_T {
                     range "0..1048575";
                }
            } // END of flowLabelFZE definition.

            leaf fragmentsFZE  {
                type  cml_data_types:CML_INT32_T;
            } // END of fragmentsFZE definition.

            leaf dscpFZE  {
                type  cml_data_types:CML_ACL_DSCP_T;
            } // END of dscpFZE definition.

            leaf tcpFlagFZE  {
                type  cml_data_types:CML_ACL_TCP_FLAGS_T;
            } // END of tcpFlagFZE definition.

        } // End of filterList-list
    } // END of accessListAttr definition.

    grouping  accessMasterIPv4-grouping {
    container accessMasterIPv4 {
        description
            "accessMasterIPv4";
        leaf vrId  {
            type  cml_data_types:CML_INT32_T;
        } // END of vrId definition.


        list accessListIPv4 {
            key "aclNameIPv4";
            description
                "accessListIPv4";
            leaf aclNameIPv4  {
                type  cml_data_types:CML_STRING_T {
                    length "1..64";
                }
            } // END of aclNameIPv4 definition.

            uses accessListAttr;
        } // End of accessListIPv4-list

        list accessListMac {
            key "aclNameMAC";
            description
                "accessListMac";
            leaf aclNameMAC  {
                type  cml_data_types:CML_STRING_T {
                    length "1..64";
                }
            } // END of aclNameMAC definition.

            uses accessListAttr;
        } // End of accessListMac-list
    } // END of accessMasterIPv4-container definition.
    } // END of accessMasterIPv4-container definition.

    grouping  accessMasterIPv6-grouping {
    container accessMasterIPv6 {
        description
            "accessMasterIPv6";
        leaf vrId  {
            type  cml_data_types:CML_INT32_T;
        } // END of vrId definition.


        list accessListIPv6 {
            key "aclNameIPv6";
            description
                "accessListIPv6";
            leaf aclNameIPv6  {
                type  cml_data_types:CML_STRING_T {
                    length "1..64";
                }
            } // END of aclNameIPv6 definition.

            uses accessListAttr;
        } // End of accessListIPv6-list
    } // END of accessMasterIPv6-container definition.
    } // END of accessMasterIPv6-container definition.


}
