/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : routemap.yang
*
*/

submodule routemap {

    belongs-to  ZebOS { prefix ZebOS; }

    import cml_data_types {
        prefix cml_data_types;
    }

    import feature_list {
        prefix feature_list;
    }

    include interface;
    organization
        "IP Infusion Inc.";

    contact
        "Address: 3965 Freedom Circle, Suite 200, Santa Clara, CA 95054
        Phone: +1 408-400-1900
        E-mail: support@ipinfusion.com
        Web: http://www.ipinfusion.com/";

    description
        "Layer-3 pbr configurations";


    revision "2017-11-27" {
        description "Added CML_RANGE_T data type.";
    }

    revision "2016-12-28" {
        description "support added for auto generation of routemap commands.";
    }

    revision "2016-01-03" {
        description "support added for implicit delete tags.";
    }



    grouping pbrConfig-grouping {
        list pbrConfig {
            key "RouteMap";
            description
                "PBR Config related operations";
            leaf vrId  {
                type  cml_data_types:CML_UINT32_T;
                default "0";
            } // END of vrId definition.

            leaf RouteMap  {
                type  cml_data_types:CML_STRING_T {
                    length "0..255";
                }
            } // END of RouteMap definition.


            list pbrPermit {
                key "RmapPermit";
                description
                    "PBR Config related operations";
                leaf RmapPermit  {
                    type  cml_data_types:CML_RMAP_PERMIT_T;
                } // END of RmapPermit definition.


                list pbrSeq {
                    key "RmapSeq";
                    description
                        "PBR Config related operations";
                    leaf RmapSeq  {
                        type  cml_data_types:CML_INT32_T {
                             range "1..65535";
                        }
                    } // END of RmapSeq definition.

                    leaf ifName  {
                        type  cml_data_types:CML_STRING_T {
                            length "0..255";
                        }
                    } // END of ifName definition.

                    leaf forwardInterface  {
                        type  cml_data_types:CML_FORWARDTYPE_T;
                    } // END of forwardInterface definition.

                    leaf matchMetric  {
                        type  cml_data_types:CML_UINT32_T {
                             range "0..4294967295";
                        }
                    } // END of matchMetric definition.

                    leaf metricValue  {
                        type  cml_data_types:CML_STRING_T {
                            length "0..255";
                        }
                    } // END of metricValue definition.

                    leaf spfMinLength  {
                        if-feature feature_list:HAVE_PBR;
                        type  cml_data_types:CML_UINT32_T {
                             range "0..2147483647";
                        }
                        default "500";
                    } // END of spfMinLength definition.

                    leaf spfMaxLength  {
                        if-feature feature_list:HAVE_PBR;
                        type  cml_data_types:CML_UINT32_T {
                             range "0..2147483647";
                        }
                        default "5000";
                    } // END of spfMaxLength definition.

                    leaf vlanId  {
                        if-feature feature_list:HAVE_PBR;
                        if-feature feature_list:HAVE_VLAN;
                        type  cml_data_types:CML_RANGE_T;
                    } // END of vlanId definition.

                    leaf MacList  {
                        if-feature feature_list:HAVE_PBR;
                        if-feature feature_list:HAVE_VLAN;
                        type  cml_data_types:CML_STRING_T {
                            length "0..63";
                        }
                    } // END of MacList definition.

                    leaf Address  {
                        type  cml_data_types:CML_ROUTEMAP_LIST_T;
                    } // END of Address definition.

                    leaf prefixList  {
                        type  cml_data_types:CML_STRING_T {
                            length "0..255";
                        }
                    } // END of prefixList definition.

                    leaf matchNexthop  {
                        type  cml_data_types:CML_ROUTEMAP_LIST_T;
                    } // END of matchNexthop definition.

                    leaf matchPeer  {
                        type  cml_data_types:CML_ROUTEMAP_LIST_T;
                    } // END of matchPeer definition.

                    leaf matchPeerV6  {
                        if-feature feature_list:HAVE_IPV6;
                        type  cml_data_types:CML_ROUTEMAP_LIST_T;
                    } // END of matchPeerV6 definition.

                    leaf nextHopPlist  {
                        type  cml_data_types:CML_STRING_T {
                            length "0..255";
                        }
                    } // END of nextHopPlist definition.

                    leaf loadShare  {
                        type  cml_data_types:CML_BOOL_T;
                    } // END of loadShare definition.

                    leaf NextHop  {
                        if-feature feature_list:HAVE_PBR;
                        type  cml_data_types:CML_STRING_T {
                            length "0..255";
                        }
                    } // END of NextHop definition.

                    leaf NextHopv6  {
                        type  cml_data_types:CML_IPV6_ADDR_T;
                    } // END of NextHopv6 definition.

                    leaf defaultHop  {
                        type  cml_data_types:CML_STRING_T {
                            length "0..255";
                        }
                    } // END of defaultHop definition.

                    leaf DefaultHopV6  {
                        type  cml_data_types:CML_IPV6_ADDR_T;
                    } // END of DefaultHopV6 definition.

                    leaf localHopV6  {
                        type  cml_data_types:CML_IPV6_ADDR_T;
                    } // END of localHopV6 definition.

                    leaf nexthopPeerAddr  {
                        type  cml_data_types:CML_BOOL_T;
                    } // END of nexthopPeerAddr definition.

                    leaf asPathTag  {
                        type  cml_data_types:CML_BOOL_T;
                    } // END of asPathTag definition.

                    leaf addPathRmap  {
                        if-feature feature_list:HAVE_BGP_ADD_PATH;
                        type  cml_data_types:CML_ADDPATH_RMAP_T;
                    } // END of addPathRmap definition.

                    leaf Addressv6  {
                        type  cml_data_types:CML_STRING_T {
                            length "0..255";
                        }
                    } // END of Addressv6 definition.

                    leaf prefixList6  {
                        type  cml_data_types:CML_STRING_T {
                            length "0..255";
                        }
                    } // END of prefixList6 definition.

                    leaf matchNexthop6  {
                        if-feature feature_list:HAVE_ACL;
                        type  cml_data_types:CML_ROUTEMAP_MATCH_T;
                    } // END of matchNexthop6 definition.

                    leaf nextHopPlist6  {
                        type  cml_data_types:CML_STRING_T {
                            length "0..255";
                        }
                    } // END of nextHopPlist6 definition.

                    leaf vpn4NextHopAddr  {
                        if-feature feature_list:HAVE_VRF;
                        type  cml_data_types:CML_IPV4_ADDR_T;
                    } // END of vpn4NextHopAddr definition.

                    leaf matchNextTagValue  {
                        type  cml_data_types:CML_STRING_T {
                            length "0..255";
                        }
                    } // END of matchNextTagValue definition.

                    leaf matchRouteType  {
                        type  cml_data_types:CML_ROUTEMAP_EXTERNAL_TYPE_LIST;
                    } // END of matchRouteType definition.

                    leaf destRoutingTagValue  {
                        type  cml_data_types:CML_UINT32_T {
                             range "0..4294967295";
                        }
                    } // END of destRoutingTagValue definition.

                    leaf matchAspathTag  {
                        type  cml_data_types:CML_STRING_T {
                            length "0..255";
                        }
                    } // END of matchAspathTag definition.

                    leaf ospfMetricType  {
                        type  cml_data_types:CML_ROUTEMAP_OSPF_METRIC_TYPE_LIST;
                    } // END of ospfMetricType definition.

                    leaf isisMetricType  {
                        type  cml_data_types:CML_ROUTEMAP_ISIS_METRIC_TYPE_LIST;
                    } // END of isisMetricType definition.

                    leaf matchOriginCode  {
                        type  cml_data_types:CML_ROUTEMAP_ORIGIN_CODE;
                    } // END of matchOriginCode definition.

                    leaf exactMatch  {
                        type  cml_data_types:CML_ROUT_MAP_EXACT_MATCH_T;
                    } // END of exactMatch definition.

                    leaf matchCommunity  {
                        type  cml_data_types:CML_ROUTEMAP_COMMUNITY_LIST_T;
                    } // END of matchCommunity definition.

                    leaf matchExtCommunity  {
                        type  cml_data_types:CML_ROUTEMAP_COMMUNITY_LIST_T;
                    } // END of matchExtCommunity definition.

                    leaf prependLastAs  {
                        type  cml_data_types:CML_UINT32_T {
                             range "1..10";
                        }
                    } // END of prependLastAs definition.

                    leaf originCode  {
                        type  cml_data_types:CML_ROUTEMAP_ORIGIN_CODE;
                    } // END of originCode definition.

                    leaf localPreference  {
                        type  cml_data_types:CML_STRING_T {
                            length "0..255";
                        }
                    } // END of localPreference definition.

                    leaf weight  {
                        type  cml_data_types:CML_STRING_T {
                            length "0..255";
                        }
                    } // END of weight definition.

                    leaf atomicAggregate  {
                        type  cml_data_types:CML_BOOL_T;
                    } // END of atomicAggregate definition.

                    leaf aggregatorIpAddress  {
                        type  cml_data_types:CML_IPV4_ADDR_T;
                    } // END of aggregatorIpAddress definition.

                    leaf aggregatorAs  {
                        type  cml_data_types:CML_UINT32_T {
                             range "1..4294967295";
                        }
                    } // END of aggregatorAs definition.

                    leaf originatorId  {
                        type  cml_data_types:CML_IPV4_ADDR_T;
                    } // END of originatorId definition.

                    leaf communityList  {
                        type  cml_data_types:CML_ROUTEMAP_COMMUNITY_LIST_T;
                    } // END of communityList definition.

                    leaf unreachabilityHalftime  {
                        type  cml_data_types:CML_UINT16_T {
                             range "1..45";
                        }
                    } // END of unreachabilityHalftime definition.

                    leaf maxSupressStableRouteTime  {
                        type  cml_data_types:CML_UINT16_T {
                             range "1..255";
                        }
                    } // END of maxSupressStableRouteTime definition.

                    leaf supressRouteTime  {
                        type  cml_data_types:CML_UINT16_T {
                             range "1..20000";
                        }
                    } // END of supressRouteTime definition.

                    leaf reuseRouteTime  {
                        type  cml_data_types:CML_UINT16_T {
                             range "1..20000";
                        }
                    } // END of reuseRouteTime definition.

                    leaf reachabilityHalfTime  {
                        type  cml_data_types:CML_UINT16_T {
                             range "1..45";
                        }
                    } // END of reachabilityHalfTime definition.

                    leaf level  {
                        type  cml_data_types:CML_LEVEL_LIST_T;
                    } // END of level definition.

                    leaf asPathPrepend  {
                        if-feature feature_list:HAVE_EXT_CAP_ASN;
                        type  cml_data_types:CML_RANGE_T;
                    } // END of asPathPrepend definition.

                    leaf additive  {
                        type  cml_data_types:CML_ROUTEMAP_ADDITIVE_LIST_T;
                    } // END of additive definition.

                    leaf community  {
                        type  cml_data_types:CML_ROUTEMAP_COMMUNITY_T;
                    } // END of community definition.

                    leaf extAdditive  {
                        type  cml_data_types:CML_ROUTEMAP_ADDITIVE_LIST_T;
                    } // END of extAdditive definition.

                    leaf extCommunityRt  {
                        type  cml_data_types:CML_RANGE_T;
                    } // END of extCommunityRt definition.

                    leaf extCommunitySo  {
                        type  cml_data_types:CML_RANGE_T;
                    } // END of extCommunitySo definition.

                    leaf extCommunityCost  {
                        type  cml_data_types:CML_UINT32_T {
                             range "0..4294967295";
                        }
                    } // END of extCommunityCost definition.

                    leaf extCommunityId  {
                        type  cml_data_types:CML_INT32_T {
                             range "0..255";
                        }
                    } // END of extCommunityId definition.

                    leaf communityCostComparision  {
                        type  cml_data_types:CML_ROUTEMAP_COST_COMPARISION_T;
                    } // END of communityCostComparision definition.

                } // End of pbrSeq-list
            } // End of pbrPermit-list
        } // End of pbrConfig-list
    } // END of pbrConfig-grouping definition.


}
