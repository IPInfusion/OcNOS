/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : aclinterface.yang
*
*/

submodule aclinterface {

    belongs-to  ZebOS { prefix ZebOS; }

    import cml_data_types {
        prefix cml_data_types;
    }

    include interface;
    organization
        "IP Infusion Inc.";

    contact
        "Address: 3965 Freedom Circle, Suite 200, Santa Clara, CA 95054
        Phone: +1 408-400-1900
        E-mail: support@ipinfusion.com
        Web: http://www.ipinfusion.com/";

    description
        "Access List Interface Related Configurations";


    revision "2016-11-17" {
        description " Intial Version.";
    }



    grouping aclInterface-grouping {
        list aclInterface {
            key "ifName";
            description
                "ACL interface related operations";
            leaf ifName  {
                type  cml_data_types:CML_STRING_T {
                    length "0..255";
                }
            } // END of ifName definition.


            list aclIntfTypeList {
                key "ifAclType";
                description
                    "aclIntfTypeList";
                leaf ifAclType  {
                    type  cml_data_types:CML_ACL_TYPES_T;
                } // END of ifAclType definition.


                list aclIntfDirList {
                    key "ifAclDir";
                    description
                        "aclIntfDirList";
                    leaf ifAclName  {
                        type  cml_data_types:CML_STRING_T {
                            length "0..255";
                        }
                    } // END of ifAclName definition.

                    leaf ifAclDir  {
                        type  cml_data_types:CML_ACL_PACKET_DIR_T;
                    } // END of ifAclDir definition.

                } // End of aclIntfDirList-list
            } // End of aclIntfTypeList-list
        } // End of aclInterface-list
    } // END of aclInterface-grouping definition.


}
