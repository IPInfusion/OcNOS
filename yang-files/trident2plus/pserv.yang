/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : pserv.yang
*
*/

submodule pserv {

    belongs-to  ZebOS { prefix ZebOS; }

    import cml_data_types {
        prefix cml_data_types;
    }

    import feature_list {
        prefix feature_list;
    }

    organization
        "IP Infusion Inc.";

    contact
        "Address: 3965 Freedom Circle, Suite 200, Santa Clara, CA 95054
        Phone: +1 408-400-1900
        E-mail: support@ipinfusion.com
        Web: http://www.ipinfusion.com/";

    description
        "pserv configurations";


    revision "2017-05-29" {
        description "Added autopopulate custom tag for hsl.";
    }

    revision "2017-05-15" {
        description "Added autopopulate custom tag.";
    }

    revision "2016-12-27" {
        description "Added snmp oid and documentation tag.";
    }

    revision "2016-10-28" {
        description "Initial version of PSERV datamodel.";
    }


    grouping  pservd-grouping {
    container pservd {
        description
            "pservd";
        leaf featuresoftware_watchdog  {
            if-feature feature_list:HAVE_PSERVD;
            type  cml_data_types:CML_BOOL_T;
            description "feature software-watchdog";
        } // END of featuresoftware_watchdog definition.

        leaf keepalivetime  {
            if-feature feature_list:HAVE_PSERVD;
            type  cml_data_types:CML_UINT32_T {
                 range "30..1800";
            }
            description "software-watchdog keep-alive-time";
        } // END of keepalivetime definition.


        list watchdog {
            key "enablesoftware_watchdog";
            description
                "watchdog";
            leaf enablesoftware_watchdog  {
                type  cml_data_types:CML_STRING_T {
                    length "0..255";
                }
                description "software-watchdog";
            } // END of enablesoftware_watchdog definition.

            leaf pservglobals  {
                type  cml_data_types:CML_STRING_T {
                    length "0..255";
                }
                config false;
                description "protocol status";
            } // END of pservglobals definition.

        } // End of watchdog-list
    } // END of pservd-container definition.
    } // END of pservd-container definition.


}
