/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : usermgmt.yang
*
*/

submodule usermgmt {

    belongs-to  ZebOS { prefix ZebOS; }

    import cml_data_types {
        prefix cml_data_types;
    }

    organization
        "IP Infusion Inc.";

    contact
        "Address: 3965 Freedom Circle, Suite 200, Santa Clara, CA 95054
        Phone: +1 408-400-1900
        E-mail: support@ipinfusion.com
        Web: http://www.ipinfusion.com/";

    description
        "Layer-3 usermgmt configurations";


    revision "2017-09-06" {
        description "Added role restriction for clear command.";
    }

    revision "2017-09-04" {
        description "Updated range check for username attr.";
    }

    revision "2017-05-11" {
        description "Updated notif for cleartext password.";
    }

    revision "2017-01-19" {
        description "User not created properly-[jira-12851].";
    }

    revision "2016-12-27" {
        description "Added snmp oid and documentation tag.";
    }

    revision "2016-10-28" {
        description "Initial version of USERMGMT datamodel.";
    }



    grouping usermgmt-grouping {
        list usermgmt {
            key "username";
            description
                "usermgmt";
            leaf username  {
                type  cml_data_types:CML_STRING_T {
                    length "2..15";
                }
                description "Login name of the user";
            } // END of username definition.

            leaf encryptPassword  {
                type  cml_data_types:CML_STRING_T {
                    length "26..106";
                }
                description "username with encrypted password";
            } // END of encryptPassword definition.

            leaf password  {
                type  cml_data_types:CML_STRING_T {
                    length "5..32";
                }
                description "username with password";
            } // END of password definition.

            leaf role  {
                type  cml_data_types:USER_MGMT_ROLE_OPTIONS_T;
                default "network-user";
                description "role name";
            } // END of role definition.

        } // End of usermgmt-list
    } // END of usermgmt-grouping definition.

    grouping  userDebug-grouping {
    container userDebug {
        description
            "userDebug";
        leaf debugconfuser  {
            type  cml_data_types:CML_BOOL_T;
            description "debug user-mgmt";
        } // END of debugconfuser definition.

        leaf debuguser  {
            type  cml_data_types:CML_BOOL_T;
            description "debug user-mgmt";
        } // END of debuguser definition.

    } // END of userDebug-container definition.
    } // END of userDebug-container definition.


}
