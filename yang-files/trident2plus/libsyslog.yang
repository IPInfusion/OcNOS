/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : libsyslog.yang
*
*/

submodule libsyslog {

    belongs-to  ZebOS { prefix ZebOS; }

    import cml_data_types {
        prefix cml_data_types;
    }

    organization
        "IP Infusion Inc.";

    contact
        "Address: 3965 Freedom Circle, Suite 200, Santa Clara, CA 95054
        Phone: +1 408-400-1900
        E-mail: support@ipinfusion.com
        Web: http://www.ipinfusion.com/";

    description
        "syslog configurations";


    revision "2016-12-27" {
        description "Added snmp oid and documetation tag.";
    }

    revision "2016-10-28" {
        description "Initial version of SYSLOG datamodel.";
    }

    revision "2016-10-27" {
        description "Added auto_populate tag for logging_level.";
    }



    grouping logginglevel-grouping {
        list logginglevel {
            key "loggingmodule";
            description
                "for show logging level";
            leaf loggingmodule  {
                type  cml_data_types:CML_MODULE_NAME_T;
                description "logging level";
            } // END of loggingmodule definition.

            leaf logginglevel  {
                type  cml_data_types:CML_UINT32_T {
                     range "0..7";
                }
                mandatory true;
            } // END of logginglevel definition.

        } // End of logginglevel-list
    } // END of logginglevel-grouping definition.

    grouping  log-grouping {
    container log {
        description
            "log";
        leaf monitorseverity  {
            type  cml_data_types:CML_INT8_T {
                 range "0..7";
            }
            default "2";
            description "logging monitor";
        } // END of monitorseverity definition.

        leaf consoleseverity  {
            type  cml_data_types:CML_INT8_T {
                 range "0..7";
            }
            default "2";
            description "logging console";
        } // END of consoleseverity definition.

        leaf logfile  {
            type  cml_data_types:CML_STRING_T {
                length "0..255";

                pattern "[a-zA-Z0-9_]*";
            }
            description " Log filename";
        } // END of logfile definition.

        leaf severity  {
            type  cml_data_types:CML_UINT32_T {
                 range "0..7";
            }
            default "6";
            description "logfile_severity";
        } // END of severity definition.

        leaf size  {
            type  cml_data_types:CML_UINT32_T {
                 range "4096..4194304";
            }
            default "4194304";
            description "logging logfile";
        } // END of size definition.

        leaf debuglogfile  {
            type  cml_data_types:CML_STRING_T {
                length "0..255";
            }
            description "debug file name";
        } // END of debuglogfile definition.

        leaf debugsize  {
            type  cml_data_types:CML_UINT32_T {
                 range "4096..4194304";
            }
            description "debug logfile";
        } // END of debugsize definition.

        leaf log_syslog  {
            type  cml_data_types:CML_BOOL_T;
            description "log syslog";
        } // END of log_syslog definition.

        leaf timestamp  {
            type  cml_data_types:CML_TIMESTAMP_T;
            description "logging timestamp";
        } // END of timestamp definition.

    } // END of log-container definition.
    } // END of log-container definition.


}
