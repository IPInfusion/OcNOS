/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-rip.yang
*
*/

submodule zebos-rip {

    belongs-to  zebos { prefix zebos; }

    import cml_data_types {
        prefix cml_data_types;
    }

    import feature_list {
        prefix feature_list;
    }

    include zebos-interface;
    include zebos-vrf;
    organization
        "IP Infusion Inc.";

    contact
        "Address: 3965 Freedom Circle, Suite 200, Santa Clara, CA 95054
        Phone: +1 408-400-1900
        E-mail: support@ipinfusion.com
        Web: http://www.ipinfusion.com/";

    description
        "Routing Information Protocol";


    revision "2017-09-05" {
        description "Removed autoPopulate tag.";
    }

    revision "2017-02-11" {
        description "Added Config and runtime attributes.";
    }

    grouping ripContents {
        description
            "Elements for all rip instances";
        leaf version  {
            type  cml_data_types:CML_UINT8_T {
                 range "1..2";
            }
            default "2";
            description "";
        } // END of version definition.

        leaf-list enableNetwork  {
            type  cml_data_types:CML_IPV4_PREFIX_T;
            description "";
        } // END of enableNetwork definition.

        leaf-list enableInterface  {
            type  cml_data_types:CML_STRING_T {
                length "0..255";
            }
            description "";
        } // END of enableInterface definition.

        leaf-list neighbor  {
            type  cml_data_types:CML_IPV4_ADDR_T;
            description "";
        } // END of neighbor definition.

        leaf defaultInformation  {
            type  cml_data_types:CML_RIP_DEFAULT_ORIGINATE_T;
            description "";
        } // END of defaultInformation definition.

        leaf defaultMapName  {
            type  cml_data_types:CML_STRING_T {
                length "0..255";
            }
            default "NULL";
            description "";
        } // END of defaultMapName definition.

        leaf defaultMetric  {
            type  cml_data_types:CML_INT32_T {
                 range "1..15";
            }
            description "";
        } // END of defaultMetric definition.

        leaf metricType  {
            type  cml_data_types:CML_RIP_METRIC_T;
            default "disable";
            description "";
        } // END of metricType definition.

        leaf defaultDistance  {
            type  cml_data_types:CML_UINT8_T {
                 range "1..255";
            }
            description "";
        } // END of defaultDistance definition.

        leaf pcounter  {
            type  cml_data_types:CML_UINT32_T;
            config false;
            description "";
        } // END of pcounter definition.

        leaf pconnect  {
            type  cml_data_types:CML_UINT32_T;
            config false;
            description "";
        } // END of pconnect definition.

        leaf protocolUpdateDueTime  {
            type  cml_data_types:CML_UINT32_T;
            config false;
            description "";
        } // END of protocolUpdateDueTime definition.


        list ripOffsetDistributeListIfname {
            key "ifName";
            description
                "ripOffsetDistributeListIfname";
            leaf ifName  {
                type  cml_data_types:CML_STRING_T {
                    length "0..255";
                }
                description "";
            } // END of ifName definition.

            uses ripListCmdsUtility;
        } // End of ripOffsetDistributeListIfname-list

        list distanceTable {
            key "sourceAddr";
            description
                "distanceTable";
            leaf sourceAddr  {
                type  cml_data_types:CML_IPV4_PREFIX_T;
                description "";
            } // END of sourceAddr definition.

            leaf distance  {
                type  cml_data_types:CML_UINT8_T {
                     range "1..255";
                }
                mandatory true;
                description "";
            } // END of distance definition.

            leaf alistVal  {
                type  cml_data_types:CML_STRING_T {
                    length "0..255";
                }
                mandatory true;
                description "";
            } // END of alistVal definition.

        } // End of distanceTable-list

        list ripInterface {
            key "ifName";
            config false;
            description
                "RIP specific interface configuration";
            leaf ifName  {
                type  cml_data_types:CML_STRING_T {
                    length "0..255";
                }
                description "";
            } // END of ifName definition.

            leaf ifFlags  {
                type  cml_data_types:CML_UINT8_T;
                description "";
            } // END of ifFlags definition.

            leaf lock  {
                type  cml_data_types:CML_UINT16_T;
                description "";
            } // END of lock definition.

            leaf ifAuthMode  {
                type  cml_data_types:CML_RIP_AUTH_MODE_T;
                description "";
            } // END of ifAuthMode definition.

            leaf ifAuthStr  {
                type  cml_data_types:CML_STRING_T {
                    length "0..255";
                }
                description "";
            } // END of ifAuthStr definition.

            leaf ifKeyChain  {
                type  cml_data_types:CML_STRING_T {
                    length "0..255";
                }
                description "";
            } // END of ifKeyChain definition.

            leaf ifSplitHorizon  {
                type  cml_data_types:CML_RIP_SPLIT_HORIZON_T;
                description "";
            } // END of ifSplitHorizon definition.

            leaf ifSendVersionType  {
                type  cml_data_types:CML_RIP_SEND_VERSION_TYPE_T;
                description "";
            } // END of ifSendVersionType definition.

            leaf ifRecvVersionType  {
                type  cml_data_types:CML_RIP_RECV_VERSION_TYPE_T;
                description "";
            } // END of ifRecvVersionType definition.

            leaf-list ifAccessList  {
                type  cml_data_types:CML_STRING_T {
                    length "0..255";
                }
                description "";
            } // END of ifAccessList definition.

            leaf-list ifPrefixList  {
                type  cml_data_types:CML_STRING_T {
                    length "0..255";
                }
                description "";
            } // END of ifPrefixList definition.

            leaf ifAddr  {
                type  cml_data_types:CML_STRING_T {
                    length "0..255";
                }
                description "";
            } // END of ifAddr definition.

            leaf sentMcastUpdates  {
                type  cml_data_types:CML_UINT32_T;
                description "";
            } // END of sentMcastUpdates definition.

            leaf sentMcastRequests  {
                type  cml_data_types:CML_UINT32_T;
                description "";
            } // END of sentMcastRequests definition.

            leaf sentUnicastUpdates  {
                type  cml_data_types:CML_UINT32_T;
                description "";
            } // END of sentUnicastUpdates definition.

            leaf sentUnicastRequests  {
                type  cml_data_types:CML_UINT32_T;
                description "";
            } // END of sentUnicastRequests definition.

            leaf recvMcastUpdates  {
                type  cml_data_types:CML_UINT32_T;
                description "";
            } // END of recvMcastUpdates definition.

            leaf recvMcastRequests  {
                type  cml_data_types:CML_UINT32_T;
                description "";
            } // END of recvMcastRequests definition.

            leaf recvUnicastUpdates  {
                type  cml_data_types:CML_UINT32_T;
                description "";
            } // END of recvUnicastUpdates definition.

            leaf recvUnicastRequests  {
                type  cml_data_types:CML_UINT32_T;
                description "";
            } // END of recvUnicastRequests definition.

            leaf recvBadpackets  {
                type  cml_data_types:CML_UINT32_T;
                description "";
            } // END of recvBadpackets definition.

            leaf recvBadroutes  {
                type  cml_data_types:CML_UINT32_T;
                description "";
            } // END of recvBadroutes definition.

            leaf sentUpdates  {
                type  cml_data_types:CML_UINT32_T;
                description "";
            } // END of sentUpdates definition.

        } // End of ripInterface-list

        list ripDatabase {
            key "prefix";
            config false;
            description
                "RIP routing information base";
            leaf prefix  {
                type  cml_data_types:CML_STRING_T {
                    length "0..255";
                }
                description "";
            } // END of prefix definition.

            leaf routeType  {
                type  cml_data_types:CML_INT32_T;
                description "";
            } // END of routeType definition.

            leaf subType  {
                type  cml_data_types:CML_INT32_T;
                description "";
            } // END of subType definition.

            leaf tag  {
                type  cml_data_types:CML_UINT16_T;
                description "";
            } // END of tag definition.

            leaf distance  {
                type  cml_data_types:CML_UINT8_T;
                description "";
            } // END of distance definition.

            leaf flags  {
                type  cml_data_types:CML_UINT8_T;
                description "";
            } // END of flags definition.

            leaf routeCounter  {
                type  cml_data_types:CML_UINT32_T;
                description "";
            } // END of routeCounter definition.


            list nexthop {
                key "nextHopAddr";
                config false;
                description
                    "RIP nexthop";
                leaf nextHopAddr  {
                    type  cml_data_types:CML_STRING_T {
                        length "0..255";
                    }
                    description "";
                } // END of nextHopAddr definition.

                leaf from  {
                    type  cml_data_types:CML_STRING_T {
                        length "0..255";
                    }
                    description "";
                } // END of from definition.

                leaf ifindex  {
                    type  cml_data_types:CML_UINT32_T;
                    description "";
                } // END of ifindex definition.

                leaf nexthopFlags  {
                    type  cml_data_types:CML_UINT8_T;
                    description "";
                } // END of nexthopFlags definition.

                leaf routeMetric  {
                    type  cml_data_types:CML_UINT32_T;
                    description "";
                } // END of routeMetric definition.

                leaf timeout  {
                    type  cml_data_types:CML_STRING_T {
                        length "0..255";
                    }
                    description "";
                } // END of timeout definition.

                leaf nextHopOut  {
                    type  cml_data_types:CML_STRING_T {
                        length "0..255";
                    }
                    description "";
                } // END of nextHopOut definition.

                leaf metricSet  {
                    type  cml_data_types:CML_UINT8_T;
                    description "";
                } // END of metricSet definition.

                leaf metricOut  {
                    type  cml_data_types:CML_UINT32_T;
                    description "";
                } // END of metricOut definition.

                leaf ifindexOut  {
                    type  cml_data_types:CML_UINT32_T;
                    description "";
                } // END of ifindexOut definition.

                leaf nexthopTimeoutTime  {
                    type  cml_data_types:CML_UINT32_T;
                    description "";
                } // END of nexthopTimeoutTime definition.

            } // End of nexthop-list
        } // End of ripDatabase-list

        list ripPeer {
            key "peerAddr";
            config false;
            description
                "RIP peer table";
            leaf peerAddr  {
                type  cml_data_types:CML_STRING_T {
                    length "0..255";
                }
                description "";
            } // END of peerAddr definition.

            leaf domain  {
                type  cml_data_types:CML_INT32_T;
                description "";
            } // END of domain definition.

            leaf uptime  {
                type  cml_data_types:CML_STRING_T {
                    length "0..255";
                }
                description "";
            } // END of uptime definition.

            leaf ifindex  {
                type  cml_data_types:CML_INT32_T;
                description "";
            } // END of ifindex definition.

            leaf peerVersion  {
                type  cml_data_types:CML_UINT8_T;
                description "";
            } // END of peerVersion definition.

            leaf peerFlags  {
                type  cml_data_types:CML_UINT8_T;
                description "";
            } // END of peerFlags definition.

            leaf recvBadpackets  {
                type  cml_data_types:CML_INT32_T;
                description "";
            } // END of recvBadpackets definition.

            leaf recvBadroutes  {
                type  cml_data_types:CML_INT32_T;
                description "";
            } // END of recvBadroutes definition.

        } // End of ripPeer-list
        uses ripListCmdsUtility;
    } // END of ripContents definition.
    grouping ripListCmdsUtility {
        description
            "ripListCmdsUtility";

        list offsetList {
            key "directStr";
            description
                "offsetList";
            leaf alistName  {
                type  cml_data_types:CML_STRING_T {
                    length "0..255";
                }
                mandatory true;
                description "";
            } // END of alistName definition.

            leaf directStr  {
                type  cml_data_types:CML_RIP_DIRECTION_T;
                description "";
            } // END of directStr definition.

            leaf metric  {
                type  cml_data_types:CML_UINT32_T {
                     range "0..16";
                }
                mandatory true;
                description "";
            } // END of metric definition.

        } // End of offsetList-list

        list distributionList {
            key "directionStr";
            description
                "distributionList";
            leaf listName  {
                type  cml_data_types:CML_STRING_T {
                    length "0..255";
                }
                mandatory true;
                description "";
            } // END of listName definition.

            leaf directionStr  {
                type  cml_data_types:CML_RIP_DIRECTION_T;
                description "";
            } // END of directionStr definition.

        } // End of distributionList-list

        list distributionPrefixList {
            key "distributeType";
            description
                "distributionPrefixList";
            leaf prefixListName  {
                type  cml_data_types:CML_STRING_T {
                    length "0..255";
                }
                mandatory true;
                description "";
            } // END of prefixListName definition.

            leaf distributeType  {
                type  cml_data_types:CML_RIP_DIRECTION_T;
                description "";
            } // END of distributeType definition.

        } // End of distributionPrefixList-list
    } // END of ripListCmdsUtility definition.

    grouping  ripConfiguration-grouping {
    container ripConfiguration {
        description
            "RIP master for system wide configuration and variables";
        leaf gracePeriod  {
            if-feature feature_list:HAVE_RIP_GR_SUPPORT;
            if-feature feature_list:HAVE_RESTART;
            type  cml_data_types:CML_UINT32_T {
                 range "1..65535";
            }
            default "65535";
            description "";
        } // END of gracePeriod definition.

        leaf globalQueries  {
            type  cml_data_types:CML_INT32_T;
            config false;
            description "";
        } // END of globalQueries definition.

        leaf globalRouteChanges  {
            type  cml_data_types:CML_INT32_T;
            config false;
            description "";
        } // END of globalRouteChanges definition.

        leaf debugFlag  {
            type  cml_data_types:CML_RIP_DEBUG_T;
            description "";
        } // END of debugFlag definition.


        list ripIntParam {
            key "ifName";
            description
                "RIP interface parameter pool";
            leaf ifName  {
                type  cml_data_types:CML_STRING_T {
                    length "0..255";
                }
                description "";
            } // END of ifName definition.

            leaf receivePacket  {
                type  cml_data_types:CML_BOOL_T;
                description "";
            } // END of receivePacket definition.

            leaf sendPacket  {
                type  cml_data_types:CML_BOOL_T;
                description "";
            } // END of sendPacket definition.

            leaf recvVersionType  {
                type  cml_data_types:CML_RIP_RECV_VERSION_TYPE_T;
                description "";
            } // END of recvVersionType definition.

            leaf sendVersionType  {
                type  cml_data_types:CML_RIP_SEND_VERSION_TYPE_T;
                default "1";
                description "";
            } // END of sendVersionType definition.

            leaf authMode  {
                type  cml_data_types:CML_RIP_AUTH_MODE_T;
                description "";
            } // END of authMode definition.

            leaf authString  {
                type  cml_data_types:CML_STRING_T {
                    length "0..255";
                }
                description "";
            } // END of authString definition.

            leaf keyChain  {
                type  cml_data_types:CML_STRING_T {
                    length "0..255";
                }
                description "";
            } // END of keyChain definition.

            leaf splitHorizon  {
                type  cml_data_types:CML_RIP_SPLIT_HORIZON_T;
                description "";
            } // END of splitHorizon definition.

        } // End of ripIntParam-list
        container rip {
            presence "yes";
            description
                "RIP Default instance";
            leaf ripDefaultInstance  {
                type  cml_data_types:CML_RIP_INSTANCE_T;
                mandatory true;
                description "";
            } // END of ripDefaultInstance definition.

            leaf-list passiveifName  {
                type  cml_data_types:CML_STRING_T {
                    length "0..255";
                }
                description "";
            } // END of passiveifName definition.

            leaf-list route  {
                type  cml_data_types:CML_IPV4_ADDR_T;
                description "";
            } // END of route definition.

            leaf BFDfalloverCheck  {
                if-feature feature_list:HAVE_BFD;
                type  cml_data_types:CML_BOOL_T;
                description "";
            } // END of BFDfalloverCheck definition.

            leaf-list bfdNeighborAddr  {
                if-feature feature_list:HAVE_BFD;
                type  cml_data_types:CML_IPV4_ADDR_T;
                description "";
            } // END of bfdNeighborAddr definition.

            leaf updateTime  {
                type  cml_data_types:CML_UINT32_T {
                     range "5..2147483647";
                }
                default "30";
                description "";
            } // END of updateTime definition.

            leaf timeoutTime  {
                type  cml_data_types:CML_UINT32_T {
                     range "5..2147483647";
                }
                default "180";
                description "";
            } // END of timeoutTime definition.

            leaf garbageTime  {
                type  cml_data_types:CML_UINT32_T {
                     range "5..2147483647";
                }
                default "120";
                description "";
            } // END of garbageTime definition.

            leaf maxPrefixString  {
                type  cml_data_types:CML_UINT32_T {
                     range "1..65535";
                }
                default "1";
                description "";
            } // END of maxPrefixString definition.

            leaf thresholdStr  {
                type  cml_data_types:CML_INT32_T {
                     range "1..100";
                }
                default "75";
                description "";
            } // END of thresholdStr definition.

            leaf recvBufsize  {
                type  cml_data_types:CML_UINT32_T {
                     range "8192..2147483647";
                }
                default "8192";
                description "";
            } // END of recvBufsize definition.


            list redistributeMap {
                key "routeTypeVal";
                description
                    "redistributeMap";
                leaf routeTypeVal  {
                    type  cml_data_types:CML_RIP_REDIST_PROTOS_T;
                    description "";
                } // END of routeTypeVal definition.

                leaf metric  {
                    type  cml_data_types:CML_INT32_T {
                         range "0..16";
                    }
                    mandatory true;
                    description "";
                } // END of metric definition.

                leaf routeMap  {
                    type  cml_data_types:CML_STRING_T {
                        length "0..255";
                    }
                    mandatory true;
                    description "";
                } // END of routeMap definition.

            } // End of redistributeMap-list

            list vrfRip {
                if-feature feature_list:HAVE_VRF_RIP;
                key "vrfName";
                description
                    "Configure a RIP address family for each VRF configured";
                leaf vrfName  {
                    type  cml_data_types:CML_STRING_T {
                        length "0..255";
                    }
                    description "";
                } // END of vrfName definition.


                list redistributeMapVRF {
                    key "vrfRouteType";
                    description
                        "redistributeMapVRF";
                    leaf vrfRouteType  {
                        type  cml_data_types:CML_RIP_VRF_REDIST_PROTOS_T;
                        description "";
                    } // END of vrfRouteType definition.

                    leaf metric  {
                        type  cml_data_types:CML_INT32_T {
                             range "0..16";
                        }
                        mandatory true;
                        description "";
                    } // END of metric definition.

                    leaf vrfRouteMap  {
                        type  cml_data_types:CML_STRING_T {
                            length "0..255";
                        }
                        mandatory true;
                        description "";
                    } // END of vrfRouteMap definition.

                } // End of redistributeMapVRF-list
                uses ripContents;
            } // End of vrfRip-list
            uses ripContents;
        } // END of rip-container definition.
    } // END of ripConfiguration-container definition.
    } // END of ripConfiguration-container definition.


}
