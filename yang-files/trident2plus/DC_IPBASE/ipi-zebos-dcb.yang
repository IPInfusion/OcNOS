/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-zebos-dcb.yang
*
*/

submodule ipi-zebos-dcb {

    belongs-to  ipi-zebos { prefix ipi-zebos; }

    import cml-data-types {
        prefix cml-data-types;
    }

    import feature-list {
        prefix feature-list;
    }

    include ipi-zebos-interface;
    organization
        "IP Infusion Inc.";

    contact
        "Address: 3965 Freedom Circle, Suite 200, Santa Clara, CA 95054
        Phone: +1 408-400-1900
        E-mail: support@ipinfusion.com
        Web: http://www.ipinfusion.com/";

    description
        "Layer-2 dcb bridge configurations";


    revision "2018-06-21" {
        description " Initial Version.";
        reference "";
    }



    grouping nsmDcbIf-grouping {
    description
        "nsmDcbIf";
        list nsmDcbIf {
            key "ifName";
            description
                "nsmDcbIf";
            leaf ifName  {
                type  cml-data-types:CML_STRING_T;
                description "";
            } // END of ifName definition.

            leaf isCp  {
                type  cml-data-types:CML_UINT8_T;
                description "";
            } // END of isCp definition.

            leaf pfcMode  {
                type  cml-data-types:CML_ETS_MODE_T;
                default "on";
                description "";
            } // END of pfcMode definition.

            leaf etsMode  {
                type  cml-data-types:CML_ETS_MODE_T;
                default "on";
                description "";
            } // END of etsMode definition.

            leaf appMode  {
                type  cml-data-types:CML_NSM_DCB_QCN_MODE_T;
                description "";
            } // END of appMode definition.

            leaf dcbIfFlags  {
                type  cml-data-types:CML_UINT8_T;
                description "";
            } // END of dcbIfFlags definition.

            leaf pfcRequestsSent  {
                type  cml-data-types:CML_UINT8_T;
                description "";
            } // END of pfcRequestsSent definition.

            leaf pfcIndicationsRcvd  {
                type  cml-data-types:CML_UINT8_T;
                description "";
            } // END of pfcIndicationsRcvd definition.

            container nsmQcnCnpvData {
                description
                    "nsm qcn data";
                leaf isaCnpv  {
                    type  cml-data-types:CML_UINT8_T {
                         range "0..7";
                    }
                    description "";
                } // END of isaCnpv definition.

                leaf nsmdcbQcnMode  {
                    type  cml-data-types:CML_NSM_DCB_QCN_MODE_T;
                    description "";
                } // END of nsmdcbQcnMode definition.

                leaf alternatePriority  {
                    type  cml-data-types:CML_UINT8_T;
                    description "";
                } // END of alternatePriority definition.

                leaf defenseMode  {
                    type  cml-data-types:CML_DEFENSEMODE_T;
                    default "disabled";
                    description "";
                } // END of defenseMode definition.

                leaf portalternatePriority  {
                    type  cml-data-types:CML_UINT8_T {
                         range "0..7";
                    }
                    description "";
                } // END of portalternatePriority definition.

                container nsmCpIfData {
                    description
                        "nsm qcn if data";
                    leaf isCpEnable  {
                        type  cml-data-types:CML_BOOL_T;
                        description "";
                    } // END of isCpEnable definition.

                    leaf samplebase  {
                        type  cml-data-types:CML_UINT32_T;
                        description "";
                    } // END of samplebase definition.

                    leaf weight  {
                        type  cml-data-types:CML_UINT8_T;
                        description "";
                    } // END of weight definition.

                    leaf minhdroctet  {
                        type  cml-data-types:CML_UINT32_T;
                        description "";
                    } // END of minhdroctet definition.

                } // END of nsmCpIfData-container definition.
            } // END of nsmQcnCnpvData-container definition.
            container pfcConfigAdmin {
                description
                    "Priority Flow Control Configuration for the interface Admin params";
                leaf flags  {
                    type  cml-data-types:CML_UINT8_T;
                    description "";
                } // END of flags definition.

                leaf acceptPeerConfig  {
                    type  cml-data-types:CML_UINT8_T;
                    description "";
                } // END of acceptPeerConfig definition.

                leaf advertiseLocalConfig  {
                    type  cml-data-types:CML_UINT8_T;
                    description "";
                } // END of advertiseLocalConfig definition.

                leaf prioritymap  {
                    type  cml-data-types:CML_UINT8_T {
                         range "0..7";
                    }
                    description "";
                } // END of prioritymap definition.

                leaf prioritymap1  {
                    type  cml-data-types:CML_UINT8_T {
                         range "0..7";
                    }
                    description "";
                } // END of prioritymap1 definition.

                leaf prioritymap2  {
                    type  cml-data-types:CML_UINT8_T {
                         range "0..7";
                    }
                    description "";
                } // END of prioritymap2 definition.

                leaf prioritymap3  {
                    type  cml-data-types:CML_UINT8_T {
                         range "0..7";
                    }
                    description "";
                } // END of prioritymap3 definition.

                leaf prioritymap4  {
                    type  cml-data-types:CML_UINT8_T {
                         range "0..7";
                    }
                    description "";
                } // END of prioritymap4 definition.

                leaf prioritymap5  {
                    type  cml-data-types:CML_UINT8_T {
                         range "0..7";
                    }
                    description "";
                } // END of prioritymap5 definition.

                leaf prioritymap6  {
                    type  cml-data-types:CML_UINT8_T {
                         range "0..7";
                    }
                    description "";
                } // END of prioritymap6 definition.

                leaf prioritymap7  {
                    type  cml-data-types:CML_UINT8_T {
                         range "0..7";
                    }
                    description "";
                } // END of prioritymap7 definition.

                leaf pfcMbc  {
                    type  cml-data-types:CML_UINT8_T;
                    description "";
                } // END of pfcMbc definition.

                leaf cap  {
                    type  cml-data-types:CML_UINT8_T {
                         range "0..8";
                    }
                    description "";
                } // END of cap definition.

                leaf linkDelayAllowance  {
                    type  cml-data-types:CML_UINT32_T {
                         range "0..65535";
                    }
                    description "";
                } // END of linkDelayAllowance definition.

            } // END of pfcConfigAdmin-container definition.
            container pfcConfigOper {
                description
                    "Priority Flow Control Configuration for the interface Oper params";
                leaf flags  {
                    type  cml-data-types:CML_UINT8_T;
                    description "";
                } // END of flags definition.

                leaf wflags  {
                    type  cml-data-types:CML_UINT8_T;
                    description "";
                } // END of wflags definition.

                leaf prioritymapPfc  {
                    type  cml-data-types:CML_UINT8_T;
                    description "";
                } // END of prioritymapPfc definition.

                leaf pfcMbc  {
                    type  cml-data-types:CML_UINT8_T;
                    description "";
                } // END of pfcMbc definition.

                leaf cap  {
                    type  cml-data-types:CML_UINT8_T;
                    description "";
                } // END of cap definition.

                leaf linkDelayAllowance  {
                    type  cml-data-types:CML_UINT32_T;
                    description "";
                } // END of linkDelayAllowance definition.

            } // END of pfcConfigOper-container definition.
            container etsConfigAdmin {
                description
                    "ETS configuration for the interface admin params";
                leaf flags  {
                    type  cml-data-types:CML_UINT8_T;
                    description "";
                } // END of flags definition.

                leaf applicationPriority  {
                    type  cml-data-types:CML_UINT8_T;
                    description "";
                } // END of applicationPriority definition.

                leaf advertiselocalConfigEts  {
                    type  cml-data-types:CML_UINT8_T;
                    description "";
                } // END of advertiselocalConfigEts definition.

                leaf wflags  {
                    type  cml-data-types:CML_UINT8_T;
                    description "";
                } // END of wflags definition.

                leaf cbs  {
                    type  cml-data-types:CML_UINT8_T;
                    description "";
                } // END of cbs definition.

                leaf maxTcgs  {
                    type  cml-data-types:CML_UINT8_T {
                         range "0..2";
                    }
                    description "";
                } // END of maxTcgs definition.

                leaf prioTcgMap  {
                    type  cml-data-types:CML_UINT8_T {
                         range "0..1";
                    }
                    description "";
                } // END of prioTcgMap definition.

                leaf prioFlag  {
                    type  cml-data-types:CML_PRIOFLAG_T;
                    description "";
                } // END of prioFlag definition.

                leaf maxPriority  {
                    type  cml-data-types:CML_UINT8_T {
                         range "0..7";
                    }
                    description "";
                } // END of maxPriority definition.

                leaf maxPriority1  {
                    type  cml-data-types:CML_UINT8_T {
                         range "0..7";
                    }
                    description "";
                } // END of maxPriority1 definition.

                leaf maxPriority2  {
                    type  cml-data-types:CML_UINT8_T {
                         range "0..7";
                    }
                    description "";
                } // END of maxPriority2 definition.

                leaf maxPriority3  {
                    type  cml-data-types:CML_UINT8_T {
                         range "0..7";
                    }
                    description "";
                } // END of maxPriority3 definition.

                leaf maxPriority4  {
                    type  cml-data-types:CML_UINT8_T {
                         range "0..7";
                    }
                    description "";
                } // END of maxPriority4 definition.

                leaf maxPriority5  {
                    type  cml-data-types:CML_UINT8_T {
                         range "0..7";
                    }
                    description "";
                } // END of maxPriority5 definition.

                leaf maxPriority6  {
                    type  cml-data-types:CML_UINT8_T {
                         range "0..7";
                    }
                    description "";
                } // END of maxPriority6 definition.

                leaf maxPriority7  {
                    type  cml-data-types:CML_UINT8_T {
                         range "0..7";
                    }
                    description "";
                } // END of maxPriority7 definition.

                leaf tcgBwTable  {
                    type  cml-data-types:CML_UINT8_T;
                    description "";
                } // END of tcgBwTable definition.

                leaf tcgBwval  {
                    type  cml-data-types:CML_UINT8_T {
                         range "0..1";
                    }
                    description "";
                } // END of tcgBwval definition.

                leaf tcgBwPer  {
                    type  cml-data-types:CML_UINT8_T {
                         range "0..100";
                    }
                    description "";
                } // END of tcgBwPer definition.

                leaf tcgBwval1  {
                    type  cml-data-types:CML_UINT8_T {
                         range "0..1";
                    }
                    description "";
                } // END of tcgBwval1 definition.

                leaf tcgBwPer1  {
                    type  cml-data-types:CML_UINT8_T {
                         range "0..100";
                    }
                    description "";
                } // END of tcgBwPer1 definition.

                leaf tcgBwval2  {
                    if-feature feature-list:NOT_HAVE_BROADCOM;
                    type  cml-data-types:CML_UINT8_T {
                         range "0..7";
                    }
                    description "";
                } // END of tcgBwval2 definition.

                leaf tcgBwPer2  {
                    if-feature feature-list:NOT_HAVE_BROADCOM;
                    type  cml-data-types:CML_UINT8_T {
                         range "0..100";
                    }
                    description "";
                } // END of tcgBwPer2 definition.

                leaf tcgBwval3  {
                    if-feature feature-list:NOT_HAVE_BROADCOM;
                    type  cml-data-types:CML_UINT8_T {
                         range "0..7";
                    }
                    description "";
                } // END of tcgBwval3 definition.

                leaf tcgBwPer3  {
                    if-feature feature-list:NOT_HAVE_BROADCOM;
                    type  cml-data-types:CML_UINT8_T {
                         range "0..100";
                    }
                    description "";
                } // END of tcgBwPer3 definition.

                leaf tcgBwval4  {
                    if-feature feature-list:NOT_HAVE_BROADCOM;
                    type  cml-data-types:CML_UINT8_T {
                         range "0..7";
                    }
                    description "";
                } // END of tcgBwval4 definition.

                leaf tcgBwPer4  {
                    if-feature feature-list:NOT_HAVE_BROADCOM;
                    type  cml-data-types:CML_UINT8_T {
                         range "0..100";
                    }
                    description "";
                } // END of tcgBwPer4 definition.

                leaf tcgBwval5  {
                    if-feature feature-list:NOT_HAVE_BROADCOM;
                    type  cml-data-types:CML_UINT8_T {
                         range "0..7";
                    }
                    description "";
                } // END of tcgBwval5 definition.

                leaf tcgBwPer5  {
                    if-feature feature-list:NOT_HAVE_BROADCOM;
                    type  cml-data-types:CML_UINT8_T {
                         range "0..100";
                    }
                    description "";
                } // END of tcgBwPer5 definition.

                leaf tcgBwval6  {
                    if-feature feature-list:NOT_HAVE_BROADCOM;
                    type  cml-data-types:CML_UINT8_T {
                         range "0..7";
                    }
                    description "";
                } // END of tcgBwval6 definition.

                leaf tcgBwPer6  {
                    if-feature feature-list:NOT_HAVE_BROADCOM;
                    type  cml-data-types:CML_UINT8_T {
                         range "0..100";
                    }
                    description "";
                } // END of tcgBwPer6 definition.

                leaf tcgBwval7  {
                    if-feature feature-list:NOT_HAVE_BROADCOM;
                    type  cml-data-types:CML_UINT8_T {
                         range "0..7";
                    }
                    description "";
                } // END of tcgBwval7 definition.

                leaf tcgBwPer7  {
                    if-feature feature-list:NOT_HAVE_BROADCOM;
                    type  cml-data-types:CML_UINT8_T {
                         range "0..100";
                    }
                    description "";
                } // END of tcgBwPer7 definition.

                leaf tsaTcTable  {
                    type  cml-data-types:CML_UINT8_T;
                    description "";
                } // END of tsaTcTable definition.

            } // END of etsConfigAdmin-container definition.
            container etsConfigOper {
                description
                    "ETS configuration for the interface oper params";
                leaf flags  {
                    type  cml-data-types:CML_UINT8_T;
                    description "";
                } // END of flags definition.

                leaf wflags  {
                    type  cml-data-types:CML_UINT8_T;
                    description "";
                } // END of wflags definition.

                leaf cbs  {
                    type  cml-data-types:CML_UINT8_T;
                    description "";
                } // END of cbs definition.

                leaf maxTcgs  {
                    type  cml-data-types:CML_UINT8_T;
                    description "";
                } // END of maxTcgs definition.

                leaf prioTcgMap  {
                    type  cml-data-types:CML_UINT8_T;
                    description "";
                } // END of prioTcgMap definition.

                leaf tcgBwTable  {
                    type  cml-data-types:CML_UINT8_T;
                    description "";
                } // END of tcgBwTable definition.

                leaf tsaTcTable  {
                    type  cml-data-types:CML_UINT8_T;
                    description "";
                } // END of tsaTcTable definition.

            } // END of etsConfigOper-container definition.
            container etsRecParam {
                description
                    "ETS configuration for the interface Recommendational Params";
                leaf flags  {
                    type  cml-data-types:CML_UINT8_T;
                    description "";
                } // END of flags definition.

                leaf prioTcgMap  {
                    type  cml-data-types:CML_UINT8_T;
                    description "";
                } // END of prioTcgMap definition.

                leaf tcgBwTable  {
                    type  cml-data-types:CML_UINT8_T;
                    description "";
                } // END of tcgBwTable definition.

                leaf tsaTcTable  {
                    type  cml-data-types:CML_UINT8_T;
                    description "";
                } // END of tsaTcTable definition.

            } // END of etsRecParam-container definition.
            container appConfigAdmin {
                description
                    "Application Priority configuration on the interface admin params";
                leaf flags  {
                    type  cml-data-types:CML_UINT8_T;
                    description "";
                } // END of flags definition.

                leaf wflags  {
                    type  cml-data-types:CML_UINT8_T;
                    description "";
                } // END of wflags definition.

                leaf applPrioCount  {
                    type  cml-data-types:CML_UINT8_T;
                    description "";
                } // END of applPrioCount definition.

                container appPrioTable {
                    description
                        "Application Priority configuration on the interface admin params";
                    leaf enable  {
                        type  cml-data-types:CML_UINT8_T;
                        description "";
                    } // END of enable definition.

                    leaf protoId  {
                        type  cml-data-types:CML_PROTOID_T;
                        description "";
                    } // END of protoId definition.

                    leaf sel  {
                        type  cml-data-types:CML_UINT8_T;
                        description "";
                    } // END of sel definition.

                    leaf portNo  {
                        type  cml-data-types:CML_UINT32_T {
                             range "1..1023";
                        }
                        description "";
                    } // END of portNo definition.

                    leaf serviceName  {
                        type  cml-data-types:CML_STRING_T;
                        description "";
                    } // END of serviceName definition.

                    leaf priorityMapVal  {
                        type  cml-data-types:CML_UINT8_T {
                             range "0..7";
                        }
                        description "";
                    } // END of priorityMapVal definition.

                    leaf mappingType  {
                        type  cml-data-types:CML_MAPPING_TYPE_T;
                        description "";
                    } // END of mappingType definition.

                    leaf etherType  {
                        type  cml-data-types:CML_STRING_T;
                        description "";
                    } // END of etherType definition.

                    leaf etherName  {
                        type  cml-data-types:CML_STRING_T;
                        description "";
                    } // END of etherName definition.

                } // END of appPrioTable-container definition.
            } // END of appConfigAdmin-container definition.
            container appConfigOper {
                description
                    "Application Priority configuration on the interface oper params";
                leaf flags  {
                    type  cml-data-types:CML_UINT8_T;
                    description "";
                } // END of flags definition.

                leaf wflags  {
                    type  cml-data-types:CML_UINT8_T;
                    description "";
                } // END of wflags definition.

                leaf applPrioCount  {
                    type  cml-data-types:CML_UINT8_T;
                    description "";
                } // END of applPrioCount definition.

                container appPrioTable {
                    description
                        "Application Priority configuration on the interface Oper params";
                    leaf enable  {
                        type  cml-data-types:CML_UINT8_T;
                        description "";
                    } // END of enable definition.

                    leaf protoId  {
                        type  cml-data-types:CML_UINT8_T;
                        description "";
                    } // END of protoId definition.

                    leaf sel  {
                        type  cml-data-types:CML_UINT8_T;
                        description "";
                    } // END of sel definition.

                    leaf priorityMapApp  {
                        type  cml-data-types:CML_UINT8_T;
                        description "";
                    } // END of priorityMapApp definition.

                    leaf mappingType  {
                        type  cml-data-types:CML_MAPPING_TYPE_T;
                        description "";
                    } // END of mappingType definition.

                } // END of appPrioTable-container definition.
            } // END of appConfigOper-container definition.
        } // End of nsmDcbIf-list
    } // END of nsmDcbIf-grouping definition.
    grouping globalConfigurationFlags {
        description
            "globalConfigurationFlags";
        leaf dcbEnable  {
            type  cml-data-types:CML_BOOL_T;
            description "";
        } // END of dcbEnable definition.

        leaf dcbEtsEnable  {
            type  cml-data-types:CML_BOOL_T;
            description "";
        } // END of dcbEtsEnable definition.

        leaf dcbPfcEnable  {
            type  cml-data-types:CML_BOOL_T;
            description "";
        } // END of dcbPfcEnable definition.

        leaf dcbAppEnable  {
            type  cml-data-types:CML_BOOL_T;
            description "";
        } // END of dcbAppEnable definition.

    } // END of globalConfigurationFlags definition.

    grouping  nsmDcbBridge-grouping {
    description
        "nsmDcbBridge";
    container nsmDcbBridge {
        if-feature feature-list:HAVE_DCB;
        description
            "nsmDcbBridge";

        list nsmQcnData {
            key "dcbQCNEnable";
            description
                "QCN";
            leaf dcbQCNEnable  {
                type  cml-data-types:CML_BOOL_T;
                description "";
            } // END of dcbQCNEnable definition.

            leaf cnmTransmitPriority  {
                type  cml-data-types:CML_UINT8_T {
                     range "0..7";
                }
                description "";
            } // END of cnmTransmitPriority definition.

            container nsmQcnCnpvData {
                if-feature feature-list:HAVE_DCB;
                description
                    "nsm qcn data";
                leaf isaCnpv  {
                    type  cml-data-types:CML_INT8_T {
                         range "0..7";
                    }
                    description "";
                } // END of isaCnpv definition.

                leaf nsmdcbQcnMode  {
                    type  cml-data-types:CML_NSM_DCB_QCN_MODE_T;
                    description "";
                } // END of nsmdcbQcnMode definition.

                leaf alternatePriority  {
                    type  cml-data-types:CML_UINT8_T {
                         range "0..7";
                    }
                    description "";
                } // END of alternatePriority definition.

                leaf alternatePriority1  {
                    type  cml-data-types:CML_UINT8_T {
                         range "0..7";
                    }
                    description "";
                } // END of alternatePriority1 definition.

                leaf alternatePriority2  {
                    type  cml-data-types:CML_UINT8_T {
                         range "0..7";
                    }
                    description "";
                } // END of alternatePriority2 definition.

                leaf alternatePriority3  {
                    type  cml-data-types:CML_UINT8_T {
                         range "0..7";
                    }
                    description "";
                } // END of alternatePriority3 definition.

                leaf alternatePriority4  {
                    type  cml-data-types:CML_UINT8_T {
                         range "0..7";
                    }
                    description "";
                } // END of alternatePriority4 definition.

                leaf alternatePriority5  {
                    type  cml-data-types:CML_UINT8_T {
                         range "0..7";
                    }
                    description "";
                } // END of alternatePriority5 definition.

                leaf alternatePriority6  {
                    type  cml-data-types:CML_UINT8_T {
                         range "0..7";
                    }
                    description "";
                } // END of alternatePriority6 definition.

                leaf defenseMode  {
                    type  cml-data-types:CML_DEFENSEMODE_T;
                    default "disabled";
                    description "";
                } // END of defenseMode definition.

                leaf alterPriority  {
                    type  cml-data-types:CML_UINT8_T {
                         range "0..7";
                    }
                    description "";
                } // END of alterPriority definition.

                leaf ifName  {
                    type  cml-data-types:CML_STRING_T;
                    description "";
                } // END of ifName definition.

                container nsmCpIfData {
                    description
                        "nsm qcn if data";
                    leaf ifName  {
                        type  cml-data-types:CML_STRING_T;
                        description "";
                    } // END of ifName definition.

                    leaf isCpEnable  {
                        type  cml-data-types:CML_UINT8_T {
                             range "0..7";
                        }
                        description "";
                    } // END of isCpEnable definition.

                    leaf samplebase  {
                        type  cml-data-types:CML_UINT32_T {
                             range "1024..10240";
                        }
                        description "";
                    } // END of samplebase definition.

                    leaf weight  {
                        type  cml-data-types:CML_STRING_T;
                        description "";
                    } // END of weight definition.

                    leaf minhdroctet  {
                        type  cml-data-types:CML_UINT32_T {
                             range "0..64";
                        }
                        description "";
                    } // END of minhdroctet definition.

                } // END of nsmCpIfData-container definition.
            } // END of nsmQcnCnpvData-container definition.
        } // End of nsmQcnData-list
        uses globalConfigurationFlags;
    } // END of nsmDcbBridge-container definition.
    } // END of nsmDcbBridge-container definition.

    grouping  Dcbdebug-grouping {
    description
        "Dcbdebug";
    container Dcbdebug {
        description
            "Dcbdebug";
        leaf dcbState  {
            type  cml-data-types:CML_DCBSTATE_T;
            description "";
        } // END of dcbState definition.

    } // END of Dcbdebug-container definition.
    } // END of Dcbdebug-container definition.

    grouping  nsmDcbDefaultBridge-grouping {
    description
        "nsmDcbDefaultBridge";
    container nsmDcbDefaultBridge {
        if-feature feature-list:HAVE_DEFAULT_BRIDGE;
        description
            "nsmDcbDefaultBridge";

        list nsmdefaultbridgeQcnData {
            key "dcbQCNEnable";
            description
                "QCN";
            leaf dcbQCNEnable  {
                type  cml-data-types:CML_BOOL_T;
                description "";
            } // END of dcbQCNEnable definition.

            leaf cnmTransmitPriority  {
                type  cml-data-types:CML_UINT8_T {
                     range "0..7";
                }
                description "";
            } // END of cnmTransmitPriority definition.

            container nsmQcnCnpvData {
                description
                    "nsm qcn data";
                leaf isaCnpv  {
                    type  cml-data-types:CML_UINT8_T;
                    description "";
                } // END of isaCnpv definition.

                leaf nsmdcbQcnMode  {
                    type  cml-data-types:CML_NSM_DCB_QCN_MODE_T;
                    description "";
                } // END of nsmdcbQcnMode definition.

                leaf alternatePriority  {
                    type  cml-data-types:CML_UINT8_T;
                    description "";
                } // END of alternatePriority definition.

                leaf defenseMode  {
                    type  cml-data-types:CML_DEFENSEMODE_T;
                    description "";
                } // END of defenseMode definition.

                container nsmCpIfData {
                    description
                        "nsm qcn if data";
                    leaf isCpEnable  {
                        type  cml-data-types:CML_BOOL_T;
                        description "";
                    } // END of isCpEnable definition.

                    leaf samplebase  {
                        type  cml-data-types:CML_UINT32_T;
                        description "";
                    } // END of samplebase definition.

                    leaf weight  {
                        type  cml-data-types:CML_UINT8_T;
                        description "";
                    } // END of weight definition.

                    leaf minhdroctet  {
                        type  cml-data-types:CML_UINT32_T;
                        description "";
                    } // END of minhdroctet definition.

                } // END of nsmCpIfData-container definition.
            } // END of nsmQcnCnpvData-container definition.
        } // End of nsmdefaultbridgeQcnData-list
        uses globalConfigurationFlags;
    } // END of nsmDcbDefaultBridge-container definition.
    } // END of nsmDcbDefaultBridge-container definition.


}
