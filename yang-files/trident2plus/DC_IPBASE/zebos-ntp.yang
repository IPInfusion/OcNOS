/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-ntp.yang
*
*/

submodule zebos-ntp {

    belongs-to  zebos { prefix zebos; }

    import cml_data_types {
        prefix cml_data_types;
    }

    import feature_list {
        prefix feature_list;
    }

    include zebos-vrf;
    organization
        "IP Infusion Inc.";

    contact
        "Address: 3965 Freedom Circle, Suite 200, Santa Clara, CA 95054
        Phone: +1 408-400-1900
        E-mail: support@ipinfusion.com
        Web: http://www.ipinfusion.com/";

    description
        "ntp configurations";


    revision "2018-06-21" {
        description " Initial Version.";
        reference "";
    }



    grouping ntp-grouping {
    description
        "NTP related commands";
        list ntp {
            key "vrfName";
            description
                "NTP related commands";
            leaf vrfName  {
                type  cml_data_types:CML_STRING_T;
                description "";
            } // END of vrfName definition.

            leaf featurentp  {
                if-feature feature_list:HAVE_HOSTP_NTP;
                type  cml_data_types:CML_NTP_FEATURE_T;
                description "";
            } // END of featurentp definition.

            leaf enableNTP  {
                if-feature feature_list:HAVE_HOSTP_NTP;
                type  cml_data_types:CML_BOOL_T;
                description "";
            } // END of enableNTP definition.

            leaf loggingNTP  {
                if-feature feature_list:HAVE_HOSTP_NTP;
                type  cml_data_types:CML_BOOL_T;
                default false;
                description "";
            } // END of loggingNTP definition.

            leaf authenticateNTP  {
                if-feature feature_list:HAVE_HOSTP_NTP;
                type  cml_data_types:CML_BOOL_T;
                default false;
                description "";
            } // END of authenticateNTP definition.


            list ntpKey {
                key "keyAuthenticate";
                description
                    "ntpKey";
                leaf keyAuthenticate  {
                    type  cml_data_types:CML_INT32_T {
                         range "1..65535";
                    }
                    description "";
                } // END of keyAuthenticate definition.

                leaf authenticateScheme  {
                    type  cml_data_types:CML_STRING_T {
                        length "1..8";
                    }
                    mandatory true;
                    description "";
                } // END of authenticateScheme definition.

                leaf keyEncrytion  {
                    type  cml_data_types:CML_HOSTP_KEY_TYPE_T;
                    description "";
                } // END of keyEncrytion definition.

            } // End of ntpKey-list

            list trustedKey {
                key "trustedkeyNTP";
                description
                    "trustedKey";
                leaf trustedkeyNTP  {
                    type  cml_data_types:CML_INT32_T {
                         range "1..65535";
                    }
                    description "";
                } // END of trustedkeyNTP definition.

            } // End of trustedKey-list

            list ntpServer {
                key "serverAddress";
                description
                    "NTP server configurations";
                leaf serverAddress  {
                    type  cml_data_types:CML_STRING_T {
                        length "1..63";
                    }
                    description "";
                } // END of serverAddress definition.

                uses serverPeerOptions;
            } // End of ntpServer-list

            list ntpPeer {
                key "peerAddress";
                description
                    "NTP peer configurations";
                leaf peerAddress  {
                    type  cml_data_types:CML_STRING_T {
                        length "1..63";
                    }
                    description "";
                } // END of peerAddress definition.

                uses serverPeerOptions;
            } // End of ntpPeer-list
        } // End of ntp-list
    } // END of ntp-grouping definition.
    grouping serverPeerOptions {
        description
            "serverPeerOptions";
        leaf preferredServer  {
            type  cml_data_types:CML_NTP_PREFER_T;
            description "";
        } // END of preferredServer definition.

        leaf key  {
            type  cml_data_types:CML_UINT32_T {
                 range "1..65535";
            }
            default "65535";
            description "";
        } // END of key definition.

        leaf minpoll  {
            type  cml_data_types:CML_UINT16_T {
                 range "4..16";
            }
            default "4";
            description "";
        } // END of minpoll definition.

        leaf maxpoll  {
            type  cml_data_types:CML_UINT16_T {
                 range "4..16";
            }
            default "6";
            description "";
        } // END of maxpoll definition.

    } // END of serverPeerOptions definition.

    grouping  sourceNTP-grouping {
    description
        "sourceNTP";
    container sourceNTP {
        description
            "sourceNTP";
        leaf sourceInterface  {
            if-feature feature_list:HAVE_HOSTP_NTP;
            type  cml_data_types:CML_STRING_T;
            description "";
        } // END of sourceInterface definition.

    } // END of sourceNTP-container definition.
    } // END of sourceNTP-container definition.

    grouping  debugNTP-grouping {
    description
        "debugNTP";
    container debugNTP {
        description
            "debugNTP";
        leaf debugntp  {
            type  cml_data_types:CML_BOOL_T;
            description "";
        } // END of debugntp definition.

        leaf debugntpConf  {
            type  cml_data_types:CML_BOOL_T;
            description "";
        } // END of debugntpConf definition.

    } // END of debugNTP-container definition.
    } // END of debugNTP-container definition.


}
