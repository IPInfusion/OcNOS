/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-lldpv2.yang
*
*/

submodule zebos-lldpv2 {

    belongs-to  zebos { prefix zebos; }

    import cml_data_types {
        prefix cml_data_types;
    }

    import feature_list {
        prefix feature_list;
    }

    organization
        "IP Infusion Inc.";

    contact
        "Address: 3965 Freedom Circle, Suite 200, Santa Clara, CA 95054
        Phone: +1 408-400-1900
        E-mail: support@ipinfusion.com
        Web: http://www.ipinfusion.com/";

    description
        "Link Layer Discovery Protocol";


    revision "2018-06-21" {
        description " Initial Version.";
        reference "";
    }


    grouping  lldpMaster-grouping {
    description
        "lldpMaster";
    container lldpMaster {
        if-feature feature_list:HAVE_LLDPV2;
        description
            "lldpMaster";
        leaf lldpRun  {
            type  cml_data_types:CML_BOOL_T;
            description "";
        } // END of lldpRun definition.

        leaf ifCnt  {
            type  cml_data_types:CML_UINT16_T;
            config false;
            description "";
        } // END of ifCnt definition.

        leaf syscapEnabled  {
            type  cml_data_types:CML_UINT16_T;
            config false;
            description "";
        } // END of syscapEnabled definition.

        leaf sysNameConf  {
            type  cml_data_types:CML_BOOL_T;
            config false;
            description "";
        } // END of sysNameConf definition.

        leaf sysDescrConf  {
            type  cml_data_types:CML_BOOL_T;
            config false;
            description "";
        } // END of sysDescrConf definition.

        leaf lldpStatsTablesInserts  {
            type  cml_data_types:CML_UINT32_T;
            config false;
            description "";
        } // END of lldpStatsTablesInserts definition.

        leaf lldpStatsTablesDeletes  {
            type  cml_data_types:CML_UINT32_T;
            config false;
            description "";
        } // END of lldpStatsTablesDeletes definition.

        leaf lldpStatsTablesDrops  {
            type  cml_data_types:CML_UINT32_T;
            config false;
            description "";
        } // END of lldpStatsTablesDrops definition.

        leaf lldpStateRemTablesAgeouts  {
            type  cml_data_types:CML_UINT32_T;
            config false;
            description "";
        } // END of lldpStateRemTablesAgeouts definition.

        leaf lldpNtfInterval  {
            type  cml_data_types:CML_UINT32_T;
            config false;
            description "";
        } // END of lldpNtfInterval definition.

        leaf lldpStatStablesAgeouts  {
            type  cml_data_types:CML_UINT32_T;
            config false;
            description "";
        } // END of lldpStatStablesAgeouts definition.

        leaf confFlag  {
            type  cml_data_types:CML_UINT8_T;
            config false;
            description "";
        } // END of confFlag definition.

        leaf hostConfName  {
            type  cml_data_types:CML_STRING_T;
            config false;
            description "";
        } // END of hostConfName definition.

        container lldpTLVs {
            description
                "lldpTLVs";
            container basicMgmt {
                description
                    "basicMgmt";
                leaf portDescription  {
                    type  cml_data_types:CML_BOOL_T;
                    description "";
                } // END of portDescription definition.

                leaf systemDescription  {
                    type  cml_data_types:CML_BOOL_T;
                    description "";
                } // END of systemDescription definition.

                leaf systemName  {
                    type  cml_data_types:CML_BOOL_T;
                    description "";
                } // END of systemName definition.

                leaf systemCapabilities  {
                    type  cml_data_types:CML_BOOL_T;
                    description "";
                } // END of systemCapabilities definition.

                leaf mgmtAddress  {
                    type  cml_data_types:CML_BOOL_T;
                    description "";
                } // END of mgmtAddress definition.

            } // END of basicMgmt-container definition.
            container ieee8021orgSpecific {
                description
                    "ieee8021orgSpecific";
                leaf portVlanid  {
                    type  cml_data_types:CML_BOOL_T;
                    description "";
                } // END of portVlanid definition.

                leaf portPtclVlanid  {
                    type  cml_data_types:CML_BOOL_T;
                    description "";
                } // END of portPtclVlanid definition.

                leaf vlanName  {
                    type  cml_data_types:CML_BOOL_T;
                    description "";
                } // END of vlanName definition.

                leaf ptclIdentity  {
                    type  cml_data_types:CML_BOOL_T;
                    description "";
                } // END of ptclIdentity definition.

                leaf vidDigest  {
                    type  cml_data_types:CML_BOOL_T;
                    description "";
                } // END of vidDigest definition.

                leaf mgmtVid  {
                    type  cml_data_types:CML_BOOL_T;
                    description "";
                } // END of mgmtVid definition.

                leaf linkAgg  {
                    type  cml_data_types:CML_BOOL_T;
                    description "";
                } // END of linkAgg definition.

                leaf dcb  {
                    if-feature feature_list:HAVE_DCB;
                    type  cml_data_types:CML_BOOL_T;
                    description "";
                } // END of dcb definition.

            } // END of ieee8021orgSpecific-container definition.
            container ieee8023orgSpecific {
                description
                    "ieee8023orgSpecific";
                leaf macPhy  {
                    type  cml_data_types:CML_BOOL_T;
                    description "";
                } // END of macPhy definition.

                leaf maxMtuSize  {
                    type  cml_data_types:CML_BOOL_T;
                    description "";
                } // END of maxMtuSize definition.

                leaf powerViaMdi  {
                    if-feature feature_list:HAVE_POE;
                    type  cml_data_types:CML_BOOL_T;
                    description "";
                } // END of powerViaMdi definition.

            } // END of ieee8023orgSpecific-container definition.
        } // END of lldpTLVs-container definition.
        container lldpMgmtIF {
            description
                "lldpMgmtIF";
            leaf locallyAssigned  {
                type  cml_data_types:CML_STRING_T;
                default "NULL";
                description "";
            } // END of locallyAssigned definition.

        } // END of lldpMgmtIF-container definition.
    } // END of lldpMaster-container definition.
    } // END of lldpMaster-container definition.

    grouping  lldpv2Interface-grouping {
    description
        "LLDPV2 interface related operations";
    container lldpv2Interface {
        description
            "LLDPV2 interface related operations";
        leaf lldpAgtCircuitId  {
            type  cml_data_types:CML_STRING_T;
            default "NULL";
            description "";
        } // END of lldpAgtCircuitId definition.

        leaf lldpmedDevType  {
            type  cml_data_types:CML_LLDP_MEDDEV_T;
            description "";
        } // END of lldpmedDevType definition.

        leaf localName  {
            type  cml_data_types:CML_STRING_T;
            description "";
        } // END of localName definition.

        leaf evbCdcp  {
            if-feature feature_list:HAVE_DCB;
            type  cml_data_types:CML_ENABLE_DISABLE_T;
            description "";
        } // END of evbCdcp definition.

        leaf evbReflective  {
            if-feature feature_list:HAVE_DCB;
            type  cml_data_types:CML_ENABLE_DISABLE_T;
            description "";
        } // END of evbReflective definition.

        leaf maxRetries  {
            if-feature feature_list:HAVE_DCB;
            type  cml_data_types:CML_UINT8_T {
                 range "0..7";
            }
            description "";
        } // END of maxRetries definition.

        leaf acktimer  {
            if-feature feature_list:HAVE_DCB;
            type  cml_data_types:CML_UINT8_T {
                 range "10..20";
            }
            description "";
        } // END of acktimer definition.

        leaf rwd  {
            if-feature feature_list:HAVE_DCB;
            type  cml_data_types:CML_UINT8_T {
                 range "0..31";
            }
            description "";
        } // END of rwd definition.

        leaf rka  {
            if-feature feature_list:HAVE_DCB;
            type  cml_data_types:CML_UINT8_T {
                 range "0..31";
            }
            description "";
        } // END of rka definition.

        leaf ref-relay  {
            if-feature feature_list:HAVE_DCB;
            type  cml_data_types:CML_ENABLE_DISABLE_T;
            description "";
        } // END of ref-relay definition.

        leaf scid1  {
            if-feature feature_list:HAVE_DCB;
            type  cml_data_types:CML_UINT32_T {
                 range "0..167";
            }
            description "";
        } // END of scid1 definition.

        leaf svid1  {
            if-feature feature_list:HAVE_DCB;
            type  cml_data_types:CML_UINT32_T {
                 range "2..4094";
            }
            description "";
        } // END of svid1 definition.

        leaf scid2  {
            if-feature feature_list:HAVE_DCB;
            type  cml_data_types:CML_UINT32_T {
                 range "0..167";
            }
            description "";
        } // END of scid2 definition.

        leaf svid2  {
            if-feature feature_list:HAVE_DCB;
            type  cml_data_types:CML_UINT32_T {
                 range "2..4094";
            }
            description "";
        } // END of svid2 definition.

        leaf scid3  {
            if-feature feature_list:HAVE_DCB;
            type  cml_data_types:CML_UINT32_T {
                 range "0..167";
            }
            description "";
        } // END of scid3 definition.

        leaf svid3  {
            if-feature feature_list:HAVE_DCB;
            type  cml_data_types:CML_UINT32_T {
                 range "2..4094";
            }
            description "";
        } // END of svid3 definition.

        leaf scid4  {
            if-feature feature_list:HAVE_DCB;
            type  cml_data_types:CML_UINT32_T {
                 range "0..167";
            }
            description "";
        } // END of scid4 definition.

        leaf svid4  {
            if-feature feature_list:HAVE_DCB;
            type  cml_data_types:CML_UINT32_T {
                 range "2..4094";
            }
            description "";
        } // END of svid4 definition.

        leaf scid5  {
            if-feature feature_list:HAVE_DCB;
            type  cml_data_types:CML_UINT32_T {
                 range "0..167";
            }
            description "";
        } // END of scid5 definition.

        leaf svid5  {
            if-feature feature_list:HAVE_DCB;
            type  cml_data_types:CML_UINT32_T {
                 range "2..4094";
            }
            description "";
        } // END of svid5 definition.

        leaf scid6  {
            if-feature feature_list:HAVE_DCB;
            type  cml_data_types:CML_UINT32_T {
                 range "0..167";
            }
            description "";
        } // END of scid6 definition.

        leaf svid6  {
            if-feature feature_list:HAVE_DCB;
            type  cml_data_types:CML_UINT32_T {
                 range "2..4094";
            }
            description "";
        } // END of svid6 definition.

        leaf scid7  {
            if-feature feature_list:HAVE_DCB;
            type  cml_data_types:CML_UINT32_T {
                 range "0..167";
            }
            description "";
        } // END of scid7 definition.

        leaf svid7  {
            if-feature feature_list:HAVE_DCB;
            type  cml_data_types:CML_UINT32_T {
                 range "2..4094";
            }
            description "";
        } // END of svid7 definition.

        leaf scid8  {
            if-feature feature_list:HAVE_DCB;
            type  cml_data_types:CML_UINT32_T {
                 range "0..167";
            }
            description "";
        } // END of scid8 definition.

        leaf svid8  {
            if-feature feature_list:HAVE_DCB;
            type  cml_data_types:CML_UINT32_T {
                 range "2..4094";
            }
            description "";
        } // END of svid8 definition.

        leaf scid9  {
            if-feature feature_list:HAVE_DCB;
            type  cml_data_types:CML_UINT32_T {
                 range "0..167";
            }
            description "";
        } // END of scid9 definition.

        leaf svid9  {
            if-feature feature_list:HAVE_DCB;
            type  cml_data_types:CML_UINT32_T {
                 range "2..4094";
            }
            description "";
        } // END of svid9 definition.

        leaf entityPhyAliasPort  {
            type  cml_data_types:CML_STRING_T;
            config false;
            description "";
        } // END of entityPhyAliasPort definition.

        leaf entityPhyAliasChassis  {
            type  cml_data_types:CML_STRING_T;
            config false;
            description "";
        } // END of entityPhyAliasChassis definition.

        leaf lldpAgentLocallyEnabled  {
            type  cml_data_types:CML_BOOL_T;
            config false;
            description "";
        } // END of lldpAgentLocallyEnabled definition.

        leaf lldpAgentDisabled  {
            type  cml_data_types:CML_BOOL_T;
            config false;
            description "";
        } // END of lldpAgentDisabled definition.


        list lldpAgent {
            key "lldpAgent";
            description
                "LLDP configuration related operations";
            leaf lldpAgent  {
                type  cml_data_types:CML_LLDP_AGENT_T;
                description "";
            } // END of lldpAgent definition.

            leaf lldpEnable  {
                type  cml_data_types:CML_LLDP_ENABLE_T;
                default "rxonly";
                description "";
            } // END of lldpEnable definition.

            leaf dcbxEnable  {
                if-feature feature_list:HAVE_DCB;
                type  cml_data_types:CML_BOOL_T;
                description "";
            } // END of dcbxEnable definition.

            leaf newNeighbour  {
                type  cml_data_types:CML_UINT32_T;
                config false;
                description "";
            } // END of newNeighbour definition.

            container lldpTxSmConfig {
                description
                    "lldpTxSmConfig";
                leaf reinitDelay  {
                    type  cml_data_types:CML_STRING_T;
                    description "";
                } // END of reinitDelay definition.

                leaf MsgTxInterval  {
                    type  cml_data_types:CML_UINT32_T {
                         range "5..3600";
                    }
                    default "30";
                    description "";
                } // END of MsgTxInterval definition.

                leaf MsgTxValue  {
                    type  cml_data_types:CML_STRING_T;
                    description "";
                } // END of MsgTxValue definition.

                leaf MsgFastTx  {
                    type  cml_data_types:CML_UINT32_T {
                         range "1..3600";
                    }
                    default "1";
                    description "";
                } // END of MsgFastTx definition.

                leaf txMaxCredit  {
                    type  cml_data_types:CML_UINT32_T {
                         range "1..10";
                    }
                    default "5";
                    description "";
                } // END of txMaxCredit definition.

                leaf txFastInit  {
                    type  cml_data_types:CML_UINT32_T {
                         range "1..8";
                    }
                    default "4";
                    description "";
                } // END of txFastInit definition.

            } // END of lldpTxSmConfig-container definition.
            container lldpTxSm {
                config false;
                description
                    "lldpTxSm";
                leaf txCredit  {
                    type  cml_data_types:CML_UINT32_T;
                    description "";
                } // END of txCredit definition.

                leaf txFast  {
                    type  cml_data_types:CML_UINT32_T;
                    description "";
                } // END of txFast definition.

                leaf state  {
                    type  cml_data_types:CML_UINT8_T;
                    description "";
                } // END of state definition.

                leaf txNow  {
                    type  cml_data_types:CML_BOOL_T;
                    description "";
                } // END of txNow definition.

                leaf txTick  {
                    type  cml_data_types:CML_BOOL_T;
                    description "";
                } // END of txTick definition.

                leaf localChange  {
                    type  cml_data_types:CML_BOOL_T;
                    description "";
                } // END of localChange definition.

                leaf txTtl  {
                    type  cml_data_types:CML_INT16_T;
                    description "";
                } // END of txTtl definition.

                leaf lengthErrorsTotal  {
                    type  cml_data_types:CML_UINT32_T;
                    description "";
                } // END of lengthErrorsTotal definition.

                leaf framesOutTotal  {
                    type  cml_data_types:CML_UINT32_T;
                    description "";
                } // END of framesOutTotal definition.

            } // END of lldpTxSm-container definition.
            container lldpRxSmConfig {
                description
                    "lldpRxSmConfig";
                leaf neighborLimit  {
                    type  cml_data_types:CML_UINT32_T {
                         range "1..65535";
                    }
                    description "";
                } // END of neighborLimit definition.

                leaf neighborTimer  {
                    type  cml_data_types:CML_UINT32_T {
                         range "1..65535";
                    }
                    description "";
                } // END of neighborTimer definition.

                leaf portMac  {
                    type  cml_data_types:CML_STRING_T;
                    description "";
                } // END of portMac definition.

                leaf portTimer  {
                    type  cml_data_types:CML_UINT32_T {
                         range "1..65535";
                    }
                    description "";
                } // END of portTimer definition.

            } // END of lldpRxSmConfig-container definition.
            container lldpRxSm {
                config false;
                description
                    "lldpRxSm";
                leaf badFrame  {
                    type  cml_data_types:CML_BOOL_T;
                    description "";
                } // END of badFrame definition.

                leaf rxChanges  {
                    type  cml_data_types:CML_BOOL_T;
                    description "";
                } // END of rxChanges definition.

                leaf remoteChanges  {
                    type  cml_data_types:CML_BOOL_T;
                    description "";
                } // END of remoteChanges definition.

                leaf tooManyNeighbours  {
                    type  cml_data_types:CML_BOOL_T;
                    description "";
                } // END of tooManyNeighbours definition.

                leaf rxInfoAge  {
                    type  cml_data_types:CML_BOOL_T;
                    description "";
                } // END of rxInfoAge definition.

                leaf ageoutsTotal  {
                    type  cml_data_types:CML_UINT32_T;
                    description "";
                } // END of ageoutsTotal definition.

                leaf framesDiscardedTotal  {
                    type  cml_data_types:CML_UINT32_T;
                    description "";
                } // END of framesDiscardedTotal definition.

                leaf framesInErrorsTotal  {
                    type  cml_data_types:CML_UINT32_T;
                    description "";
                } // END of framesInErrorsTotal definition.

                leaf framesInTotal  {
                    type  cml_data_types:CML_UINT32_T;
                    description "";
                } // END of framesInTotal definition.

                leaf tlvsDiscardedTotal  {
                    type  cml_data_types:CML_UINT32_T;
                    description "";
                } // END of tlvsDiscardedTotal definition.

                leaf tlvsUnrecognizedTotal  {
                    type  cml_data_types:CML_UINT32_T;
                    description "";
                } // END of tlvsUnrecognizedTotal definition.

                leaf tooManyNeighborsFlag  {
                    type  cml_data_types:CML_UINT8_T;
                    description "";
                } // END of tooManyNeighborsFlag definition.

                leaf tooManyNeighborsCount  {
                    type  cml_data_types:CML_UINT32_T;
                    description "";
                } // END of tooManyNeighborsCount definition.

                leaf tooManyNeighborsDiscardType  {
                    type  cml_data_types:CML_UINT8_T;
                    description "";
                } // END of tooManyNeighborsDiscardType definition.

                leaf tooManyNeighborsDiscardMac  {
                    type  cml_data_types:CML_STRING_T;
                    description "";
                } // END of tooManyNeighborsDiscardMac definition.


                list rlldpList {
                    key "remoteIfname";
                    config false;
                    description
                        "rlldpList";
                    leaf remoteIfname  {
                        type  cml_data_types:CML_STRING_T;
                        description "";
                    } // END of remoteIfname definition.

                    leaf remoteSysName  {
                        type  cml_data_types:CML_STRING_T;
                        description "";
                    } // END of remoteSysName definition.

                    leaf remotePortIdSubtype  {
                        type  cml_data_types:CML_UINT8_T;
                        description "";
                    } // END of remotePortIdSubtype definition.

                    leaf remoteChassicComp  {
                        type  cml_data_types:CML_UINT8_T;
                        description "";
                    } // END of remoteChassicComp definition.

                    leaf remotePortComp  {
                        type  cml_data_types:CML_UINT8_T;
                        description "";
                    } // END of remotePortComp definition.

                    leaf remoteIfalias  {
                        type  cml_data_types:CML_STRING_T;
                        description "";
                    } // END of remoteIfalias definition.

                    leaf remoteMacAddr  {
                        type  cml_data_types:CML_STRING_T;
                        description "";
                    } // END of remoteMacAddr definition.

                    leaf remoteIfagentcircuitid  {
                        type  cml_data_types:CML_STRING_T;
                        description "";
                    } // END of remoteIfagentcircuitid definition.

                    leaf remoteLocal  {
                        type  cml_data_types:CML_STRING_T;
                        description "";
                    } // END of remoteLocal definition.

                    leaf remoteEntityPhyAlias  {
                        type  cml_data_types:CML_STRING_T;
                        description "";
                    } // END of remoteEntityPhyAlias definition.

                    leaf remoteChassisIdType  {
                        type  cml_data_types:CML_UINT8_T;
                        description "";
                    } // END of remoteChassisIdType definition.

                    leaf remotePortIdType  {
                        type  cml_data_types:CML_UINT8_T;
                        description "";
                    } // END of remotePortIdType definition.

                    leaf rxTtl  {
                        type  cml_data_types:CML_UINT16_T;
                        description "";
                    } // END of rxTtl definition.

                    leaf remoteIfNumbering  {
                        type  cml_data_types:CML_UINT8_T;
                        description "";
                    } // END of remoteIfNumbering definition.

                    leaf remoteIfNumber  {
                        type  cml_data_types:CML_UINT32_T;
                        description "";
                    } // END of remoteIfNumber definition.

                    leaf remotePortVlanId  {
                        type  cml_data_types:CML_UINT16_T;
                        description "";
                    } // END of remotePortVlanId definition.

                    leaf remotePpvidFlag  {
                        type  cml_data_types:CML_UINT8_T;
                        description "";
                    } // END of remotePpvidFlag definition.

                    leaf remotePpVlanId  {
                        type  cml_data_types:CML_UINT16_T;
                        description "";
                    } // END of remotePpVlanId definition.

                    leaf remoteProtocol  {
                        type  cml_data_types:CML_UINT16_T;
                        description "";
                    } // END of remoteProtocol definition.

                    leaf remoteVidUsageDigest  {
                        type  cml_data_types:CML_UINT32_T;
                        description "";
                    } // END of remoteVidUsageDigest definition.

                    leaf remoteMgmtVlan  {
                        type  cml_data_types:CML_UINT16_T;
                        description "";
                    } // END of remoteMgmtVlan definition.

                    leaf remoteAutonegoSupport  {
                        type  cml_data_types:CML_UINT8_T;
                        description "";
                    } // END of remoteAutonegoSupport definition.

                    leaf remoteAutonegoCap  {
                        type  cml_data_types:CML_UINT16_T;
                        description "";
                    } // END of remoteAutonegoCap definition.

                    leaf remoteOperMauType  {
                        type  cml_data_types:CML_UINT16_T;
                        description "";
                    } // END of remoteOperMauType definition.

                    leaf remoteLinkAggrStatus  {
                        type  cml_data_types:CML_UINT8_T;
                        description "";
                    } // END of remoteLinkAggrStatus definition.

                    leaf remoteLinkAggrId  {
                        type  cml_data_types:CML_UINT32_T;
                        description "";
                    } // END of remoteLinkAggrId definition.

                    leaf remoteMaxFrameSize  {
                        type  cml_data_types:CML_UINT16_T;
                        description "";
                    } // END of remoteMaxFrameSize definition.

                    leaf remoteSysDescr  {
                        type  cml_data_types:CML_STRING_T;
                        description "";
                    } // END of remoteSysDescr definition.

                    leaf remoteSysCap  {
                        type  cml_data_types:CML_UINT16_T;
                        description "";
                    } // END of remoteSysCap definition.

                    leaf remoteSysCapEnabled  {
                        type  cml_data_types:CML_UINT16_T;
                        description "";
                    } // END of remoteSysCapEnabled definition.

                    leaf remoteMgmtAddr  {
                        type  cml_data_types:CML_STRING_T;
                        description "";
                    } // END of remoteMgmtAddr definition.

                    leaf remoteMgmtAddrSubType  {
                        type  cml_data_types:CML_UINT8_T;
                        description "";
                    } // END of remoteMgmtAddrSubType definition.

                    leaf remoteOid  {
                        type  cml_data_types:CML_STRING_T;
                        description "";
                    } // END of remoteOid definition.

                    leaf timeMarkIndex  {
                        type  cml_data_types:CML_UINT8_T;
                        description "";
                    } // END of timeMarkIndex definition.

                    leaf remoteIndex  {
                        type  cml_data_types:CML_UINT32_T;
                        description "";
                    } // END of remoteIndex definition.

                    leaf remoteUnknownTlvType  {
                        type  cml_data_types:CML_UINT32_T;
                        description "";
                    } // END of remoteUnknownTlvType definition.

                    leaf remoteUnknownTlvInfo  {
                        type  cml_data_types:CML_STRING_T;
                        description "";
                    } // END of remoteUnknownTlvInfo definition.

                    leaf remoteUnknownTlvInfoLen  {
                        type  cml_data_types:CML_UINT16_T;
                        description "";
                    } // END of remoteUnknownTlvInfoLen definition.

                    leaf remoteMdiPowerSupport  {
                        type  cml_data_types:CML_UINT8_T;
                        description "";
                    } // END of remoteMdiPowerSupport definition.

                    leaf remotePsePowerPair  {
                        type  cml_data_types:CML_UINT8_T;
                        description "";
                    } // END of remotePsePowerPair definition.

                    leaf remotePowerClass  {
                        type  cml_data_types:CML_UINT8_T;
                        description "";
                    } // END of remotePowerClass definition.

                    leaf remoteTypeSourcePriority  {
                        type  cml_data_types:CML_UINT8_T;
                        description "";
                    } // END of remoteTypeSourcePriority definition.

                    leaf remotePdRequestedPower  {
                        type  cml_data_types:CML_UINT16_T;
                        description "";
                    } // END of remotePdRequestedPower definition.

                    leaf remotePseAllocatedPower  {
                        type  cml_data_types:CML_UINT16_T;
                        description "";
                    } // END of remotePseAllocatedPower definition.

                    leaf peerEts  {
                        type  cml_data_types:CML_BOOL_T;
                        description "";
                    } // END of peerEts definition.

                    leaf etsError  {
                        type  cml_data_types:CML_BOOL_T;
                        description "";
                    } // END of etsError definition.

                    leaf etsTcgNum  {
                        type  cml_data_types:CML_UINT8_T;
                        description "";
                    } // END of etsTcgNum definition.

                    leaf peerApp  {
                        type  cml_data_types:CML_BOOL_T;
                        description "";
                    } // END of peerApp definition.

                    leaf appError  {
                        type  cml_data_types:CML_BOOL_T;
                        description "";
                    } // END of appError definition.

                    leaf cdcpStatus  {
                        type  cml_data_types:CML_BOOL_T;
                        description "";
                    } // END of cdcpStatus definition.

                    leaf peerEvb  {
                        type  cml_data_types:CML_BOOL_T;
                        description "";
                    } // END of peerEvb definition.

                    leaf peerCdcp  {
                        type  cml_data_types:CML_BOOL_T;
                        description "";
                    } // END of peerCdcp definition.

                    leaf remoteQcnTlv  {
                        type  cml_data_types:CML_BOOL_T;
                        description "";
                    } // END of remoteQcnTlv definition.

                    leaf remoteQcnCnpv  {
                        type  cml_data_types:CML_UINT8_T;
                        description "";
                    } // END of remoteQcnCnpv definition.

                    leaf remoteQcnReady  {
                        type  cml_data_types:CML_UINT8_T;
                        description "";
                    } // END of remoteQcnReady definition.


                    list remoteVlanList {
                        key "vlanId";
                        config false;
                        description
                            "remoteVlanList";
                        leaf vlanId  {
                            type  cml_data_types:CML_UINT16_T;
                            description "";
                        } // END of vlanId definition.

                        leaf vlanName  {
                            type  cml_data_types:CML_STRING_T;
                            description "";
                        } // END of vlanName definition.

                    } // End of remoteVlanList-list

                    list remoteMgmtInfo {
                        key "remoteMgmtAddr";
                        config false;
                        description
                            "remoteMgmtInfo";
                        leaf remoteMgmtAddr  {
                            type  cml_data_types:CML_STRING_T;
                            description "";
                        } // END of remoteMgmtAddr definition.

                        leaf remoteMgmtAddrSubType  {
                            type  cml_data_types:CML_UINT8_T;
                            description "";
                        } // END of remoteMgmtAddrSubType definition.

                        leaf remoteIfNumbering  {
                            type  cml_data_types:CML_UINT8_T;
                            description "";
                        } // END of remoteIfNumbering definition.

                        leaf remoteIfNumber  {
                            type  cml_data_types:CML_UINT32_T;
                            description "";
                        } // END of remoteIfNumber definition.

                        leaf remoteOid  {
                            type  cml_data_types:CML_STRING_T;
                            description "";
                        } // END of remoteOid definition.

                    } // End of remoteMgmtInfo-list
                } // End of rlldpList-list
            } // END of lldpRxSm-container definition.
            container lldpTlvConfigCmd {
                description
                    "lldpTlvConfigCmd";
                leaf portAddr  {
                    type  cml_data_types:CML_LLDP_MGMT_ADDR_T;
                    default "mac-address";
                    description "";
                } // END of portAddr definition.

                leaf chassisId  {
                    type  cml_data_types:CML_LLDP_CHASSIS_T;
                    default "mac-address";
                    description "";
                } // END of chassisId definition.

                leaf portId  {
                    type  cml_data_types:CML_LLDP_PORT_T;
                    default "mac-address";
                    description "";
                } // END of portId definition.

                leaf-list tlvMed  {
                    type  cml_data_types:CML_LLDP_MED_T;
                    description "";
                } // END of tlvMed definition.

                container lldpTLVs {
                    description
                        "lldpTLVs";
                    container basicMgmt {
                        description
                            "basicMgmt";
                        leaf portDescription  {
                            type  cml_data_types:CML_BOOL_T;
                            description "";
                        } // END of portDescription definition.

                        leaf systemDescription  {
                            type  cml_data_types:CML_BOOL_T;
                            description "";
                        } // END of systemDescription definition.

                        leaf systemName  {
                            type  cml_data_types:CML_BOOL_T;
                            description "";
                        } // END of systemName definition.

                        leaf systemCapabilities  {
                            type  cml_data_types:CML_BOOL_T;
                            description "";
                        } // END of systemCapabilities definition.

                        leaf mgmtAddress  {
                            type  cml_data_types:CML_BOOL_T;
                            description "";
                        } // END of mgmtAddress definition.

                    } // END of basicMgmt-container definition.
                    container ieee8021orgSpecific {
                        description
                            "ieee8021orgSpecific";
                        leaf portVlanid  {
                            type  cml_data_types:CML_BOOL_T;
                            description "";
                        } // END of portVlanid definition.

                        leaf portPtclVlanid  {
                            type  cml_data_types:CML_BOOL_T;
                            description "";
                        } // END of portPtclVlanid definition.

                        leaf vlanName  {
                            type  cml_data_types:CML_BOOL_T;
                            description "";
                        } // END of vlanName definition.

                        leaf ptclIdentity  {
                            type  cml_data_types:CML_BOOL_T;
                            description "";
                        } // END of ptclIdentity definition.

                        leaf vidDigest  {
                            type  cml_data_types:CML_BOOL_T;
                            description "";
                        } // END of vidDigest definition.

                        leaf mgmtVid  {
                            type  cml_data_types:CML_BOOL_T;
                            description "";
                        } // END of mgmtVid definition.

                        leaf linkAgg  {
                            type  cml_data_types:CML_BOOL_T;
                            description "";
                        } // END of linkAgg definition.

                        leaf dcb  {
                            if-feature feature_list:HAVE_DCB;
                            type  cml_data_types:CML_BOOL_T;
                            description "";
                        } // END of dcb definition.

                    } // END of ieee8021orgSpecific-container definition.
                    container ieee8023orgSpecific {
                        description
                            "ieee8023orgSpecific";
                        leaf macPhy  {
                            type  cml_data_types:CML_BOOL_T;
                            description "";
                        } // END of macPhy definition.

                        leaf maxMtuSize  {
                            type  cml_data_types:CML_BOOL_T;
                            description "";
                        } // END of maxMtuSize definition.

                        leaf powerViaMdi  {
                            if-feature feature_list:HAVE_POE;
                            type  cml_data_types:CML_BOOL_T;
                            description "";
                        } // END of powerViaMdi definition.

                    } // END of ieee8023orgSpecific-container definition.
                } // END of lldpTLVs-container definition.
            } // END of lldpTlvConfigCmd-container definition.
            container lldpTlvConfig {
                config false;
                description
                    "lldpTlvConfig";
                leaf protocol  {
                    type  cml_data_types:CML_UINT16_T;
                    description "";
                } // END of protocol definition.

                leaf tooManyNeighborsCount  {
                    type  cml_data_types:CML_UINT32_T;
                    description "";
                } // END of tooManyNeighborsCount definition.

                leaf tooManyNeighborsLimit  {
                    type  cml_data_types:CML_UINT32_T;
                    description "";
                } // END of tooManyNeighborsLimit definition.

                leaf tooManyNeighborsDiscardType  {
                    type  cml_data_types:CML_UINT8_T;
                    description "";
                } // END of tooManyNeighborsDiscardType definition.

                leaf tooManyNeighborsDiscardMac  {
                    type  cml_data_types:CML_STRING_T;
                    description "";
                } // END of tooManyNeighborsDiscardMac definition.

                leaf tooManyNeighborsInterval  {
                    type  cml_data_types:CML_UINT32_T;
                    description "";
                } // END of tooManyNeighborsInterval definition.

            } // END of lldpTlvConfig-container definition.
        } // End of lldpAgent-list
    } // END of lldpv2Interface-container definition.
    } // END of lldpv2Interface-container definition.

    grouping  evbbridge-grouping {
    description
        "evbbridge";
    container evbbridge {
        if-feature feature_list:HAVE_DCB;
        description
            "evbbridge";
        leaf lowsvidPoolRange  {
            type  cml_data_types:CML_UINT32_T {
                 range "2..4094";
            }
            description "";
        } // END of lowsvidPoolRange definition.

        leaf highsvidPoolRange  {
            type  cml_data_types:CML_UINT32_T {
                 range "2..4094";
            }
            description "";
        } // END of highsvidPoolRange definition.

        leaf tlvModeFlag  {
            type  cml_data_types:CML_LLDP_TLV_MODE_T;
            description "";
        } // END of tlvModeFlag definition.

        leaf resourceWaitDelay  {
            type  cml_data_types:CML_UINT8_T {
                 range "0..31";
            }
            description "";
        } // END of resourceWaitDelay definition.

        leaf keepAlive  {
            type  cml_data_types:CML_UINT8_T {
                 range "0..31";
            }
            description "";
        } // END of keepAlive definition.

        leaf ecpAcktimer  {
            type  cml_data_types:CML_UINT8_T {
                 range "10..20";
            }
            description "";
        } // END of ecpAcktimer definition.

        leaf ecpMaxRetry  {
            type  cml_data_types:CML_UINT8_T {
                 range "0..7";
            }
            description "";
        } // END of ecpMaxRetry definition.

        leaf channelCapacity  {
            type  cml_data_types:CML_UINT8_T {
                 range "1..167";
            }
            description "";
        } // END of channelCapacity definition.

    } // END of evbbridge-container definition.
    } // END of evbbridge-container definition.

    grouping  lldpDebug-grouping {
    description
        "lldpDebug";
    container lldpDebug {
        description
            "lldpDebug";
        leaf lldpDebug  {
            type  cml_data_types:CML_LLDP_DEBUG_T;
            description "";
        } // END of lldpDebug definition.

    } // END of lldpDebug-container definition.
    } // END of lldpDebug-container definition.


}
