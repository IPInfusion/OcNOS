/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : syslog.yang
*
*/

submodule syslog {

    belongs-to  ZebOS { prefix ZebOS; }

    import cml_data_types {
        prefix cml_data_types;
    }

    import feature_list {
        prefix feature_list;
    }

    include vrf;
    organization
        "IP Infusion Inc.";

    contact
        "Address: 3965 Freedom Circle, Suite 200, Santa Clara, CA 95054
        Phone: +1 408-400-1900
        E-mail: support@ipinfusion.com
        Web: http://www.ipinfusion.com/";

    description
        "hostp syslog configurations";


    revision "2017-01-12" {
        description "Changed vrf name as normal attr as it is optional parameter.";
    }

    revision "2016-10-28" {
        description "Initial version of SYSLOG datamodel.";
    }


    grouping  hostpsyslog-grouping {
    container hostpsyslog {
        description
            "syslog related operations";
        leaf defaultVrfSourceInterface  {
            type  cml_data_types:CML_STRING_T {
                length "0..255";
            }
        } // END of defaultVrfSourceInterface definition.

        leaf mgmtVrfSrcInterface  {
            type  cml_data_types:CML_STRING_T {
                length "0..255";
            }
        } // END of mgmtVrfSrcInterface definition.

        leaf debuglogging  {
            if-feature feature_list:HAVE_DEBUG_MODULE_SEVERITY;
            type  cml_data_types:CML_LEVEL_T;
            description "debug logging host with level";
        } // END of debuglogging definition.

        leaf debug  {
            type  cml_data_types:CML_BOOL_T;
            description "debug logging";
        } // END of debug definition.


        list syslogServer {
            key "ServerAddr";
            description
                "list of servers";
            leaf vrfName  {
                type  cml_data_types:CML_STRING_T {
                    length "0..255";
                }
            } // END of vrfName definition.

            leaf ServerAddr  {
                type  cml_data_types:CML_STRING_T {
                    length "1..64";
                }
                description "logging server with severity and facility";
            } // END of ServerAddr definition.

            leaf ServerSeverity  {
                type  cml_data_types:CML_INT8_T {
                     range "0..7";
                }
                default "7";
            } // END of ServerSeverity definition.

            leaf ServerFacility  {
                type  cml_data_types:CML_FACILITY_T;
                default "local7";
            } // END of ServerFacility definition.

        } // End of syslogServer-list
    } // END of hostpsyslog-container definition.
    } // END of hostpsyslog-container definition.


}
