/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-zebos-vm.yang
*
*/

submodule ipi-zebos-vm {

    belongs-to  ipi-zebos { prefix ipi-zebos; }

    import cml-data-types {
        prefix cml-data-types;
    }

    organization
        "IP Infusion Inc.";

    contact
        "Address: 3965 Freedom Circle, Suite 200, Santa Clara, CA 95054
        Phone: +1 408-400-1900
        E-mail: support@ipinfusion.com
        Web: http://www.ipinfusion.com/";

    description
        "Virtual Machine";


    revision "2018-10-24" {
        description "Adding support for Guest-VM feature.";
        reference "";
    }



    typedef  CML_PROTO_T {
        type enumeration {
            enum tcp {
                value 1;
                description "Give TCP";
            }
            enum udp {
                value 2;
                description "Give UDP";
            }
        }
        description "";
        reference "";
    }

    typedef  CML_VM_OS_TYPE_T {
        type enumeration {
            enum xen {
                value 1;
                description "Give xen";
            }
            enum linux {
                value 2;
                description "Give linux";
            }
            enum hvm {
                value 3;
                description "Give hvm";
            }
            enum exe {
                value 4;
                description "Give exe";
            }
            enum uml {
                value 5;
                description "Give uml";
            }
        }
        description "";
        reference "";
    }

    typedef  CML_VM_OS_VARIANT_T {
        type enumeration {
            enum generic {
                value 1;
                description "Give generic";
            }
            enum fedora {
                value 2;
                description "Give fedora";
            }
            enum rhel {
                value 3;
                description "Give rhel";
            }
            enum ubuntu {
                value 4;
                description "Give ubuntu";
            }
            enum debian {
                value 5;
                description "Give debian";
            }
        }
        description "";
        reference "";
    }

    typedef  CML_VM_VIRT_TYPE_T {
        type enumeration {
            enum kvm {
                value 1;
                description "Give kvm";
            }
            enum qemu {
                value 2;
                description "Give qemu";
            }
        }
        description "";
        reference "";
    }

    grouping vmtemplate-grouping {
    description
        "Description about VM template";
        list vmtemplate {
            key "vmTemplateName";
            description
                "Description about VM template";
            leaf vmTemplateName  {
                type  cml-data-types:CML_STRING_T {
                    length "1..16";
                }
                description "Name of the VM template";
            } // END of vmTemplateName definition.

            leaf memory  {
                type  cml-data-types:CML_INT32_T {
                     range "128..8192";
                }
                default "128";
                description "Memory for Virtual Machine in MB";
            } // END of memory definition.

            leaf osType  {
                type  CML_VM_OS_TYPE_T;
                default "hvm";
                description "Set the operating system type of Virtual Machine";
            } // END of osType definition.

            leaf osVariant  {
                type  CML_VM_OS_VARIANT_T;
                default "generic";
                description "Set the operating system variant for a virtual machine template";
            } // END of osVariant definition.

            leaf osVirtType  {
                type  CML_VM_VIRT_TYPE_T;
                description "Used to set the virtualization type of Virtual Machine";
            } // END of osVirtType definition.

            leaf diskImage  {
                type  cml-data-types:CML_STRING_T;
                description "Location of the disk image to boot up the VM.";
            } // END of diskImage definition.

            leaf secondaryDiskImage  {
                type  cml-data-types:CML_STRING_T;
                description "Location of the secondary disk image to boot up the VM";
            } // END of secondaryDiskImage definition.

            leaf hostCoreAffinity  {
                type  cml-data-types:CML_VM_AFFINITY_T;
                description "The core affinity values between 0 and 7";
            } // END of hostCoreAffinity definition.

            leaf vcpu  {
                type  cml-data-types:CML_INT8_T {
                     range "1..16";
                }
                default "1";
                description "Virtual CPU count";
            } // END of vcpu definition.


            list vNICList {
                key "vrfName";
                description
                    "Description about Virtual NIC list";
                leaf vrfName  {
                    type  cml-data-types:CML_STRING_T {
                        length "1..16";
                    }
                    description "VRF Name";
                } // END of vrfName definition.

                leaf vNIC  {
                    type  cml-data-types:CML_BOOL_T;
                    mandatory true;
                    description "Virtual NIC ID for Virtual Machine";
                } // END of vNIC definition.

                leaf macAddress  {
                    type  cml-data-types:CML_MAC_ADDR_T;
                    mandatory true;
                    description "MAC address of the VM";
                } // END of macAddress definition.

            } // End of vNICList-list
        } // End of vmtemplate-list
    } // END of vmtemplate-grouping definition.


    grouping guestVmList-grouping {
    description
        "Description about starting vm";
        list guestVmList {
            key "vmName";
            description
                "Description about starting vm";
            leaf vmName  {
                type  cml-data-types:CML_STRING_T {
                    length "1..16";
                }
                description "Name of the VM";
            } // END of vmName definition.

            leaf startvm  {
                type  cml-data-types:CML_BOOL_T;
                mandatory true;
                description "Start guest VM";
            } // END of startvm definition.

            leaf vmTemplateName  {
                type  cml-data-types:CML_STRING_T {
                    length "1..16";
                }
                mandatory true;
                description "Name of the VM template";
            } // END of vmTemplateName definition.

            leaf vmStatus  {
                type  cml-data-types:CML_VM_STATUS_T;
                config false;
                description "Used to get status(UP/DOWN) of VM";
            } // END of vmStatus definition.

            leaf vmStartTime  {
                type  cml-data-types:CML_DATE_TIME_T;
                config false;
                description "start time of VM";
            } // END of vmStartTime definition.

            leaf vmIP  {
                type  cml-data-types:CML_IPV4_ADDR_T;
                config false;
                description "Assigned IP to VM";
            } // END of vmIP definition.

        } // End of guestVmList-list
    } // END of guestVmList-grouping definition.


    grouping iptable-grouping {
    description
        "Description about Iptables Rules template";
        list iptable {
            key "ipTabTempName";
            description
                "Description about Iptables Rules template";
            leaf ipTabTempName  {
                type  cml-data-types:CML_STRING_T {
                    length "1..16";
                }
                description "Name of the IP tables template";
            } // END of ipTabTempName definition.


            list ipTabRuleStrList {
                key "ipTabRuleStr";
                description
                    "Description about iptables rules";
                leaf ipTabRuleStr  {
                    type  cml-data-types:CML_LINE_T;
                    description "Rule string in double quotes";
                } // END of ipTabRuleStr definition.

                leaf ipTabrulePos  {
                    type  cml-data-types:CML_INT32_T {
                         range "-1..65535";
                    }
                    mandatory true;
                    description "Position to insert the rule string (1-65535)";
                } // END of ipTabrulePos definition.

            } // End of ipTabRuleStrList-list
        } // End of iptable-list
    } // END of iptable-grouping definition.


    grouping restoreList-grouping {
    description
        "Description about restoring iptables rules";
        list restoreList {
            key "ipTabTempName";
            description
                "Description about restoring iptables rules";
            leaf ipTabTempName  {
                type  cml-data-types:CML_STRING_T {
                    length "1..16";
                }
                description "Name of the IP tables template";
            } // END of ipTabTempName definition.

            leaf vrfName  {
                type  cml-data-types:CML_STRING_T;
                mandatory true;
                description "Vrf namespace name in which rule string is configured";
            } // END of vrfName definition.

            leaf iptables  {
                type  cml-data-types:CML_BOOL_T;
                mandatory true;
                description "Iptables restore";
            } // END of iptables definition.

        } // End of restoreList-list
    } // END of restoreList-grouping definition.


    grouping srcNatList-grouping {
    description
        "Describes Source NAT configurations";
        list srcNatList {
            key "sFromIpAddr";
            description
                "Describes Source NAT configurations";
            leaf sFromIpAddr  {
                type  cml-data-types:CML_IPV4_PREFIX_T;
                description "From IP address and subnet mask";
            } // END of sFromIpAddr definition.


            list srcToNatList {
                key "toIpAddr";
                description
                    "srcToNatList";
                leaf toIpAddr  {
                    type  cml-data-types:CML_IPV4_ADDR_T;
                    description "To IP address";
                } // END of toIpAddr definition.


                list srcVrfNatList {
                    key "vrfName";
                    description
                        "srcVrfNatList";
                    leaf vrfName  {
                        type  cml-data-types:CML_STRING_T;
                        description "VRF Name";
                    } // END of vrfName definition.

                } // End of srcVrfNatList-list
            } // End of srcToNatList-list
        } // End of srcNatList-list
    } // END of srcNatList-grouping definition.


    grouping dstNatList-grouping {
    description
        "Describes about Destination NAT configurations";
        list dstNatList {
            key "dFromIpAddr";
            description
                "Describes about Destination NAT configurations";
            leaf dFromIpAddr  {
                type  cml-data-types:CML_IPV4_ADDR_T;
                description "From IP address";
            } // END of dFromIpAddr definition.


            list toNatList {
                key "toIpAddr";
                description
                    "Describes about destination NAT address";
                leaf toIpAddr  {
                    type  cml-data-types:CML_IPV4_ADDR_T;
                    description "To IP address";
                } // END of toIpAddr definition.


                list vrfNatlist {
                    key "vrfName";
                    description
                        "Description about NAT configurations in VRF namespace";
                    leaf vrfName  {
                        type  cml-data-types:CML_STRING_T;
                        description "VRF Name";
                    } // END of vrfName definition.


                    list protocolType {
                        key "protocol";
                        description
                            "Description about DNAT entry protocol";
                        leaf protocol  {
                            type  CML_PROTO_T;
                            description "Use TCP or UDP for NAT";
                        } // END of protocol definition.


                        list sourcePort {
                            key "fromPortNum";
                            description
                                "Description about source port for DNAT entry";
                            leaf fromPortNum  {
                                type  cml-data-types:CML_INT32_T {
                                     range "-1..65535";
                                }
                                description "Source port number. Since '0' is valid port number, used '-1' for optional manipulation";
                            } // END of fromPortNum definition.


                            list destPort {
                                key "toPortNum";
                                description
                                    "Description about destination port for DNAT entry";
                                leaf toPortNum  {
                                    type  cml-data-types:CML_INT32_T {
                                         range "-1..65535";
                                    }
                                    description "Destination port number. Since '0' is valid port number, used '-1' for optional manipulation";
                                } // END of toPortNum definition.

                            } // End of destPort-list
                        } // End of sourcePort-list
                    } // End of protocolType-list
                } // End of vrfNatlist-list
            } // End of toNatList-list
        } // End of dstNatList-list
    } // END of dstNatList-grouping definition.


    grouping brList-grouping {
    description
        "Description about VM bridge creation";
        list brList {
            key "brName";
            description
                "Description about VM bridge creation";
            leaf brName  {
                type  cml-data-types:CML_STRING_T {
                    length "1..16";
                }
                description "Name of the VM bridge";
            } // END of brName definition.

            leaf gateWayIpAddr  {
                type  cml-data-types:CML_IPV4_PREFIX_T;
                description "Gateway IP address and subnet mask";
            } // END of gateWayIpAddr definition.

            leaf leaseMaxVal  {
                type  cml-data-types:CML_UINT32_T {
                     range "10..1000";
                }
                default "1000";
                description "Maximum number of DHCP leases";
            } // END of leaseMaxVal definition.

            leaf leaseTime  {
                type  cml-data-types:CML_UINT32_T {
                     range "2..3600";
                }
                default "300";
                description "Maximum time for leasing an IP address in minutes";
            } // END of leaseTime definition.

            leaf dhcpStartIp  {
                type  cml-data-types:CML_IPV4_ADDR_T;
                description "Starting IP address of the DHCP range";
            } // END of dhcpStartIp definition.

            leaf dhcpEndIp  {
                type  cml-data-types:CML_IPV4_ADDR_T;
                description "Ending IP address of the DHCP range";
            } // END of dhcpEndIp definition.


            list macAddrList {
                key "ipAddr";
                description
                    "Description about Macaddress";
                leaf ipAddr  {
                    type  cml-data-types:CML_IPV4_ADDR_T;
                    description "IP Address";
                } // END of ipAddr definition.

                leaf macAddr  {
                    type  cml-data-types:CML_MAC_ADDR_T;
                    mandatory true;
                    description "MAC Address";
                } // END of macAddr definition.

            } // End of macAddrList-list
            container dnsMasq {
                description
                    "Description about DNS MASQ service";
                leaf service  {
                    type  cml-data-types:CML_BOOL_T;
                    description "Start dns-masq service";
                } // END of service definition.

            } // END of dnsMasq-container definition.
        } // End of brList-list
    } // END of brList-grouping definition.

    grouping  guestVm-grouping {
    description
        "Description about guest vm feature enable";
    container guestVm {
        description
            "Description about guest vm feature enable";
        leaf featureGuestVm  {
            type  cml-data-types:CML_BOOL_T;
            description "Global command to enable Guest-VM feature";
        } // END of featureGuestVm definition.

    } // END of guestVm-container definition.
    } // END of guestVm-container definition.

    grouping  debugVmEvents-grouping {
    description
        "Description about vm debug configs";
    container debugVmEvents {
        description
            "Description about vm debug configs";
        leaf vmDebugFlag  {
            type  cml-data-types:CML_BOOL_T;
            description "Log virtual machine events";
        } // END of vmDebugFlag definition.

    } // END of debugVmEvents-container definition.
    } // END of debugVmEvents-container definition.


}
