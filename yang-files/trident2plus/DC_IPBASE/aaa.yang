/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : aaa.yang
*
*/

submodule aaa {

    belongs-to  ZebOS { prefix ZebOS; }

    import cml_data_types {
        prefix cml_data_types;
    }

    include vrf;
    include tacacs;
    include radius;
    organization
        "IP Infusion Inc.";

    contact
        "Address: 3965 Freedom Circle, Suite 200, Santa Clara, CA 95054
        Phone: +1 408-400-1900
        E-mail: support@ipinfusion.com
        Web: http://www.ipinfusion.com/";

    description
        "Layer-3 aaa configurations";


    revision "2017-09-06" {
        description "Added role restriction for clear command.";
    }

    revision "2017-05-26" {
        description "Unlock Timeout Attribute.";
    }

    revision "2017-05-16" {
        description "Modified the cli-sequence to cli-command and removed unwanted attrs.";
    }

    revision "2017-05-11" {
        description "Modified the cli-sequence to cli-command and removed attrs.";
    }

    revision "2016-12-27" {
        description "Added snmp oid and documentation tag.";
    }

    revision "2016-10-28" {
        description "Initial version of AAA datamodel.";
    }


    grouping  aaa-grouping {
    container aaa {
        description
            "aaa related commands";
        leaf vrfName  {
            type  cml_data_types:CML_STRING_T {
                length "0..255";
            }
        } // END of vrfName definition.

        leaf acctGroup  {
            type  cml_data_types:CML_LINE_T;
            description "aaa accounting details group";
        } // END of acctGroup definition.

        leaf acctLocal  {
            type  cml_data_types:CML_BOOL_T;
            description "aaa accounting details local";
        } // END of acctLocal definition.

        leaf errorEnable  {
            type  cml_data_types:CML_BOOL_T;
            description "aaa authentication login";
        } // END of errorEnable definition.

        leaf authDefaultGroup  {
            type  cml_data_types:CML_LINE_T;
            description "aaa authentication login default group";
        } // END of authDefaultGroup definition.

        leaf authMaxfail  {
            type  cml_data_types:CML_UINT8_T {
                 range "1..25";
            }
            default "3";
            description "aaa local authentication attempts max-fail";
        } // END of authMaxfail definition.

        leaf localUserUnlockTimeout  {
            type  cml_data_types:CML_UINT16_T {
                 range "1..3600";
            }
            default "1200";
            description "aaa local user authentication unlock after timeout";
        } // END of localUserUnlockTimeout definition.

        leaf authDefaultFallback  {
            type  cml_data_types:CML_BOOL_T;
            description "aaa authentication login default fallback error";
        } // END of authDefaultFallback definition.

        leaf authLocalDefault  {
            type  cml_data_types:CML_BOOL_T;
            description "aaa authentication login default local";
        } // END of authLocalDefault definition.

        leaf authNoneDefault  {
            type  cml_data_types:CML_BOOL_T;
            description "aaa authentication login default none";
        } // END of authNoneDefault definition.

        leaf debugaaa  {
            type  cml_data_types:CML_BOOL_T;
            description "debug aaa";
        } // END of debugaaa definition.

        leaf debugaaaConfig  {
            type  cml_data_types:CML_BOOL_T;
        } // END of debugaaaConfig definition.


        list aaaGroupServerNameRadius {
            key "groupWordRadius";
            description
                "aaaGroupServerNameRadius";
            leaf groupWordRadius  {
                type  cml_data_types:CML_STRING_T {
                    length "1..127";
                }
                description "aaa group server radius";
            } // END of groupWordRadius definition.


            list aaaRadiusServer {
                key "hostAddr";
                description
                    "aaaRadiusServer";
                leaf vrfName  {
                    type  cml_data_types:CML_STRING_T {
                        length "0..255";
                    }
                } // END of vrfName definition.

                leaf hostAddr  {
                    type  cml_data_types:CML_STRING_T {
                        length "1..64";
                    }
                    description "radius server";
                } // END of hostAddr definition.

            } // End of aaaRadiusServer-list
        } // End of aaaGroupServerNameRadius-list

        list aaaGroupServerNameTacacs {
            key "groupWordTacacs";
            description
                "aaaGroupServerNameTacacs";
            leaf groupWordTacacs  {
                type  cml_data_types:CML_STRING_T {
                    length "1..127";
                }
                description "aaa group server tacacs+";
            } // END of groupWordTacacs definition.


            list aaaTacacsServer {
                key "hostAddr";
                description
                    "aaaTacacsServer";
                leaf vrfName  {
                    type  cml_data_types:CML_STRING_T {
                        length "0..255";
                    }
                } // END of vrfName definition.

                leaf hostAddr  {
                    type  cml_data_types:CML_STRING_T {
                        length "1..64";
                    }
                    description "tacacs server";
                } // END of hostAddr definition.

            } // End of aaaTacacsServer-list
        } // End of aaaGroupServerNameTacacs-list
        container console {
            description
                "console";
            leaf authConsoleGroup  {
                type  cml_data_types:CML_LINE_T;
                description "aaa authentication login console";
            } // END of authConsoleGroup definition.

            leaf authConsoleFallback  {
                type  cml_data_types:CML_BOOL_T;
                description "aaa authentication login console fallback error";
            } // END of authConsoleFallback definition.

            leaf authLocal  {
                type  cml_data_types:CML_BOOL_T;
                description "aaa authentication login console";
            } // END of authLocal definition.

            leaf authNone  {
                type  cml_data_types:CML_BOOL_T;
                description "aaa authentication login console none";
            } // END of authNone definition.

        } // END of console-container definition.
    } // END of aaa-container definition.
    } // END of aaa-container definition.


}
