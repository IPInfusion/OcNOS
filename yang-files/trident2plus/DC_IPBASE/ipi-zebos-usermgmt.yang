/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-zebos-usermgmt.yang
*
*/

submodule ipi-zebos-usermgmt {

    belongs-to  ipi-zebos { prefix ipi-zebos; }

    import cml-data-types {
        prefix cml-data-types;
    }

    include ipi-zebos-ssh;
    organization
        "IP Infusion Inc.";

    contact
        "Address: 3965 Freedom Circle, Suite 200, Santa Clara, CA 95054
        Phone: +1 408-400-1900
        E-mail: support@ipinfusion.com
        Web: http://www.ipinfusion.com/";

    description
        "Layer-3 usermgmt configurations";


    revision "2018-06-21" {
        description " Initial Version.";
        reference "";
    }



    grouping usermgmt-grouping {
    description
        "usermgmt";
        list usermgmt {
            key "username";
            description
                "usermgmt";
            leaf username  {
                type  cml-data-types:CML_STRING_T {
                    length "2..15";
                }
                description "";
            } // END of username definition.

            leaf encryptPassword  {
                type  cml-data-types:CML_STRING_T {
                    length "26..106";
                }
                description "";
            } // END of encryptPassword definition.

            leaf password  {
                type  cml-data-types:CML_STRING_T {
                    length "5..32";
                }
                description "";
            } // END of password definition.

            leaf role  {
                type  cml-data-types:CML_STRING_T;
                description "";
            } // END of role definition.

            uses sshKeyList-grouping;
        } // End of usermgmt-list
    } // END of usermgmt-grouping definition.

    grouping  userDebug-grouping {
    description
        "userDebug";
    container userDebug {
        description
            "userDebug";
        leaf debugconfuser  {
            type  cml-data-types:CML_BOOL_T;
            description "";
        } // END of debugconfuser definition.

        leaf debuguser  {
            type  cml-data-types:CML_BOOL_T;
            description "";
        } // END of debuguser definition.

    } // END of userDebug-container definition.
    } // END of userDebug-container definition.


}
