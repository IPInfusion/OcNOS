/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : imi.yang
*
*/

submodule imi {

    belongs-to  ZebOS { prefix ZebOS; }

    import cml_data_types {
        prefix cml_data_types;
    }

    import feature_list {
        prefix feature_list;
    }

    organization
        "IP Infusion Inc.";

    contact
        "Address: 3965 Freedom Circle, Suite 200, Santa Clara, CA 95054
        Phone: +1 408-400-1900
        E-mail: support@ipinfusion.com
        Web: http://www.ipinfusion.com/";

    description
        "imi global configs";


    revision "2017-09-06" {
        description "Added role restriction for clear command.";
    }

    revision "2017-05-16" {
        description "Initial version of imi datamodel.";
    }

    grouping execTimeout {
        description
            "line mode configs for console or vty.";
        leaf min  {
            type  cml_data_types:CML_UINT32_T {
                 range "0..35791";
            }
            default "10";
        } // END of min definition.

        leaf sec  {
            type  cml_data_types:CML_UINT32_T {
                 range "0..2147483";
            }
            default "0";
        } // END of sec definition.

        leaf login  {
            type  cml_data_types:CML_BOOL_T;
        } // END of login definition.

        leaf privLevel  {
            type  cml_data_types:CML_UINT8_T {
                 range "1..16";
            }
        } // END of privLevel definition.

        leaf loginLocal  {
            type  cml_data_types:CML_BOOL_T;
        } // END of loginLocal definition.

        leaf historyMax  {
            type  cml_data_types:CML_UINT32_T {
                 range "0..2147483647";
            }
        } // END of historyMax definition.

    } // END of execTimeout definition.

    grouping  hostname-grouping {
    container hostname {
        description
            "Set system's network name";
        leaf hostname  {
            type  cml_data_types:CML_STRING_T {
                length "0..255";
            }
        } // END of hostname definition.

    } // END of hostname-container definition.
    } // END of hostname-container definition.

    grouping  webUser-grouping {
    container webUser {
        description
            "web user login credentials";
        leaf loginName  {
            type  cml_data_types:CML_STRING_T {
                length "0..255";
            }
        } // END of loginName definition.

        leaf loginPasswd  {
            type  cml_data_types:CML_STRING_T {
                length "0..255";
            }
        } // END of loginPasswd definition.

    } // END of webUser-container definition.
    } // END of webUser-container definition.

    grouping  loggingCli-grouping {
    container loggingCli {
        description
            "Enable flag to log ZebOS command lines.";
        leaf enableLoggingCli  {
            if-feature feature_list:HAVE_SYSLOG;
            type  cml_data_types:CML_BOOL_T;
            description "Logging control";
        } // END of enableLoggingCli definition.

    } // END of loggingCli-container definition.
    } // END of loggingCli-container definition.

    grouping  memInfo-grouping {
    container memInfo {
        description
            "Memory Info enable";
        leaf memInfoIMI  {
            type  cml_data_types:CML_BOOL_T;
        } // END of memInfoIMI definition.

    } // END of memInfo-container definition.
    } // END of memInfo-container definition.


}
