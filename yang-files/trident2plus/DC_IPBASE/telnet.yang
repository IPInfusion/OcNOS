/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : telnet.yang
*
*/

submodule telnet {

    belongs-to  ZebOS { prefix ZebOS; }

    import cml_data_types {
        prefix cml_data_types;
    }

    import feature_list {
        prefix feature_list;
    }

    include vrf;
    organization
        "IP Infusion Inc.";

    contact
        "Address: 3965 Freedom Circle, Suite 200, Santa Clara, CA 95054
        Phone: +1 408-400-1900
        E-mail: support@ipinfusion.com
        Web: http://www.ipinfusion.com/";

    description
        "Telnet configurations";


    revision "2017-05-15" {
        description "Added autopopulate custom tag.";
    }

    revision "2017-01-19" {
        description "Changed vrf name as normal attr as it is optional parameter.";
    }

    revision "2016-12-27" {
        description "Added snmp oid and documentation tag.";
    }

    revision "2016-10-28" {
        description "Initial version of TELNET datamodel.";
    }


    grouping  telnet-grouping {
    container telnet {
        description
            "telnet related commands";
        leaf vrfName  {
            type  cml_data_types:CML_STRING_T {
                length "0..255";
            }
        } // END of vrfName definition.

        leaf featureTelnet  {
            type  cml_data_types:CML_BOOL_T;
            description "feature telnet";
        } // END of featureTelnet definition.

        leaf port  {
            if-feature feature_list:HAVE_TELNET_SERVER;
            type  cml_data_types:CML_INT32_T {
                 range "1024..65535";
            }
            description "Telnet server port";
        } // END of port definition.

        leaf debugtelnet  {
            if-feature feature_list:HAVE_TELNET_SERVER;
            type  cml_data_types:CML_BOOL_T;
            description "debug telnet server";
        } // END of debugtelnet definition.

        leaf debugtelnetConf  {
            if-feature feature_list:HAVE_TELNET_SERVER;
            type  cml_data_types:CML_BOOL_T;
            description "debug telnet server";
        } // END of debugtelnetConf definition.

    } // END of telnet-container definition.
    } // END of telnet-container definition.


}
