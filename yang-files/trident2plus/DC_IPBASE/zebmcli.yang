/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebmcli.yang
*
*/



module zebmcli {
    namespace "http://ipinfusion.com/ns/zebmcli";

    prefix zebmcli;

    import cml_data_types {
        prefix cml_data_types;
    }
    organization
        "IP Infusion Inc.";

    contact
        "3965 Freedom Circle, Suite 200
        Santa Clara, CA 95054 +1 408-400-1900
        E-mail: support@ipinfusion.com
        Web: http://www.ipinfusion.com/";


    revision "2015-10-15" {
        description "initial version: revisied on 2015-10-15.";}

    rpc rollback-transaction {

        input {
            leaf savepointName {
                type cml_data_types:CML_STRING_T;
                mandatory true;
            }
        }
    }

    rpc create-savepoint {

        input {
            leaf savepointName {
                type cml_data_types:CML_STRING_T;
                mandatory true;
            }
        }
    }

    rpc force-unlock {

        input {
            leaf target {
                type enumeration {
                    enum running {}
                }
                mandatory true;
            }
            leaf after {
                type cml_data_types:CML_UINT32_T {
                    range "0..600";
                }
            }
        }
    }

    rpc delete-savepoint {

        input {
            leaf savepointName {
                type cml_data_types:CML_STRING_T;
                mandatory true;
            }
        }
    }

    rpc set-transaction-limit {

        input {
            leaf transaction-limit {
                type cml_data_types:CML_UINT32_T {
                    range "10..50000";
                }
mandatory true;
            }
        }
    }

    rpc show-savepoint {
        output {
            leaf-list savepoint {
                type string;
            }
        }
    }

    notification warning-notification {
        leaf warningMsg {
            type string;
            mandatory true;
        }
    }

    rpc show-transaction-limit {
        output {
            leaf transaction-limit {
                type string;
            }
        }
    }

    rpc config-sync {
        input {
            leaf status {
                type enumeration {
                    enum disable;
                    enum enable;
                }
            }
        }
    }

    rpc sync-running-config {}

}
