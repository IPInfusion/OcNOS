/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-zebos-lacp.yang
*
*/

submodule ipi-zebos-lacp {

    belongs-to  ipi-zebos { prefix ipi-zebos; }

    import cml-data-types {
        prefix cml-data-types;
    }

    organization
        "IP Infusion Inc.";

    contact
        "Address: 3965 Freedom Circle, Suite 200, Santa Clara, CA 95054
        Phone: +1 408-400-1900
        E-mail: support@ipinfusion.com
        Web: http://www.ipinfusion.com/";

    description
        "Layer-2 lacp  configurations";


    revision "2018-06-21" {
        description " Initial Version.";
        reference "";
    }


    grouping  nsmlacpInterface-grouping {
    description
        "NSM LACP interface related operations";
    container nsmlacpInterface {
        presence "yes";
        description
            "NSM LACP interface related operations";
        leaf channelGroup  {
            type  cml-data-types:CML_UINT16_T {
                 range "1..16383";
            }
            mandatory true;
            description "";
        } // END of channelGroup definition.

        leaf modeOperation  {
            type  cml-data-types:CML_LACP_MODE_T;
            mandatory true;
            description "";
        } // END of modeOperation definition.

    } // END of nsmlacpInterface-container definition.
    } // END of nsmlacpInterface-container definition.

    grouping  nsmportInterface-grouping {
    description
        "NSM LACP interface related operations";
    container nsmportInterface {
        presence "yes";
        description
            "NSM LACP interface related operations";
        leaf staticChannelGroup  {
            type  cml-data-types:CML_UINT16_T {
                 range "1..16383";
            }
            mandatory true;
            description "";
        } // END of staticChannelGroup definition.

    } // END of nsmportInterface-container definition.
    } // END of nsmportInterface-container definition.

    grouping  nsmPoInterfaceBandwidth-grouping {
    description
        "NSM LACP interface related operations";
    container nsmPoInterfaceBandwidth {
        presence "yes";
        description
            "NSM LACP interface related operations";
        leaf minBandwidth  {
            type  cml-data-types:CML_STRING_T;
            mandatory true;
            description "";
        } // END of minBandwidth definition.

    } // END of nsmPoInterfaceBandwidth-container definition.
    } // END of nsmPoInterfaceBandwidth-container definition.


}
