/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : oambfd.yang
*
*/

submodule oambfd {

    belongs-to  ZebOS { prefix ZebOS; }

    import cml_data_types {
        prefix cml_data_types;
    }

    import feature_list {
        prefix feature_list;
    }

    include interface;
    organization
        "IP Infusion Inc.";

    contact
        "Address: 3965 Freedom Circle, Suite 200, Santa Clara, CA 95054
        Phone: +1 408-400-1900
        E-mail: support@ipinfusion.com
        Web: http://www.ipinfusion.com/";


    revision "2017-06-30" {
        description "Datamodel remodeling for bfd multihop and auth commands.";
    }

    revision "2017-06-02" {
        description "Datamodel implementation of bfd-firmware command.";
    }

    revision "2017-05-15" {
        description "Corrected BFD interface Configurations.";
    }

    revision "2017-05-11" {
        description "Adding bfd interval command in global mode.";
    }

    revision "2017-05-04" {
        description "Removed bfd process id, and make objectlist as container.";
    }

    revision "2016-12-26" {
        description "Adding desc and ignore_doc changes.";
    }

    revision "2016-10-10" {
        description "Adding the new OAM-LPS DM.";
    }



    grouping bfdSession-grouping {
        list bfdSession {
            key "bfdSessionIndex";
            config false;
            description
                "bfd Session table for runtime attrs";
            leaf bfdSessionIndex  {
                type  cml_data_types:CML_UINT32_T;
            } // END of bfdSessionIndex definition.

            leaf bfdSessRemoteDisc  {
                type  cml_data_types:CML_UINT32_T;
            } // END of bfdSessRemoteDisc definition.

            leaf bfdLlType  {
                type  cml_data_types:CML_OAMBFD_SESS_LOWER_LAYER_T;
            } // END of bfdLlType definition.

            leaf bfdSessionType  {
                type  cml_data_types:CML_OAMBFD_SESSION_TYPE_T;
            } // END of bfdSessionType definition.

            leaf bfdSessionState  {
                type  cml_data_types:CML_OAMBFD_SESSION_STATE_T;
            } // END of bfdSessionState definition.

            leaf bfdSessionUptime  {
                type  cml_data_types:CML_STRING_T {
                    length "0..255";
                }
            } // END of bfdSessionUptime definition.

            leaf bfdRemoteAddr  {
                type  cml_data_types:CML_STRING_T {
                    length "0..255";
                }
            } // END of bfdRemoteAddr definition.

            leaf bfdSessIfIdx  {
                type  cml_data_types:CML_UINT32_T;
            } // END of bfdSessIfIdx definition.

            leaf bfdSessVersion  {
                type  cml_data_types:CML_UINT32_T;
            } // END of bfdSessVersion definition.

            leaf bfdSessLocDisc  {
                type  cml_data_types:CML_UINT32_T;
            } // END of bfdSessLocDisc definition.

            leaf bfdSessLocAddr  {
                type  cml_data_types:CML_STRING_T {
                    length "0..255";
                }
            } // END of bfdSessLocAddr definition.

            leaf bfdRemotePort  {
                type  cml_data_types:CML_UINT32_T;
            } // END of bfdRemotePort definition.

            leaf bfdLocalPort  {
                type  cml_data_types:CML_UINT32_T;
            } // END of bfdLocalPort definition.

            leaf bfdLocalEchoPort  {
                type  cml_data_types:CML_UINT32_T;
            } // END of bfdLocalEchoPort definition.

            leaf bfdMplsLspType  {
                type  cml_data_types:CML_UINT32_T;
            } // END of bfdMplsLspType definition.

            leaf bfdMplsTnlName  {
                type  cml_data_types:CML_STRING_T {
                    length "0..255";
                }
            } // END of bfdMplsTnlName definition.

            leaf bfdMplsFecAddr  {
                type  cml_data_types:CML_STRING_T {
                    length "0..255";
                }
            } // END of bfdMplsFecAddr definition.

            leaf bfdMplsLspPingItvl  {
                type  cml_data_types:CML_UINT32_T;
            } // END of bfdMplsLspPingItvl definition.

            leaf bfdMplsFtnIndx  {
                type  cml_data_types:CML_UINT32_T;
            } // END of bfdMplsFtnIndx definition.

            leaf bfdMplsMinTx  {
                type  cml_data_types:CML_UINT32_T;
            } // END of bfdMplsMinTx definition.

            leaf bfdMplsMinRx  {
                type  cml_data_types:CML_UINT32_T;
            } // END of bfdMplsMinRx definition.

            leaf bfdMplsMult  {
                type  cml_data_types:CML_UINT32_T;
            } // END of bfdMplsMult definition.

            leaf bfdMplsTnlLabel  {
                type  cml_data_types:CML_UINT32_T;
            } // END of bfdMplsTnlLabel definition.

            leaf bfdVccvVcId  {
                type  cml_data_types:CML_UINT32_T;
            } // END of bfdVccvVcId definition.

            leaf bfdVccvInVcLabel  {
                type  cml_data_types:CML_UINT32_T;
            } // END of bfdVccvInVcLabel definition.

            leaf bfdVccvOutVcLabel  {
                type  cml_data_types:CML_UINT32_T;
            } // END of bfdVccvOutVcLabel definition.

            leaf bfdVccvCcType  {
                type  cml_data_types:CML_UINT32_T;
            } // END of bfdVccvCcType definition.

            leaf bfdVccvCvType  {
                type  cml_data_types:CML_UINT32_T;
            } // END of bfdVccvCvType definition.

            leaf bfdVccvAcIx  {
                type  cml_data_types:CML_UINT32_T;
            } // END of bfdVccvAcIx definition.

            leaf bfdVccvTnlLabel  {
                type  cml_data_types:CML_UINT32_T;
            } // END of bfdVccvTnlLabel definition.

            leaf bfdVccvPeerAddr  {
                type  cml_data_types:CML_UINT32_T;
            } // END of bfdVccvPeerAddr definition.

            leaf bfdMplstpMegName  {
                type  cml_data_types:CML_STRING_T {
                    length "0..255";
                }
            } // END of bfdMplstpMegName definition.

            leaf bfdMplstpMeName  {
                type  cml_data_types:CML_STRING_T {
                    length "0..255";
                }
            } // END of bfdMplstpMeName definition.

            leaf bfdMplstpPathType  {
                type  cml_data_types:CML_UINT8_T;
            } // END of bfdMplstpPathType definition.

            leaf bfdSessOptionFlag  {
                type  cml_data_types:CML_OAMBFD_SESSION_FLAGS_T;
            } // END of bfdSessOptionFlag definition.

            leaf bfdSessPerfDiag  {
                type  cml_data_types:CML_OAMBFD_PERFORM_DIAG_T;
            } // END of bfdSessPerfDiag definition.

            leaf bfdSessMinTx  {
                type  cml_data_types:CML_UINT32_T;
            } // END of bfdSessMinTx definition.

            leaf bfdSessMinRx  {
                type  cml_data_types:CML_UINT32_T;
            } // END of bfdSessMinRx definition.

            leaf bfdSessMultplier  {
                type  cml_data_types:CML_UINT32_T;
            } // END of bfdSessMultplier definition.

            leaf bfdSessNegTx  {
                type  cml_data_types:CML_UINT32_T;
            } // END of bfdSessNegTx definition.

            leaf bfdSessNegRx  {
                type  cml_data_types:CML_UINT32_T;
            } // END of bfdSessNegRx definition.

            leaf bfdSessNegMultiplier  {
                type  cml_data_types:CML_UINT32_T;
            } // END of bfdSessNegMultiplier definition.

            leaf bfdSessEchoTx  {
                type  cml_data_types:CML_UINT32_T;
            } // END of bfdSessEchoTx definition.

            leaf bfdSessEchoRx  {
                type  cml_data_types:CML_UINT32_T;
            } // END of bfdSessEchoRx definition.

            leaf bfdSessEchoIntvl  {
                type  cml_data_types:CML_UINT32_T;
            } // END of bfdSessEchoIntvl definition.

            leaf bfdSessStorTye  {
                type  cml_data_types:CML_UINT32_T;
            } // END of bfdSessStorTye definition.

            leaf bfdSessDownTime  {
                type  cml_data_types:CML_STRING_T {
                    length "0..255";
                }
            } // END of bfdSessDownTime definition.

            leaf bfdSessDisconTime  {
                type  cml_data_types:CML_STRING_T {
                    length "0..255";
                }
            } // END of bfdSessDisconTime definition.

            leaf bfdSessAuthKeyId  {
                type  cml_data_types:CML_UINT32_T;
            } // END of bfdSessAuthKeyId definition.

            leaf bfdSessPktIn  {
                type  cml_data_types:CML_STRING_T {
                    length "0..255";
                }
            } // END of bfdSessPktIn definition.

            leaf bfdSessPktOut  {
                type  cml_data_types:CML_STRING_T {
                    length "0..255";
                }
            } // END of bfdSessPktOut definition.

            leaf bfdSessEchoOut  {
                type  cml_data_types:CML_STRING_T {
                    length "0..255";
                }
            } // END of bfdSessEchoOut definition.

            leaf bfdSessIpv6EchoOut  {
                type  cml_data_types:CML_STRING_T {
                    length "0..255";
                }
            } // END of bfdSessIpv6EchoOut definition.

            leaf bfdSessIpv6PktOut  {
                type  cml_data_types:CML_STRING_T {
                    length "0..255";
                }
            } // END of bfdSessIpv6PktOut definition.

            leaf bfdSessIpv6PktIn  {
                type  cml_data_types:CML_STRING_T {
                    length "0..255";
                }
            } // END of bfdSessIpv6PktIn definition.

            leaf bfdSessUpCount  {
                type  cml_data_types:CML_UINT32_T;
            } // END of bfdSessUpCount definition.

            leaf bfdSessUpTime  {
                type  cml_data_types:CML_STRING_T {
                    length "0..255";
                }
            } // END of bfdSessUpTime definition.

            leaf bfdSessHoldCntr  {
                type  cml_data_types:CML_UINT32_T;
            } // END of bfdSessHoldCntr definition.

            leaf bfdSessHoldDown  {
                type  cml_data_types:CML_UINT32_T;
            } // END of bfdSessHoldDown definition.

            leaf bfdSessFwdHelloCntr  {
                type  cml_data_types:CML_UINT32_T;
            } // END of bfdSessFwdHelloCntr definition.

            leaf bfdSessPktVersion  {
                type  cml_data_types:CML_UINT32_T;
            } // END of bfdSessPktVersion definition.

            leaf bfdSessPktDiag  {
                type  cml_data_types:CML_UINT32_T;
            } // END of bfdSessPktDiag definition.

            leaf bfdSessPktState  {
                type  cml_data_types:CML_UINT32_T;
            } // END of bfdSessPktState definition.

            leaf bfdSessPktDemandEn  {
                type  cml_data_types:CML_UINT32_T;
            } // END of bfdSessPktDemandEn definition.

            leaf bfdSessPktPollSeq  {
                type  cml_data_types:CML_UINT32_T;
            } // END of bfdSessPktPollSeq definition.

            leaf bfdSessPktFlagState  {
                type  cml_data_types:CML_STRING_T {
                    length "0..255";
                }
            } // END of bfdSessPktFlagState definition.

            leaf bfdSessPktMult  {
                type  cml_data_types:CML_UINT32_T;
            } // END of bfdSessPktMult definition.

            leaf bfdSessPktLength  {
                type  cml_data_types:CML_UINT32_T;
            } // END of bfdSessPktLength definition.

            leaf bfdSessPktMyDisc  {
                type  cml_data_types:CML_UINT32_T;
            } // END of bfdSessPktMyDisc definition.

            leaf bfdSessPktUrDisc  {
                type  cml_data_types:CML_UINT32_T;
            } // END of bfdSessPktUrDisc definition.

            leaf bfdSessPktMinTx  {
                type  cml_data_types:CML_UINT32_T;
            } // END of bfdSessPktMinTx definition.

            leaf bfdSessPktMinRx  {
                type  cml_data_types:CML_UINT32_T;
            } // END of bfdSessPktMinRx definition.

            leaf bfdSessPktMinEchoIntvl  {
                type  cml_data_types:CML_UINT32_T;
            } // END of bfdSessPktMinEchoIntvl definition.


            list bfdSessionClientInfo {
                key "bfdSessProtoClientId";
                config false;
                description
                    "BFD session client Info";
                leaf bfdSessProtoClientId  {
                    type  cml_data_types:CML_UINT32_T;
                } // END of bfdSessProtoClientId definition.

                leaf bfdSessClientFlag  {
                    type  cml_data_types:CML_STRING_T {
                        length "0..255";
                    }
                } // END of bfdSessClientFlag definition.

            } // End of bfdSessionClientInfo-list
        } // End of bfdSession-list
    } // END of bfdSession-grouping definition.


    grouping bfdInterface-grouping {
        list bfdInterface {
            key "ifName";
            description
                "BFD interface related operations";
            leaf ifName  {
                type  cml_data_types:CML_STRING_T {
                    length "0..255";
                }
            } // END of ifName definition.

            leaf isBfdDisable  {
                type  cml_data_types:CML_BFD_SESSION_STATE_T;
                description "bfd disable";
            } // END of isBfdDisable definition.

            leaf bfdIfTransmitIntvl  {
                type  cml_data_types:CML_UINT32_T {
                     range "3..999";
                }
            } // END of bfdIfTransmitIntvl definition.

            leaf bfdIfRecieveIntvl  {
                type  cml_data_types:CML_UINT32_T {
                     range "3..999";
                }
            } // END of bfdIfRecieveIntvl definition.

            leaf bfdIfHelloMultiplier  {
                type  cml_data_types:CML_UINT32_T {
                     range "3..50";
                }
                default "3";
                description "bfd interval";
            } // END of bfdIfHelloMultiplier definition.

            leaf bfdEchoInterval  {
                type  cml_data_types:CML_UINT32_T {
                     range "1..4294967";
                }
                description "bfd echo interval";
            } // END of bfdEchoInterval definition.

            leaf bfdIfSrcAddr  {
                type  cml_data_types:CML_STRING_T {
                    length "0..255";
                }
                description "echo ipv4 source";
            } // END of bfdIfSrcAddr definition.

            leaf bfdIfAuthType  {
                type  cml_data_types:CML_BFD_MULTIHOP_AUTH_TYPE_T;
            } // END of bfdIfAuthType definition.

            leaf bfdIfKeyChain  {
                type  cml_data_types:CML_LINE_T;
                description "bfd multihop-peer A.B.C.D|X:X::X:X";
            } // END of bfdIfKeyChain definition.

            leaf bfdIfKeyId  {
                type  cml_data_types:CML_UINT32_T {
                     range "0..255";
                }
            } // END of bfdIfKeyId definition.

            leaf bfdIfKeyStr  {
                type  cml_data_types:CML_LINE_T;
                description "bfd multihop-peer";
            } // END of bfdIfKeyStr definition.

            leaf bfdIfIndex  {
                type  cml_data_types:CML_UINT32_T;
                config false;
            } // END of bfdIfIndex definition.

            leaf bfdIfState  {
                type  cml_data_types:CML_STRING_T {
                    length "0..255";
                }
                config false;
            } // END of bfdIfState definition.

            container bfdSessionSingleHopIpv4 {
                description
                    "bfd sinfgle hop session";

                list bfdIpv4ShUserIntfSessSrc {
                    key "bfdIpv4ShUserSrcAddr";
                    description
                        "BFD ipv4 user intf src related configs";
                    leaf bfdIpv4ShUserSrcAddr  {
                        type  cml_data_types:CML_IPV4_ADDR_T;
                    } // END of bfdIpv4ShUserSrcAddr definition.


                    list bfdIpv4ShUserIntfSessDest {
                        key "bfdIpv4ShUserDestAddr";
                        description
                            "BFD ipv4 user intf dest related configs";
                        leaf bfdIpv4ShUserDestAddr  {
                            type  cml_data_types:CML_IPV4_ADDR_T;
                        } // END of bfdIpv4ShUserDestAddr definition.

                        uses bfdSessionAttr;
                    } // End of bfdIpv4ShUserIntfSessDest-list
                } // End of bfdIpv4ShUserIntfSessSrc-list
            } // END of bfdSessionSingleHopIpv4-container definition.
            container bfdSessionMultiHopIpv4 {
                description
                    "bfd single hop session";

                list bfdIpv4MhUserIntfSessSrc {
                    key "bfdIpv4MhUserSrcAddr";
                    description
                        "BFD ipv4 user intf src related configs";
                    leaf bfdIpv4MhUserSrcAddr  {
                        type  cml_data_types:CML_IPV4_ADDR_T;
                    } // END of bfdIpv4MhUserSrcAddr definition.


                    list bfdIpv4MhUserIntfSessDest {
                        key "bfdIpv4MhUserDestAddr";
                        description
                            "BFD ipv4 user intf dest related configs";
                        leaf bfdIpv4MhUserDestAddr  {
                            type  cml_data_types:CML_IPV4_ADDR_T;
                        } // END of bfdIpv4MhUserDestAddr definition.

                        leaf multihopIpv4  {
                            type  cml_data_types:CML_BFD_MULTI_HOP_TYPE_T;
                        } // END of multihopIpv4 definition.

                        uses bfdSessionAttr;
                    } // End of bfdIpv4MhUserIntfSessDest-list
                } // End of bfdIpv4MhUserIntfSessSrc-list
            } // END of bfdSessionMultiHopIpv4-container definition.
            container bfdSessionSingleHopIpv6 {
                description
                    "bfd single hop session";

                list bfdIpv6ShUserIntfSessSrc {
                    key "bfdIpv6ShUserSrcAddr";
                    description
                        "BFD ipv4 user intf src related configs";
                    leaf bfdIpv6ShUserSrcAddr  {
                        type  cml_data_types:CML_IPV6_ADDR_T;
                    } // END of bfdIpv6ShUserSrcAddr definition.


                    list bfdIpv6ShUserIntfSessDest {
                        key "bfdIpv6ShUserDestAddr";
                        description
                            "BFD ipv6 user intf dest related configs";
                        leaf bfdIpv6ShUserDestAddr  {
                            type  cml_data_types:CML_IPV6_ADDR_T;
                        } // END of bfdIpv6ShUserDestAddr definition.

                        uses bfdSessionAttr;
                    } // End of bfdIpv6ShUserIntfSessDest-list
                } // End of bfdIpv6ShUserIntfSessSrc-list
            } // END of bfdSessionSingleHopIpv6-container definition.
            container bfdSessionMultiHopIpv6 {
                description
                    "bfd single hop session";

                list bfdIpv6MhUserIntfSessSrc {
                    key "bfdIpv6MhUserSrcAddr";
                    description
                        "BFD ipv6 user intf src related configs";
                    leaf bfdIpv6MhUserSrcAddr  {
                        type  cml_data_types:CML_IPV6_ADDR_T;
                    } // END of bfdIpv6MhUserSrcAddr definition.


                    list bfdIpv6MhUserIntfSessDest {
                        key "bfdIpv6MhUserDestAddr";
                        description
                            "BFD ipv6 user intf dest related configs";
                        leaf bfdIpv6MhUserDestAddr  {
                            type  cml_data_types:CML_IPV6_ADDR_T;
                        } // END of bfdIpv6MhUserDestAddr definition.

                        leaf multihopIpv6  {
                            type  cml_data_types:CML_BFD_MULTI_HOP_TYPE_T;
                        } // END of multihopIpv6 definition.

                        uses bfdSessionAttr;
                    } // End of bfdIpv6MhUserIntfSessDest-list
                } // End of bfdIpv6MhUserIntfSessSrc-list
            } // END of bfdSessionMultiHopIpv6-container definition.
        } // End of bfdInterface-list
    } // END of bfdInterface-grouping definition.


    grouping confModeDebug-grouping {
        list confModeDebug {
            key "vrId";
            description
                "config mode debug commands";
            leaf vrId  {
                type  cml_data_types:CML_INT32_T;
            } // END of vrId definition.

            leaf isConfDebugAll  {
                type  cml_data_types:CML_BOOL_T;
            } // END of isConfDebugAll definition.

            leaf confModePackets  {
                type  cml_data_types:CML_BOOL_T;
            } // END of confModePackets definition.

            leaf confModeEvents  {
                type  cml_data_types:CML_BOOL_T;
            } // END of confModeEvents definition.

            leaf confModeIpcErr  {
                type  cml_data_types:CML_BOOL_T;
            } // END of confModeIpcErr definition.

            leaf confModeIpcEvent  {
                type  cml_data_types:CML_BOOL_T;
            } // END of confModeIpcEvent definition.

            leaf confModeSession  {
                type  cml_data_types:CML_BOOL_T;
            } // END of confModeSession definition.

            leaf confModeNsm  {
                type  cml_data_types:CML_BOOL_T;
            } // END of confModeNsm definition.

        } // End of confModeDebug-list
    } // END of confModeDebug-grouping definition.


    grouping execModeDebug-grouping {
        list execModeDebug {
            key "vrId";
            description
                "exec mode debug commands";
            leaf vrId  {
                type  cml_data_types:CML_INT32_T;
            } // END of vrId definition.

            leaf isExecDebugAll  {
                type  cml_data_types:CML_BOOL_T;
            } // END of isExecDebugAll definition.

            leaf execModePackets  {
                type  cml_data_types:CML_BOOL_T;
            } // END of execModePackets definition.

            leaf execModeEvents  {
                type  cml_data_types:CML_BOOL_T;
            } // END of execModeEvents definition.

            leaf execModeIpcErr  {
                type  cml_data_types:CML_BOOL_T;
            } // END of execModeIpcErr definition.

            leaf execModeIpcEvent  {
                type  cml_data_types:CML_BOOL_T;
            } // END of execModeIpcEvent definition.

            leaf execModeSession  {
                type  cml_data_types:CML_BOOL_T;
            } // END of execModeSession definition.

            leaf execModeNsm  {
                type  cml_data_types:CML_BOOL_T;
            } // END of execModeNsm definition.

        } // End of execModeDebug-list
    } // END of execModeDebug-grouping definition.
    grouping bfdSessionAttr {
        description
            "bfdSessionAttr";
        leaf demandMode  {
            type  cml_data_types:CML_BOOL_T;
        } // END of demandMode definition.

        leaf nonPersistant  {
            type  cml_data_types:CML_BOOL_T;
        } // END of nonPersistant definition.

        leaf adminDown  {
            type  cml_data_types:CML_BOOL_T;
            description "bfd session ";
        } // END of adminDown definition.

    } // END of bfdSessionAttr definition.

    grouping  bfd-grouping {
    container bfd {
        description
            "BFD basic configurations";
        leaf enGtsmProtection  {
            if-feature feature_list:HAVE_BFD_MONO;
            type  cml_data_types:CML_BFD_SESSION_STATE_T;
            description "bfd gtsm";
        } // END of enGtsmProtection definition.

        leaf bfdNotfEn  {
            if-feature feature_list:HAVE_BFD_MONO;
            type  cml_data_types:CML_BFD_SESSION_STATE_T;
            description "bfd notification ";
        } // END of bfdNotfEn definition.

        leaf isEchoSet  {
            if-feature feature_list:HAVE_BFD_MONO;
            type  cml_data_types:CML_BOOL_T;
            description "bfd echo";
        } // END of isEchoSet definition.

        leaf gtsmTtl  {
            if-feature feature_list:HAVE_BFD_MONO;
            type  cml_data_types:CML_UINT8_T {
                 range "1..255";
            }
            default "255";
            description "bfd gtsm ttl";
        } // END of gtsmTtl definition.

        leaf bfdGbTransmitIntvl  {
            if-feature feature_list:HAVE_BFD_MONO;
            type  cml_data_types:CML_UINT32_T {
                 range "3..999";
            }
        } // END of bfdGbTransmitIntvl definition.

        leaf bfdGbRecieveIntvl  {
            if-feature feature_list:HAVE_BFD_MONO;
            type  cml_data_types:CML_UINT32_T {
                 range "3..999";
            }
        } // END of bfdGbRecieveIntvl definition.

        leaf bfdGbHelloMultiplier  {
            if-feature feature_list:HAVE_BFD_MONO;
            type  cml_data_types:CML_UINT32_T {
                 range "3..50";
            }
            default "3";
            description "bfd interval ";
        } // END of bfdGbHelloMultiplier definition.

        leaf bfdStartTime  {
            if-feature feature_list:HAVE_BFD_MONO;
            type  cml_data_types:CML_STRING_T {
                length "0..255";
            }
            config false;
        } // END of bfdStartTime definition.

        leaf bfdSessionCount  {
            if-feature feature_list:HAVE_BFD_MONO;
            type  cml_data_types:CML_UINT32_T;
            config false;
        } // END of bfdSessionCount definition.

        leaf bfdAdminState  {
            if-feature feature_list:HAVE_BFD_MONO;
            type  cml_data_types:CML_OAMBFD_ADMIN_STATE_T;
            config false;
        } // END of bfdAdminState definition.

        leaf bfdImageType  {
            if-feature feature_list:HAVE_BFD_MONO;
            type  cml_data_types:CML_OAMBFD_IMAGE_TYPE_T;
            config false;
        } // END of bfdImageType definition.

        leaf bfdLocalDisc  {
            if-feature feature_list:HAVE_BFD_MONO;
            type  cml_data_types:CML_UINT32_T;
            config false;
        } // END of bfdLocalDisc definition.

        leaf slowTimerIntvl  {
            if-feature feature_list:HAVE_BFD_MONO;
            type  cml_data_types:CML_UINT32_T {
                 range "1000..30000";
            }
            default "2000";
            description "bfd slow-timer";
        } // END of slowTimerIntvl definition.

        leaf bfdFirmwareSess  {
            if-feature feature_list:HAVE_BFD_HW_OFFLOAD;
            if-feature feature_list:HAVE_BROADCOM;
            type  cml_data_types:CML_OAM_BFD_FW_T;
        } // END of bfdFirmwareSess definition.


        list bfdMultihopKeyChain {
            if-feature feature_list:HAVE_BFD_MONO;
            key "bfdMultihopAddr";
            description
                "BFD multihop peer configs";
            leaf bfdMultihopAddr  {
                type  cml_data_types:CML_STRING_T {
                    length "0..255";
                }
            } // END of bfdMultihopAddr definition.

            leaf bfdAuthType  {
                type  cml_data_types:CML_HW_BFD_MULTIHOP_AUTH_TYPE_T;
            } // END of bfdAuthType definition.

            leaf bfdKeyChain  {
                type  cml_data_types:CML_LINE_T;
            } // END of bfdKeyChain definition.

            leaf bfdMultihopKeyId  {
                type  cml_data_types:CML_UINT32_T {
                     range "0..255";
                }
            } // END of bfdMultihopKeyId definition.

            leaf bfdKeyStr  {
                type  cml_data_types:CML_LINE_T;
            } // END of bfdKeyStr definition.

            leaf bfdTransmitIntvl  {
                type  cml_data_types:CML_UINT32_T {
                     range "3..999";
                }
            } // END of bfdTransmitIntvl definition.

            leaf bfdRecieveIntvl  {
                type  cml_data_types:CML_UINT32_T {
                     range "3..999";
                }
            } // END of bfdRecieveIntvl definition.

            leaf bfdHelloMultiplier  {
                type  cml_data_types:CML_UINT32_T {
                     range "3..50";
                }
                default "3";
                description "bfd interval ";
            } // END of bfdHelloMultiplier definition.

        } // End of bfdMultihopKeyChain-list
    } // END of bfd-container definition.
    } // END of bfd-container definition.

    grouping  oamMpls-grouping {
    container oamMpls {
        description
            "Oam mpls configs";
        leaf mplsPingReq  {
            if-feature feature_list:HAVE_MPLS_OAM;
            type  cml_data_types:CML_BOOL_T;
            description "mpls ping request dsmap tlv";
        } // END of mplsPingReq definition.

        leaf mplsPingReply  {
            if-feature feature_list:HAVE_MPLS_OAM;
            type  cml_data_types:CML_BOOL_T;
            description "mpls ping reply tlv";
        } // END of mplsPingReply definition.

    } // END of oamMpls-container definition.
    } // END of oamMpls-container definition.


}
