/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ssh.yang
*
*/

submodule ssh {

    belongs-to  ZebOS { prefix ZebOS; }

    import cml_data_types {
        prefix cml_data_types;
    }

    import feature_list {
        prefix feature_list;
    }

    include vrf;
    organization
        "IP Infusion Inc.";

    contact
        "Address: 3965 Freedom Circle, Suite 200, Santa Clara, CA 95054
        Phone: +1 408-400-1900
        E-mail: support@ipinfusion.com
        Web: http://www.ipinfusion.com/";

    description
        "ssh configurations";


    revision "2017-05-30" {
        description "clear ssh hosts.";
    }

    revision "2017-05-19" {
        description "Added missing commands and rsa/dsa keys are made objectAction.";
    }

    revision "2017-05-15" {
        description "Added autopopulate custom tag.";
    }

    revision "2017-01-19" {
        description "Changed vrf name as normal attr as it is optional parameter.";
    }

    revision "2016-12-27" {
        description "Added snmp oid and documentation tag.";
    }

    revision "2016-10-28" {
        description "Initial version of SSH datamodel.";
    }


    grouping  ssh-grouping {
    container ssh {
        description
            "ssh related operations";
        leaf vrfName  {
            type  cml_data_types:CML_STRING_T {
                length "0..255";
            }
        } // END of vrfName definition.

        leaf featuressh  {
            if-feature feature_list:HAVE_SSH_SERVER;
            type  cml_data_types:CML_BOOL_T;
            description "feature ssh";
        } // END of featuressh definition.

        leaf serverPort  {
            if-feature feature_list:HAVE_SSH_SERVER;
            type  cml_data_types:CML_INT32_T {
                 range "1024..65535";
            }
            description "SSH server port";
        } // END of serverPort definition.

        leaf loginAttempts  {
            if-feature feature_list:HAVE_SSH_SERVER;
            type  cml_data_types:CML_INT32_T;
            default "3";
            description "ssh login-attempts";
        } // END of loginAttempts definition.

        leaf debugssh  {
            if-feature feature_list:HAVE_SSH_SERVER;
            type  cml_data_types:CML_BOOL_T;
            description "debug ssh server";
        } // END of debugssh definition.

        leaf debugsshConf  {
            if-feature feature_list:HAVE_SSH_SERVER;
            type  cml_data_types:CML_BOOL_T;
            description "debug ssh server";
        } // END of debugsshConf definition.

        container sessionEncryption {
            description
                "Algorithm to encrypt ssh session";
            leaf vrfName  {
                type  cml_data_types:CML_STRING_T {
                    length "0..255";
                }
                default "default";
            } // END of vrfName definition.

            leaf aes128-ctr  {
                if-feature feature_list:HAVE_SSH_SERVER;
                type  cml_data_types:CML_BOOL_T;
                description "ssh server cipher encryption algorithm configurations.";
            } // END of aes128-ctr definition.

            leaf aes192-ctr  {
                if-feature feature_list:HAVE_SSH_SERVER;
                type  cml_data_types:CML_BOOL_T;
                description "ssh server cipher encryption algorithm configurations.";
            } // END of aes192-ctr definition.

            leaf aes256-ctr  {
                if-feature feature_list:HAVE_SSH_SERVER;
                type  cml_data_types:CML_BOOL_T;
                description "ssh server cipher encryption algorithm configurations.";
            } // END of aes256-ctr definition.

            leaf aes128-cbc  {
                if-feature feature_list:HAVE_SSH_SERVER;
                type  cml_data_types:CML_BOOL_T;
                description "ssh server cipher encryption algorithm configurations.";
            } // END of aes128-cbc definition.

            leaf aes192-cbc  {
                if-feature feature_list:HAVE_SSH_SERVER;
                type  cml_data_types:CML_BOOL_T;
                description "ssh server cipher encryption algorithm configurations.";
            } // END of aes192-cbc definition.

            leaf aes256-cbc  {
                if-feature feature_list:HAVE_SSH_SERVER;
                type  cml_data_types:CML_BOOL_T;
                description "ssh server cipher encryption algorithm configurations.";
            } // END of aes256-cbc definition.

            leaf des-cbc  {
                if-feature feature_list:HAVE_SSH_SERVER;
                type  cml_data_types:CML_BOOL_T;
                description "ssh server cipher encryption algorithm configurations.";
            } // END of des-cbc definition.

        } // END of sessionEncryption-container definition.
    } // END of ssh-container definition.
    } // END of ssh-container definition.


}
