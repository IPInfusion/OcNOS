/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-rtadv.yang
*
*/

submodule zebos-rtadv {

    belongs-to  zebos { prefix zebos; }

    import cml_data_types {
        prefix cml_data_types;
    }

    import feature_list {
        prefix feature_list;
    }

    organization
        "IP Infusion Inc.";

    contact
        "Address: 3965 Freedom Circle, Suite 200, Santa Clara, CA 95054
        Phone: +1 408-400-1900
        E-mail: support@ipinfusion.com
        Web: http://www.ipinfusion.com/";

    description
        "Router advertisement parameter.";


    revision "2018-01-10" {
        description " added support for Router advertisement command.";
        reference "";
    }



    grouping rtadvInterfaceNdPrefix-grouping {
    description
        "ipv6 nd prefix operations";
        list rtadvInterfaceNdPrefix {
            if-feature feature_list:HAVE_RTADV;
            key "ipv6AddrPrefix";
            description
                "ipv6 nd prefix operations";
            leaf ipv6AddrPrefix  {
                type  cml_data_types:CML_IPV6_PREFIX_T;
                description "";
            } // END of ipv6AddrPrefix definition.

            leaf vlifetimePrefix  {
                type  cml_data_types:CML_UINT32_T {
                     range "0..4294967295";
                }
                default "2592000";
                description "";
            } // END of vlifetimePrefix definition.

            leaf plifetimePrefix  {
                type  cml_data_types:CML_UINT32_T {
                     range "0..4294967295";
                }
                default "604800";
                description "";
            } // END of plifetimePrefix definition.

            leaf offlinkPrefix  {
                type  cml_data_types:CML_BOOL_T;
                description "";
            } // END of offlinkPrefix definition.

            leaf noautoconfigPrefix  {
                type  cml_data_types:CML_BOOL_T;
                description "";
            } // END of noautoconfigPrefix definition.

        } // End of rtadvInterfaceNdPrefix-list
    } // END of rtadvInterfaceNdPrefix-grouping definition.

    grouping  rtadvInterface-grouping {
    description
        "rtadvInterface";
    container rtadvInterface {
        if-feature feature_list:HAVE_RTADV;
        description
            "rtadvInterface";
        leaf suppressRa  {
            type  cml_data_types:CML_SUPPRESSRA_T;
            default "enable";
            description "";
        } // END of suppressRa definition.

        leaf suppressRaMtu  {
            type  cml_data_types:CML_SUPPRESSRA_MTU_T;
            default "enable";
            description "";
        } // END of suppressRaMtu definition.

        leaf managedconfigflag  {
            type  cml_data_types:CML_BOOL_T;
            description "";
        } // END of managedconfigflag definition.

        leaf otherconfigflag  {
            type  cml_data_types:CML_BOOL_T;
            description "";
        } // END of otherconfigflag definition.

        leaf prefixOfflink  {
            type  cml_data_types:CML_BOOL_T;
            description "";
        } // END of prefixOfflink definition.

        leaf noautoconf  {
            type  cml_data_types:CML_BOOL_T;
            description "";
        } // END of noautoconf definition.

        leaf routerlifetime  {
            type  cml_data_types:CML_UINT16_T {
                 range "0..9000";
            }
            description "";
        } // END of routerlifetime definition.

        leaf randomrainterval  {
            type  cml_data_types:CML_UINT32_T;
            description "";
        } // END of randomrainterval definition.

        leaf reachabletime  {
            type  cml_data_types:CML_UINT32_T {
                 range "0..3600000";
            }
            description "";
        } // END of reachabletime definition.

        leaf retranstimer  {
            type  cml_data_types:CML_UINT32_T {
                 range "0..4294967295";
            }
            description "";
        } // END of retranstimer definition.

        leaf currhoplimit  {
            type  cml_data_types:CML_UINT8_T {
                 range "0..255";
            }
            description "";
        } // END of currhoplimit definition.

        leaf linkmtu  {
            type  cml_data_types:CML_UINT32_T {
                 range "1280..65535";
            }
            description "";
        } // END of linkmtu definition.

        leaf minrainterval  {
            type  cml_data_types:CML_UINT32_T {
                 range "3..1350";
            }
            description "";
        } // END of minrainterval definition.

        leaf maxrainterval  {
            type  cml_data_types:CML_UINT32_T {
                 range "4..1800";
            }
            description "";
        } // END of maxrainterval definition.

        leaf maxinitialrtradvert  {
            type  cml_data_types:CML_UINT8_T;
            description "";
        } // END of maxinitialrtradvert definition.

        leaf suppressrarun  {
            type  cml_data_types:CML_UINT8_T;
            description "";
        } // END of suppressrarun definition.

        leaf prefixvalidlifetime  {
            type  cml_data_types:CML_UINT32_T {
                 range "0..4294967295";
            }
            description "";
        } // END of prefixvalidlifetime definition.

        leaf prefixpreferredlifetime  {
            type  cml_data_types:CML_UINT32_T {
                 range "0..4294967295";
            }
            description "";
        } // END of prefixpreferredlifetime definition.

        leaf blockrsondelay  {
            type  cml_data_types:CML_UINT8_T;
            description "";
        } // END of blockrsondelay definition.

        leaf rowstatus  {
            type  cml_data_types:CML_UINT32_T;
            description "";
        } // END of rowstatus definition.

        leaf dadattempts  {
            type  cml_data_types:CML_INT32_T {
                 range "0..600";
            }
            description "";
        } // END of dadattempts definition.

        leaf homeAgeant  {
            if-feature feature_list:HAVE_MIP6;
            type  cml_data_types:CML_BOOL_T;
            description "";
        } // END of homeAgeant definition.

        leaf advinterval  {
            if-feature feature_list:HAVE_MIP6;
            type  cml_data_types:CML_BOOL_T;
            description "";
        } // END of advinterval definition.

        leaf hapreference  {
            if-feature feature_list:HAVE_MIP6;
            type  cml_data_types:CML_UINT16_T {
                 range "0..65535";
            }
            description "";
        } // END of hapreference definition.

        leaf halifetime  {
            if-feature feature_list:HAVE_MIP6;
            type  cml_data_types:CML_UINT16_T {
                 range "0..65535";
            }
            description "";
        } // END of halifetime definition.

        leaf ipv6Addr  {
            type  cml_data_types:CML_IPV6_PREFIX_T;
            description "";
        } // END of ipv6Addr definition.

        leaf vlifetime  {
            type  cml_data_types:CML_UINT32_T {
                 range "0..4294967295";
            }
            default "2592000";
            description "";
        } // END of vlifetime definition.

        leaf plifetime  {
            type  cml_data_types:CML_UINT32_T {
                 range "0..4294967295";
            }
            default "604800";
            description "";
        } // END of plifetime definition.

    } // END of rtadvInterface-container definition.
    } // END of rtadvInterface-container definition.


}
