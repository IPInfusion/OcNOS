/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-zebos-nat.yang
*
*/

submodule ipi-zebos-nat {

    belongs-to  ipi-zebos { prefix ipi-zebos; }

    import cml-data-types {
        prefix cml-data-types;
    }

    organization
        "IP Infusion Inc.";

    contact
        "Address: 3965 Freedom Circle, Suite 200, Santa Clara, CA 95054
        Phone: +1 408-400-1900
        E-mail: support@ipinfusion.com
        Web: http://www.ipinfusion.com/";

    description
        "nat configurations";


    revision "2018-06-21" {
        description " Initial Version.";
        reference "";
    }



    grouping imiNatAddressPool-grouping {
    description
        " NAT address pool list of struct imiNatAddressPool";
        list imiNatAddressPool {
            key "poolName";
            description
                " NAT address pool list of struct imiNatAddressPool";
            leaf poolName  {
                type  cml-data-types:CML_STRING_T;
                description "Address pool name";
            } // END of poolName definition.

            leaf minIp  {
                type  cml-data-types:CML_IPV4_ADDR_T;
                mandatory true;
                description "minIp of address pool";
            } // END of minIp definition.

            leaf maxIp  {
                type  cml-data-types:CML_IPV4_ADDR_T;
                mandatory true;
                description "maxIp of address pool";
            } // END of maxIp definition.

            leaf mask  {
                type  cml-data-types:CML_IPV4_ADDR_T;
                mandatory true;
                description "mask of address pool";
            } // END of mask definition.

        } // End of imiNatAddressPool-list
    } // END of imiNatAddressPool-grouping definition.


    grouping imi_rule_acl-grouping {
    description
        "imiCMLSEPruleCMLSEPacl";
        list imi_rule_acl {
            key "aclListSrcIn";
            description
                "imiCMLSEPruleCMLSEPacl";
            leaf aclListSrcIn  {
                type  cml-data-types:CML_STRING_T;
                description "Access list name";
            } // END of aclListSrcIn definition.

            leaf poolSrcIn  {
                type  cml-data-types:CML_STRING_T;
                mandatory true;
                description "Address pool name";
            } // END of poolSrcIn definition.

        } // End of imi_rule_acl-list
    } // END of imi_rule_acl-grouping definition.


    grouping imiRuleLocaladdr-grouping {
    description
        "imiRuleLocaladdr";
        list imiRuleLocaladdr {
            key "localAddrSrcIn";
            description
                "imiRuleLocaladdr";
            leaf localAddrSrcIn  {
                type  cml-data-types:CML_IPV4_ADDR_T;
                description "Outside local IP address";
            } // END of localAddrSrcIn definition.


            list imiRuleGlobaladdr {
                key "globalAddrSrcIn";
                description
                    "imiRuleGlobaladdr";
                leaf globalAddrSrcIn  {
                    type  cml-data-types:CML_IPV4_ADDR_T;
                    description "Outside global IP address";
                } // END of globalAddrSrcIn definition.

            } // End of imiRuleGlobaladdr-list
        } // End of imiRuleLocaladdr-list
    } // END of imiRuleLocaladdr-grouping definition.


    grouping imiRuleAclDestIn-grouping {
    description
        "imiRuleAclDestIn";
        list imiRuleAclDestIn {
            key "aclListDstIn";
            description
                "imiRuleAclDestIn";
            leaf aclListDstIn  {
                type  cml-data-types:CML_STRING_T;
                description "Access list name";
            } // END of aclListDstIn definition.

            leaf poolDstIn  {
                type  cml-data-types:CML_STRING_T;
                mandatory true;
                description "Address pool name";
            } // END of poolDstIn definition.

        } // End of imiRuleAclDestIn-list
    } // END of imiRuleAclDestIn-grouping definition.


    grouping imiRuleLocaladdrDestIn-grouping {
    description
        "imiRuleLocaladdrDestIn";
        list imiRuleLocaladdrDestIn {
            key "localAddrDstIn";
            description
                "imiRuleLocaladdrDestIn";
            leaf localAddrDstIn  {
                type  cml-data-types:CML_IPV4_ADDR_T;
                description "Outside local IP address";
            } // END of localAddrDstIn definition.


            list imiRuleGlobaladdr {
                key "globalAddrDstIn";
                description
                    "imiRuleGlobaladdr";
                leaf globalAddrDstIn  {
                    type  cml-data-types:CML_IPV4_ADDR_T;
                    description "Outside global IP address";
                } // END of globalAddrDstIn definition.

            } // End of imiRuleGlobaladdr-list
        } // End of imiRuleLocaladdrDestIn-list
    } // END of imiRuleLocaladdrDestIn-grouping definition.


    grouping imiRuleAclSrcOut-grouping {
    description
        "imiRuleAclSrcOut";
        list imiRuleAclSrcOut {
            key "aclListSrcOut";
            description
                "imiRuleAclSrcOut";
            leaf aclListSrcOut  {
                type  cml-data-types:CML_STRING_T;
                description "Access list name";
            } // END of aclListSrcOut definition.

            leaf poolSrcOut  {
                type  cml-data-types:CML_STRING_T;
                mandatory true;
                description "Address pool name";
            } // END of poolSrcOut definition.

        } // End of imiRuleAclSrcOut-list
    } // END of imiRuleAclSrcOut-grouping definition.


    grouping imiRuleLocaladdrSrcOut-grouping {
    description
        "imiRuleLocaladdrSrcOut";
        list imiRuleLocaladdrSrcOut {
            key "localAddrSrcOut";
            description
                "imiRuleLocaladdrSrcOut";
            leaf localAddrSrcOut  {
                type  cml-data-types:CML_IPV4_ADDR_T;
                description "Outside local IP address";
            } // END of localAddrSrcOut definition.


            list imiRuleGlobaladdr {
                key "globalAddrSrcOut";
                description
                    "imiRuleGlobaladdr";
                leaf globalAddrSrcOut  {
                    type  cml-data-types:CML_IPV4_ADDR_T;
                    description "Outside global IP address";
                } // END of globalAddrSrcOut definition.

            } // End of imiRuleGlobaladdr-list
        } // End of imiRuleLocaladdrSrcOut-list
    } // END of imiRuleLocaladdrSrcOut-grouping definition.


    grouping imiRuleAclOutDest-grouping {
    description
        "imiRuleAclOutDest";
        list imiRuleAclOutDest {
            key "aclListDstOut";
            description
                "imiRuleAclOutDest";
            leaf aclListDstOut  {
                type  cml-data-types:CML_STRING_T;
                description "Access list name";
            } // END of aclListDstOut definition.

            leaf poolDstOut  {
                type  cml-data-types:CML_STRING_T;
                mandatory true;
                description "Address pool name";
            } // END of poolDstOut definition.

        } // End of imiRuleAclOutDest-list
    } // END of imiRuleAclOutDest-grouping definition.


    grouping imiRuleLocaladdrOutDest-grouping {
    description
        "imiRuleLocaladdrOutDest";
        list imiRuleLocaladdrOutDest {
            key "localAddrDstOut";
            description
                "imiRuleLocaladdrOutDest";
            leaf localAddrDstOut  {
                type  cml-data-types:CML_IPV4_ADDR_T;
                description "Outside local IP address";
            } // END of localAddrDstOut definition.


            list imiRuleGlobaladdr {
                key "globalAddrDstOut";
                description
                    "imiRuleGlobaladdr";
                leaf globalAddrDstOut  {
                    type  cml-data-types:CML_IPV4_ADDR_T;
                    description "Outside global IP address";
                } // END of globalAddrDstOut definition.

            } // End of imiRuleGlobaladdr-list
        } // End of imiRuleLocaladdrOutDest-list
    } // END of imiRuleLocaladdrOutDest-grouping definition.


    grouping imiRuleLocaladdrStatic-grouping {
    description
        "imiRuleLocaladdrStatic";
        list imiRuleLocaladdrStatic {
            key "Port";
            description
                "imiRuleLocaladdrStatic";
            leaf Port  {
                type  cml-data-types:CML_NAT_PORT_TYPE_T;
                description "";
            } // END of Port definition.


            list imiRuleLocaladdress {
                key "localAddress";
                description
                    "imiRuleLocaladdress";
                leaf localAddress  {
                    type  cml-data-types:CML_IPV4_ADDR_T;
                    description "Outside local IP address";
                } // END of localAddress definition.


                list imiRuleDestport {
                    key "destport";
                    description
                        "imiRuleDestport";
                    leaf destport  {
                        type  cml-data-types:CML_UINT32_T {
                             range "0..65535";
                        }
                        description "Destination port number";
                    } // END of destport definition.


                    list imiRuleGlobaladdress {
                        key "globalAddress";
                        description
                            "imiRuleGlobaladdress";
                        leaf globalAddress  {
                            type  cml-data-types:CML_IPV4_ADDR_T;
                            description "Outside global IP address";
                        } // END of globalAddress definition.

                        leaf destinationport  {
                            type  cml-data-types:CML_UINT32_T {
                                 range "0..65535";
                            }
                            description "Destination port number";
                        } // END of destinationport definition.

                    } // End of imiRuleGlobaladdress-list
                } // End of imiRuleDestport-list
            } // End of imiRuleLocaladdress-list
        } // End of imiRuleLocaladdrStatic-list
    } // END of imiRuleLocaladdrStatic-grouping definition.

    grouping  imiNatTimeouts-grouping {
    description
        "imiNatTimeouts";
    container imiNatTimeouts {
        description
            "imiNatTimeouts";
        leaf genericTimeout  {
            type  cml-data-types:CML_UINT32_T {
                 range "0..536870";
            }
            default "0";
            description "generic timeout";
        } // END of genericTimeout definition.

        leaf icmpTimeout  {
            type  cml-data-types:CML_UINT32_T {
                 range "0..536870";
            }
            default "0";
            description "icmp timeout";
        } // END of icmpTimeout definition.

        leaf tcpTimeout  {
            type  cml-data-types:CML_UINT32_T {
                 range "0..536870";
            }
            default "0";
            description "tcp timeout";
        } // END of tcpTimeout definition.

        leaf udpTimeout  {
            type  cml-data-types:CML_UINT32_T {
                 range "0..536870";
            }
            default "0";
            description "udp timeout";
        } // END of udpTimeout definition.

        leaf tcpFinTimeout  {
            type  cml-data-types:CML_UINT32_T {
                 range "0..536870";
            }
            default "0";
            description "";
        } // END of tcpFinTimeout definition.

        leaf dnsTimeout  {
            type  cml-data-types:CML_UINT32_T {
                 range "0..536870";
            }
            default "0";
            description "";
        } // END of dnsTimeout definition.

    } // END of imiNatTimeouts-container definition.
    } // END of imiNatTimeouts-container definition.

    grouping  nat_interface-grouping {
    description
        "interface";
    container nat_interface {
        description
            "interface";
        leaf inside  {
            type  cml-data-types:CML_BOOL_T;
            description "Inside interface";
        } // END of inside definition.

        leaf outside  {
            type  cml-data-types:CML_BOOL_T;
            description "Outside interface";
        } // END of outside definition.

    } // END of nat_interface-container definition.
    } // END of nat_interface-container definition.


}
