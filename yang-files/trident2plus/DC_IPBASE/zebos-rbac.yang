/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-rbac.yang
*
*/

submodule zebos-rbac {

    belongs-to  zebos { prefix zebos; }

    import cml_data_types {
        prefix cml_data_types;
    }

    organization
        "IP Infusion Inc.";

    contact
        "Address: 3965 Freedom Circle, Suite 200, Santa Clara, CA 95054
        Phone: +1 408-400-1900
        E-mail: support@ipinfusion.com
        Web: http://www.ipinfusion.com/";

    description
        "Role Based Access Control";


    revision "2018-06-21" {
        description "Intial datamodel for Role Based Access Control.";
        reference "";
    }


    grouping  rbacFeature-grouping {
    description
        "RBAC feature";
    container rbacFeature {
        description
            "RBAC feature";
        leaf rbacEnable  {
            type  cml_data_types:CML_BOOL_T;
            description "Role based access control of RBAC feature";
        } // END of rbacEnable definition.


        list policyList {
            key "policyName";
            description
                "list of rbac policies";
            leaf policyName  {
                type  cml_data_types:CML_STRING_T {
                    length "2..16";
                }
                description "Policy name";
            } // END of policyName definition.


            list ruleList {
                key "rule";
                description
                    "Rules list configured for a policy";
                leaf ruleType  {
                    type  cml_data_types:CML_HOSTP_RBAC_RULE_TYPE_T;
                    description "This attribute specifies whether to deny or permit the configured rule";
                } // END of ruleType definition.

                leaf rule  {
                    type  cml_data_types:CML_LINE_T {
                        length "2..255";
                    }
                    description "This attribute specifies rule string configured as regex-expression for cli authorization";
                } // END of rule definition.

                leaf-list cliMode  {
                    type  cml_data_types:CML_STRING_T;
                    description "Command prompt string such as 'config-router' or 'config-if', deny/Permit access to the command only in this mode.";
                } // END of cliMode definition.

            } // End of ruleList-list
        } // End of policyList-list

        list roleList {
            key "role";
            description
                "object list for rbac user role";
            leaf role  {
                type  cml_data_types:CML_STRING_T {
                    length "2..16";
                }
                description "Role name";
            } // END of role definition.

            leaf defaultRule  {
                type  cml_data_types:CML_HOSTP_RBAC_DEFAULT_RULE_TYPE_T;
                default "deny-all";
                description "Permit or Deny all commands";
            } // END of defaultRule definition.


            list attachedPolicyList {
                key "policyName";
                description
                    "policy list attached to a role";
                leaf policyName  {
                    type  cml_data_types:CML_STRING_T {
                        length "2..16";
                    }
                    description "Name of the policy";
                } // END of policyName definition.

            } // End of attachedPolicyList-list
        } // End of roleList-list
    } // END of rbacFeature-container definition.
    } // END of rbacFeature-container definition.


}
