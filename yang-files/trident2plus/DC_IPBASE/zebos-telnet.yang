/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-telnet.yang
*
*/

submodule zebos-telnet {

    belongs-to  zebos { prefix zebos; }

    import cml_data_types {
        prefix cml_data_types;
    }

    import feature_list {
        prefix feature_list;
    }

    include zebos-vrf;
    organization
        "IP Infusion Inc.";

    contact
        "Address: 3965 Freedom Circle, Suite 200, Santa Clara, CA 95054
        Phone: +1 408-400-1900
        E-mail: support@ipinfusion.com
        Web: http://www.ipinfusion.com/";

    description
        "Telnet configurations";


    revision "2017-11-01" {
        description "Auto populate default VRF name when management VRF is disabled.";
    }

    revision "2017-01-19" {
        description "Changed vrf name as normal attr as it is optional parameter.";
    }

    revision "2016-12-27" {
        description "Added snmp oid and documentation tag.";
    }

    revision "2016-10-28" {
        description "Initial version of TELNET datamodel.";
    }



    grouping telnetVrfInstance-grouping {
        list telnetVrfInstance {
            key "vrfName";
            description
                "telnet vrf instance";
            leaf vrfName  {
                type  cml_data_types:CML_STRING_T {
                    length "0..255";
                }
                description "";
            } // END of vrfName definition.

            leaf featureTelnet  {
                type  cml_data_types:CML_BOOL_T;
                description "";
            } // END of featureTelnet definition.

            leaf port  {
                if-feature feature_list:HAVE_TELNET_SERVER;
                type  cml_data_types:CML_INT32_T {
                     range "1024..65535";
                }
                description "";
            } // END of port definition.

        } // End of telnetVrfInstance-list
    } // END of telnetVrfInstance-grouping definition.

    grouping  debugTELNETconfig-grouping {
    container debugTELNETconfig {
        description
            "telnet related operations";
        leaf debugtelnet  {
            if-feature feature_list:HAVE_TELNET_SERVER;
            type  cml_data_types:CML_BOOL_T;
            default false;
            description "";
        } // END of debugtelnet definition.

    } // END of debugTELNETconfig-container definition.
    } // END of debugTELNETconfig-container definition.


}
