/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-dns.yang
*
*/

submodule zebos-dns {

    belongs-to  zebos { prefix zebos; }

    import cml_data_types {
        prefix cml_data_types;
    }

    import feature_list {
        prefix feature_list;
    }

    include zebos-vrf;
    organization
        "IP Infusion Inc.";

    contact
        "Address: 3965 Freedom Circle, Suite 200, Santa Clara, CA 95054
        Phone: +1 408-400-1900
        E-mail: support@ipinfusion.com
        Web: http://www.ipinfusion.com/";

    description
        "dns_configuration";


    revision "2016-12-27" {
        description "Added snmp oid and documentation tag.";
    }

    revision "2016-10-28" {
        description "Initial version of DNS datamodel.";
    }


    grouping  dns-grouping {
    container dns {
        description
            "dns";
        leaf vrfName  {
            type  cml_data_types:CML_STRING_T {
                length "0..255";
            }
            description "";
        } // END of vrfName definition.

        leaf domainlookup  {
            type  cml_data_types:CML_BOOL_T;
            description "";
        } // END of domainlookup definition.

        leaf defaultdomain  {
            if-feature feature_list:HAVE_DNS_CLIENT;
            type  cml_data_types:CML_BOOL_T;
            description "";
        } // END of defaultdomain definition.

        leaf domainname  {
            if-feature feature_list:HAVE_DNS_CLIENT;
            type  cml_data_types:CML_STRING_T {
                length "0..255";
            }
            description "";
        } // END of domainname definition.

        leaf debugdns  {
            if-feature feature_list:HAVE_DNS_CLIENT;
            type  cml_data_types:CML_BOOL_T;
            description "";
        } // END of debugdns definition.


        list domainlistNAME {
            key "domainlist";
            description
                "domainlistNAME";
            leaf vrfName  {
                type  cml_data_types:CML_STRING_T {
                    length "0..255";
                }
                description "";
            } // END of vrfName definition.

            leaf domainlist  {
                type  cml_data_types:CML_STRING_T {
                    length "0..255";
                }
                description "";
            } // END of domainlist definition.

        } // End of domainlistNAME-list

        list vrfHOST {
            key "vrfName";
            description
                "vrfHOST";
            leaf vrfName  {
                type  cml_data_types:CML_STRING_T {
                    length "0..255";
                }
                description "";
            } // END of vrfName definition.


            list hostname {
                key "host";
                description
                    "hostname";
                leaf host  {
                    type  cml_data_types:CML_STRING_T {
                        length "0..255";
                    }
                    description "";
                } // END of host definition.

                leaf ipv4  {
                    type  cml_data_types:CML_IPV4_ADDR_T;
                    description "";
                } // END of ipv4 definition.

                leaf ipv6  {
                    type  cml_data_types:CML_IPV6_ADDR_T;
                    description "";
                } // END of ipv6 definition.

            } // End of hostname-list
            container dnsNameServer {
                description
                    "dnsNameServer";
                leaf-list nameServer  {
                    type  cml_data_types:CML_IP_ADDR_T;
                    description "";
                } // END of nameServer definition.

            } // END of dnsNameServer-container definition.
        } // End of vrfHOST-list
    } // END of dns-container definition.
    } // END of dns-container definition.


}
