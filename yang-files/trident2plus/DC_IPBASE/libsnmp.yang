/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : libsnmp.yang
*
*/

submodule libsnmp {

    belongs-to  ZebOS { prefix ZebOS; }

    import cml_data_types {
        prefix cml_data_types;
    }

    import feature_list {
        prefix feature_list;
    }

    include vrf;
    organization
        "IP Infusion Inc.";

    contact
        "Address: 3965 Freedom Circle, Suite 200, Santa Clara, CA 95054
        Phone: +1 408-400-1900
        E-mail: support@ipinfusion.com
        Web: http://www.ipinfusion.com/";

    description
        "snmp configurations";


    revision "2017-02-20" {
        description "Added snmp-server enable cli.";
    }

    revision "2016-10-28" {
        description "Initial version of LIBSNMP datamodel.";
    }


    grouping  snmpVrfName-grouping {
    container snmpVrfName {
        if-feature feature_list:HAVE_SNMP_AGENT;
        description
            "snmp-server configuration common for all modules";
        leaf vrfName  {
            type  cml_data_types:CML_STRING_T {
                length "0..255";
            }
            description "snmp-server enable traps with vrfname";
        } // END of vrfName definition.

        leaf-list traps  {
            type  cml_data_types:SNMP_TRAP_OPTIONS_T;
            description "snmp-server enable traps";
        } // END of traps definition.

    } // END of snmpVrfName-container definition.
    } // END of snmpVrfName-container definition.


}
