/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-zebos-featuredhcp.yang
*
*/

submodule ipi-zebos-featuredhcp {

    belongs-to  ipi-zebos { prefix ipi-zebos; }

    import cml-data-types {
        prefix cml-data-types;
    }

    organization
        "IP Infusion Inc.";

    contact
        "Address: 3965 Freedom Circle, Suite 200, Santa Clara, CA 95054
        Phone: +1 408-400-1900
        E-mail: support@ipinfusion.com
        Web: http://www.ipinfusion.com/";

    description
        "feature_dhcp_configuration";


    revision "2018-06-21" {
        description " Initial Version.";
        reference "";
    }


    grouping  featuredhcp-grouping {
    description
        "featuredhcp";
    container featuredhcp {
        description
            "featuredhcp";
        leaf dhcp  {
            type  cml-data-types:CML_BOOL_T;
            description "";
        } // END of dhcp definition.

    } // END of featuredhcp-container definition.
    } // END of featuredhcp-container definition.


}
