/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-zebos-evpn.yang
*
*/

submodule ipi-zebos-evpn {

    belongs-to  ipi-zebos { prefix ipi-zebos; }

    import cml-data-types {
        prefix cml-data-types;
    }

    organization
        "IP Infusion Inc.";

    contact
        "Address: 3965 Freedom Circle, Suite 200, Santa Clara, CA 95054
        Phone: +1 408-400-1900
        E-mail: support@ipinfusion.com
        Web: http://www.ipinfusion.com/";

    description
        "";


    revision "2018-12-28" {
        description " Initial Version.";
        reference "";
    }


    grouping  evpn-service-type-grouping {
    description
        "EVPN Service Type";
    container evpn-service-type {
        description
            "EVPN Service Type";
        leaf service_type  {
            type  cml-data-types:CML_EVPN_SERVICE_TYPE_T;
            description "Vlan-Based EVPN-Service Type";
        } // END of service_type definition.

    } // END of evpn-service-type-container definition.
    } // END of evpn-service-type-container definition.


}
