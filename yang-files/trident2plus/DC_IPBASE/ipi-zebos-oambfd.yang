/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-zebos-oambfd.yang
*
*/

submodule ipi-zebos-oambfd {

    belongs-to  ipi-zebos { prefix ipi-zebos; }

    import cml-data-types {
        prefix cml-data-types;
    }

    import feature-list {
        prefix feature-list;
    }

    include ipi-zebos-interface;
    organization
        "IP Infusion Inc.";

    contact
        "Address: 3965 Freedom Circle, Suite 200, Santa Clara, CA 95054
        Phone: +1 408-400-1900
        E-mail: support@ipinfusion.com
        Web: http://www.ipinfusion.com/";

    description
        "";


    revision "2018-06-21" {
        description " Initial Version.";
        reference "";
    }



    grouping bfdSession-grouping {
    description
        "bfd Session table for runtime attrs";
        list bfdSession {
            key "bfdSessionIndex";
            config false;
            description
                "bfd Session table for runtime attrs";
            leaf bfdSessionIndex  {
                type  cml-data-types:CML_UINT32_T;
                description " BFD Session Index";
            } // END of bfdSessionIndex definition.

            leaf bfdSessRemoteDisc  {
                type  cml-data-types:CML_UINT32_T;
                description " BFD Session Remote Discriminator";
            } // END of bfdSessRemoteDisc definition.

            leaf bfdLlType  {
                type  cml-data-types:CML_OAMBFD_SESS_LOWER_LAYER_T;
                description "BFD Session Lower Layer Type";
            } // END of bfdLlType definition.

            leaf bfdSessionType  {
                type  cml-data-types:CML_OAMBFD_SESSION_TYPE_T;
                description "BFD Session Type (single or multi)";
            } // END of bfdSessionType definition.

            leaf bfdSessionState  {
                type  cml-data-types:CML_OAMBFD_SESSION_STATE_T;
                description "BFD Session State";
            } // END of bfdSessionState definition.

            leaf bfdSessionUptime  {
                type  cml-data-types:CML_STRING_T;
                description "BFD Session Up Time";
            } // END of bfdSessionUptime definition.

            leaf bfdRemoteAddr  {
                type  cml-data-types:CML_STRING_T;
                description "BFD Session Remote Peer Address";
            } // END of bfdRemoteAddr definition.

            leaf bfdSessIfIdx  {
                type  cml-data-types:CML_UINT32_T;
                description "BFD Session Interface Index";
            } // END of bfdSessIfIdx definition.

            leaf bfdSessVersion  {
                type  cml-data-types:CML_UINT32_T;
                description "BFD Session Version";
            } // END of bfdSessVersion definition.

            leaf bfdSessLocDisc  {
                type  cml-data-types:CML_UINT32_T;
                description "BFD Session Local Discriminator";
            } // END of bfdSessLocDisc definition.

            leaf bfdSessLocAddr  {
                type  cml-data-types:CML_STRING_T;
                description "BFD Session Local Address";
            } // END of bfdSessLocAddr definition.

            leaf bfdRemotePort  {
                type  cml-data-types:CML_UINT32_T;
                description "BFD Session Remote Side Port Number";
            } // END of bfdRemotePort definition.

            leaf bfdLocalPort  {
                type  cml-data-types:CML_UINT32_T;
                description "BFD Session Local Port Number";
            } // END of bfdLocalPort definition.

            leaf bfdLocalEchoPort  {
                type  cml-data-types:CML_UINT32_T;
                description "BFD Session Local Echo Port Number";
            } // END of bfdLocalEchoPort definition.

            leaf bfdMplsLspType  {
                type  cml-data-types:CML_UINT32_T;
                description "BFD Session MPLS LSP path Type";
            } // END of bfdMplsLspType definition.

            leaf bfdMplsTnlName  {
                type  cml-data-types:CML_STRING_T;
                description "BFD Session MPLS Tunnel Name";
            } // END of bfdMplsTnlName definition.

            leaf bfdMplsFecAddr  {
                type  cml-data-types:CML_STRING_T;
                description "BFD Session MPLS FEC Address";
            } // END of bfdMplsFecAddr definition.

            leaf bfdMplsLspPingItvl  {
                type  cml-data-types:CML_UINT32_T;
                description "BFD Session MPLS Ping Interval";
            } // END of bfdMplsLspPingItvl definition.

            leaf bfdMplsFtnIndx  {
                type  cml-data-types:CML_UINT32_T;
                description "BFD Session MPLS FTN index";
            } // END of bfdMplsFtnIndx definition.

            leaf bfdMplsMinTx  {
                type  cml-data-types:CML_UINT32_T;
                description "BFD Session MPLS Minimum Transmit interval";
            } // END of bfdMplsMinTx definition.

            leaf bfdMplsMinRx  {
                type  cml-data-types:CML_UINT32_T;
                description "BFD Session MPLS Minimum Receive interval";
            } // END of bfdMplsMinRx definition.

            leaf bfdMplsMult  {
                type  cml-data-types:CML_UINT32_T;
                description "BFD Session MPLS Transmit Multiplier";
            } // END of bfdMplsMult definition.

            leaf bfdMplsTnlLabel  {
                type  cml-data-types:CML_UINT32_T;
                description "BFD Session MPLS Tunnel Label";
            } // END of bfdMplsTnlLabel definition.

            leaf bfdVccvVcId  {
                type  cml-data-types:CML_UINT32_T;
                description "BFD Session VCCV VC identifier";
            } // END of bfdVccvVcId definition.

            leaf bfdVccvInVcLabel  {
                type  cml-data-types:CML_UINT32_T;
                description "BFD Session VCCV incoming VC label";
            } // END of bfdVccvInVcLabel definition.

            leaf bfdVccvOutVcLabel  {
                type  cml-data-types:CML_UINT32_T;
                description "BFD Session VCCV outgoing VC label";
            } // END of bfdVccvOutVcLabel definition.

            leaf bfdVccvCcType  {
                type  cml-data-types:CML_UINT32_T;
                description "BFD Session VCCV CC type";
            } // END of bfdVccvCcType definition.

            leaf bfdVccvCvType  {
                type  cml-data-types:CML_UINT32_T;
                description "BFD Session VCCV CV type";
            } // END of bfdVccvCvType definition.

            leaf bfdVccvAcIx  {
                type  cml-data-types:CML_UINT32_T;
                description "BFD Session VCCV AC identifier";
            } // END of bfdVccvAcIx definition.

            leaf bfdVccvTnlLabel  {
                type  cml-data-types:CML_UINT32_T;
                description "BFD Session VCCV Tunnel Label";
            } // END of bfdVccvTnlLabel definition.

            leaf bfdVccvPeerAddr  {
                type  cml-data-types:CML_UINT32_T;
                description "BFD Session VCCV Peer Address";
            } // END of bfdVccvPeerAddr definition.

            leaf bfdMplstpMegName  {
                type  cml-data-types:CML_STRING_T;
                description "BFD Session MPLS TP Meg name";
            } // END of bfdMplstpMegName definition.

            leaf bfdMplstpMeName  {
                type  cml-data-types:CML_STRING_T;
                description "BFD Session MPLS MPLS TP Me name";
            } // END of bfdMplstpMeName definition.

            leaf bfdMplstpPathType  {
                type  cml-data-types:CML_UINT8_T;
                description "BFD Session MPLS TP Path Type";
            } // END of bfdMplstpPathType definition.

            leaf bfdSessOptionFlag  {
                type  cml-data-types:CML_OAMBFD_SESSION_FLAGS_T;
                description "BFD Session Options Flag";
            } // END of bfdSessOptionFlag definition.

            leaf bfdSessPerfDiag  {
                type  cml-data-types:CML_OAMBFD_PERFORM_DIAG_T;
                description "BFD Session perf diagnostics";
            } // END of bfdSessPerfDiag definition.

            leaf bfdSessMinTx  {
                type  cml-data-types:CML_UINT32_T;
                description "BFD Session Minimum Transmit Interval";
            } // END of bfdSessMinTx definition.

            leaf bfdSessMinRx  {
                type  cml-data-types:CML_UINT32_T;
                description "BFD Session Minimum Receive Interval";
            } // END of bfdSessMinRx definition.

            leaf bfdSessMultplier  {
                type  cml-data-types:CML_UINT32_T;
                description "BFD Session Transmit Multiplier";
            } // END of bfdSessMultplier definition.

            leaf bfdSessNegTx  {
                type  cml-data-types:CML_UINT32_T;
                description "BFD Session Negotiated Transmit Interval";
            } // END of bfdSessNegTx definition.

            leaf bfdSessNegRx  {
                type  cml-data-types:CML_UINT32_T;
                description "BFD Session Negotiated Received Interval";
            } // END of bfdSessNegRx definition.

            leaf bfdSessNegMultiplier  {
                type  cml-data-types:CML_UINT32_T;
                description "BFD Session Negotiated Multiplier value";
            } // END of bfdSessNegMultiplier definition.

            leaf bfdSessEchoTx  {
                type  cml-data-types:CML_UINT32_T;
                description "BFD Session Echo Transmit Interval";
            } // END of bfdSessEchoTx definition.

            leaf bfdSessEchoRx  {
                type  cml-data-types:CML_UINT32_T;
                description "BFD Session Echo Receive Interval";
            } // END of bfdSessEchoRx definition.

            leaf bfdSessEchoIntvl  {
                type  cml-data-types:CML_UINT32_T;
                description "BFD Session Echo Interval";
            } // END of bfdSessEchoIntvl definition.

            leaf bfdSessStorTye  {
                type  cml-data-types:CML_UINT32_T;
                description "BFD Session Storage Type";
            } // END of bfdSessStorTye definition.

            leaf bfdSessDownTime  {
                type  cml-data-types:CML_STRING_T;
                description "BFD Session Down Time";
            } // END of bfdSessDownTime definition.

            leaf bfdSessDisconTime  {
                type  cml-data-types:CML_STRING_T;
                description "BFD Session Disconnect time";
            } // END of bfdSessDisconTime definition.

            leaf bfdSessAuthKeyId  {
                type  cml-data-types:CML_UINT32_T;
                description "BFD Session Authentication Key Identifier";
            } // END of bfdSessAuthKeyId definition.

            leaf bfdSessPktIn  {
                type  cml-data-types:CML_STRING_T;
                description "BFD Session Received Packet Count";
            } // END of bfdSessPktIn definition.

            leaf bfdSessPktOut  {
                type  cml-data-types:CML_STRING_T;
                description "BFD Session Sent Packet Count";
            } // END of bfdSessPktOut definition.

            leaf bfdSessEchoOut  {
                type  cml-data-types:CML_STRING_T;
                description "BFD Session Echo Sent Packet Count";
            } // END of bfdSessEchoOut definition.

            leaf bfdSessIpv6EchoOut  {
                if-feature feature-list:HAVE_IPV6;
                type  cml-data-types:CML_STRING_T;
                description "BFD Session IPv6 Echo Sent Packet Count";
            } // END of bfdSessIpv6EchoOut definition.

            leaf bfdSessIpv6PktOut  {
                if-feature feature-list:HAVE_IPV6;
                type  cml-data-types:CML_STRING_T;
                description "BFD Session IPv6 Sent Packet Count";
            } // END of bfdSessIpv6PktOut definition.

            leaf bfdSessIpv6PktIn  {
                if-feature feature-list:HAVE_IPV6;
                type  cml-data-types:CML_STRING_T;
                description "BFD Session IPv6 Received Packet Count";
            } // END of bfdSessIpv6PktIn definition.

            leaf bfdSessUpCount  {
                type  cml-data-types:CML_UINT32_T;
                description "Number of BFD Session Up count";
            } // END of bfdSessUpCount definition.

            leaf bfdSessUpTime  {
                type  cml-data-types:CML_STRING_T;
                description "BFD Session Up time";
            } // END of bfdSessUpTime definition.

            leaf bfdSessHoldCntr  {
                type  cml-data-types:CML_UINT32_T;
                description "BFD Session Hold time counter";
            } // END of bfdSessHoldCntr definition.

            leaf bfdSessHoldDown  {
                type  cml-data-types:CML_UINT32_T;
                description "BFD Session Hold Down Time";
            } // END of bfdSessHoldDown definition.

            leaf bfdSessFwdHelloCntr  {
                type  cml-data-types:CML_UINT32_T;
                description "BFD Session Forward Hello counter";
            } // END of bfdSessFwdHelloCntr definition.

            leaf bfdSessPktVersion  {
                type  cml-data-types:CML_UINT32_T;
                description "BFD Session Packet Version";
            } // END of bfdSessPktVersion definition.

            leaf bfdSessPktDiag  {
                type  cml-data-types:CML_UINT32_T;
                description "BFD Session Packet Diagnostics";
            } // END of bfdSessPktDiag definition.

            leaf bfdSessPktState  {
                type  cml-data-types:CML_UINT32_T;
                description "BFD Session Packet State";
            } // END of bfdSessPktState definition.

            leaf bfdSessPktDemandEn  {
                type  cml-data-types:CML_UINT32_T;
                description "BFD Session Packet is Demand mode Enabled";
            } // END of bfdSessPktDemandEn definition.

            leaf bfdSessPktPollSeq  {
                type  cml-data-types:CML_UINT32_T;
                description "BFD Session Packet Poll Sequence";
            } // END of bfdSessPktPollSeq definition.

            leaf bfdSessPktFlagState  {
                type  cml-data-types:CML_STRING_T;
                description "BFD Session Packet Flag State";
            } // END of bfdSessPktFlagState definition.

            leaf bfdSessPktMult  {
                type  cml-data-types:CML_UINT32_T;
                description "BFD Session Packet Multiplier";
            } // END of bfdSessPktMult definition.

            leaf bfdSessPktLength  {
                type  cml-data-types:CML_UINT32_T;
                description "BFD Session Packet Length";
            } // END of bfdSessPktLength definition.

            leaf bfdSessPktMyDisc  {
                type  cml-data-types:CML_UINT32_T;
                description "BFD Session Packet Own discriminator";
            } // END of bfdSessPktMyDisc definition.

            leaf bfdSessPktUrDisc  {
                type  cml-data-types:CML_UINT32_T;
                description "BFD Session Packet Neighbor Discriminator";
            } // END of bfdSessPktUrDisc definition.

            leaf bfdSessPktMinTx  {
                type  cml-data-types:CML_UINT32_T;
                description "BFD Session Packet Minimum Transmit Interval";
            } // END of bfdSessPktMinTx definition.

            leaf bfdSessPktMinRx  {
                type  cml-data-types:CML_UINT32_T;
                description "BFD Session Packet Minimum Receive Interval";
            } // END of bfdSessPktMinRx definition.

            leaf bfdSessPktMinEchoIntvl  {
                type  cml-data-types:CML_UINT32_T;
                description "BFD Session Packet Minimum Echo Interval";
            } // END of bfdSessPktMinEchoIntvl definition.


            list bfdSessionClientInfo {
                key "bfdSessProtoClientId";
                config false;
                description
                    "BFD session client Info";
                leaf bfdSessProtoClientId  {
                    type  cml-data-types:CML_UINT32_T;
                    description "BFD Session Protocol Client Identifier";
                } // END of bfdSessProtoClientId definition.

                leaf bfdSessClientFlag  {
                    type  cml-data-types:CML_STRING_T;
                    description "BFD Session Protocol Client Flags";
                } // END of bfdSessClientFlag definition.

            } // End of bfdSessionClientInfo-list
        } // End of bfdSession-list
    } // END of bfdSession-grouping definition.


    grouping bfdInterface-grouping {
    description
        "BFD interface related operations";
        list bfdInterface {
            key "ifName";
            description
                "BFD interface related operations";
            leaf ifName  {
                type  cml-data-types:CML_STRING_T;
                description "BFD Interface Name";
            } // END of ifName definition.

            leaf isBfdDisable  {
                type  cml-data-types:CML_BOOL_T;
                description "BFD Enabled/Disabled check flag on Interface";
            } // END of isBfdDisable definition.

            leaf bfdIfTransmitIntvl  {
                type  cml-data-types:CML_UINT32_T {
                     range "3..999";
                }
                description "BFD Transmit interval of BFD Interface";
            } // END of bfdIfTransmitIntvl definition.

            leaf bfdIfRecieveIntvl  {
                type  cml-data-types:CML_UINT32_T {
                     range "3..999";
                }
                description "BFD Receive Interval of BFD interface";
            } // END of bfdIfRecieveIntvl definition.

            leaf bfdIfHelloMultiplier  {
                type  cml-data-types:CML_UINT32_T {
                     range "3..50";
                }
                description "BFD Hello Multiplier of BFD Interface";
            } // END of bfdIfHelloMultiplier definition.

            leaf bfdEchoInterval  {
                type  cml-data-types:CML_UINT32_T {
                     range "50..4294967";
                }
                description "BFD Echo Interval";
            } // END of bfdEchoInterval definition.

            leaf bfdIfSrcAddr  {
                type  cml-data-types:CML_IPV4_ADDR_T;
                description "BFD Session Source of BFD interface";
            } // END of bfdIfSrcAddr definition.

            leaf bfdIfAuthType  {
                type  cml-data-types:CML_BFD_MULTIHOP_AUTH_TYPE_T;
                description "BFD Session Authentication Type of BFD Interface";
            } // END of bfdIfAuthType definition.

            leaf bfdIfKeyChain  {
                type  cml-data-types:CML_LINE_T;
                description "BFD Session Authentication Key Chain of BFD Interface";
            } // END of bfdIfKeyChain definition.

            leaf bfdIfKeyId  {
                type  cml-data-types:CML_UINT32_T {
                     range "0..255";
                }
                description "BFD Session Authentication Key ID of BFD Interface";
            } // END of bfdIfKeyId definition.

            leaf bfdIfKeyStr  {
                type  cml-data-types:CML_LINE_T;
                description "BFD Session Authentication Key String of BFD Interface";
            } // END of bfdIfKeyStr definition.

            leaf bfdIfIndex  {
                type  cml-data-types:CML_UINT32_T;
                config false;
                description "BFD Interface Index";
            } // END of bfdIfIndex definition.

            leaf bfdIfState  {
                type  cml-data-types:CML_STRING_T;
                config false;
                description "BFD Interface State";
            } // END of bfdIfState definition.

            container bfdSessionSingleHopIpv4 {
                description
                    "bfd single hop session";

                list bfdIpv4ShUserIntfSessSrc {
                    key "bfdIpv4ShUserSrcAddr";
                    description
                        "BFD ipv4 user intf src related configs";
                    leaf bfdIpv4ShUserSrcAddr  {
                        type  cml-data-types:CML_IPV4_ADDR_T;
                        description "BFD Singlehop Session IPv4 Source Address";
                    } // END of bfdIpv4ShUserSrcAddr definition.


                    list bfdIpv4ShUserIntfSessDest {
                        key "bfdIpv4ShUserDestAddr";
                        description
                            "BFD ipv4 user intf dest related configs";
                        leaf bfdIpv4ShUserDestAddr  {
                            type  cml-data-types:CML_IPV4_ADDR_T;
                            description "BFD Singlehop Session IPv4 Destination Address";
                        } // END of bfdIpv4ShUserDestAddr definition.

                        uses bfdSessionAttr;
                    } // End of bfdIpv4ShUserIntfSessDest-list
                } // End of bfdIpv4ShUserIntfSessSrc-list
            } // END of bfdSessionSingleHopIpv4-container definition.
            container bfdSessionMultiHopIpv4 {
                description
                    "bfd single hop session";

                list bfdIpv4MhUserIntfSessSrc {
                    key "bfdIpv4MhUserSrcAddr";
                    description
                        "BFD ipv4 user intf src related configs";
                    leaf bfdIpv4MhUserSrcAddr  {
                        type  cml-data-types:CML_IPV4_ADDR_T;
                        description "BFD Multihop Session IPv4 Source Address";
                    } // END of bfdIpv4MhUserSrcAddr definition.


                    list bfdIpv4MhUserIntfSessDest {
                        key "bfdIpv4MhUserDestAddr";
                        description
                            "BFD ipv4 user intf dest related configs";
                        leaf bfdIpv4MhUserDestAddr  {
                            type  cml-data-types:CML_IPV4_ADDR_T;
                            description "BFD Multihop Session IPv4 Destination Address";
                        } // END of bfdIpv4MhUserDestAddr definition.

                        leaf multihopIpv4  {
                            type  cml-data-types:CML_BFD_MULTI_HOP_TYPE_T;
                            description "BFD Multihop Type";
                        } // END of multihopIpv4 definition.

                        uses bfdSessionAttr;
                    } // End of bfdIpv4MhUserIntfSessDest-list
                } // End of bfdIpv4MhUserIntfSessSrc-list
            } // END of bfdSessionMultiHopIpv4-container definition.
            container bfdSessionSingleHopIpv6 {
                description
                    "bfd single hop session";

                list bfdIpv6ShUserIntfSessSrc {
                    key "bfdIpv6ShUserSrcAddr";
                    description
                        "BFD ipv4 user intf src related configs";
                    leaf bfdIpv6ShUserSrcAddr  {
                        type  cml-data-types:CML_IPV6_ADDR_T;
                        description "BFD Singlehop Session IPv6 Source Address";
                    } // END of bfdIpv6ShUserSrcAddr definition.


                    list bfdIpv6ShUserIntfSessDest {
                        key "bfdIpv6ShUserDestAddr";
                        description
                            "BFD ipv6 user intf dest related configs";
                        leaf bfdIpv6ShUserDestAddr  {
                            type  cml-data-types:CML_IPV6_ADDR_T;
                            description "BFD Singlehop Session IPv6 Destination Address";
                        } // END of bfdIpv6ShUserDestAddr definition.

                        uses bfdSessionAttr;
                    } // End of bfdIpv6ShUserIntfSessDest-list
                } // End of bfdIpv6ShUserIntfSessSrc-list
            } // END of bfdSessionSingleHopIpv6-container definition.
            container bfdSessionMultiHopIpv6 {
                description
                    "bfd single hop session";

                list bfdIpv6MhUserIntfSessSrc {
                    key "bfdIpv6MhUserSrcAddr";
                    description
                        "BFD ipv6 user intf src related configs";
                    leaf bfdIpv6MhUserSrcAddr  {
                        type  cml-data-types:CML_IPV6_ADDR_T;
                        description "BFD Multihop Session IPv6 Source Address";
                    } // END of bfdIpv6MhUserSrcAddr definition.


                    list bfdIpv6MhUserIntfSessDest {
                        key "bfdIpv6MhUserDestAddr";
                        description
                            "BFD ipv6 user intf dest related configs";
                        leaf bfdIpv6MhUserDestAddr  {
                            type  cml-data-types:CML_IPV6_ADDR_T;
                            description "BFD Multihop Session IPv6 Destination Address";
                        } // END of bfdIpv6MhUserDestAddr definition.

                        leaf multihopIpv6  {
                            type  cml-data-types:CML_BFD_MULTI_HOP_TYPE_T;
                            description "BFD Multihop IPv6 Session Type";
                        } // END of multihopIpv6 definition.

                        uses bfdSessionAttr;
                    } // End of bfdIpv6MhUserIntfSessDest-list
                } // End of bfdIpv6MhUserIntfSessSrc-list
            } // END of bfdSessionMultiHopIpv6-container definition.
        } // End of bfdInterface-list
    } // END of bfdInterface-grouping definition.


    grouping confModeDebug-grouping {
    description
        "config mode debug commands";
        list confModeDebug {
            key "vrId";
            description
                "config mode debug commands";
            leaf vrId  {
                type  cml-data-types:CML_INT32_T;
                description "VR Identifier";
            } // END of vrId definition.

            leaf isConfDebugAll  {
                type  cml-data-types:CML_BOOL_T;
                description "Config Mode Debug enable/disable all";
            } // END of isConfDebugAll definition.

            leaf confModePackets  {
                type  cml-data-types:CML_BOOL_T;
                description "Config Mode Debug enable/disable of BFD Packets";
            } // END of confModePackets definition.

            leaf confModeEvents  {
                type  cml-data-types:CML_BOOL_T;
                description "Config Mode Debug enable/disable of BFD Events";
            } // END of confModeEvents definition.

            leaf confModeIpcErr  {
                type  cml-data-types:CML_BOOL_T;
                description "Config Mode Debug enable/disable of IPC Errors";
            } // END of confModeIpcErr definition.

            leaf confModeIpcEvent  {
                type  cml-data-types:CML_BOOL_T;
                description "Config Mode Debug enable/disable of IPC Events";
            } // END of confModeIpcEvent definition.

            leaf confModeSession  {
                type  cml-data-types:CML_BOOL_T;
                description "Config Mode Debug enable/disable of BFD Session";
            } // END of confModeSession definition.

            leaf confModeNsm  {
                type  cml-data-types:CML_BOOL_T;
                description "Config Mode Debug enable/disable of NSM w.r.t BFD";
            } // END of confModeNsm definition.

        } // End of confModeDebug-list
    } // END of confModeDebug-grouping definition.


    grouping execModeDebug-grouping {
    description
        "exec mode debug commands";
        list execModeDebug {
            key "vrId";
            description
                "exec mode debug commands";
            leaf vrId  {
                type  cml-data-types:CML_INT32_T;
                description "VR  Identifier";
            } // END of vrId definition.

            leaf isExecDebugAll  {
                type  cml-data-types:CML_BOOL_T;
                description "Exec Mode Debug enable/disable of all BFD";
            } // END of isExecDebugAll definition.

            leaf execModePackets  {
                type  cml-data-types:CML_BOOL_T;
                description "Exec Mode Debug enable/disable of BFD packets";
            } // END of execModePackets definition.

            leaf execModeEvents  {
                type  cml-data-types:CML_BOOL_T;
                description "Exec Mode Debug enable/disable of BFD Events";
            } // END of execModeEvents definition.

            leaf execModeIpcErr  {
                type  cml-data-types:CML_BOOL_T;
                description "Exec Mode Debug enable/disable of IPC errors";
            } // END of execModeIpcErr definition.

            leaf execModeIpcEvent  {
                type  cml-data-types:CML_BOOL_T;
                description "Exec Mode Debug enable/disable of IPC Events";
            } // END of execModeIpcEvent definition.

            leaf execModeSession  {
                type  cml-data-types:CML_BOOL_T;
                description "Exec Mode Debug enable/disable of BFD Session";
            } // END of execModeSession definition.

            leaf execModeNsm  {
                type  cml-data-types:CML_BOOL_T;
                description "Exec Mode Debug enable/disable of NSM w.r.t BFD ";
            } // END of execModeNsm definition.

        } // End of execModeDebug-list
    } // END of execModeDebug-grouping definition.
    grouping bfdSessionAttr {
        description
            "bfdSessionAttr";
        leaf demandMode  {
            type  cml-data-types:CML_BOOL_T;
            description "BFD Demand Mde enable/disable";
        } // END of demandMode definition.

        leaf nonPersistant  {
            type  cml-data-types:CML_BOOL_T;
            description "BFD Session type- Persistent/Non-Persistent";
        } // END of nonPersistant definition.

        leaf adminDown  {
            type  cml-data-types:CML_BOOL_T;
            description "BFD Session Admin-down enable/disable";
        } // END of adminDown definition.

    } // END of bfdSessionAttr definition.

    grouping  bfd-grouping {
    description
        "BFD basic configurations";
    container bfd {
        description
            "BFD basic configurations";
        leaf enGtsmProtection  {
            if-feature feature-list:HAVE_BFD_MONO;
            if-feature feature-list:NOT_HAVE_BFD_HW_OFFLOAD;
            type  cml-data-types:CML_BFD_SESSION_STATE_T;
            description "BFD GTSM Protection enable/disable";
        } // END of enGtsmProtection definition.

        leaf bfdNotfEn  {
            if-feature feature-list:HAVE_BFD_MONO;
            type  cml-data-types:CML_BFD_SESSION_STATE_T;
            description "BFD Notification Enable/Disable";
        } // END of bfdNotfEn definition.

        leaf bfdGbTransmitIntvl  {
            if-feature feature-list:HAVE_BFD_MONO;
            type  cml-data-types:CML_UINT32_T {
                 range "3..999";
            }
            description "BFD Session Global Transmit Interval";
        } // END of bfdGbTransmitIntvl definition.

        leaf bfdGbRecieveIntvl  {
            if-feature feature-list:HAVE_BFD_MONO;
            type  cml-data-types:CML_UINT32_T {
                 range "3..999";
            }
            description "BFD Session Global Receive Interval";
        } // END of bfdGbRecieveIntvl definition.

        leaf bfdGbHelloMultiplier  {
            if-feature feature-list:HAVE_BFD_MONO;
            type  cml-data-types:CML_UINT32_T {
                 range "3..50";
            }
            description "BFD Session Global Hello Pkt multiplier";
        } // END of bfdGbHelloMultiplier definition.

        leaf isEchoSet  {
            if-feature feature-list:HAVE_BFD_MONO;
            type  cml-data-types:CML_BOOL_T;
            description "BFD Echo enable/disable";
        } // END of isEchoSet definition.

        leaf gtsmTtl  {
            if-feature feature-list:HAVE_BFD_MONO;
            if-feature feature-list:NOT_HAVE_BFD_HW_OFFLOAD;
            type  cml-data-types:CML_UINT8_T {
                 range "1..255";
            }
            default "255";
            description "BFD GTSM Value";
        } // END of gtsmTtl definition.

        leaf bfdStartTime  {
            if-feature feature-list:HAVE_BFD_MONO;
            type  cml-data-types:CML_STRING_T;
            config false;
            description "BFD Start Time";
        } // END of bfdStartTime definition.

        leaf bfdSessionCount  {
            if-feature feature-list:HAVE_BFD_MONO;
            type  cml-data-types:CML_UINT32_T;
            config false;
            description "BFD Sessions Count";
        } // END of bfdSessionCount definition.

        leaf bfdAdminState  {
            if-feature feature-list:HAVE_BFD_MONO;
            type  cml-data-types:CML_OAMBFD_ADMIN_STATE_T;
            config false;
            description "BFD Administrative State";
        } // END of bfdAdminState definition.

        leaf bfdImageType  {
            if-feature feature-list:HAVE_BFD_MONO;
            type  cml-data-types:CML_OAMBFD_IMAGE_TYPE_T;
            config false;
            description "BFD Image Type";
        } // END of bfdImageType definition.

        leaf bfdLocalDisc  {
            if-feature feature-list:HAVE_BFD_MONO;
            type  cml-data-types:CML_UINT32_T;
            config false;
            description "BFD Local Discriminator Value";
        } // END of bfdLocalDisc definition.

        leaf slowTimerIntvl  {
            if-feature feature-list:HAVE_BFD_MONO;
            type  cml-data-types:CML_UINT32_T {
                 range "1000..30000";
            }
            description "BFD Slow timer Interval Value";
        } // END of slowTimerIntvl definition.


        list bfdMultihopKeyChain {
            if-feature feature-list:HAVE_BFD_MONO;
            key "bfdMultihopAddr";
            description
                "BFD multihop peer configs";
            leaf bfdMultihopAddr  {
                type  cml-data-types:CML_IP_ADDR_T;
                description "BFD Multihop Peer Address";
            } // END of bfdMultihopAddr definition.

            leaf bfdAuthType  {
                type  cml-data-types:CML_BFD_MULTIHOP_AUTH_TYPE_T;
                description "BFD Mulithop Session Authentication Type";
            } // END of bfdAuthType definition.

            leaf bfdKeyChain  {
                type  cml-data-types:CML_LINE_T;
                description "BFD Mulithop Session Auth Key Chain";
            } // END of bfdKeyChain definition.

            leaf bfdMultihopKeyId  {
                type  cml-data-types:CML_UINT32_T {
                     range "0..255";
                }
                description "BFD Mulithop Session Auth Key Id";
            } // END of bfdMultihopKeyId definition.

            leaf bfdKeyStr  {
                type  cml-data-types:CML_LINE_T;
                description "BFD Mulithop Session Auth Key String";
            } // END of bfdKeyStr definition.

            leaf bfdTransmitIntvl  {
                type  cml-data-types:CML_UINT32_T {
                     range "50..999";
                }
                description "BFD Multihop Session Transmit Interval";
            } // END of bfdTransmitIntvl definition.

            leaf bfdRecieveIntvl  {
                type  cml-data-types:CML_UINT32_T {
                     range "50..999";
                }
                description "BFD Multihop Session Receive Interval";
            } // END of bfdRecieveIntvl definition.

            leaf bfdHelloMultiplier  {
                type  cml-data-types:CML_UINT32_T {
                     range "3..50";
                }
                description "BFD Multihop Session Hello Multiplier";
            } // END of bfdHelloMultiplier definition.

        } // End of bfdMultihopKeyChain-list
    } // END of bfd-container definition.
    } // END of bfd-container definition.

    grouping  oamMpls-grouping {
    description
        "Oam mpls configs";
    container oamMpls {
        if-feature feature-list:HAVE_MPLS_OAM;
        description
            "Oam mpls configs";
        leaf mplsPingReq  {
            type  cml-data-types:CML_BOOL_T;
            description "OAM MPLS Ping request";
        } // END of mplsPingReq definition.

        leaf mplsPingReply  {
            type  cml-data-types:CML_BOOL_T;
            description "OAM MPLS Ping reply";
        } // END of mplsPingReply definition.

    } // END of oamMpls-container definition.
    } // END of oamMpls-container definition.


}
