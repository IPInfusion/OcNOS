/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-zebos-vlan.yang
*
*/

submodule ipi-zebos-vlan {

    belongs-to  ipi-zebos { prefix ipi-zebos; }

    import cml-data-types {
        prefix cml-data-types;
    }

    import feature-list {
        prefix feature-list;
    }

    include ipi-zebos-interface;
    organization
        "IP Infusion Inc.";

    contact
        "Address: 3965 Freedom Circle, Suite 200, Santa Clara, CA 95054
        Phone: +1 408-400-1900
        E-mail: support@ipinfusion.com
        Web: http://www.ipinfusion.com/";

    description
        "vlan configuration";


    revision "2019-04-08" {
        description " Support Vlan XC.";
        reference "";
    }

    revision "2018-06-21" {
        description " Initial Version.";
        reference "";
    }



    grouping vlan-grouping {
    description
        "vlan";
        list vlan {
            key "vlanId";
            description
                "vlan";
            leaf cvlanName  {
                type  cml-data-types:CML_STRING_T;
                description "";
            } // END of cvlanName definition.

            leaf svlanName  {
                type  cml-data-types:CML_STRING_T;
                description "";
            } // END of svlanName definition.

            leaf vlanId  {
                type  cml-data-types:CML_RANGE_T;
                description "";
            } // END of vlanId definition.

            leaf cvlanType  {
                type  cml-data-types:CML_VLAN_TYPE_CUSTOMER_T;
                description "";
            } // END of cvlanType definition.

            leaf svlanType  {
                type  cml-data-types:CML_VLAN_TYPE_SERVICE_T;
                description "";
            } // END of svlanType definition.

            leaf pvlanConfigured  {
                if-feature feature-list:HAVE_PVLAN;
                type  cml-data-types:CML_INT32_T;
                config false;
                description "";
            } // END of pvlanConfigured definition.

            leaf evId  {
                type  cml-data-types:CML_INT8_T;
                config false;
                description "";
            } // END of evId definition.

            leaf ovId  {
                type  cml-data-types:CML_INT8_T;
                config false;
                description "";
            } // END of ovId definition.

            leaf pvlanType  {
                type  cml-data-types:CML_PVLAN_TYPE_T;
                description "";
            } // END of pvlanType definition.

            leaf associateAddRemove  {
                type  cml-data-types:CML_PVLAN_ADD_REMOVE_TYPE_T;
                description "";
            } // END of associateAddRemove definition.

            leaf associateVid  {
                type  cml-data-types:CML_RANGE_T;
                description "";
            } // END of associateVid definition.

            leaf ceVlanFlag  {
                type  cml-data-types:CML_CE_SVLAN_T;
                description "";
            } // END of ceVlanFlag definition.

            leaf preserveCos  {
                type  cml-data-types:CML_OVC_TYPE_T;
                description "";
            } // END of preserveCos definition.

            leaf preserveVlanid  {
                type  cml-data-types:CML_OVC_TYPE_T;
                description "";
            } // END of preserveVlanid definition.

            leaf pcpDscpFlag  {
                if-feature feature-list:HAVE_PROVIDER_BRIDGE;
                type  cml-data-types:CML_INT8_T;
                config false;
                description "";
            } // END of pcpDscpFlag definition.

            leaf cvlanState  {
                type  cml-data-types:CML_VLANSTATE_T;
                description "";
            } // END of cvlanState definition.

            leaf svlanState  {
                type  cml-data-types:CML_VLANSTATE_T;
                description "";
            } // END of svlanState definition.

            leaf cvlanMtuVal  {
                type  cml-data-types:CML_UINT32_T;
                default "1500";
                description "";
            } // END of cvlanMtuVal definition.

            leaf svlanMtuVal  {
                type  cml-data-types:CML_UINT32_T;
                default "1500";
                description "";
            } // END of svlanMtuVal definition.

            leaf instance  {
                type  cml-data-types:CML_INT32_T;
                config false;
                description "";
            } // END of instance definition.

            leaf primaryVid  {
                if-feature feature-list:HAVE_G8032V2;
                if-feature feature-list:HAVE_G8032;
                type  cml-data-types:CML_UINT8_T;
                config false;
                description "";
            } // END of primaryVid definition.

            leaf erpsBitmask  {
                if-feature feature-list:NSM_VLAN_ERPS_CONF;
                type  cml-data-types:CML_UINT8_T;
                config false;
                description "";
            } // END of erpsBitmask definition.

            leaf operStatus  {
                type  cml-data-types:CML_VLAN_OPERSTATUS_T;
                config false;
                description "";
            } // END of operStatus definition.

            leaf bindStatus  {
                if-feature feature-list:HAVE_NVO;
                type  cml-data-types:CML_UINT8_T;
                config false;
                description "";
            } // END of bindStatus definition.

            leaf macLearnDisable  {
                type  cml-data-types:CML_INT32_T;
                default "1";
                description "";
            } // END of macLearnDisable definition.

            leaf macLimitMax  {
                if-feature feature-list:HAVE_CUSTOM_CLI_STYLE;
                type  cml-data-types:CML_INT32_T {
                     range "5..32768";
                }
                description "";
            } // END of macLimitMax definition.

            leaf isAllowed  {
                type  cml-data-types:CML_ALLOWED_FORBIDDEN_T;
                default "forbidden";
                description "";
            } // END of isAllowed definition.

            leaf multicast  {
                type  cml-data-types:CML_BOOL_T;
                default false;
                description "";
            } // END of multicast definition.

            leaf addFlag  {
                type  cml-data-types:CML_ADD_REMOVE_T;
                default "remove";
                description "";
            } // END of addFlag definition.

            leaf ifName  {
                type  cml-data-types:CML_STRING_T;
                description "";
            } // END of ifName definition.

            leaf vlanRuntimeName  {
                type  cml-data-types:CML_STRING_T;
                config false;
                description "";
            } // END of vlanRuntimeName definition.

            leaf taggedInterface  {
                type  cml-data-types:CML_LINE_T;
                config false;
                description "";
            } // END of taggedInterface definition.

        } // End of vlan-list
    } // END of vlan-grouping definition.


    grouping nsmEvcInfo-grouping {
    description
        "nsm evc vlan information";
        list nsmEvcInfo {
            key "evcId";
            description
                "nsm evc vlan information";
            leaf evcId  {
                type  cml-data-types:CML_STRING_T;
                description "";
            } // END of evcId definition.

            leaf evcMaxUni  {
                type  cml-data-types:CML_UINT32_T;
                description "";
            } // END of evcMaxUni definition.

        } // End of nsmEvcInfo-list
    } // END of nsmEvcInfo-grouping definition.


    grouping nsmOvcInfo-grouping {
    description
        "nsm ovc vlan information";
        list nsmOvcInfo {
            key "svlanId";
            description
                "nsm ovc vlan information";
            leaf svlanId  {
                type  cml-data-types:CML_UINT32_T;
                description "";
            } // END of svlanId definition.

            leaf ovcId  {
                type  cml-data-types:CML_STRING_T;
                description "";
            } // END of ovcId definition.

            leaf oepId  {
                type  cml-data-types:CML_STRING_T;
                description "";
            } // END of oepId definition.

            leaf preserveVlan  {
                type  cml-data-types:CML_INT8_T;
                config false;
                description "";
            } // END of preserveVlan definition.

            leaf num_ovcs  {
                type  cml-data-types:CML_INT16_T;
                config false;
                description "";
            } // END of num_ovcs definition.

            leaf ovcMaxUni  {
                type  cml-data-types:CML_UINT32_T;
                description "";
            } // END of ovcMaxUni definition.

        } // End of nsmOvcInfo-list
    } // END of nsmOvcInfo-grouping definition.


    grouping ovcVlanType-grouping {
    description
        "nsm ovc vlan type information";
        list ovcVlanType {
            key "ovcInfo";
            description
                "nsm ovc vlan type information";
            leaf ovcInfo  {
                type  cml-data-types:CML_STRING_T;
                description "";
            } // END of ovcInfo definition.

            leaf ovcVlanType  {
                type  cml-data-types:CML_CE_SVLAN_T;
                description "";
            } // END of ovcVlanType definition.

            leaf-list TypeCos  {
                type  cml-data-types:CML_OVC_TYPE_T;
                description "";
            } // END of TypeCos definition.

            leaf-list TypeVlanid  {
                type  cml-data-types:CML_OVC_TYPE_T;
                description "";
            } // END of TypeVlanid definition.

        } // End of ovcVlanType-list
    } // END of ovcVlanType-grouping definition.


    grouping nsmVlanAccess-grouping {
    description
        "nsmVlanAccess";
        list nsmVlanAccess {
            key "accessMapName";
            description
                "nsmVlanAccess";
            leaf accessMapName  {
                type  cml-data-types:CML_STRING_T {
                    length "1..32";
                }
                description "";
            } // END of accessMapName definition.

            leaf aclCount  {
                type  cml-data-types:CML_COUNTER32_T;
                config false;
                description "";
            } // END of aclCount definition.

            leaf attached  {
                type  cml-data-types:CML_INT32_T;
                config false;
                description "";
            } // END of attached definition.

            leaf ruleCnt  {
                type  cml-data-types:CML_COUNTER32_T;
                config false;
                description "";
            } // END of ruleCnt definition.

            leaf statisticsEntry  {
                type  cml-data-types:CML_INT32_T;
                description "";
            } // END of statisticsEntry definition.

            leaf sequenceNum  {
                type  cml-data-types:CML_UINT32_T {
                     range "1..4294967295";
                }
                mandatory true;
                description "";
            } // END of sequenceNum definition.

            leaf aclType  {
                type  cml-data-types:CML_ACLTYPE_T;
                description "";
            } // END of aclType definition.

            leaf accessGroup  {
                type  cml-data-types:CML_STRING_T;
                description "";
            } // END of accessGroup definition.

            leaf vlanIdCount  {
                type  cml-data-types:CML_STRING_T;
                description "";
            } // END of vlanIdCount definition.

            leaf actionType  {
                type  cml-data-types:CML_ACTIONTYPE_T;
                description "";
            } // END of actionType definition.

            leaf ifName  {
                type  cml-data-types:CML_STRING_T;
                description "";
            } // END of ifName definition.

            leaf vlanAccessEnd  {
                type  cml-data-types:CML_INT32_T;
                description "";
            } // END of vlanAccessEnd definition.

        } // End of nsmVlanAccess-list
    } // END of nsmVlanAccess-grouping definition.


    grouping vlanClassifierRule-grouping {
    description
        "vlanClassifierRule";
        list vlanClassifierRule {
            key "ruleId";
            description
                "vlanClassifierRule";
            leaf type  {
                type  cml-data-types:CML_UINT32_T;
                description "";
            } // END of type definition.

            leaf ruleId  {
                type  cml-data-types:CML_UINT32_T {
                     range "1..256";
                }
                description "";
            } // END of ruleId definition.

            leaf macAddr  {
                type  cml-data-types:CML_STRING_T;
                description "";
            } // END of macAddr definition.

            leaf ipv4Addr  {
                type  cml-data-types:CML_IPV4_PREFIX_T;
                description "";
            } // END of ipv4Addr definition.

            leaf etherType  {
                type  cml-data-types:CML_ETHERTYPE_T;
                description "";
            } // END of etherType definition.

        } // End of vlanClassifierRule-list
    } // END of vlanClassifierRule-grouping definition.


    grouping vlanClassifierGroup-grouping {
    description
        "vlanClassifierGroup";
        list vlanClassifierGroup {
            key "groupId";
            description
                "vlanClassifierGroup";
            leaf groupId  {
                type  cml-data-types:CML_UINT32_T {
                     range "1..16";
                }
                description "";
            } // END of groupId definition.


            list vlanClassifierGroupruleId {
                key "ruleId";
                description
                    "vlanClassifierGroupruleId";
                leaf ruleId  {
                    type  cml-data-types:CML_UINT32_T {
                         range "1..256";
                    }
                    description "";
                } // END of ruleId definition.

                leaf bind  {
                    type  cml-data-types:CML_BIND_T;
                    description "";
                } // END of bind definition.

            } // End of vlanClassifierGroupruleId-list

            list vlanClassifierInterface {
                key "ifName";
                description
                    "vlanClassifierInterface";
                leaf ifName  {
                    type  cml-data-types:CML_STRING_T;
                    description "";
                } // END of ifName definition.

                leaf groupId  {
                    type  cml-data-types:CML_UINT32_T {
                         range "1..16";
                    }
                    description "";
                } // END of groupId definition.

                leaf vlanId  {
                    type  cml-data-types:CML_STRING_T;
                    description "";
                } // END of vlanId definition.

            } // End of vlanClassifierInterface-list
        } // End of vlanClassifierGroup-list
    } // END of vlanClassifierGroup-grouping definition.


    grouping vlanDtag-grouping {
    description
        "vlanDtag";
        list vlanDtag {
            if-feature feature-list:HAVE_SUBSCRIBER_INTERFACE;
            key "dtagCli";
            description
                "vlanDtag";
            leaf dtagCli  {
                type  cml-data-types:CML_STRING_T;
                description "Outer-VLAN identifier and inner-VLAN identifier in the format 100.200, where 100 is the outer tag and 200 is the inner tag";
            } // END of dtagCli definition.

            leaf stateFlag  {
                type  cml-data-types:CML_VLANSTATE_T;
                mandatory true;
                description "Enable/Suspend double tagging";
            } // END of stateFlag definition.

            leaf subscriberFlag  {
                type  cml-data-types:CML_BOOL_T;
                mandatory true;
                description "DTAG on subscriber interface";
            } // END of subscriberFlag definition.

        } // End of vlanDtag-list
    } // END of vlanDtag-grouping definition.

    grouping  debugConfigMode-grouping {
    description
        "debugConfigMode";
    container debugConfigMode {
        description
            "debugConfigMode";
        leaf configMode  {
            type  cml-data-types:CML_NSM_CONFIG_MODE_T;
            description "";
        } // END of configMode definition.

        leaf configPkt  {
            if-feature feature-list:HAVE_L2;
            type  cml-data-types:CML_NSM_PKT_MGR_T;
            description "";
        } // END of configPkt definition.

    } // END of debugConfigMode-container definition.
    } // END of debugConfigMode-container definition.

    grouping  debugExecMode-grouping {
    description
        "debugExecMode";
    container debugExecMode {
        description
            "debugExecMode";
        leaf ExecMode  {
            type  cml-data-types:CML_NSM_EXEC_MODE_T;
            description "";
        } // END of ExecMode definition.

        leaf ExecPkt  {
            if-feature feature-list:HAVE_L2;
            type  cml-data-types:CML_NSM_PKT_MGR_T;
            description "";
        } // END of ExecPkt definition.

        leaf execStats  {
            type  cml-data-types:CML_BOOL_T;
            description "";
        } // END of execStats definition.

        leaf execErrorStats  {
            type  cml-data-types:CML_EXEC_MSTP_T;
            description "";
        } // END of execErrorStats definition.

        leaf execEnable  {
            type  cml-data-types:CML_ENABLE_DISABLE_T;
            description "";
        } // END of execEnable definition.

    } // END of debugExecMode-container definition.
    } // END of debugExecMode-container definition.


}
