/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-imi.yang
*
*/

submodule zebos-imi {

    belongs-to  zebos { prefix zebos; }

    import cml_data_types {
        prefix cml_data_types;
    }

    import feature_list {
        prefix feature_list;
    }

    organization
        "IP Infusion Inc.";

    contact
        "Address: 3965 Freedom Circle, Suite 200, Santa Clara, CA 95054
        Phone: +1 408-400-1900
        E-mail: support@ipinfusion.com
        Web: http://www.ipinfusion.com/";

    description
        "imi global configs";


    revision "2018-06-21" {
        description " Initial Version.";
        reference "";
    }

    grouping execTimeout {
        description
            "line mode configs for console or vty.";
        leaf min  {
            type  cml_data_types:CML_UINT32_T {
                 range "0..35791";
            }
            default "10";
            description "";
        } // END of min definition.

        leaf sec  {
            type  cml_data_types:CML_UINT32_T {
                 range "0..2147483";
            }
            default "0";
            description "";
        } // END of sec definition.

        leaf login  {
            type  cml_data_types:CML_BOOL_T;
            description "";
        } // END of login definition.

        leaf privLevel  {
            type  cml_data_types:CML_UINT8_T {
                 range "1..16";
            }
            description "";
        } // END of privLevel definition.

        leaf loginLocal  {
            type  cml_data_types:CML_BOOL_T;
            description "";
        } // END of loginLocal definition.

        leaf historyMax  {
            type  cml_data_types:CML_UINT32_T {
                 range "0..2147483647";
            }
            description "";
        } // END of historyMax definition.

    } // END of execTimeout definition.

    grouping  hostname-grouping {
    description
        "Set system's network name";
    container hostname {
        description
            "Set system's network name";
        leaf hostname  {
            type  cml_data_types:CML_STRING_T {
                length "1..63";
            }
            description "";
        } // END of hostname definition.

    } // END of hostname-container definition.
    } // END of hostname-container definition.

    grouping  webUser-grouping {
    description
        "web user login credentials";
    container webUser {
        description
            "web user login credentials";
        leaf loginName  {
            type  cml_data_types:CML_STRING_T {
                length "0..255";
            }
            description "";
        } // END of loginName definition.

        leaf loginPasswd  {
            type  cml_data_types:CML_STRING_T {
                length "0..255";
            }
            description "";
        } // END of loginPasswd definition.

    } // END of webUser-container definition.
    } // END of webUser-container definition.

    grouping  loggingCli-grouping {
    description
        "Enable flag to log ZebOS command lines.";
    container loggingCli {
        description
            "Enable flag to log ZebOS command lines.";
        leaf enableLoggingCli  {
            if-feature feature_list:HAVE_SYSLOG;
            type  cml_data_types:CML_BOOL_T;
            description "Logging control";
        } // END of enableLoggingCli definition.

    } // END of loggingCli-container definition.
    } // END of loggingCli-container definition.

    grouping  memInfo-grouping {
    description
        "Memory Info enable";
    container memInfo {
        description
            "Memory Info enable";
        leaf memInfoIMI  {
            type  cml_data_types:CML_BOOL_T;
            description "";
        } // END of memInfoIMI definition.

    } // END of memInfo-container definition.
    } // END of memInfo-container definition.


}
