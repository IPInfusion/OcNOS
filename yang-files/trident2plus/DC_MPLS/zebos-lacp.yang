/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-lacp.yang
*
*/

submodule zebos-lacp {

    belongs-to  zebos { prefix zebos; }

    import cml_data_types {
        prefix cml_data_types;
    }

    organization
        "IP Infusion Inc.";

    contact
        "Address: 3965 Freedom Circle, Suite 200, Santa Clara, CA 95054
        Phone: +1 408-400-1900
        E-mail: support@ipinfusion.com
        Web: http://www.ipinfusion.com/";

    description
        "Layer-2 lacp  configurations";


    revision "2017-10-11" {
        description "added swithport interface dependence.";
    }

    revision "2017-10-03" {
        description "modified the trigger to update po and mlag interface.";
    }

    revision "2017-09-14" {
        description "modified the trigger to update lacp_nsmlacpInterface.";
    }

    revision "2017-06-20" {
        description "added trigger to update lacp_nsmlacpInterface table.";
    }

    revision "2017-03-23" {
        description "presence-container implementation.";
    }

    revision "2017-03-21" {
        description "Updated dependecy with interface module.";
    }

    revision "2015-10-20" {
        description "Initial version of datamodel.";
    }


    grouping  nsmlacpInterface-grouping {
    container nsmlacpInterface {
        presence "yes";
        description
            "NSM LACP interface related operations";
        leaf channelGroup  {
            type  cml_data_types:CML_UINT16_T {
                 range "1..16383";
            }
            mandatory true;
            description "";
        } // END of channelGroup definition.

        leaf modeOperation  {
            type  cml_data_types:CML_LACP_MODE_T;
            mandatory true;
            description "";
        } // END of modeOperation definition.

    } // END of nsmlacpInterface-container definition.
    } // END of nsmlacpInterface-container definition.

    grouping  nsmportInterface-grouping {
    container nsmportInterface {
        presence "yes";
        description
            "NSM LACP interface related operations";
        leaf static-channel-group  {
            type  cml_data_types:CML_UINT16_T {
                 range "1..12";
            }
            mandatory true;
            description "";
        } // END of static-channel-group definition.

    } // END of nsmportInterface-container definition.
    } // END of nsmportInterface-container definition.


}
