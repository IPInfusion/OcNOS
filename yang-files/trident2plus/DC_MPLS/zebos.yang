/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos.yang
*
*/

module zebos {

    namespace   "http://www.ipinfusion.com/CMLSchema/zebos";

    prefix "zebos";

    import cml_data_types {
        prefix cml_data_types;
    }

    import feature_list {
        prefix feature_list;
    }

    include zebos-vr;
    include zebos-vrf;
    include zebos-interface;
    include zebos-vlan;
    include zebos-switchportinterface;
    include zebos-bridge;
    include zebos-mstp;
    include zebos-lacp;
    include zebos-lag;
    include zebos-lldpv2;
    include zebos-rib;
    include zebos-ospf;
    include zebos-ospfv3;
    include zebos-bgp;
    include zebos-oambfd;
    include zebos-vrrp;
    include zebos-plist;
    include zebos-isis;
    include zebos-keychain;
    include zebos-pim;
    include zebos-pim4;
    include zebos-pim6;
    include zebos-tfo;
    include zebos-syslog;
    include zebos-snmp;
    include zebos-featuredhcp;
    include zebos-radius;
    include zebos-tacacs;
    include zebos-ldap;
    include zebos-usermgmt;
    include zebos-ssh;
    include zebos-telnet;
    include zebos-ntp;
    include zebos-aaa;
    include zebos-dhcpr;
    include zebos-dns;
    include zebos-dhcpc;
    include zebos-sflow;
    include zebos-libsyslog;
    include zebos-license;
    include zebos-pserv;
    include zebos-mrib4;
    include zebos-mrib6;
    include zebos-igmp;
    include zebos-igmpsnooping;
    include zebos-mld;
    include zebos-routemap;
    include zebos-libsnmp;
    include zebos-ldp;
    include zebos-rsvp;
    include zebos-mpls;
    include zebos-vpls;
    include zebos-mplsbfd;
    include zebos-mcec;
    include zebos-mlag;
    include zebos-hqos;
    include zebos-cmm;
    include zebos-auth;
    include zebos-rip;
    include zebos-acl;
    include zebos-aclinterface;
    include zebos-nsmsnmp;
    include zebos-dhcpsnooping;
    include zebos-ras;
    include zebos-rpf;
    include zebos-linktrack;
    include zebos-pmirror;
    include zebos-hsl;
    include zebos-authradius;
    organization
        "IP Infusion Inc.";

    contact
        "Address: 3965 Freedom Circle, Suite 200, Santa Clara, CA 95054
        Phone: +1 408-400-1900
        E-mail: support@ipinfusion.com
        Web: http://www.ipinfusion.com/";

    description
        "ZebOS Managed Object";


    revision "2017-10-09" {
        description "changed heirarchy object for vpls fib.";
    }

    revision "2017-10-05" {
        description "sequence changed for staticfdb objectlist fo rreplace operation.";
    }

    revision "2017-10-04" {
        description "helpstring change for mac-address-table commands.";
    }

    revision "2017-10-03" {
        description "added if-feature support for bridge.";
    }

    revision "2017-09-27" {
        description "added flag for clear arp command.";
    }

    revision "2017-09-25" {
        description "helstring added for vlan classifier.";
    }

    revision "2017-09-21" {
        description "JIRA-19164.";
    }

    revision "2017-09-19" {
        description "Fix for JIRA-18634 and JIRA-19057.";
    }

    revision "2017-09-18" {
        description "Interface module feature flags updated.";
    }

    revision "2017-09-15" {
        description "modified the mac-address clear commands.";
    }

    revision "2017-09-14" {
        description "changed the macro for interface get api and modified the custome trigger for lacp interface update.";
    }

    revision "2017-09-13" {
        description "custome trigger to delete vlan interface when bridge is deleted.";
    }

    revision "2017-09-07" {
        description "Added dependentObject for mstpPort.";
    }

    revision "2017-09-05" {
        description "JIRA-14201, JIRA-13483.";
    }

    revision "2017-09-03" {
        description "Added vlan in IPV6 access-lists.";
    }

    revision "2017-08-29" {
        description "Added vlan in IPV4 access-lists.";
    }

    revision "2017-08-28" {
        description "UT fixes for SNMP.";
    }

    revision "2017-08-23" {
        description "JIRA-13340.";
    }

    revision "2017-08-22" {
        description "JIRA-18348.";
    }

    revision "2017-08-11" {
        description "Changes done for ARP-ND cache disable..";
    }

    revision "2017-08-10" {
        description "SNMP chnages done for JIRA-18238.";
    }

    revision "2017-08-01" {
        description "Changes done for Static MAC only route..";
    }

    revision "2017-07-27" {
        description "Added description to attributes.";
    }

    revision "2017-07-26" {
        description "Added support for more than one format of MAC address.";
    }

    revision "2017-07-18" {
        description "added clear command for bridge mstp and vlan.";
    }

    revision "2017-07-11" {
        description "Added FORCE_SET flag for mtu,speed,storm-control..";
    }

    revision "2017-07-10" {
        description "Added the multival support fro hardware-profile filter.";
    }

    revision "2017-07-05" {
        description "Changes done for hold timer for MAC removal.";
    }

    revision "2017-07-03" {
        description "Port Mirroring feature support added.";
    }

    revision "2017-06-30" {
        description "Changes done for vxlan/evpn statistics as JIRA-16129.";
    }

    revision "2017-06-23" {
        description "l2protocol container is changed to objectlist,added trigger to update lacp_nsmlacpInterface table.";
    }

    revision "2017-06-20" {
        description "porting snmp and syslog datamodel changes  from LINX.";
    }

    revision "2017-06-14" {
        description "porting tech support from LINX and Uplifted the HQOS changes from linx branch.";
    }

    revision "2017-06-13" {
        description "port pservd and sflow code changes from LINX.";
    }

    revision "2017-06-12" {
        description "fix for cvlan.";
    }

    revision "2017-06-10" {
        description "Added restriction to allow only for admin role.";
    }

    revision "2017-06-08" {
        description "Uplifted the changes from linx branch.";
    }

    revision "2017-06-07" {
        description "Added the support of storm-control configuration with absolute value.";
    }

    revision "2017-06-06" {
        description "opeation type changed for switchport mode command.";
    }

    revision "2017-06-02" {
        description "Unlock Timeout Attribute.";
    }

    revision "2017-06-01" {
        description "removed CML_INITIALIZED flag from vlanId.";
    }

    revision "2017-05-29" {
        description "Data model chnages done for JIRA-16075.";
    }

    revision "2017-05-24" {
        description "Data model chnages done for JIRA-15684.";
    }

    revision "2017-05-23" {
        description "corrected the staticMac parent hierarchy.";
    }

    revision "2017-05-16" {
        description "Vxlan Data model chnages done for JIRA-15643.";
    }

    revision "2017-05-11" {
        description "Updated notif for cleartext password.";
    }

    revision "2017-04-27" {
        description "vlan classifier objectlist changed.";
    }

    revision "2017-04-18" {
        description "data model corrections as per backend struct.";
    }

    revision "2017-04-11" {
        description "changes for JIRA-14761 vxlan data model.";
    }

    revision "2017-04-07" {
        description "changes for mac and arp learning disable for vxlan.";
    }

    revision "2017-04-06" {
        description "changes for JIRA-14587 vxlan data model.";
    }

    revision "2017-03-28" {
        description "removed unused runtime attribute in mstp,made ifName as RDN in staticMac in bridge.";
    }

    revision "2017-03-25" {
        description "Corrected LAG hierarchy.";
    }

    revision "2017-03-24" {
        description "Added switchport allowed ethertype support in interface module.";
    }

    revision "2017-03-21" {
        description "Updated dependecy with interface module in lacp.";
    }

    revision "2017-03-15" {
        description "Adding bfdHwMultihopVal attribute.";
    }

    revision "2017-03-09" {
        description "Changes for mrib datamodel for jira-13147 and changes for acl datamodel.";
    }

    revision "2017-03-05" {
        description "added support for deletion of vlan type.";
    }

    revision "2017-03-03" {
        description "vlaninterface datamodel name has been changed to switchportInterface.";
    }

    revision "2017-02-27" {
        description "added dependentObject for brigdePort.";
    }

    revision "2017-02-25" {
        description "added support for show cml running-config.";
    }

    revision "2017-02-24" {
        description "cliflag added in vlanAccess objectlist.";
    }

    revision "2017-02-23" {
        description "hal statistics attribute added in ifStat container.";
    }

    revision "2017-02-22" {
        description "added bridgeId in bridgePort table, optimising ACL datamodel.";
    }

    revision "2017-02-21" {
        description "private-vlan changes.";
    }

    revision "2017-02-20" {
        description "added run-time attrs in ISIS datamodel.";
    }

    revision "2017-02-14" {
        description "adding missing flag for cli generation.";
    }

    revision "2017-02-13" {
        description "Add the load balance commands.";
    }

    revision "2017-02-11" {
        description "Rip datamodel modifeid.";
    }

    revision "2017-02-10" {
        description "disabling trill bridge creation command.";
    }

    revision "2017-02-08" {
        description "Defect fix for Mcast datamodel.";
    }

    revision "2017-02-07" {
        description "mapped mstp datamodel strcuture with mstpd structure.";
    }

    revision "2017-02-03" {
        description "changes for Mcast datamodel.";
    }

    revision "2017-02-02" {
        description "Defect fixes for isis,pim datamodel.";
    }

    revision "2017-01-31" {
        description "Removed extra attributes from interface datamodel.";
    }

    revision "2017-01-30" {
        description "datamodel adding for HQOS.";
    }

    revision "2017-01-28" {
        description "adding flag for default bridge objectlist in mstp.";
    }

    revision "2017-01-27" {
        description "changes for Debug command.";
    }

    revision "2017-01-25" {
        description "Defect fix in Mcast datamodel.";
    }

    revision "2017-01-23" {
        description "Defect fix in OSPF datamodel.";
    }

    revision "2017-01-20" {
        description "mapped interface datamodel attribute with interface structure.";
    }

    revision "2017-01-19" {
        description "Defect fixes in VRRP datamodel.";
    }

    revision "2017-01-16" {
        description "Ported LDP and RSVP changes from XP-master.";
    }

    revision "2017-01-12" {
        description "auto-populate of default bridge disabled.";
    }

    revision "2017-01-11" {
        description "default bridge command disabled.";
    }

    revision "2017-01-10" {
        description "Defect fixes in OSPF and ISIS datamodel.";
    }

    revision "2017-01-04" {
        description "Changes done to add implicit delete tags.";
    }

    revision "2016-12-30" {
        description "Changes ported from XP-master for vr and vrf.";
    }

    revision "2016-12-29" {
        description "Added support for Routemap SMI auto generation.";
    }

    revision "2016-12-28" {
        description "Added support for Vxlan commands in cmlsh..";
    }

    revision "2016-12-26" {
        description "Added support for LLDPv2 get API.";
    }

    revision "2016-12-22" {
        description "Added support for OSPF SMI auto generation.";
    }

    revision "2016-12-17" {
        description "ISIS redistribute CLI's are changed as per backend CLI's.";
    }

    revision "2016-10-28" {
        description "Top level module includes all ZebOS managed objects.";
    }

    revision "2016-01-29" {
        description "Changes done for ospf getapi and snmp tags.";
    }


    uses lacpSystemPriority-grouping;
    uses lacpdebug-grouping;
    uses oamMpls-grouping;
    uses VrrpDebug-grouping;
    uses tfo-grouping;
    uses hostpsyslog-grouping;
    uses snmp-grouping;
    uses radius-grouping;
    uses tacacs-grouping;
    uses ldap-grouping;
    uses userDebug-grouping;
    uses debugSSHconfig-grouping;
    uses debugTELNETconfig-grouping;
    uses ntp-grouping;
    uses aaa-grouping;
    uses dhcprelay-grouping;
    uses dhcprelay6-grouping;
    uses dns-grouping;
    uses sflow-grouping;
    uses debugsflow-grouping;
    uses ACLsFlow-grouping;
    uses log-grouping;
    uses pservd-grouping;
    uses igmpConfig-grouping;
    uses snmpVrfName-grouping;
    uses ldpMaster-grouping;
    uses rsvpMaster-grouping;
    uses mcecMaster-grouping;
    uses nsmMlag-grouping;
    uses cmmGlobals-grouping;
    uses cmmDmm-grouping;
    uses ddmFalseAlarm-grouping;
    uses cmmCpuInfo-grouping;
    uses cmmSysRamTable-grouping;
    uses cmmStackUnitUtilTable-grouping;
    uses cmmSysLedTable-grouping;
    uses cmmSysSwModuleTable-grouping;
    uses cmmAlarmVariable-grouping;
    uses debugdot1x-grouping;
    uses nsmsnmp-grouping;
    uses debugDhcpSnooping-grouping;
    uses logginghsl-grouping;
    uses vr-grouping;
    uses lldpMaster-grouping;
    uses ospfMaster-grouping;
    uses hashTableSize-grouping;
    uses bfdSession-grouping;
    uses confModeDebug-grouping;
    uses execModeDebug-grouping;
    uses prefixMaster-grouping;
    uses prefixMaster6-grouping;
    uses Hostpdradius-grouping;
    uses usermgmt-grouping;
    uses sshVrfInstance-grouping;
    uses telnetVrfInstance-grouping;
    uses dhcprelayinterface-grouping;
    uses dhcp6nterface-grouping;
    uses logginglevel-grouping;
    uses cmmStackUnitTable-grouping;
    uses cmmSysPowerSupplyTable-grouping;
    uses cmmSysFanTable-grouping;
    uses cmmSysTemperatureTable-grouping;
    uses cmmSysChipTemperatureTable-grouping;
    uses dhcpSnooping-grouping;
    uses defaultbridgedhcpsnooping-grouping;
    uses dhcp_interface-grouping;
    uses interfaceTrack-grouping;

    rpc interface-clear-arp-cache {
        if-feature feature_list:HAVE_L3;
        input  {
            leaf vrId  {
                type cml_data_types:CML_UINT32_T;
                mandatory true;
            }
        }
    }

    rpc interface-clear-ipv6-neighbors {
        if-feature feature_list:HAVE_L3;
        if-feature feature_list:HAVE_IPV6;
        input  {
            leaf vrId  {
                type cml_data_types:CML_UINT32_T;
                mandatory true;
            }
        }
    }

    rpc vlan-clearvlanAccessList {
        input  {
            leaf vrId  {
                type cml_data_types:CML_UINT32_T;
                mandatory true;
            }
            leaf accessMapName  {
                type cml_data_types:CML_STRING_T;
                mandatory true;
            }
        }
    }

    rpc bridge-clearcvlan {
        input  {
            leaf macType  {
                type cml_data_types:CML_UINT8_T;
                mandatory true;
            }
            leaf bridgeId  {
                type cml_data_types:CML_STRING_T;
                mandatory true;
            }
            leaf cvlanId  {
                type cml_data_types:CML_INT32_T;
                mandatory true;
            }
            leaf sVlanId  {
                type cml_data_types:CML_INT32_T;
                mandatory true;
            }
        }
    }

    rpc bridge-cleardynamiccvlan {
        input  {
            leaf bridgeId  {
                type cml_data_types:CML_STRING_T;
                mandatory true;
            }
            leaf cvlanId  {
                type cml_data_types:CML_INT32_T;
                mandatory true;
            }
            leaf sVlanId  {
                type cml_data_types:CML_INT32_T;
                mandatory true;
            }
        }
    }

    rpc bridge-clearFbbVlanPort {
        input  {
            leaf macType  {
                type cml_data_types:CML_UINT8_T;
                mandatory true;
            }
            leaf macAddr  {
                type cml_data_types:CML_STRING_T;
                mandatory true;
            }
            leaf ifName  {
                type cml_data_types:CML_STRING_T;
                mandatory true;
            }
            leaf vlanId  {
                type cml_data_types:CML_INT32_T;
                mandatory true;
            }
            leaf bridgeId  {
                type cml_data_types:CML_STRING_T;
                mandatory true;
            }
        }
    }

    rpc bridge-clearvxlan {
        input  {
            leaf vrId  {
                type cml_data_types:CML_UINT32_T;
                mandatory true;
            }
            leaf vxlan  {
                type cml_data_types:CML_BOOL_T;
                mandatory true;
            }
        }
    }

    rpc bridge-clearbridge {
        input  {
            leaf vrId  {
                type cml_data_types:CML_UINT32_T;
                mandatory true;
            }
            leaf bridgeId  {
                type cml_data_types:CML_STRING_T;
                mandatory true;
            }
        }
    }

    rpc bridge-clearDynamicMacAddr {
        input  {
            leaf macAddr  {
                type cml_data_types:CML_STRING_T;
                mandatory true;
            }
            leaf ifName  {
                type cml_data_types:CML_STRING_T;
                mandatory true;
            }
            leaf instanceId  {
                type cml_data_types:CML_INT32_T;
                mandatory true;
            }
            leaf vlanId  {
                type cml_data_types:CML_INT32_T;
                mandatory true;
            }
            leaf bridgeId  {
                type cml_data_types:CML_STRING_T;
                mandatory true;
            }
        }
    }

    rpc bridge-clearnsmipc {
        if-feature feature_list:HAVE_ASYNC;
        input  {
            leaf vrId  {
                type cml_data_types:CML_UINT32_T;
                mandatory true;
            }
        }
    }

    rpc mstp-clearDetectedProtocols {
        input  {
            leaf vrId  {
                type cml_data_types:CML_UINT32_T;
                mandatory true;
            }
            leaf bridgeId  {
                type cml_data_types:CML_STRING_T;
                mandatory true;
            }
        }
    }

    rpc mstp-clearDetectedProtocolsinterface {
        input  {
            leaf vrId  {
                type cml_data_types:CML_UINT32_T;
                mandatory true;
            }
            leaf interface  {
                type cml_data_types:CML_STRING_T;
                mandatory true;
            }
        }
    }

    rpc mstp-clear-spanning-tree-stat {
        input  {
            leaf bridgeId  {
                type cml_data_types:CML_STRING_T;
                mandatory true;
            }
            leaf ifName  {
                type cml_data_types:CML_STRING_T;
                mandatory true;
            }
            leaf instanceId  {
                type cml_data_types:CML_INT32_T;
                mandatory true;
            }
            leaf vlanId  {
                type cml_data_types:CML_STRING_T;
                mandatory true;
            }
        }
    }

    rpc lag-lacp-snmp-restart {
        if-feature feature_list:HAVE_SNMP;
    }

    rpc rib-clearIpRouteKernel {
        input  {
            leaf vrId  {
                type cml_data_types:CML_UINT32_T;
                mandatory true;
            }
        }
    }

    rpc rib-clearIpKernelRoute {
        input  {
            leaf vrId  {
                type cml_data_types:CML_UINT32_T;
                mandatory true;
            }
        }
    }

    rpc rib-clearIpv6RouteKernel {
        if-feature feature_list:HAVE_IPV6;
        input  {
            leaf vrId  {
                type cml_data_types:CML_UINT32_T;
                mandatory true;
            }
        }
    }

    rpc rib-clearIpRouteAll {
        input  {
            leaf vrId  {
                type cml_data_types:CML_UINT32_T;
                mandatory true;
            }
            leaf starPrint  {
                type cml_data_types:CML_STRING_T;
                mandatory true;
            }
        }
    }

    rpc rib-clearIpRoutePrefix {
        input  {
            leaf vrId  {
                type cml_data_types:CML_UINT32_T;
                mandatory true;
            }
            leaf prefixAddr  {
                type cml_data_types:CML_STRING_T;
                mandatory true;
            }
        }
    }

    rpc rib-clearIpv4RouteAll {
        input  {
            leaf vrId  {
                type cml_data_types:CML_UINT32_T;
                mandatory true;
            }
            leaf starPrint  {
                type cml_data_types:CML_STRING_T;
                mandatory true;
            }
        }
    }

    rpc rib-clearIpv4RoutePrefix {
        input  {
            leaf vrId  {
                type cml_data_types:CML_UINT32_T;
                mandatory true;
            }
            leaf prefixAddr  {
                type cml_data_types:CML_STRING_T;
                mandatory true;
            }
        }
    }

    rpc rib-clearIpv6RouteAll {
        if-feature feature_list:HAVE_IPV6;
        input  {
            leaf vrId  {
                type cml_data_types:CML_UINT32_T;
                mandatory true;
            }
            leaf starPrint  {
                type cml_data_types:CML_STRING_T;
                mandatory true;
            }
        }
    }

    rpc rib-clearIpv6RoutePrefix {
        input  {
            leaf vrId  {
                type cml_data_types:CML_UINT32_T;
                mandatory true;
            }
            leaf prefixIpv6Addr  {
                type cml_data_types:CML_STRING_T;
                mandatory true;
            }
        }
    }

    rpc rib-clearIpVrfRouteAll {
        if-feature feature_list:HAVE_VRF;
        input  {
            leaf vrId  {
                type cml_data_types:CML_UINT32_T;
                mandatory true;
            }
            leaf vrfName  {
                type cml_data_types:CML_STRING_T;
                mandatory true;
            }
            leaf starPrint  {
                type cml_data_types:CML_STRING_T;
                mandatory true;
            }
        }
    }

    rpc rib-clearIpVrfRoutePrefix {
        if-feature feature_list:HAVE_VRF;
        input  {
            leaf vrId  {
                type cml_data_types:CML_UINT32_T;
                mandatory true;
            }
            leaf vrfName  {
                type cml_data_types:CML_STRING_T;
                mandatory true;
            }
            leaf prefixAddr  {
                type cml_data_types:CML_STRING_T;
                mandatory true;
            }
        }
    }

    rpc rib-clearIpv4VrfRouteAll {
        if-feature feature_list:HAVE_VRF;
        input  {
            leaf vrId  {
                type cml_data_types:CML_UINT32_T;
                mandatory true;
            }
            leaf vrfName  {
                type cml_data_types:CML_STRING_T;
                mandatory true;
            }
            leaf starPrint  {
                type cml_data_types:CML_STRING_T;
                mandatory true;
            }
        }
    }

    rpc rib-clearIpv4VrfRoutePrefix {
        if-feature feature_list:HAVE_VRF;
        input  {
            leaf vrId  {
                type cml_data_types:CML_UINT32_T;
                mandatory true;
            }
            leaf vrfName  {
                type cml_data_types:CML_STRING_T;
                mandatory true;
            }
            leaf prefixAddr  {
                type cml_data_types:CML_STRING_T;
                mandatory true;
            }
        }
    }

    rpc rib-clearIpv6VrdRouteAll {
        if-feature feature_list:HAVE_VRF;
        if-feature feature_list:HAVE_IPV6;
        input  {
            leaf vrId  {
                type cml_data_types:CML_UINT32_T;
                mandatory true;
            }
            leaf vrfName  {
                type cml_data_types:CML_STRING_T;
                mandatory true;
            }
            leaf starPrint  {
                type cml_data_types:CML_STRING_T;
                mandatory true;
            }
        }
    }

    rpc rib-clearIpv6RoutePrefixVrf {
        input  {
            leaf vrId  {
                type cml_data_types:CML_UINT32_T;
                mandatory true;
            }
            leaf vrfName  {
                type cml_data_types:CML_STRING_T;
                mandatory true;
            }
            leaf prefixIpv6Addr  {
                type cml_data_types:CML_STRING_T;
                mandatory true;
            }
        }
    }

    rpc ospf-restart-ospf-graceful {
        if-feature feature_list:HAVE_RESTART;
        input  {
            leaf vrId  {
                type cml_data_types:CML_UINT32_T;
                mandatory true;
            }
            leaf restartGracePeriod  {
                type cml_data_types:CML_UINT32_T;
                mandatory true;
            }
        }
    }

    rpc ospf-restart-ospf-hitless {
        if-feature feature_list:HAVE_RESTART;
        input  {
            leaf vrId  {
                type cml_data_types:CML_UINT32_T;
                mandatory true;
            }
            leaf hitlessGracePeriod  {
                type cml_data_types:CML_UINT32_T;
                mandatory true;
            }
        }
    }

    rpc ospf-ospf-snmp-restart {
        if-feature feature_list:HAVE_SNMP;
    }

    rpc ospf-clear-ospf-process {
        input  {
            leaf vrId  {
                type cml_data_types:CML_UINT32_T;
                mandatory true;
            }
        }
    }

    rpc ospf-clear-ospf-process-id {
        input  {
            leaf vrId  {
                type cml_data_types:CML_UINT32_T;
                mandatory true;
            }
            leaf procId  {
                type cml_data_types:CML_UINT32_T;
                mandatory true;
            }
        }
    }

    rpc ospfv3-ospf6-clear {
        input  {
            leaf vrId  {
                type cml_data_types:CML_UINT32_T;
                mandatory true;
            }
            leaf ospfProcess  {
                type cml_data_types:CML_STRING_T;
                mandatory true;
            }
        }
    }

    rpc ospfv3-ospf6-restart-hitless {
        input  {
            leaf vrId  {
                type cml_data_types:CML_UINT32_T;
                mandatory true;
            }
            leaf gracePeriod  {
                type cml_data_types:CML_UINT32_T;
                mandatory true;
            }
        }
    }

    rpc ospfv3-ospf6-restart {
        input  {
            leaf vrId  {
                type cml_data_types:CML_UINT32_T;
                mandatory true;
            }
            leaf gracePeriod  {
                type cml_data_types:CML_UINT32_T;
                mandatory true;
            }
        }
    }

    rpc ospfv3-ospf6-snmp-restart {
        if-feature feature_list:HAVE_SNMP;
    }

    rpc bgp-restartBgp {
        if-feature feature_list:HAVE_RESTART;
    }

    rpc bgp-clearBgp {
        input  {
            leaf vrId  {
                type cml_data_types:CML_UINT32_T;
                mandatory true;
            }
            leaf clearAll  {
                type cml_data_types:CML_STRING_T;
                mandatory true;
            }
        }
    }

    rpc vrrp-snmp-restart-vrrp {
        if-feature feature_list:HAVE_SNMP;
    }

    rpc plist-clear-ip-prefix {
        input  {
            leaf vrId  {
                type cml_data_types:CML_UINT32_T;
                mandatory true;
            }
        }
    }

    rpc plist-clear-ip-prefix-by-name {
        input  {
            leaf vrId  {
                type cml_data_types:CML_UINT32_T;
                mandatory true;
            }
            leaf name  {
                type cml_data_types:CML_STRING_T;
                mandatory true;
            }
        }
    }

    rpc plist-clear-ip-prefix-by-prefix {
        input  {
            leaf vrId  {
                type cml_data_types:CML_UINT32_T;
                mandatory true;
            }
            leaf name  {
                type cml_data_types:CML_STRING_T;
                mandatory true;
            }
            leaf prefix  {
                type cml_data_types:CML_STRING_T;
                mandatory true;
            }
        }
    }

    rpc plist-clear-ipv6-prefix {
        input  {
            leaf vrId  {
                type cml_data_types:CML_UINT32_T;
                mandatory true;
            }
        }
    }

    rpc plist-clear-ipv6-prefix-by-name {
        input  {
            leaf vrId  {
                type cml_data_types:CML_UINT32_T;
                mandatory true;
            }
            leaf name  {
                type cml_data_types:CML_STRING_T;
                mandatory true;
            }
        }
    }

    rpc plist-clear-ipv6-prefix-by-prefix {
        input  {
            leaf vrId  {
                type cml_data_types:CML_UINT32_T;
                mandatory true;
            }
            leaf name  {
                type cml_data_types:CML_STRING_T;
                mandatory true;
            }
            leaf prefix  {
                type cml_data_types:CML_STRING_T;
                mandatory true;
            }
        }
    }

    rpc isis-isis-restart {
        if-feature feature_list:HAVE_RESTART;
        input  {
            leaf vrId  {
                type cml_data_types:CML_UINT32_T;
                mandatory true;
            }
            leaf graceCMLSEPperiod  {
                type cml_data_types:CML_UINT16_T;
                mandatory true;
            }
        }
    }

    rpc isis-clear-is-neighbors {
        input  {
            leaf vrId  {
                type cml_data_types:CML_UINT32_T;
                mandatory true;
            }
            leaf SystemID  {
                type cml_data_types:CML_STRING_T;
                mandatory true;
            }
        }
    }

    rpc isis-clear-neighbors {
        input  {
            leaf vrId  {
                type cml_data_types:CML_UINT32_T;
                mandatory true;
            }
        }
    }

    rpc isis-clear-ip-route {
        input  {
            leaf vrId  {
                type cml_data_types:CML_UINT32_T;
                mandatory true;
            }
            leaf isisInstanceTag  {
                type cml_data_types:CML_STRING_T;
                mandatory true;
            }
            leaf ipv4route  {
                type cml_data_types:CML_UINT8_T;
                mandatory true;
            }
        }
    }

    rpc isis-clear-ipv6-route {
        input  {
            leaf vrId  {
                type cml_data_types:CML_UINT32_T;
                mandatory true;
            }
            leaf isisInstanceTag  {
                type cml_data_types:CML_STRING_T;
                mandatory true;
            }
            leaf ipv6route  {
                type cml_data_types:CML_UINT8_T;
                mandatory true;
            }
        }
    }

    rpc isis-isis-proc-clear {
        input  {
            leaf vrId  {
                type cml_data_types:CML_UINT32_T;
                mandatory true;
            }
            leaf isisInstanceTag  {
                type cml_data_types:CML_STRING_T;
                mandatory true;
            }
        }
    }

    rpc isis-isis-clear-counters {
        input  {
            leaf vrId  {
                type cml_data_types:CML_UINT32_T;
                mandatory true;
            }
        }
    }

    rpc isis-clear-interface-counters {
        input  {
            leaf vrId  {
                type cml_data_types:CML_UINT32_T;
                mandatory true;
            }
            leaf ifName  {
                type cml_data_types:CML_STRING_T;
                mandatory true;
            }
        }
    }

    rpc isis-clear-adjacency-all {
        input  {
            leaf vrId  {
                type cml_data_types:CML_UINT32_T;
                mandatory true;
            }
            leaf adjall  {
                type cml_data_types:CML_BOOL_T;
                mandatory true;
            }
            leaf adjvrfname  {
                type cml_data_types:CML_STRING_T;
                mandatory true;
            }
        }
    }

    rpc isis-clear-adjacency-word-all {
        input  {
            leaf vrId  {
                type cml_data_types:CML_UINT32_T;
                mandatory true;
            }
            leaf tagname  {
                type cml_data_types:CML_STRING_T;
                mandatory true;
            }
            leaf adjall  {
                type cml_data_types:CML_BOOL_T;
                mandatory true;
            }
            leaf adjvrfname  {
                type cml_data_types:CML_STRING_T;
                mandatory true;
            }
        }
    }

    rpc isis-clear-adjacency-word-ifname {
        input  {
            leaf vrId  {
                type cml_data_types:CML_UINT32_T;
                mandatory true;
            }
            leaf tagname  {
                type cml_data_types:CML_STRING_T;
                mandatory true;
            }
            leaf tagifname  {
                type cml_data_types:CML_STRING_T;
                mandatory true;
            }
            leaf adjvrfname  {
                type cml_data_types:CML_STRING_T;
                mandatory true;
            }
        }
    }

    rpc isis-clear-adjacency-ifname {
        input  {
            leaf vrId  {
                type cml_data_types:CML_UINT32_T;
                mandatory true;
            }
            leaf adjifname  {
                type cml_data_types:CML_STRING_T;
                mandatory true;
            }
            leaf adjvrfname  {
                type cml_data_types:CML_STRING_T;
                mandatory true;
            }
        }
    }

    rpc isis-clear-adjacency-word-systemid {
        input  {
            leaf vrId  {
                type cml_data_types:CML_UINT32_T;
                mandatory true;
            }
            leaf tagname  {
                type cml_data_types:CML_STRING_T;
                mandatory true;
            }
            leaf tagsystemid  {
                type cml_data_types:CML_STRING_T;
                mandatory true;
            }
            leaf tagvrfname  {
                type cml_data_types:CML_STRING_T;
                mandatory true;
            }
        }
    }

    rpc isis-clear-adjacency-systemid {
        input  {
            leaf vrId  {
                type cml_data_types:CML_UINT32_T;
                mandatory true;
            }
            leaf adjsystemid  {
                type cml_data_types:CML_STRING_T;
                mandatory true;
            }
            leaf adjvrfname  {
                type cml_data_types:CML_STRING_T;
                mandatory true;
            }
        }
    }

    rpc isis-snmp-restart-isis {
        if-feature feature_list:HAVE_SNMP;
    }

    rpc pim-snmp-restart-pim {
        if-feature feature_list:HAVE_SNMP;
    }

    rpc pim4-clear-ip-mroute {
        input  {
            leaf vrId  {
                type cml_data_types:CML_UINT32_T;
                mandatory true;
            }
            leaf vrfName  {
                type cml_data_types:CML_STRING_T;
                mandatory true;
            }
            leaf allFlag  {
                type cml_data_types:CML_BOOL_T;
                mandatory true;
            }
            leaf pimmode  {
                type cml_data_types:CML_UINT8_T;
                mandatory true;
            }
        }
    }

    rpc pim4-clear-ip-mroute-xg {
        input  {
            leaf vrId  {
                type cml_data_types:CML_UINT32_T;
                mandatory true;
            }
            leaf vrfName  {
                type cml_data_types:CML_STRING_T;
                mandatory true;
            }
            leaf mrouteXg  {
                type cml_data_types:CML_STRING_T;
                mandatory true;
            }
        }
    }

    rpc pim4-clear-ip-mroute-sg {
        input  {
            leaf vrId  {
                type cml_data_types:CML_UINT32_T;
                mandatory true;
            }
            leaf vrfName  {
                type cml_data_types:CML_STRING_T;
                mandatory true;
            }
            leaf mrouteGaddr  {
                type cml_data_types:CML_STRING_T;
                mandatory true;
            }
            leaf mrouteSaddr  {
                type cml_data_types:CML_STRING_T;
                mandatory true;
            }
            leaf pimgsmode  {
                type cml_data_types:CML_UINT8_T;
                mandatory true;
            }
        }
    }

    rpc pim4-clear-ip-pim {
        if-feature feature_list:HAVE_PIM_SM;
        input  {
            leaf vrId  {
                type cml_data_types:CML_UINT32_T;
                mandatory true;
            }
            leaf vrfName  {
                type cml_data_types:CML_STRING_T;
                mandatory true;
            }
            leaf allRp  {
                type cml_data_types:CML_BOOL_T;
                mandatory true;
            }
        }
    }

    rpc pim4-clear-ip-msdp-peer {
        if-feature feature_list:HAVE_PIM_MSDP_API;
        input  {
            leaf vrId  {
                type cml_data_types:CML_UINT32_T;
                mandatory true;
            }
            leaf vrfName  {
                type cml_data_types:CML_STRING_T;
                mandatory true;
            }
            leaf peerAddress  {
                type cml_data_types:CML_STRING_T;
                mandatory true;
            }
        }
    }

    rpc pim4-clear-ip-msdp-sacache {
        if-feature feature_list:HAVE_PIM_MSDP_API;
        input  {
            leaf vrId  {
                type cml_data_types:CML_UINT32_T;
                mandatory true;
            }
            leaf vrfName  {
                type cml_data_types:CML_STRING_T;
                mandatory true;
            }
            leaf saAddress  {
                type cml_data_types:CML_STRING_T;
                mandatory true;
            }
        }
    }

    rpc pim6-clear-ipv6-mroute {
        input  {
            leaf vrId  {
                type cml_data_types:CML_UINT32_T;
                mandatory true;
            }
            leaf vrfName  {
                type cml_data_types:CML_STRING_T;
                mandatory true;
            }
            leaf allFlag  {
                type cml_data_types:CML_BOOL_T;
                mandatory true;
            }
            leaf pimmode  {
                type cml_data_types:CML_UINT8_T;
                mandatory true;
            }
        }
    }

    rpc pim6-clear-ipv6-mroute-xg {
        input  {
            leaf vrId  {
                type cml_data_types:CML_UINT32_T;
                mandatory true;
            }
            leaf vrfName  {
                type cml_data_types:CML_STRING_T;
                mandatory true;
            }
            leaf mrouteXg  {
                type cml_data_types:CML_STRING_T;
                mandatory true;
            }
        }
    }

    rpc pim6-clear-ipv6-mroue-sg {
        input  {
            leaf vrId  {
                type cml_data_types:CML_UINT32_T;
                mandatory true;
            }
            leaf vrfName  {
                type cml_data_types:CML_STRING_T;
                mandatory true;
            }
            leaf mrouteGaddr  {
                type cml_data_types:CML_STRING_T;
                mandatory true;
            }
            leaf mrouteSaddr  {
                type cml_data_types:CML_STRING_T;
                mandatory true;
            }
            leaf pimgsmode  {
                type cml_data_types:CML_UINT8_T;
                mandatory true;
            }
        }
    }

    rpc pim6-clear-ipv6-pim {
        input  {
            leaf vrId  {
                type cml_data_types:CML_UINT32_T;
                mandatory true;
            }
            leaf vrfName  {
                type cml_data_types:CML_STRING_T;
                mandatory true;
            }
            leaf allRp  {
                type cml_data_types:CML_BOOL_T;
                mandatory true;
            }
        }
    }

    rpc tfo-cleartfocounter {
        if-feature feature_list:HAVE_TFO;
    }

    rpc tfo-cleartfocounterfog {
        if-feature feature_list:HAVE_TFO;
        input  {
            leaf fognum  {
                type cml_data_types:CML_INT32_T;
                mandatory true;
            }
        }
    }

    rpc ssh-lengthRSA {
        if-feature feature_list:HAVE_SSH_SERVER;
        input  {
            leaf usernameRSA  {
                type cml_data_types:CML_STRING_T;
                mandatory true;
            }
            leaf keyRSA  {
                type cml_data_types:CML_BOOL_T;
                mandatory true;
            }
            leaf lengthRSA  {
                type cml_data_types:CML_INT32_T;
                mandatory true;
            }
            leaf forceRSA  {
                type cml_data_types:CML_BOOL_T;
                mandatory true;
            }
        }
    }

    rpc ssh-keyDSA {
        if-feature feature_list:HAVE_SSH_SERVER;
        input  {
            leaf usernameDSA  {
                type cml_data_types:CML_STRING_T;
                mandatory true;
            }
            leaf keyDSA  {
                type cml_data_types:CML_BOOL_T;
                mandatory true;
            }
            leaf forceDSA  {
                type cml_data_types:CML_BOOL_T;
                mandatory true;
            }
        }
    }

    rpc ssh-keyGenRSA {
        if-feature feature_list:HAVE_SSH_SERVER;
        input  {
            leaf keyGenRSA  {
                type cml_data_types:CML_BOOL_T;
                mandatory true;
            }
            leaf keyGenlengthRSA  {
                type cml_data_types:CML_UINT32_T;
                mandatory true;
            }
            leaf keyGenforceRSA  {
                type cml_data_types:CML_BOOL_T;
                mandatory true;
            }
            leaf vrfName  {
                type cml_data_types:CML_STRING_T;
                mandatory true;
            }
        }
    }

    rpc ssh-keyDelRSA {
        if-feature feature_list:HAVE_SSH_SERVER;
        input  {
            leaf keyDelRSA  {
                type cml_data_types:CML_BOOL_T;
                mandatory true;
            }
            leaf vrfName  {
                type cml_data_types:CML_STRING_T;
                mandatory true;
            }
        }
    }

    rpc ssh-keyGenDSA {
        if-feature feature_list:HAVE_SSH_SERVER;
        input  {
            leaf keyGenDSA  {
                type cml_data_types:CML_BOOL_T;
                mandatory true;
            }
            leaf keyGenforceDSA  {
                type cml_data_types:CML_BOOL_T;
                mandatory true;
            }
            leaf vrfName  {
                type cml_data_types:CML_STRING_T;
                mandatory true;
            }
        }
    }

    rpc ssh-keyDelDSA {
        if-feature feature_list:HAVE_SSH_SERVER;
        input  {
            leaf keyDelDSA  {
                type cml_data_types:CML_BOOL_T;
                mandatory true;
            }
            leaf vrfName  {
                type cml_data_types:CML_STRING_T;
                mandatory true;
            }
        }
    }

    rpc ssh-keyDelSSHkeys {
        if-feature feature_list:HAVE_SSH_SERVER;
        input  {
            leaf keyDelSSHkeys  {
                type cml_data_types:CML_BOOL_T;
                mandatory true;
            }
            leaf vrfName  {
                type cml_data_types:CML_STRING_T;
                mandatory true;
            }
        }
    }

    rpc ssh-clearSSHhosts {
        if-feature feature_list:HAVE_SSH_SERVER;
        input  {
            leaf clearSSHhosts  {
                type cml_data_types:CML_BOOL_T;
                mandatory true;
            }
        }
    }

    rpc ntp-sync-retry {
        if-feature feature_list:HAVE_HOSTP_NTP;
        input  {
            leaf vrf  {
                type cml_data_types:CML_STRING_T;
                mandatory true;
            }
        }
    }

    rpc ntp-clear {
        if-feature feature_list:HAVE_HOSTP_NTP;
        input  {
            leaf statistics  {
                type cml_data_types:CML_INT32_T;
                mandatory true;
            }
        }
    }

    rpc aaa-lockout {
        if-feature feature_list:HAVE_HOSTPD;
        if-feature feature_list:HAVE_AAA;
        input  {
            leaf username  {
                type cml_data_types:CML_STRING_T;
                mandatory true;
            }
        }
    }

    rpc libsyslog-cleardebuglogfile {
    }

    rpc libsyslog-clearlogginglogfile {
    }

    rpc license-licenseget {
        if-feature feature_list:HAVE_FLEXLM;
        input  {
            leaf sourceCMLSEPinterface  {
                type cml_data_types:CML_STRING_T;
                mandatory true;
            }
            leaf url  {
                type cml_data_types:CML_STRING_T;
                mandatory true;
            }
        }
    }

    rpc license-licenserefresh {
        if-feature feature_list:HAVE_FLEXLM;
    }

    rpc mrib4-snmp-restart-mrib {
        if-feature feature_list:HAVE_SNMP;
    }

    rpc mrib4-mrib-bulking-start {
        if-feature feature_list:HAVE_ASYNC;
    }

    rpc mrib4-mrib-bulking-stop {
        if-feature feature_list:HAVE_ASYNC;
    }

    rpc mrib4-mrib-bulking-flush {
        if-feature feature_list:HAVE_ASYNC;
    }

    rpc mrib4-clear-mrib-vrf-all {
        input  {
            leaf vrId  {
                type cml_data_types:CML_UINT32_T;
                mandatory true;
            }
            leaf vrfName  {
                type cml_data_types:CML_STRING_T;
                mandatory true;
            }
            leaf allroute  {
                type cml_data_types:CML_BOOL_T;
                mandatory true;
            }
        }
    }

    rpc mrib4-clear-mrib-grp {
        input  {
            leaf vrId  {
                type cml_data_types:CML_UINT32_T;
                mandatory true;
            }
            leaf vrfName  {
                type cml_data_types:CML_STRING_T;
                mandatory true;
            }
            leaf grpAddr  {
                type cml_data_types:CML_STRING_T;
                mandatory true;
            }
        }
    }

    rpc mrib4-clear-mrib-vrf-src-grp {
        input  {
            leaf vrId  {
                type cml_data_types:CML_UINT32_T;
                mandatory true;
            }
            leaf vrfName  {
                type cml_data_types:CML_STRING_T;
                mandatory true;
            }
            leaf srcAddr  {
                type cml_data_types:CML_STRING_T;
                mandatory true;
            }
            leaf grpAddr  {
                type cml_data_types:CML_STRING_T;
                mandatory true;
            }
        }
    }

    rpc mrib4-clear-mrib-stats-all {
        input  {
            leaf vrId  {
                type cml_data_types:CML_UINT32_T;
                mandatory true;
            }
            leaf vrfName  {
                type cml_data_types:CML_STRING_T;
                mandatory true;
            }
            leaf allroute  {
                type cml_data_types:CML_BOOL_T;
                mandatory true;
            }
        }
    }

    rpc mrib4-clear-mrib-vrf-grp-stats {
        input  {
            leaf vrId  {
                type cml_data_types:CML_UINT32_T;
                mandatory true;
            }
            leaf vrfName  {
                type cml_data_types:CML_STRING_T;
                mandatory true;
            }
            leaf grpAddr  {
                type cml_data_types:CML_STRING_T;
                mandatory true;
            }
        }
    }

    rpc mrib4-clear-mrib-vrf-src-grp-stats {
        input  {
            leaf vrId  {
                type cml_data_types:CML_UINT32_T;
                mandatory true;
            }
            leaf vrfName  {
                type cml_data_types:CML_STRING_T;
                mandatory true;
            }
            leaf srcAddr  {
                type cml_data_types:CML_STRING_T;
                mandatory true;
            }
            leaf grpAddr  {
                type cml_data_types:CML_STRING_T;
                mandatory true;
            }
        }
    }

    rpc mrib6-clear-mrib6-vrf-all {
        if-feature feature_list:HAVE_MCAST_IPV6;
        input  {
            leaf vrId  {
                type cml_data_types:CML_UINT32_T;
                mandatory true;
            }
            leaf vrfName  {
                type cml_data_types:CML_STRING_T;
                mandatory true;
            }
            leaf allroute  {
                type cml_data_types:CML_BOOL_T;
                mandatory true;
            }
        }
    }

    rpc mrib6-clear-mrib6-vrf-grp {
        if-feature feature_list:HAVE_MCAST_IPV6;
        input  {
            leaf vrId  {
                type cml_data_types:CML_UINT32_T;
                mandatory true;
            }
            leaf vrfName  {
                type cml_data_types:CML_STRING_T;
                mandatory true;
            }
            leaf grpAddr  {
                type cml_data_types:CML_STRING_T;
                mandatory true;
            }
        }
    }

    rpc mrib6-clear-mrib6-vrf-src-grp {
        if-feature feature_list:HAVE_MCAST_IPV6;
        input  {
            leaf vrId  {
                type cml_data_types:CML_UINT32_T;
                mandatory true;
            }
            leaf vrfName  {
                type cml_data_types:CML_STRING_T;
                mandatory true;
            }
            leaf srcAddr  {
                type cml_data_types:CML_STRING_T;
                mandatory true;
            }
            leaf grpAddr  {
                type cml_data_types:CML_STRING_T;
                mandatory true;
            }
        }
    }

    rpc mrib6-clear-mrib6-vrf-stats-all {
        if-feature feature_list:HAVE_MCAST_IPV6;
        input  {
            leaf vrId  {
                type cml_data_types:CML_UINT32_T;
                mandatory true;
            }
            leaf vrfName  {
                type cml_data_types:CML_STRING_T;
                mandatory true;
            }
            leaf allroute  {
                type cml_data_types:CML_BOOL_T;
                mandatory true;
            }
        }
    }

    rpc mrib6-clear-mrib6-vrf-grp-stats {
        if-feature feature_list:HAVE_MCAST_IPV6;
        input  {
            leaf vrId  {
                type cml_data_types:CML_UINT32_T;
                mandatory true;
            }
            leaf vrfName  {
                type cml_data_types:CML_STRING_T;
                mandatory true;
            }
            leaf grpAddr  {
                type cml_data_types:CML_STRING_T;
                mandatory true;
            }
        }
    }

    rpc mrib6-clear-mrib6-vrf-src-grp-stats {
        if-feature feature_list:HAVE_MCAST_IPV6;
        input  {
            leaf vrId  {
                type cml_data_types:CML_UINT32_T;
                mandatory true;
            }
            leaf vrfName  {
                type cml_data_types:CML_STRING_T;
                mandatory true;
            }
            leaf srcAddr  {
                type cml_data_types:CML_STRING_T;
                mandatory true;
            }
            leaf grpAddr  {
                type cml_data_types:CML_STRING_T;
                mandatory true;
            }
        }
    }

    rpc igmp-mrib4-igmp-group-clear {
        input  {
            leaf vrfName  {
                type cml_data_types:CML_STRING_T;
                mandatory true;
            }
            leaf groupAddr  {
                type cml_data_types:CML_STRING_T;
                mandatory true;
            }
            leaf ifName  {
                type cml_data_types:CML_STRING_T;
                mandatory true;
            }
        }
    }

    rpc igmp-mrib4-igmp-interface-clear {
        input  {
            leaf vrfName  {
                type cml_data_types:CML_STRING_T;
                mandatory true;
            }
            leaf ifName  {
                type cml_data_types:CML_STRING_T;
                mandatory true;
            }
        }
    }

    rpc igmp-mrib4-igmp-vrfName-clear {
        input  {
            leaf vrfName  {
                type cml_data_types:CML_STRING_T;
                mandatory true;
            }
        }
    }

    rpc igmp-mrib4-igmp-all-group-clear {
        input  {
            leaf vrfName  {
                type cml_data_types:CML_STRING_T;
                mandatory true;
            }
            leaf groupAddr  {
                type cml_data_types:CML_STRING_T;
                mandatory true;
            }
        }
    }

    rpc igmp-mrib4-igmp-group-clear-all {
        input  {
            leaf vrfName  {
                type cml_data_types:CML_STRING_T;
                mandatory true;
            }
            leaf clearAll  {
                type cml_data_types:CML_UINT8_T;
                mandatory true;
            }
        }
    }

    rpc igmpsnooping-igmpsnooping-clear-interface-group {
        input  {
            leaf groupAddr  {
                type cml_data_types:CML_STRING_T;
                mandatory true;
            }
            leaf ifName  {
                type cml_data_types:CML_STRING_T;
                mandatory true;
            }
        }
    }

    rpc igmpsnooping-igmpsnooping-clear-interface {
        input  {
            leaf ifName  {
                type cml_data_types:CML_STRING_T;
                mandatory true;
            }
        }
    }

    rpc igmpsnooping-igmpsnooping-clear-all {
    }

    rpc igmpsnooping-igmpsnooping-clear {
    }

    rpc igmpsnooping-igmpsnooping-clear-group {
        input  {
            leaf groupAddr  {
                type cml_data_types:CML_STRING_T;
                mandatory true;
            }
        }
    }

    rpc mld-mld-clear {
        if-feature feature_list:HAVE_MCAST_IPV6;
        input  {
            leaf vrId  {
                type cml_data_types:CML_UINT32_T;
                mandatory true;
            }
            leaf vrfName  {
                type cml_data_types:CML_STRING_T;
                mandatory true;
            }
        }
    }

    rpc mld-mld-clear-group-x {
        if-feature feature_list:HAVE_MCAST_IPV6;
        input  {
            leaf vrId  {
                type cml_data_types:CML_UINT32_T;
                mandatory true;
            }
            leaf vrfName  {
                type cml_data_types:CML_STRING_T;
                mandatory true;
            }
            leaf allroute  {
                type cml_data_types:CML_BOOL_T;
                mandatory true;
            }
        }
    }

    rpc mld-mld-clear-group-address {
        if-feature feature_list:HAVE_MCAST_IPV6;
        input  {
            leaf vrId  {
                type cml_data_types:CML_UINT32_T;
                mandatory true;
            }
            leaf vrfName  {
                type cml_data_types:CML_STRING_T;
                mandatory true;
            }
            leaf multicastGroupAddr  {
                type cml_data_types:CML_STRING_T;
                mandatory true;
            }
        }
    }

    rpc mld-mld-clear-group-interface {
        if-feature feature_list:HAVE_MCAST_IPV6;
        input  {
            leaf vrId  {
                type cml_data_types:CML_UINT32_T;
                mandatory true;
            }
            leaf vrfName  {
                type cml_data_types:CML_STRING_T;
                mandatory true;
            }
            leaf multicastGroupAddr  {
                type cml_data_types:CML_STRING_T;
                mandatory true;
            }
            leaf ifName  {
                type cml_data_types:CML_STRING_T;
                mandatory true;
            }
        }
    }

    rpc mld-mld-clear-interface-ifname {
        if-feature feature_list:HAVE_MCAST_IPV6;
        input  {
            leaf vrId  {
                type cml_data_types:CML_UINT32_T;
                mandatory true;
            }
            leaf vrfName  {
                type cml_data_types:CML_STRING_T;
                mandatory true;
            }
            leaf ifName  {
                type cml_data_types:CML_STRING_T;
                mandatory true;
            }
        }
    }

    rpc ldp-snmp-restart-ldp {
        if-feature feature_list:HAVE_SNMP;
    }

    rpc ldp-clear-ldp-statistics {
    }

    rpc ldp-clear-ldp-session-ipv4 {
        input  {
            leaf addr  {
                type cml_data_types:CML_STRING_T;
                mandatory true;
            }
        }
    }

    rpc ldp-clear-ldp-session-ipv6 {
        if-feature feature_list:HAVE_IPV6;
        input  {
            leaf addr  {
                type cml_data_types:CML_STRING_T;
                mandatory true;
            }
        }
    }

    rpc ldp-restart-ldp-graceful {
        if-feature feature_list:HAVE_RESTART;
    }

    rpc ldp-clear-ldp-adjacency-ipv4 {
        input  {
            leaf addr  {
                type cml_data_types:CML_STRING_T;
                mandatory true;
            }
        }
    }

    rpc ldp-clear-ldp-adjacency-ipv6 {
        if-feature feature_list:HAVE_IPV6;
        input  {
            leaf addr  {
                type cml_data_types:CML_STRING_T;
                mandatory true;
            }
        }
    }

    rpc ldp-clear-ldp-trunk {
        input  {
            leaf name  {
                type cml_data_types:CML_STRING_T;
                mandatory true;
            }
        }
    }

    rpc ldp-clear-ldp-statistics-advertise-labels {
    }

    rpc ldp-clear-ldp-statistics-advertise-labels-prefix {
        input  {
            leaf prefix  {
                type cml_data_types:CML_STRING_T;
                mandatory true;
            }
        }
    }

    rpc ldp-clear-ldp-statistics-advertise-labels-prefix-peer {
        input  {
            leaf prefix  {
                type cml_data_types:CML_STRING_T;
                mandatory true;
            }
            leaf peer  {
                type cml_data_types:CML_STRING_T;
                mandatory true;
            }
        }
    }

    rpc rsvp-restart-rsvp-graceful {
    }

    rpc rsvp-clear-rsvp-session {
    }

    rpc rsvp-clear-rsvp-gmpls-session {
    }

    rpc rsvp-clear-rsvp-statistics {
    }

    rpc rsvp-rsvp-snmp-restart {
    }

    rpc rsvp-rsvp-trunk-restart {
        input  {
            leaf trunkName  {
                type cml_data_types:CML_STRING_T;
                mandatory true;
            }
        }
    }

    rpc rsvp-clear-rsvp-trunk {
        input  {
            leaf trunkName  {
                type cml_data_types:CML_STRING_T;
                mandatory true;
            }
        }
    }

    rpc rsvp-clear-rsvp-trunk-primary {
        input  {
            leaf trunkName  {
                type cml_data_types:CML_STRING_T;
                mandatory true;
            }
        }
    }

    rpc rsvp-clear-rsvp-trunk-secondary {
        input  {
            leaf trunkName  {
                type cml_data_types:CML_STRING_T;
                mandatory true;
            }
        }
    }

    rpc rsvp-clear-rsvp-trunk-ingress {
        input  {
            leaf trunkName  {
                type cml_data_types:CML_STRING_T;
                mandatory true;
            }
        }
    }

    rpc rsvp-clear-rsvp-trunk-non-ingress {
        input  {
            leaf trunkName  {
                type cml_data_types:CML_STRING_T;
                mandatory true;
            }
        }
    }

    rpc mcec-clear-mcec-statistics {
    }

    rpc cmm-clear-ddm-transceiver-alarm {
        input  {
            leaf portNum  {
                type cml_data_types:CML_STRING_T;
                mandatory true;
            }
        }
    }

    rpc auth-snmp-restart {
        if-feature feature_list:HAVE_SNMP;
    }

    rpc rip-rip-restart {
        if-feature feature_list:HAVE_RIP_GR_SUPPORT;
        input  {
            leaf vrId  {
                type cml_data_types:CML_UINT32_T;
                mandatory true;
            }
            leaf gracePeriod  {
                type cml_data_types:CML_UINT32_T;
                mandatory true;
            }
        }
    }

    rpc rip-clear-ip-rip-route {
        input  {
            leaf vrId  {
                type cml_data_types:CML_UINT32_T;
                mandatory true;
            }
            leaf routeCMLSEPtype  {
                type cml_data_types:CML_UINT8_T;
                mandatory true;
            }
        }
    }

    rpc rip-clear-ip-rip-route-prefix {
        input  {
            leaf vrId  {
                type cml_data_types:CML_UINT32_T;
                mandatory true;
            }
            leaf routeCMLSEPtypeCMLSEPpre  {
                type cml_data_types:CML_STRING_T;
                mandatory true;
            }
        }
    }

    rpc rip-clear-ip-rip-route-vrf {
        if-feature feature_list:HAVE_VRF_RIP;
        input  {
            leaf vrId  {
                type cml_data_types:CML_UINT32_T;
                mandatory true;
            }
            leaf vrfName  {
                type cml_data_types:CML_STRING_T;
                mandatory true;
            }
            leaf prefixStr  {
                type cml_data_types:CML_STRING_T;
                mandatory true;
            }
        }
    }

    rpc rip-clear-ip-rip-stat-interf {
        input  {
            leaf vrId  {
                type cml_data_types:CML_UINT32_T;
                mandatory true;
            }
            leaf ifName  {
                type cml_data_types:CML_STRING_T;
                mandatory true;
            }
        }
    }

    rpc rip-snmp-restart-rip {
    }

    rpc dhcpsnooping-ipdhcpsnoopingdatabase {
        input  {
            leaf bridgeId  {
                type cml_data_types:CML_STRING_T;
                mandatory true;
            }
        }
    }

    rpc dhcpsnooping-renewipdhcpsnoopingdatabase {
        input  {
            leaf bridgeId  {
                type cml_data_types:CML_STRING_T;
                mandatory true;
            }
        }
    }

    rpc dhcpsnooping-ipdhcpsnoopingsourcedatabase {
        input  {
            leaf bridgeId  {
                type cml_data_types:CML_STRING_T;
                mandatory true;
            }
        }
    }

    rpc dhcpsnooping-ipdhcpsnoopingrenewsourcedatabase {
        input  {
            leaf bridgeId  {
                type cml_data_types:CML_STRING_T;
                mandatory true;
            }
        }
    }

    rpc dhcpsnooping-clearipdhcpsnoopingsourcedatabase {
        input  {
            leaf bridgeId  {
                type cml_data_types:CML_STRING_T;
                mandatory true;
            }
        }
    }

    rpc dhcpsnooping-clearipdhcpsnoopingdatabase {
        input  {
            leaf bridgeId  {
                type cml_data_types:CML_STRING_T;
                mandatory true;
            }
        }
    }

    rpc ras-clear-hsl-ipc-stat-values {
        input  {
            leaf startCMLSEPvalue  {
                type cml_data_types:CML_UINT16_T;
                mandatory true;
            }
            leaf endCMLSEPvalue  {
                type cml_data_types:CML_UINT16_T;
                mandatory true;
            }
        }
    }

    rpc ras-clear-hsl-ipc-stat {
    }

    rpc ras-clear-hsl-mlag-mac-sync {
        if-feature feature_list:HAVE_MLAG;
    }

    notification force_unlock {

        description "Notify force unlck from netconf.";

        leaf message {
            type string;
        }
    }

    notification sflowReceiverTimeoutAlarmMsg {

        description "Notify alarm message.";

        leaf message {
            type string;
        }
    }

    notification cmmAlarmCpuRisingThreshold {

        description "Trap to send information for Rising threshold, threshold interval and CPU Utilisation.";

        leaf cmmSysCpuThresholdInterval {
            type string;
        }

        leaf cmmSysCpuThreshold {
            type string;
        }

        leaf cmmStackUnitCpuUtilization {
            type string;
        }
    }

    notification cmmAlarmFreeMemBlwThreshold {

        description "Trap to send information for Free Memory and Free Memory Threshold.";

        leaf cmmSysRamFreeMem {
            type string;
        }

        leaf cmmSysRamThreshold {
            type string;
        }
    }

    notification cmmAlarmTempHigh {

        description "Set when internal temperature exceeds high alarm level.";

        leaf cmmSysPortIndex {
            type string;
        }

        leaf cmmStackUnitIndex {
            type string;
        }

        leaf cmmSysPortType {
            type string;
        }

        leaf cmmSysTemperature {
            type string;
        }

        leaf cmmAlarmVarInteger {
            type string;
        }
    }

    notification cmmAlarmTempLow {

        description "Set when internal temperature is below low alarm level.";

        leaf cmmSysPortIndex {
            type string;
        }

        leaf cmmStackUnitIndex {
            type string;
        }

        leaf cmmSysPortType {
            type string;
        }

        leaf cmmSysTemperature {
            type string;
        }

        leaf cmmAlarmVarInteger {
            type string;
        }
    }

    notification cmmWarningTempHigh {

        description "Set when internal temperature exceeds high warning level.";

        leaf cmmSysPortIndex {
            type string;
        }

        leaf cmmStackUnitIndex {
            type string;
        }

        leaf cmmSysPortType {
            type string;
        }

        leaf cmmSysTemperature {
            type string;
        }

        leaf cmmAlarmVarInteger {
            type string;
        }
    }

    notification cmmWarningTempLow {

        description "Set when internal temperature is below low warning level.";

        leaf cmmSysPortIndex {
            type string;
        }

        leaf cmmStackUnitIndex {
            type string;
        }

        leaf cmmSysPortType {
            type string;
        }

        leaf cmmSysTemperature {
            type string;
        }

        leaf cmmAlarmVarInteger {
            type string;
        }
    }

    notification cmmAlarmVoltageHigh {

        description "Set when internal supply voltage exceeds high alarm level.";

        leaf cmmSysPortIndex {
            type string;
        }

        leaf cmmStackUnitIndex {
            type string;
        }

        leaf cmmSysPortType {
            type string;
        }

        leaf cmmSysVoltage {
            type string;
        }

        leaf cmmAlarmVarString {
            type string;
        }
    }

    notification cmmAlarmVoltageLow {

        description "Set when internal supply voltage is below low alarm level.";

        leaf cmmSysPortIndex {
            type string;
        }

        leaf cmmStackUnitIndex {
            type string;
        }

        leaf cmmSysPortType {
            type string;
        }

        leaf cmmSysVoltage {
            type string;
        }

        leaf cmmAlarmVarString {
            type string;
        }
    }

    notification cmmWarningVoltageHigh {

        description "Set when internal supply voltage exceeds high warning level..";

        leaf cmmSysPortIndex {
            type string;
        }

        leaf cmmStackUnitIndex {
            type string;
        }

        leaf cmmSysPortType {
            type string;
        }

        leaf cmmSysVoltage {
            type string;
        }

        leaf cmmAlarmVarString {
            type string;
        }
    }

    notification cmmWarningVoltageLow {

        description "Set when internal supply voltage is below low warning level.";

        leaf cmmSysPortIndex {
            type string;
        }

        leaf cmmStackUnitIndex {
            type string;
        }

        leaf cmmSysPortType {
            type string;
        }

        leaf cmmSysVoltage {
            type string;
        }

        leaf cmmAlarmVarString {
            type string;
        }
    }

    notification cmmAlarmBiasHigh {

        description "Set when TX Bias current exceeds high alarm level.";

        leaf cmmSysPortIndex {
            type string;
        }

        leaf cmmStackUnitIndex {
            type string;
        }

        leaf cmmSysPortType {
            type string;
        }

        leaf cmmSysLaserBiasCurrent {
            type string;
        }

        leaf cmmAlarmVarString {
            type string;
        }
    }

    notification cmmAlarmBiasLow {

        description "Set when TX Bias current is below low alarm level.";

        leaf cmmSysPortIndex {
            type string;
        }

        leaf cmmStackUnitIndex {
            type string;
        }

        leaf cmmSysPortType {
            type string;
        }

        leaf cmmSysLaserBiasCurrent {
            type string;
        }

        leaf cmmAlarmVarString {
            type string;
        }
    }

    notification cmmWarningBiasHigh {

        description "Set when TX Bias current exceeds high warning level.";

        leaf cmmSysPortIndex {
            type string;
        }

        leaf cmmStackUnitIndex {
            type string;
        }

        leaf cmmSysPortType {
            type string;
        }

        leaf cmmSysLaserBiasCurrent {
            type string;
        }

        leaf cmmAlarmVarString {
            type string;
        }
    }

    notification cmmWarningBiasLow {

        description "Set when TX Bias current is below low warning level.";

        leaf cmmSysPortIndex {
            type string;
        }

        leaf cmmStackUnitIndex {
            type string;
        }

        leaf cmmSysPortType {
            type string;
        }

        leaf cmmSysRxInputPower {
            type string;
        }

        leaf cmmAlarmVarString {
            type string;
        }
    }

    notification cmmAlarmRxPowerHigh {

        description "Set when Received Power exceeds high alarm level.";

        leaf cmmSysPortIndex {
            type string;
        }

        leaf cmmStackUnitIndex {
            type string;
        }

        leaf cmmSysPortType {
            type string;
        }

        leaf cmmSysRxInputPower {
            type string;
        }

        leaf cmmAlarmVarString {
            type string;
        }
    }

    notification cmmAlarmRxPowerLow {

        description "Set when Received Power is below low alarm level.";

        leaf cmmSysPortIndex {
            type string;
        }

        leaf cmmStackUnitIndex {
            type string;
        }

        leaf cmmSysPortType {
            type string;
        }

        leaf cmmSysRxInputPower {
            type string;
        }

        leaf cmmAlarmVarString {
            type string;
        }
    }

    notification cmmWarningRxPowerHigh {

        description "Set when Received Power exceeds high warning level..";

        leaf cmmSysPortIndex {
            type string;
        }

        leaf cmmStackUnitIndex {
            type string;
        }

        leaf cmmSysPortType {
            type string;
        }

        leaf cmmSysRxInputPower {
            type string;
        }

        leaf cmmAlarmVarString {
            type string;
        }
    }

    notification cmmWarningRxPowerLow {

        description "Set when Received Power is below low warning level.";

        leaf cmmSysPortIndex {
            type string;
        }

        leaf cmmStackUnitIndex {
            type string;
        }

        leaf cmmSysPortType {
            type string;
        }

        leaf cmmSysRxInputPower {
            type string;
        }

        leaf cmmAlarmVarString {
            type string;
        }
    }

    notification cmmAlarmTemperatureTooHigh {

        description "Set when Temperature will be above threshold for sensor.";

        leaf cmmSysTemperatureSensorIndex {
            type string;
        }

        leaf cmmAlarmVarInteger {
            type string;
        }

        leaf cmmAlarmVarString {
            type string;
        }
    }

    notification cmmWarningPsuInserted {

        description "Set when Power supply unit is inserted.";

        leaf cmmSysPowerSupplyIndex {
            type string;
        }

        leaf cmmAlarmVarString {
            type string;
        }
    }

    notification cmmWarningPsuRemoved {

        description "Set when Power supply unit is Removed.";

        leaf cmmSysPowerSupplyIndex {
            type string;
        }

        leaf cmmAlarmVarString {
            type string;
        }
    }

    notification cmmWarningPsuFaulty {

        description "Set when Power supply unit is Faulty.";

        leaf cmmSysPowerSupplyIndex {
            type string;
        }

        leaf cmmAlarmVarString {
            type string;
        }
    }

    notification cmmWarningFanTrayInserted {

        description "Set when fan tray is inserted.";

        leaf cmmSysFanTrayNumber {
            type string;
        }

        leaf cmmSysFanRpm {
            type string;
        }

        leaf cmmAlarmVarString {
            type string;
        }
    }

    notification cmmWarningFanTrayRemoved {

        description "Set when fan tray is Removed.";

        leaf cmmSysFanTrayNumber {
            type string;
        }

        leaf cmmAlarmVarString {
            type string;
        }
    }

    notification cmmWarningFanTrayFaulty {

        description "Set when Given Fan Tray Faulty.";

        leaf cmmSysFanTrayNumber {
            type string;
        }

        leaf cmmSysFanIndex {
            type string;
        }

        leaf cmmAlarmVarString {
            type string;
        }
    }

    notification cmmWarningFanTrayRecovered {

        description "Set when Given Fan Tray is recovered.";

        leaf cmmSysFanTrayNumber {
            type string;
        }

        leaf cmmSysFanIndex {
            type string;
        }

        leaf cmmAlarmVarString {
            type string;
        }
    }

    notification cmmWarningFanTrayStall {

        description "Set when Given Fan Tray Stalled.";

        leaf cmmSysFanTrayNumber {
            type string;
        }

        leaf cmmSysFanIndex {
            type string;
        }

        leaf cmmAlarmVarString {
            type string;
        }
    }

    notification cmmWarningFanTrayStallRecovered {

        description "Set when Given Fan Tray is recovered.";

        leaf cmmSysFanTrayNumber {
            type string;
        }

        leaf cmmSysFanIndex {
            type string;
        }

        leaf cmmAlarmVarString {
            type string;
        }
    }

    notification cmmAlarmPowerExceed {

        description "Set when Power will be above threshold.";

        leaf cmmSysPowerSupplyIndex {
            type string;
        }

        leaf cmmSysPSConsumption {
            type string;
        }

        leaf cmmAlarmVarString {
            type string;
        }
    }

    notification cmmAlarmTxPowerHigh {

        description "Set when Transferred Power exceeds high alarm level.";

        leaf cmmSysPortIndex {
            type string;
        }

        leaf cmmStackUnitIndex {
            type string;
        }

        leaf cmmSysPortType {
            type string;
        }

        leaf cmmSysTxOutputPower {
            type string;
        }

        leaf cmmAlarmVarString {
            type string;
        }
    }

    notification cmmAlarmTxPowerLow {

        description "Set when Transferred Power is below low alarm level..";

        leaf cmmSysPortIndex {
            type string;
        }

        leaf cmmStackUnitIndex {
            type string;
        }

        leaf cmmSysPortType {
            type string;
        }

        leaf cmmSysTxOutputPower {
            type string;
        }

        leaf cmmAlarmVarString {
            type string;
        }
    }

    notification cmmWarningTxPowerHigh {

        description "Set when Transferred Power exceeds high warning level.";

        leaf cmmSysPortIndex {
            type string;
        }

        leaf cmmStackUnitIndex {
            type string;
        }

        leaf cmmSysPortType {
            type string;
        }

        leaf cmmSysTxOutputPower {
            type string;
        }

        leaf cmmAlarmVarString {
            type string;
        }
    }

    notification cmmWarningTxPowerLow {

        description "Set when Transferred Power is below low warning level.";

        leaf cmmSysPortIndex {
            type string;
        }

        leaf cmmStackUnitIndex {
            type string;
        }

        leaf cmmSysPortType {
            type string;
        }

        leaf cmmSysTxOutputPower {
            type string;
        }

        leaf cmmAlarmVarString {
            type string;
        }
    }

}
