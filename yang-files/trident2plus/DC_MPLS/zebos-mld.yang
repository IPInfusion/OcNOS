/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-mld.yang
*
*/

submodule zebos-mld {

    belongs-to  zebos { prefix zebos; }

    import cml_data_types {
        prefix cml_data_types;
    }

    import feature_list {
        prefix feature_list;
    }

    include zebos-interface;
    include zebos-vrf;
    organization
        "IP Infusion Inc.";

    contact
        "Address: 3965 Freedom Circle, Suite 200, Santa Clara, CA 95054
        Phone: +1 408-400-1900
        E-mail: support@ipinfusion.com
        Web: http://www.ipinfusion.com/";


    revision "2017-08-01" {
        description "changes for Jira fix.";
    }

    revision "2017-02-02" {
        description "changes for Documentation.";
    }

    revision "2017-01-27" {
        description "changes for Debug command.";
    }

    revision "2017-01-25" {
        description "fix for JIRA-12076 must case attributes.";
    }

    revision "2016-10-14" {
        description "Updated versionNumber Range value.";
    }



    grouping mrib6Mld-grouping {
        list mrib6Mld {
            if-feature feature_list:HAVE_MCAST_IPV6;
            key "vrfName";
            description
                "mrib6Mld";
            leaf vrId  {
                type  cml_data_types:CML_INT32_T;
                description "";
            } // END of vrId definition.

            leaf vrfName  {
                type  cml_data_types:CML_STRING_T {
                    length "0..255";
                }
                description "";
            } // END of vrfName definition.

            leaf setSSMEnabledFlag  {
                type  cml_data_types:CML_BOOL_T;
                default false;
                description "";
            } // END of setSSMEnabledFlag definition.

            leaf MLDlimit  {
                type  cml_data_types:CML_UINT32_T {
                     range "1..2097152";
                }
                default "1";
                description "";
            } // END of MLDlimit definition.

            leaf exceptionAccessList  {
                type  cml_data_types:CML_STRING_T {
                    length "0..255";
                }
                default "NULL";
                description "";
            } // END of exceptionAccessList definition.

            leaf mli_num_grecs  {
                type  cml_data_types:CML_UINT32_T;
                config false;
                description "";
            } // END of mli_num_grecs definition.

            leaf ssmStaticFlag  {
                type  cml_data_types:CML_STRING_T {
                    length "0..255";
                }
                config false;
                description "";
            } // END of ssmStaticFlag definition.

            leaf debugFlag  {
                type  cml_data_types:CML_MLD_DEBUG_T;
                description "";
            } // END of debugFlag definition.

            leaf termdebugFlag  {
                type  cml_data_types:CML_MLD_DEBUG_T;
                description "";
            } // END of termdebugFlag definition.


            list ssmStatic {
                key "staticAccessListName";
                description
                    "ssmStatic";
                leaf staticAccessListName  {
                    type  cml_data_types:CML_STRING_T {
                        length "0..255";
                    }
                    description "";
                } // END of staticAccessListName definition.

                leaf-list sourceAddr  {
                    type  cml_data_types:CML_STRING_T {
                        length "0..255";
                    }
                    description "";
                } // END of sourceAddr definition.

            } // End of ssmStatic-list
        } // End of mrib6Mld-list
    } // END of mrib6Mld-grouping definition.


    grouping mrib6mldInterface-grouping {
        list mrib6mldInterface {
            if-feature feature_list:HAVE_MCAST_IPV6;
            key "ifName";
            description
                "MLD interface related operations";
            leaf ifName  {
                type  cml_data_types:CML_STRING_T {
                    length "0..255";
                }
                description "";
            } // END of ifName definition.

            leaf setMLDIfFlag  {
                type  cml_data_types:CML_BOOL_T;
                description "";
            } // END of setMLDIfFlag definition.

            leaf lastMaxQueryCount  {
                type  cml_data_types:CML_UINT32_T {
                     range "2..7";
                }
                default "2";
                description "";
            } // END of lastMaxQueryCount definition.

            leaf lastMaxQueryInterval  {
                type  cml_data_types:CML_UINT32_T {
                     range "1000..25500";
                }
                default "1000";
                description "";
            } // END of lastMaxQueryInterval definition.

            leaf proxyreportInterval  {
                type  cml_data_types:CML_UINT32_T {
                     range "1000..25500";
                }
                default "1000";
                description "";
            } // END of proxyreportInterval definition.

            leaf proxyIfName  {
                type  cml_data_types:CML_STRING_T {
                    length "0..255";
                }
                default "NULL";
                description "";
            } // END of proxyIfName definition.

            leaf querierTimeout  {
                type  cml_data_types:CML_UINT16_T {
                     range "60..300";
                }
                default "250";
                description "";
            } // END of querierTimeout definition.

            leaf queryInterval  {
                type  cml_data_types:CML_UINT32_T {
                     range "1..18000";
                }
                default "125";
                description "";
            } // END of queryInterval definition.

            leaf startUpQueryInterval  {
                type  cml_data_types:CML_UINT32_T {
                     range "1..18000";
                }
                default "31";
                description "";
            } // END of startUpQueryInterval definition.

            leaf queryCount  {
                type  cml_data_types:CML_UINT32_T {
                     range "2..10";
                }
                default "2";
                description "";
            } // END of queryCount definition.

            leaf responseInterval  {
                type  cml_data_types:CML_UINT32_T {
                     range "1..240";
                }
                default "10";
                description "";
            } // END of responseInterval definition.

            leaf robustnessVariableVal  {
                type  cml_data_types:CML_UINT32_T {
                     range "2..7";
                }
                default "2";
                description "";
            } // END of robustnessVariableVal definition.

            leaf versionNumber  {
                type  cml_data_types:CML_UINT16_T {
                     range "1..2";
                }
                description "";
            } // END of versionNumber definition.

            leaf setMLDIfPxyFlag  {
                type  cml_data_types:CML_BOOL_T;
                description "";
            } // END of setMLDIfPxyFlag definition.

            leaf accessListName  {
                type  cml_data_types:CML_STRING_T {
                    length "0..255";
                }
                default "NULL";
                description "";
            } // END of accessListName definition.

            leaf immediateGroupListName  {
                type  cml_data_types:CML_STRING_T {
                    length "0..255";
                }
                default "NULL";
                description "";
            } // END of immediateGroupListName definition.

            leaf stateMLDIFLimit  {
                type  cml_data_types:CML_UINT32_T {
                     range "1..2097152";
                }
                default "1";
                description "";
            } // END of stateMLDIFLimit definition.

            leaf ifExceptionAccessList  {
                type  cml_data_types:CML_STRING_T {
                    length "0..255";
                }
                default "NULL";
                description "";
            } // END of ifExceptionAccessList definition.

            leaf interfaceName  {
                type  cml_data_types:CML_STRING_T {
                    length "0..255";
                }
                config false;
                description "";
            } // END of interfaceName definition.

            leaf state  {
                type  cml_data_types:CML_STRING_T {
                    length "0..255";
                }
                config false;
                description "";
            } // END of state definition.

            leaf hostVersion  {
                type  cml_data_types:CML_STRING_T {
                    length "0..255";
                }
                config false;
                description "";
            } // END of hostVersion definition.

            leaf InternetAddr  {
                type  cml_data_types:CML_STRING_T {
                    length "0..255";
                }
                config false;
                description "";
            } // END of InternetAddr definition.

            leaf upTime  {
                type  cml_data_types:CML_STRING_T {
                    length "0..255";
                }
                config false;
                description "";
            } // END of upTime definition.

            leaf proxyOperationalStatus  {
                type  cml_data_types:CML_STRING_T {
                    length "0..255";
                }
                config false;
                description "";
            } // END of proxyOperationalStatus definition.

            leaf OtherQuerierAddr  {
                type  cml_data_types:CML_STRING_T {
                    length "0..255";
                }
                config false;
                description "";
            } // END of OtherQuerierAddr definition.

            leaf ifIndex  {
                type  cml_data_types:CML_UINT32_T;
                config false;
                description "";
            } // END of ifIndex definition.

            leaf grpMemInterval  {
                type  cml_data_types:CML_UINT32_T;
                config false;
                description "";
            } // END of grpMemInterval definition.

            leaf stat_mlif_num_v1_reports  {
                type  cml_data_types:CML_UINT32_T;
                config false;
                description "";
            } // END of stat_mlif_num_v1_reports definition.

            leaf stat_mlif_num_v2_reports  {
                type  cml_data_types:CML_UINT32_T;
                config false;
                description "";
            } // END of stat_mlif_num_v2_reports definition.

            leaf stat_mlif_num_v1_leaves  {
                type  cml_data_types:CML_UINT32_T;
                config false;
                description "";
            } // END of stat_mlif_num_v1_leaves definition.

            leaf statesCount  {
                type  cml_data_types:CML_UINT32_T;
                config false;
                description "";
            } // END of statesCount definition.

            leaf interfaceLimit  {
                type  cml_data_types:CML_UINT32_T;
                config false;
                description "";
            } // END of interfaceLimit definition.

            leaf limitExceptAccessList  {
                type  cml_data_types:CML_STRING_T {
                    length "0..255";
                }
                config false;
                description "";
            } // END of limitExceptAccessList definition.

            leaf mcastgCount  {
                type  cml_data_types:CML_UINT32_T;
                config false;
                description "";
            } // END of mcastgCount definition.

            leaf querierState  {
                type  cml_data_types:CML_STRING_T {
                    length "0..255";
                }
                config false;
                description "";
            } // END of querierState definition.

            leaf mldState  {
                type  cml_data_types:CML_STRING_T {
                    length "0..255";
                }
                config false;
                description "";
            } // END of mldState definition.

            leaf mlif_querier_wcount  {
                type  cml_data_types:CML_UINT16_T;
                config false;
                description "";
            } // END of mlif_querier_wcount definition.


            list staticGroup {
                key "multicastGroupAddr";
                description
                    "staticGroup";
                leaf multicastGroupAddr  {
                    type  cml_data_types:CML_IPV6_ADDR_T;
                    description "";
                } // END of multicastGroupAddr definition.

                leaf sgInterfaceName  {
                    type  cml_data_types:CML_STRING_T {
                        length "0..255";
                    }
                    config false;
                    description "";
                } // END of sgInterfaceName definition.

                leaf groupFlags  {
                    type  cml_data_types:CML_STRING_T {
                        length "0..255";
                    }
                    config false;
                    description "";
                } // END of groupFlags definition.

                leaf groupUpTime  {
                    type  cml_data_types:CML_STRING_T {
                        length "0..255";
                    }
                    config false;
                    description "";
                } // END of groupUpTime definition.

                leaf groupMode  {
                    type  cml_data_types:CML_STRING_T {
                        length "0..255";
                    }
                    config false;
                    description "";
                } // END of groupMode definition.

                leaf groupExpiry  {
                    type  cml_data_types:CML_STRING_T {
                        length "0..255";
                    }
                    config false;
                    description "";
                } // END of groupExpiry definition.

                leaf groupSFlags  {
                    type  cml_data_types:CML_STRING_T {
                        length "0..255";
                    }
                    config false;
                    description "";
                } // END of groupSFlags definition.

                leaf lastReporter  {
                    type  cml_data_types:CML_STRING_T {
                        length "0..255";
                    }
                    config false;
                    description "";
                } // END of lastReporter definition.

                leaf t_mgr_v1_host_present  {
                    type  cml_data_types:CML_UINT32_T;
                    config false;
                    description "";
                } // END of t_mgr_v1_host_present definition.

            } // End of staticGroup-list

            list staticGroupSourceAddr {
                key "multicastSrcGroupAddr";
                description
                    "staticGroupSourceAddr";
                leaf multicastSrcGroupAddr  {
                    type  cml_data_types:CML_IPV6_ADDR_T;
                    description "";
                } // END of multicastSrcGroupAddr definition.

                leaf isSsmMapped  {
                    type  cml_data_types:CML_BOOL_T;
                    description "";
                } // END of isSsmMapped definition.


                list src_a_tib_grp {
                    key "StaticsourceAddr";
                    description
                        "srcCMLSEPaCMLSEPtibCMLSEPgrp";
                    leaf StaticsourceAddr  {
                        type  cml_data_types:CML_STRING_T {
                            length "0..255";
                        }
                        description "";
                    } // END of StaticsourceAddr definition.

                    leaf srcAUpTime  {
                        type  cml_data_types:CML_STRING_T {
                            length "0..255";
                        }
                        config false;
                        description "";
                    } // END of srcAUpTime definition.

                    leaf srcAExpiry  {
                        type  cml_data_types:CML_STRING_T {
                            length "0..255";
                        }
                        config false;
                        description "";
                    } // END of srcAExpiry definition.

                    leaf srcAStr  {
                        type  cml_data_types:CML_STRING_T {
                            length "0..255";
                        }
                        config false;
                        description "";
                    } // END of srcAStr definition.

                    leaf srcASFlags  {
                        type  cml_data_types:CML_STRING_T {
                            length "0..255";
                        }
                        config false;
                        description "";
                    } // END of srcASFlags definition.

                } // End of src_a_tib_grp-list

                list src_b_tib_grp {
                    key "srcBAddr";
                    config false;
                    description
                        "srcCMLSEPbCMLSEPtibCMLSEPgrp";
                    leaf srcBAddr  {
                        type  cml_data_types:CML_STRING_T {
                            length "0..255";
                        }
                        description "";
                    } // END of srcBAddr definition.

                    leaf srcBUpTime  {
                        type  cml_data_types:CML_STRING_T {
                            length "0..255";
                        }
                        description "";
                    } // END of srcBUpTime definition.

                    leaf srcBExpiry  {
                        type  cml_data_types:CML_STRING_T {
                            length "0..255";
                        }
                        description "";
                    } // END of srcBExpiry definition.

                    leaf srcBstr  {
                        type  cml_data_types:CML_STRING_T {
                            length "0..255";
                        }
                        description "";
                    } // END of srcBstr definition.

                    leaf srcBSFlags  {
                        type  cml_data_types:CML_STRING_T {
                            length "0..255";
                        }
                        description "";
                    } // END of srcBSFlags definition.

                } // End of src_b_tib_grp-list
            } // End of staticGroupSourceAddr-list

            list ProxyGroup {
                key "ProxyGroupAddr";
                config false;
                description
                    "ProxyGroup";
                leaf ProxyInterfaceName  {
                    type  cml_data_types:CML_STRING_T {
                        length "0..255";
                    }
                    description "";
                } // END of ProxyInterfaceName definition.

                leaf ProxyGroupAddr  {
                    type  cml_data_types:CML_STRING_T {
                        length "0..255";
                    }
                    description "";
                } // END of ProxyGroupAddr definition.

                leaf ProxyGroupMode  {
                    type  cml_data_types:CML_STRING_T {
                        length "0..255";
                    }
                    description "";
                } // END of ProxyGroupMode definition.

                leaf ProxyGroupState  {
                    type  cml_data_types:CML_STRING_T {
                        length "0..255";
                    }
                    description "";
                } // END of ProxyGroupState definition.

                leaf ProxyGroupMemberState  {
                    type  cml_data_types:CML_STRING_T {
                        length "0..255";
                    }
                    description "";
                } // END of ProxyGroupMemberState definition.

                leaf src_a_tib_addr  {
                    type  cml_data_types:CML_STRING_T {
                        length "0..255";
                    }
                    description "";
                } // END of src_a_tib_addr definition.

                leaf src_b_tib_addr  {
                    type  cml_data_types:CML_STRING_T {
                        length "0..255";
                    }
                    description "";
                } // END of src_b_tib_addr definition.

            } // End of ProxyGroup-list
        } // End of mrib6mldInterface-list
    } // END of mrib6mldInterface-grouping definition.


}
