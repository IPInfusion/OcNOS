/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebos-mstp.yang
*
*/

submodule zebos-mstp {

    belongs-to  zebos { prefix zebos; }

    import cml_data_types {
        prefix cml_data_types;
    }

    import feature_list {
        prefix feature_list;
    }

    include zebos-interface;
    include zebos-vlan;
    organization
        "IP Infusion Inc.";

    contact
        "Address: 3965 Freedom Circle, Suite 200, Santa Clara, CA 95054
        Phone: +1 408-400-1900
        E-mail: support@ipinfusion.com
        Web: http://www.ipinfusion.com/";

    description
        "Layer-2 bridge configurations";


    revision "2018-06-21" {
        description " Initial Version.";
        reference "";
    }



    grouping spanningPort-grouping {
    description
        "spanningPort";
        list spanningPort {
            if-feature feature_list:HAVE_DEFAULT_BRIDGE;
            key "ifName";
            description
                "spanningPort";
            leaf ifName  {
                type  cml_data_types:CML_STRING_T {
                    length "0..255";
                }
                description "";
            } // END of ifName definition.

            leaf bridgeId  {
                type  cml_data_types:CML_STRING_T {
                    length "0..255";
                }
                default "0";
                description "";
            } // END of bridgeId definition.

            leaf pathCost  {
                type  cml_data_types:CML_UINT32_T {
                     range "1..200000000";
                }
                description "";
            } // END of pathCost definition.

            uses mstpPortRuntimeAttrs;
        } // End of spanningPort-list
    } // END of spanningPort-grouping definition.


    grouping mstpPort-grouping {
    description
        "mstpPort";
        list mstpPort {
            key "ifName";
            description
                "mstpPort";
            leaf ifName  {
                type  cml_data_types:CML_STRING_T {
                    length "0..255";
                }
                description "";
            } // END of ifName definition.

            leaf adminp2pMac  {
                type  cml_data_types:CML_LINK_TYPE_T;
                default "point-to-point";
                description "";
            } // END of adminp2pMac definition.

            leaf autoEdge  {
                type  cml_data_types:CML_BOOL_T;
                default false;
                description "";
            } // END of autoEdge definition.

            leaf portfastConf  {
                type  cml_data_types:CML_PORTEDGE_T;
                default "portfast";
                description "";
            } // END of portfastConf definition.

            leaf enableBPDUrx  {
                if-feature feature_list:HAVE_L2GP;
                type  cml_data_types:CML_ENABLEBPDURX_T;
                default "enableBPDUrx";
                description "";
            } // END of enableBPDUrx definition.

            leaf psuedoRootId  {
                if-feature feature_list:HAVE_L2GP;
                type  cml_data_types:CML_STRING_T {
                    length "0..255";
                }
                description "";
            } // END of psuedoRootId definition.

            leaf adminBpduguard  {
                type  cml_data_types:CML_BPDU_T;
                default "default";
                description "";
            } // END of adminBpduguard definition.

            leaf adminBpdufilter  {
                type  cml_data_types:CML_BPDU_T;
                default "default";
                description "";
            } // END of adminBpdufilter definition.

            leaf adminRootGuard  {
                type  cml_data_types:CML_BOOL_T;
                default false;
                description "";
            } // END of adminRootGuard definition.

            leaf restrictedRole  {
                type  cml_data_types:CML_BOOL_T;
                default false;
                description "";
            } // END of restrictedRole definition.

            leaf restrictedDomainRole  {
                type  cml_data_types:CML_BOOL_T;
                default false;
                description "";
            } // END of restrictedDomainRole definition.

            leaf restrictedTCN  {
                type  cml_data_types:CML_BOOL_T;
                default false;
                description "";
            } // END of restrictedTCN definition.

            leaf helloTime  {
                type  cml_data_types:CML_INT32_T {
                     range "1..10";
                }
                default "2";
                description "";
            } // END of helloTime definition.

            leaf pathCost  {
                type  cml_data_types:CML_UINT32_T {
                     range "1..200000000";
                }
                description "";
            } // END of pathCost definition.

            leaf bridgeId  {
                type  cml_data_types:CML_STRING_T {
                    length "0..255";
                }
                description "";
            } // END of bridgeId definition.

            leaf portPriority  {
                type  cml_data_types:CML_INT16_T {
                     range "0..240";
                }
                default "128";
                description "";
            } // END of portPriority definition.


            list bridgegroup {
                key "bridgeId";
                description
                    "bridgegroup";
                leaf bridgeId  {
                    type  cml_data_types:CML_STRING_T {
                        length "0..255";
                    }
                    description "";
                } // END of bridgeId definition.

                uses vlanportgrp;
            } // End of bridgegroup-list

            list vlanRpvstRole {
                key "vlanId";
                description
                    "vlanRpvstRole";
                leaf vlanId  {
                    type  cml_data_types:CML_STRING_T {
                        length "0..255";
                    }
                    description "";
                } // END of vlanId definition.

                leaf vlanrestrictedRole  {
                    if-feature feature_list:HAVE_RPVST_PLUS;
                    type  cml_data_types:CML_BOOL_T;
                    default false;
                    description "";
                } // END of vlanrestrictedRole definition.

                leaf vlanrestrictedTCN  {
                    if-feature feature_list:HAVE_RPVST_PLUS;
                    type  cml_data_types:CML_BOOL_T;
                    default false;
                    description "";
                } // END of vlanrestrictedTCN definition.

            } // End of vlanRpvstRole-list
            uses mstpPortRuntimeAttrs;
        } // End of mstpPort-list
    } // END of mstpPort-grouping definition.


    grouping backboneBridgePort-grouping {
    description
        "backboneBridgePort";
        list backboneBridgePort {
            key "ifName";
            description
                "backboneBridgePort";
            leaf ifName  {
                type  cml_data_types:CML_STRING_T {
                    length "0..255";
                }
                description "";
            } // END of ifName definition.

            leaf bridgeId  {
                type  cml_data_types:CML_STRING_T {
                    length "0..255";
                }
                description "";
            } // END of bridgeId definition.

            leaf portPriority  {
                type  cml_data_types:CML_INT16_T {
                     range "0..240";
                }
                default "128";
                description "";
            } // END of portPriority definition.

            leaf pathCost  {
                type  cml_data_types:CML_UINT32_T {
                     range "1..200000000";
                }
                description "";
            } // END of pathCost definition.

        } // End of backboneBridgePort-list
    } // END of backboneBridgePort-grouping definition.


    grouping backboneBridgeInstance-grouping {
    description
        "backboneBridgeInstance";
        list backboneBridgeInstance {
            key "instanceId";
            description
                "backboneBridgeInstance";
            leaf instanceId  {
                type  cml_data_types:CML_INT32_T {
                     range "1..63";
                }
                description "";
            } // END of instanceId definition.


            list backboneInterface {
                key "ifName";
                description
                    "Group of mstp attribute having interface property";
                leaf ifName  {
                    type  cml_data_types:CML_STRING_T {
                        length "0..255";
                    }
                    description "";
                } // END of ifName definition.

                leaf mstiPriority  {
                    type  cml_data_types:CML_INT16_T {
                         range "0..240";
                    }
                    default "128";
                    description "";
                } // END of mstiPriority definition.

                leaf mstppathCost  {
                    type  cml_data_types:CML_UINT32_T {
                         range "1..200000000";
                    }
                    default "20000000";
                    description "";
                } // END of mstppathCost definition.

            } // End of backboneInterface-list
            uses mstpBridgeInstanceAttrs;
        } // End of backboneBridgeInstance-list
    } // END of backboneBridgeInstance-grouping definition.


    grouping customerSpanningtree-grouping {
    description
        "customerSpanningtree";
        list customerSpanningtree {
            if-feature feature_list:HAVE_PROVIDER_BRIDGE;
            key "ifName";
            description
                "customerSpanningtree";
            leaf ifName  {
                type  cml_data_types:CML_STRING_T {
                    length "0..255";
                }
                description "";
            } // END of ifName definition.

            leaf cistBridgePriority  {
                type  cml_data_types:CML_UINT32_T {
                     range "0..61440";
                }
                default "61440";
                description "";
            } // END of cistBridgePriority definition.

            leaf bridgeMaxAge  {
                type  cml_data_types:CML_INT32_T {
                     range "6..40";
                }
                default "20";
                description "";
            } // END of bridgeMaxAge definition.

            leaf bridgehelloTime  {
                type  cml_data_types:CML_INT32_T {
                     range "1..10";
                }
                default "2";
                description "";
            } // END of bridgehelloTime definition.

            leaf bridgeforwardDelay  {
                type  cml_data_types:CML_INT32_T {
                     range "4..30";
                }
                default "15";
                description "";
            } // END of bridgeforwardDelay definition.

            leaf transmitHoldCount  {
                type  cml_data_types:CML_UINT8_T {
                     range "1..10";
                }
                default "6";
                description "";
            } // END of transmitHoldCount definition.

            leaf portPriority  {
                type  cml_data_types:CML_INT16_T {
                     range "0..240";
                }
                default "128";
                description "";
            } // END of portPriority definition.

            leaf providerPortPriority  {
                type  cml_data_types:CML_INT16_T {
                     range "0..240";
                }
                default "128";
                description "";
            } // END of providerPortPriority definition.

            leaf mstppathCost  {
                type  cml_data_types:CML_UINT32_T {
                     range "1..200000000";
                }
                default "20000000";
                description "";
            } // END of mstppathCost definition.

            leaf mstpProviderpathCost  {
                type  cml_data_types:CML_UINT32_T {
                     range "1..200000000";
                }
                default "20000000";
                description "";
            } // END of mstpProviderpathCost definition.

            leaf svlanId  {
                type  cml_data_types:CML_UINT16_T {
                     range "1..4094";
                }
                description "";
            } // END of svlanId definition.

        } // End of customerSpanningtree-list
    } // END of customerSpanningtree-grouping definition.
    grouping mstpBridgeruntimeAttrs {
        description
            "mstpBridgeruntimeAttrs";
        leaf type  {
            type  cml_data_types:CML_UINT8_T;
            config false;
            description "";
        } // END of type definition.

        leaf lowPort  {
            type  cml_data_types:CML_UINT32_T;
            config false;
            description "";
        } // END of lowPort definition.

        leaf bridgeAddr  {
            type  cml_data_types:CML_STRING_T {
                length "0..255";
            }
            config false;
            description "";
        } // END of bridgeAddr definition.

        leaf cistinstBridgeId  {
            type  cml_data_types:CML_STRING_T {
                length "0..255";
            }
            config false;
            description "";
        } // END of cistinstBridgeId definition.

        leaf instcistDesignatedRoot  {
            type  cml_data_types:CML_STRING_T {
                length "0..255";
            }
            config false;
            description "";
        } // END of instcistDesignatedRoot definition.

        leaf cistRegRoot  {
            type  cml_data_types:CML_STRING_T {
                length "0..255";
            }
            config false;
            description "";
        } // END of cistRegRoot definition.

        leaf cistRcvdRegRoot  {
            type  cml_data_types:CML_STRING_T {
                length "0..255";
            }
            config false;
            description "";
        } // END of cistRcvdRegRoot definition.

        leaf cistmstpDesignatedBridge  {
            type  cml_data_types:CML_STRING_T {
                length "0..255";
            }
            config false;
            description "";
        } // END of cistmstpDesignatedBridge definition.

        leaf externalrootPathcost  {
            type  cml_data_types:CML_UINT32_T;
            config false;
            description "";
        } // END of externalrootPathcost definition.

        leaf internalrootPathcost  {
            type  cml_data_types:CML_UINT32_T;
            config false;
            description "";
        } // END of internalrootPathcost definition.

        leaf cistPortRootid  {
            type  cml_data_types:CML_UINT16_T;
            config false;
            description "";
        } // END of cistPortRootid definition.

        leaf cistRootPortIfindex  {
            type  cml_data_types:CML_UINT32_T;
            config false;
            description "";
        } // END of cistRootPortIfindex definition.

        leaf bpduRecvPortIfindex  {
            type  cml_data_types:CML_UINT32_T;
            config false;
            description "";
        } // END of bpduRecvPortIfindex definition.

        leaf rootPort  {
            type  cml_data_types:CML_STRING_T {
                length "0..255";
            }
            config false;
            description "";
        } // END of rootPort definition.

        leaf alternatePort  {
            type  cml_data_types:CML_STRING_T {
                length "0..255";
            }
            config false;
            description "";
        } // END of alternatePort definition.

        leaf cistMaxAge  {
            type  cml_data_types:CML_UINT32_T;
            config false;
            description "";
        } // END of cistMaxAge definition.

        leaf brcistMessageAge  {
            type  cml_data_types:CML_UINT32_T;
            config false;
            description "";
        } // END of brcistMessageAge definition.

        leaf brcistHelloTime  {
            type  cml_data_types:CML_UINT32_T;
            config false;
            description "";
        } // END of brcistHelloTime definition.

        leaf brcistForwardDelay  {
            type  cml_data_types:CML_UINT32_T;
            config false;
            description "";
        } // END of brcistForwardDelay definition.

        leaf hopCount  {
            type  cml_data_types:CML_UINT32_T;
            config false;
            description "";
        } // END of hopCount definition.

        leaf recentRoot  {
            type  cml_data_types:CML_UINT32_T;
            config false;
            description "";
        } // END of recentRoot definition.

        leaf brAllrrTimerCnt  {
            type  cml_data_types:CML_UINT32_T;
            config false;
            description "";
        } // END of brAllrrTimerCnt definition.

        leaf learningEnabled  {
            type  cml_data_types:CML_UINT8_T;
            config false;
            description "";
        } // END of learningEnabled definition.

        leaf topologyChange  {
            type  cml_data_types:CML_UINT8_T;
            config false;
            description "";
        } // END of topologyChange definition.

        leaf topologychangeDetected  {
            type  cml_data_types:CML_UINT8_T;
            config false;
            description "";
        } // END of topologychangeDetected definition.

        leaf bridgeEnabled  {
            type  cml_data_types:CML_UINT8_T;
            config false;
            description "";
        } // END of bridgeEnabled definition.

        leaf isVlanAware  {
            type  cml_data_types:CML_UINT8_T;
            config false;
            description "";
        } // END of isVlanAware definition.

        leaf reselect  {
            type  cml_data_types:CML_UINT8_T;
            config false;
            description "";
        } // END of reselect definition.

        leaf ageingTimeIsFwdDelay  {
            type  cml_data_types:CML_UINT8_T;
            config false;
            description "";
        } // END of ageingTimeIsFwdDelay definition.

        leaf ceBridge  {
            type  cml_data_types:CML_UINT8_T;
            config false;
            description "";
        } // END of ceBridge definition.

        leaf cnBridge  {
            type  cml_data_types:CML_UINT8_T;
            config false;
            description "";
        } // END of cnBridge definition.

        leaf isDefault  {
            type  cml_data_types:CML_UINT8_T;
            config false;
            description "";
        } // END of isDefault definition.

        leaf portIndex  {
            type  cml_data_types:CML_UINT8_T;
            config false;
            description "";
        } // END of portIndex definition.

    } // END of mstpBridgeruntimeAttrs definition.
    grouping mstpInstanceRuntimeAttr {
        description
            "mstp instance runtime attrs";
        leaf lowPort  {
            type  cml_data_types:CML_UINT32_T;
            config false;
            description "";
        } // END of lowPort definition.

        leaf master  {
            type  cml_data_types:CML_UINT8_T;
            config false;
            description "";
        } // END of master definition.

        leaf learningEnabled  {
            type  cml_data_types:CML_UINT8_T;
            config false;
            description "";
        } // END of learningEnabled definition.

        leaf mstiMastered  {
            type  cml_data_types:CML_UINT8_T;
            config false;
            description "";
        } // END of mstiMastered definition.

        leaf reselect  {
            type  cml_data_types:CML_UINT8_T;
            config false;
            description "";
        } // END of reselect definition.

        leaf instmstpEnabled  {
            type  cml_data_types:CML_UINT8_T;
            config false;
            description "";
        } // END of instmstpEnabled definition.

        leaf mstiBridgeId  {
            type  cml_data_types:CML_STRING_T {
                length "0..255";
            }
            config false;
            description "";
        } // END of mstiBridgeId definition.

        leaf recentRoot  {
            type  cml_data_types:CML_UINT32_T;
            config false;
            description "";
        } // END of recentRoot definition.

        leaf brInstAllRrTimerCntt  {
            type  cml_data_types:CML_UINT32_T;
            config false;
            description "";
        } // END of brInstAllRrTimerCntt definition.

        leaf mstidesignatedRoot  {
            type  cml_data_types:CML_STRING_T {
                length "0..255";
            }
            config false;
            description "";
        } // END of mstidesignatedRoot definition.

        leaf mstiDesignatedBridge  {
            type  cml_data_types:CML_STRING_T {
                length "0..255";
            }
            config false;
            description "";
        } // END of mstiDesignatedBridge definition.

        leaf instinternalRootPathCost  {
            type  cml_data_types:CML_UINT32_T;
            config false;
            description "";
        } // END of instinternalRootPathCost definition.

        leaf mstiRootportId  {
            type  cml_data_types:CML_UINT32_T;
            config false;
            description "";
        } // END of mstiRootportId definition.

        leaf mstiRootPortIfindex  {
            type  cml_data_types:CML_INT32_T;
            config false;
            description "";
        } // END of mstiRootPortIfindex definition.

        leaf portIndex  {
            type  cml_data_types:CML_INT32_T;
            config false;
            description "";
        } // END of portIndex definition.

        leaf hopCount  {
            type  cml_data_types:CML_INT32_T;
            config false;
            description "";
        } // END of hopCount definition.

        leaf tcFlag  {
            type  cml_data_types:CML_STRING_T {
                length "0..255";
            }
            config false;
            description "";
        } // END of tcFlag definition.

        leaf insttopologychangedetected  {
            type  cml_data_types:CML_STRING_T {
                length "0..255";
            }
            config false;
            description "";
        } // END of insttopologychangedetected definition.

        leaf timeLastTopoChange  {
            type  cml_data_types:CML_STRING_T {
                length "0..255";
            }
            config false;
            description "";
        } // END of timeLastTopoChange definition.

        leaf numTopoChanges  {
            type  cml_data_types:CML_INT32_T;
            config false;
            description "";
        } // END of numTopoChanges definition.

        leaf totalNumTopoChanges  {
            type  cml_data_types:CML_INT32_T;
            config false;
            description "";
        } // END of totalNumTopoChanges definition.

        leaf tcInitiator  {
            type  cml_data_types:CML_INT32_T;
            config false;
            description "";
        } // END of tcInitiator definition.

        leaf insttcLastRcvdFrom  {
            type  cml_data_types:CML_STRING_T {
                length "0..255";
            }
            config false;
            description "";
        } // END of insttcLastRcvdFrom definition.

        leaf messageAge  {
            if-feature feature_list:HAVE_RPVST_PLUS;
            type  cml_data_types:CML_UINT32_T;
            config false;
            description "";
        } // END of messageAge definition.

        leaf instanceMaxage  {
            if-feature feature_list:HAVE_RPVST_PLUS;
            type  cml_data_types:CML_UINT32_T;
            config false;
            description "";
        } // END of instanceMaxage definition.

        leaf fwdDelay  {
            if-feature feature_list:HAVE_RPVST_PLUS;
            type  cml_data_types:CML_UINT32_T;
            config false;
            description "";
        } // END of fwdDelay definition.

        leaf helloTimeInstance  {
            if-feature feature_list:HAVE_RPVST_PLUS;
            type  cml_data_types:CML_UINT32_T;
            config false;
            description "";
        } // END of helloTimeInstance definition.

    } // END of mstpInstanceRuntimeAttr definition.
    grouping mstpInstancePortRuntimeAttrs {
        description
            "mstpInstancePortRuntimeAttrs";
        leaf refCount  {
            type  cml_data_types:CML_STRING_T {
                length "0..255";
            }
            config false;
            description "";
        } // END of refCount definition.

        leaf typeintf  {
            type  cml_data_types:CML_UINT8_T;
            config false;
            description "";
        } // END of typeintf definition.

        leaf instifIndex  {
            type  cml_data_types:CML_UINT8_T;
            config false;
            description "";
        } // END of instifIndex definition.

        leaf mstiPortId  {
            type  cml_data_types:CML_UINT8_T;
            config false;
            description "";
        } // END of mstiPortId definition.

        leaf internalRootpathCostintf  {
            type  cml_data_types:CML_UINT32_T;
            config false;
            description "";
        } // END of internalRootpathCostintf definition.

        leaf designatedInternalrootPathcost  {
            type  cml_data_types:CML_UINT32_T;
            config false;
            description "";
        } // END of designatedInternalrootPathcost definition.

        leaf mstiRoot  {
            type  cml_data_types:CML_STRING_T {
                length "0..255";
            }
            config false;
            description "";
        } // END of mstiRoot definition.

        leaf designatedBridgePort  {
            type  cml_data_types:CML_STRING_T {
                length "0..255";
            }
            config false;
            description "";
        } // END of designatedBridgePort definition.

        leaf designatedInsPortid  {
            type  cml_data_types:CML_UINT16_T;
            config false;
            description "";
        } // END of designatedInsPortid definition.

        leaf messageAgeintf  {
            type  cml_data_types:CML_UINT32_T;
            config false;
            description "";
        } // END of messageAgeintf definition.

        leaf maxAgeintf  {
            type  cml_data_types:CML_UINT32_T;
            config false;
            description "";
        } // END of maxAgeintf definition.

        leaf fwdDelayintf  {
            type  cml_data_types:CML_UINT32_T;
            config false;
            description "";
        } // END of fwdDelayintf definition.

        leaf helloTimeintf  {
            type  cml_data_types:CML_UINT32_T;
            config false;
            description "";
        } // END of helloTimeintf definition.

        leaf hopCountintf  {
            type  cml_data_types:CML_UINT32_T;
            config false;
            description "";
        } // END of hopCountintf definition.

        leaf portstate  {
            type  cml_data_types:CML_UINT8_T;
            config false;
            description "";
        } // END of portstate definition.

        leaf portNextState  {
            type  cml_data_types:CML_UINT8_T;
            config false;
            description "";
        } // END of portNextState definition.

        leaf portInfoType  {
            type  cml_data_types:CML_UINT8_T;
            config false;
            description "";
        } // END of portInfoType definition.

        leaf portRole  {
            type  cml_data_types:CML_UINT8_T;
            config false;
            description "";
        } // END of portRole definition.

        leaf portSelectedRole  {
            type  cml_data_types:CML_UINT8_T;
            config false;
            description "";
        } // END of portSelectedRole definition.

        leaf portTopologyChange  {
            type  cml_data_types:CML_UINT8_T;
            config false;
            description "";
        } // END of portTopologyChange definition.

        leaf mstiTcState  {
            type  cml_data_types:CML_UINT8_T;
            config false;
            description "";
        } // END of mstiTcState definition.

        leaf portSendProposal  {
            type  cml_data_types:CML_UINT8_T;
            config false;
            description "";
        } // END of portSendProposal definition.

        leaf portreselect  {
            type  cml_data_types:CML_UINT8_T;
            config false;
            description "";
        } // END of portreselect definition.

        leaf portUpdtInfo  {
            type  cml_data_types:CML_UINT8_T;
            config false;
            description "";
        } // END of portUpdtInfo definition.

        leaf portPathcostConfigured  {
            type  cml_data_types:CML_UINT8_T;
            config false;
            description "";
        } // END of portPathcostConfigured definition.

        leaf tcAck  {
            if-feature feature_list:HAVE_RPVST_PLUS;
            type  cml_data_types:CML_INT8_T;
            config false;
            description "";
        } // END of tcAck definition.

        leaf portNewInfoSstp  {
            if-feature feature_list:HAVE_RPVST_PLUS;
            type  cml_data_types:CML_INT8_T;
            config false;
            description "";
        } // END of portNewInfoSstp definition.

        leaf portAnyMstiRootport  {
            if-feature feature_list:HAVE_RPVST_PLUS;
            type  cml_data_types:CML_INT8_T;
            config false;
            description "";
        } // END of portAnyMstiRootport definition.

        leaf portAnyMstiDesigport  {
            if-feature feature_list:HAVE_RPVST_PLUS;
            type  cml_data_types:CML_INT8_T;
            config false;
            description "";
        } // END of portAnyMstiDesigport definition.

        leaf portConfBpduSent  {
            type  cml_data_types:CML_INT32_T;
            config false;
            description "";
        } // END of portConfBpduSent definition.

        leaf portConfBpduRcvd  {
            type  cml_data_types:CML_UINT32_T;
            config false;
            description "";
        } // END of portConfBpduRcvd definition.

        leaf portTcnBpduSent  {
            type  cml_data_types:CML_UINT32_T;
            config false;
            description "";
        } // END of portTcnBpduSent definition.

        leaf portTcnBpduRcvd  {
            type  cml_data_types:CML_UINT32_T;
            config false;
            description "";
        } // END of portTcnBpduRcvd definition.

        leaf similarbpduCount  {
            type  cml_data_types:CML_UINT32_T;
            config false;
            description "";
        } // END of similarbpduCount definition.

    } // END of mstpInstancePortRuntimeAttrs definition.
    grouping mstpPortRuntimeAttrs {
        description
            "mstpPortRuntimeAttrs";
        leaf devAddr  {
            type  cml_data_types:CML_STRING_T {
                length "0..255";
            }
            config false;
            description "";
        } // END of devAddr definition.

        leaf Ifindex  {
            type  cml_data_types:CML_INT32_T;
            config false;
            description "";
        } // END of Ifindex definition.

        leaf txCount  {
            type  cml_data_types:CML_INT8_T;
            config false;
            description "";
        } // END of txCount definition.

        leaf totalTxCount  {
            type  cml_data_types:CML_INT32_T;
            config false;
            description "";
        } // END of totalTxCount definition.

        leaf rxCount  {
            type  cml_data_types:CML_INT8_T;
            config false;
            description "";
        } // END of rxCount definition.

        leaf forceVersion  {
            type  cml_data_types:CML_INT8_T;
            config false;
            description "";
        } // END of forceVersion definition.

        leaf infoInternal  {
            type  cml_data_types:CML_INT8_T;
            config false;
            description "";
        } // END of infoInternal definition.

        leaf rcvdInternal  {
            type  cml_data_types:CML_INT8_T;
            config false;
            description "";
        } // END of rcvdInternal definition.

        leaf operp2pmac  {
            type  cml_data_types:CML_INT8_T;
            config false;
            description "";
        } // END of operp2pmac definition.

        leaf adminEdge  {
            type  cml_data_types:CML_INT8_T;
            config false;
            description "";
        } // END of adminEdge definition.

        leaf operEdge  {
            type  cml_data_types:CML_INT8_T;
            config false;
            description "";
        } // END of operEdge definition.

        leaf portEnabled  {
            type  cml_data_types:CML_INT8_T;
            config false;
            description "";
        } // END of portEnabled definition.

        leaf rcvdmstp  {
            type  cml_data_types:CML_INT8_T;
            config false;
            description "";
        } // END of rcvdmstp definition.

        leaf rcvdstp  {
            type  cml_data_types:CML_INT8_T;
            config false;
            description "";
        } // END of rcvdstp definition.

        leaf rcvdrstp  {
            type  cml_data_types:CML_INT8_T;
            config false;
            description "";
        } // END of rcvdrstp definition.

        leaf rcvdspb  {
            type  cml_data_types:CML_INT8_T;
            config false;
            description "";
        } // END of rcvdspb definition.

        leaf sendmstp  {
            type  cml_data_types:CML_INT8_T;
            config false;
            description "";
        } // END of sendmstp definition.

        leaf agreednum  {
            type  cml_data_types:CML_INT8_T;
            config false;
            description "";
        } // END of agreednum definition.

        leaf discAgreedNum  {
            type  cml_data_types:CML_INT8_T;
            config false;
            description "";
        } // END of discAgreedNum definition.

        leaf agreedMisorder  {
            type  cml_data_types:CML_INT8_T;
            config false;
            description "";
        } // END of agreedMisorder definition.

        leaf agreeDigestValid  {
            type  cml_data_types:CML_INT8_T;
            config false;
            description "";
        } // END of agreeDigestValid definition.

        leaf agreedDigestValid  {
            type  cml_data_types:CML_INT8_T;
            config false;
            description "";
        } // END of agreedDigestValid definition.

        leaf agreeNum  {
            type  cml_data_types:CML_INT8_T;
            config false;
            description "";
        } // END of agreeNum definition.

        leaf discAgreeNum  {
            type  cml_data_types:CML_INT8_T;
            config false;
            description "";
        } // END of discAgreeNum definition.

        leaf agreedTopology  {
            type  cml_data_types:CML_INT8_T;
            config false;
            description "";
        } // END of agreedTopology definition.

        leaf sync  {
            type  cml_data_types:CML_INT8_T;
            config false;
            description "";
        } // END of sync definition.

        leaf tcAck  {
            type  cml_data_types:CML_INT8_T;
            config false;
            description "";
        } // END of tcAck definition.

        leaf selected  {
            type  cml_data_types:CML_INT8_T;
            config false;
            description "";
        } // END of selected definition.

        leaf sendProposal  {
            type  cml_data_types:CML_INT8_T;
            config false;
            description "";
        } // END of sendProposal definition.

        leaf rcvProposal  {
            type  cml_data_types:CML_INT8_T;
            config false;
            description "";
        } // END of rcvProposal definition.

        leaf reselect  {
            type  cml_data_types:CML_INT8_T;
            config false;
            description "";
        } // END of reselect definition.

        leaf updtInfo  {
            type  cml_data_types:CML_INT8_T;
            config false;
            description "";
        } // END of updtInfo definition.

        leaf disputed  {
            type  cml_data_types:CML_INT8_T;
            config false;
            description "";
        } // END of disputed definition.

        leaf agree  {
            type  cml_data_types:CML_INT8_T;
            config false;
            description "";
        } // END of agree definition.

        leaf agreed  {
            type  cml_data_types:CML_INT8_T;
            config false;
            description "";
        } // END of agreed definition.

        leaf configBpduPending  {
            type  cml_data_types:CML_INT8_T;
            config false;
            description "";
        } // END of configBpduPending definition.

        leaf isL2gp  {
            if-feature feature_list:HAVE_L2GP;
            type  cml_data_types:CML_INT8_T;
            config false;
            description "";
        } // END of isL2gp definition.

        leaf enableBPDUtx  {
            if-feature feature_list:HAVE_L2GP;
            type  cml_data_types:CML_INT8_T;
            config false;
            description "";
        } // END of enableBPDUtx definition.

        leaf operBpdufilter  {
            type  cml_data_types:CML_INT8_T;
            config false;
            description "";
        } // END of operBpdufilter definition.

        leaf operBpduguard  {
            type  cml_data_types:CML_INT8_T;
            config false;
            description "";
        } // END of operBpduguard definition.

        leaf operRootguard  {
            type  cml_data_types:CML_INT8_T;
            config false;
            description "";
        } // END of operRootguard definition.

        leaf ciscoCfgFormatId  {
            type  cml_data_types:CML_INT8_T;
            config false;
            description "";
        } // END of ciscoCfgFormatId definition.

        leaf refCount  {
            type  cml_data_types:CML_UINT32_T;
            config false;
            description "";
        } // END of refCount definition.

        leaf type  {
            type  cml_data_types:CML_UINT32_T;
            config false;
            description "";
        } // END of type definition.

        leaf portType  {
            type  cml_data_types:CML_UINT32_T;
            config false;
            description "";
        } // END of portType definition.

        leaf anyMstiRootport  {
            type  cml_data_types:CML_UINT32_T;
            config false;
            description "";
        } // END of anyMstiRootport definition.

        leaf anyMstiDesigport  {
            type  cml_data_types:CML_UINT32_T;
            config false;
            description "";
        } // END of anyMstiDesigport definition.

        leaf cistpathCost  {
            type  cml_data_types:CML_UINT32_T;
            config false;
            description "";
        } // END of cistpathCost definition.

        leaf cistPriority  {
            type  cml_data_types:CML_UINT32_T;
            config false;
            description "";
        } // END of cistPriority definition.

        leaf cistPortid  {
            type  cml_data_types:CML_UINT16_T;
            config false;
            description "";
        } // END of cistPortid definition.

        leaf cistRoot  {
            type  cml_data_types:CML_STRING_T {
                length "0..255";
            }
            config false;
            description "";
        } // END of cistRoot definition.

        leaf cistregisteredRoot  {
            type  cml_data_types:CML_STRING_T {
                length "0..255";
            }
            config false;
            description "";
        } // END of cistregisteredRoot definition.

        leaf cistRecvRegisteredRoot  {
            type  cml_data_types:CML_STRING_T {
                length "0..255";
            }
            config false;
            description "";
        } // END of cistRecvRegisteredRoot definition.

        leaf cistDesignatedBridge  {
            type  cml_data_types:CML_STRING_T {
                length "0..255";
            }
            config false;
            description "";
        } // END of cistDesignatedBridge definition.

        leaf cistExternalRpc  {
            type  cml_data_types:CML_UINT32_T;
            config false;
            description "";
        } // END of cistExternalRpc definition.

        leaf cistInternalRpc  {
            type  cml_data_types:CML_UINT32_T;
            config false;
            description "";
        } // END of cistInternalRpc definition.

        leaf cistDesignatedExternalRpc  {
            type  cml_data_types:CML_UINT32_T;
            config false;
            description "";
        } // END of cistDesignatedExternalRpc definition.

        leaf cistDesignatedInternalRpc  {
            type  cml_data_types:CML_UINT32_T;
            config false;
            description "";
        } // END of cistDesignatedInternalRpc definition.

        leaf cistDesignatedportId  {
            type  cml_data_types:CML_UINT32_T;
            config false;
            description "";
        } // END of cistDesignatedportId definition.

        leaf cistMessageAge  {
            type  cml_data_types:CML_INT32_T;
            config false;
            description "";
        } // END of cistMessageAge definition.

        leaf cistforwardDelay  {
            type  cml_data_types:CML_INT32_T;
            config false;
            description "";
        } // END of cistforwardDelay definition.

        leaf cisthelloTime  {
            type  cml_data_types:CML_INT32_T;
            config false;
            description "";
        } // END of cisthelloTime definition.

        leaf hopCount  {
            type  cml_data_types:CML_INT32_T;
            config false;
            description "";
        } // END of hopCount definition.

        leaf newInfoCist  {
            type  cml_data_types:CML_BOOL_T;
            config false;
            description "";
        } // END of newInfoCist definition.

        leaf newInfoMsti  {
            type  cml_data_types:CML_BOOL_T;
            config false;
            description "";
        } // END of newInfoMsti definition.

        leaf criticalBpdu  {
            type  cml_data_types:CML_BOOL_T;
            config false;
            description "";
        } // END of criticalBpdu definition.

        leaf cistState  {
            type  cml_data_types:CML_STRING_T {
                length "0..255";
            }
            config false;
            description "";
        } // END of cistState definition.

        leaf cistInfoType  {
            type  cml_data_types:CML_INT32_T;
            config false;
            description "";
        } // END of cistInfoType definition.

        leaf cistPortrole  {
            type  cml_data_types:CML_STRING_T {
                length "0..255";
            }
            config false;
            description "";
        } // END of cistPortrole definition.

        leaf cistSelectedRole  {
            type  cml_data_types:CML_STRING_T {
                length "0..255";
            }
            config false;
            description "";
        } // END of cistSelectedRole definition.

        leaf cistTcState  {
            type  cml_data_types:CML_STRING_T {
                length "0..255";
            }
            config false;
            description "";
        } // END of cistTcState definition.

        leaf helloWhen  {
            type  cml_data_types:CML_UINT8_T;
            config false;
            description "";
        } // END of helloWhen definition.

        leaf cistForwardTransition  {
            type  cml_data_types:CML_UINT32_T;
            config false;
            description "";
        } // END of cistForwardTransition definition.

        leaf svid  {
            type  cml_data_types:CML_INT16_T;
            config false;
            description "";
        } // END of svid definition.

        leaf spanningTreeDisable  {
            type  cml_data_types:CML_INT8_T;
            config false;
            description "";
        } // END of spanningTreeDisable definition.

        leaf isid  {
            if-feature feature_list:HAVE_I_BEB;
            type  cml_data_types:CML_INT32_T;
            config false;
            description "";
        } // END of isid definition.

        leaf pip_port  {
            if-feature feature_list:HAVE_I_BEB;
            type  cml_data_types:CML_INT32_T;
            config false;
            description "";
        } // END of pip_port definition.

        leaf bvid  {
            if-feature feature_list:HAVE_I_BEB;
            type  cml_data_types:CML_INT32_T;
            config false;
            description "";
        } // END of bvid definition.

        leaf rpvstEvent  {
            if-feature feature_list:HAVE_RPVST_PLUS;
            type  cml_data_types:CML_INT32_T;
            config false;
            description "";
        } // END of rpvstEvent definition.

        leaf rpvstBpduType  {
            if-feature feature_list:HAVE_RPVST_PLUS;
            type  cml_data_types:CML_INT32_T;
            config false;
            description "";
        } // END of rpvstBpduType definition.

        leaf newInfoSstp  {
            if-feature feature_list:HAVE_RPVST_PLUS;
            type  cml_data_types:CML_INT32_T;
            config false;
            description "";
        } // END of newInfoSstp definition.

        leaf vidTag  {
            if-feature feature_list:HAVE_RPVST_PLUS;
            type  cml_data_types:CML_INT32_T;
            config false;
            description "";
        } // END of vidTag definition.

        leaf defaultVlan  {
            if-feature feature_list:HAVE_RPVST_PLUS;
            type  cml_data_types:CML_INT32_T;
            config false;
            description "";
        } // END of defaultVlan definition.

        leaf confBpduSent  {
            type  cml_data_types:CML_INT32_T;
            config false;
            description "";
        } // END of confBpduSent definition.

        leaf confBpduRcvd  {
            type  cml_data_types:CML_UINT32_T;
            config false;
            description "";
        } // END of confBpduRcvd definition.

        leaf tcnBpduSent  {
            type  cml_data_types:CML_UINT32_T;
            config false;
            description "";
        } // END of tcnBpduSent definition.

        leaf tcnBpduRcvd  {
            type  cml_data_types:CML_UINT32_T;
            config false;
            description "";
        } // END of tcnBpduRcvd definition.

        leaf sourcemacCount  {
            type  cml_data_types:CML_INT32_T;
            config false;
            description "";
        } // END of sourcemacCount definition.

        leaf similarbpduCount  {
            type  cml_data_types:CML_UINT32_T;
            config false;
            description "";
        } // END of similarbpduCount definition.

        leaf msgAgeTimerCnt  {
            type  cml_data_types:CML_UINT32_T;
            config false;
            description "";
        } // END of msgAgeTimerCnt definition.

        leaf totalSrcMacCount  {
            type  cml_data_types:CML_INT32_T;
            config false;
            description "";
        } // END of totalSrcMacCount definition.

        leaf agg  {
            type  cml_data_types:CML_BOOL_T;
            config false;
            description "";
        } // END of agg definition.

        leaf portTypeP2p  {
            type  cml_data_types:CML_BOOL_T;
            config false;
            description "";
        } // END of portTypeP2p definition.

    } // END of mstpPortRuntimeAttrs definition.
    grouping mstpBridgeAttrs {
        description
            "mstpBridgeAttrs";
        leaf bridgeMaxAge  {
            type  cml_data_types:CML_INT32_T {
                 range "6..40";
            }
            default "20";
            description "";
        } // END of bridgeMaxAge definition.

        leaf bridgehelloTime  {
            type  cml_data_types:CML_INT32_T {
                 range "1..10";
            }
            default "2";
            description "";
        } // END of bridgehelloTime definition.

        leaf bridgeforwardDelay  {
            type  cml_data_types:CML_INT32_T {
                 range "4..30";
            }
            default "15";
            description "";
        } // END of bridgeforwardDelay definition.

        leaf bridgemaxHops  {
            type  cml_data_types:CML_INT32_T {
                 range "1..40";
            }
            default "20";
            description "";
        } // END of bridgemaxHops definition.

        leaf cistBridgePriority  {
            type  cml_data_types:CML_UINT32_T {
                 range "0..61440";
            }
            default "32768";
            description "";
        } // END of cistBridgePriority definition.

        leaf ageingTime  {
            type  cml_data_types:CML_INT32_T {
                 range "10..1000000";
            }
            default "300";
            description "";
        } // END of ageingTime definition.

        leaf adminCisco  {
            type  cml_data_types:CML_ENABLE_DISABLE_T;
            default "disable";
            description "";
        } // END of adminCisco definition.

        leaf transmitHoldCount  {
            type  cml_data_types:CML_UINT8_T {
                 range "1..10";
            }
            default "6";
            description "";
        } // END of transmitHoldCount definition.

        leaf ageingStatus  {
            type  cml_data_types:CML_BRIDGE_AGEING_STATE;
            description "";
        } // END of ageingStatus definition.

    } // END of mstpBridgeAttrs definition.
    grouping mstpBridgeInstanceAttrs {
        description
            "mstpBridgeInstanceAttrs";
        leaf mstiBridgePriority  {
            type  cml_data_types:CML_UINT32_T {
                 range "0..61440";
            }
            default "32768";
            description "";
        } // END of mstiBridgePriority definition.

        leaf vlanId  {
            type  cml_data_types:CML_RANGE_T {
                length "1..255";
            }
            description "";
        } // END of vlanId definition.

    } // END of mstpBridgeInstanceAttrs definition.
    grouping vlanportgrp {
        description
            "vlanportgrp";

        list vlanport {
            if-feature feature_list:HAVE_RPVST_PLUS;
            key "vlanId";
            description
                "vlan port commands";
            leaf vlanId  {
                type  cml_data_types:CML_STRING_T {
                    length "0..255";
                }
                description "";
            } // END of vlanId definition.

            leaf vlanportPriority  {
                type  cml_data_types:CML_UINT32_T {
                     range "0..240";
                }
                default "128";
                description "";
            } // END of vlanportPriority definition.

            leaf vlanpathCost  {
                type  cml_data_types:CML_UINT32_T {
                     range "1..200000000";
                }
                default "1";
                description "";
            } // END of vlanpathCost definition.

        } // End of vlanport-list
    } // END of vlanportgrp definition.

    grouping  mstpbridge-grouping {
    description
        "mstpbridge";
    container mstpbridge {
        description
            "mstpbridge";
        leaf forceVersion  {
            type  cml_data_types:CML_UINT8_T {
                 range "0..4";
            }
            default "0";
            description "";
        } // END of forceVersion definition.

        leaf bridgeForward  {
            type  cml_data_types:CML_BRIDGE_FORWARD_T;
            description "";
        } // END of bridgeForward definition.

        leaf pathCostMethod  {
            type  cml_data_types:CML_PATHCOST_METHOD_T;
            description "";
        } // END of pathCostMethod definition.

        leaf maxInstances  {
            type  cml_data_types:CML_UINT16_T;
            config false;
            description "";
        } // END of maxInstances definition.

        leaf numPorts  {
            type  cml_data_types:CML_INT16_T;
            config false;
            description "";
        } // END of numPorts definition.

        leaf lastTopologychangeTime  {
            type  cml_data_types:CML_STRING_T {
                length "0..255";
            }
            config false;
            description "";
        } // END of lastTopologychangeTime definition.

        leaf numTopoChanges  {
            type  cml_data_types:CML_UINT32_T;
            config false;
            description "";
        } // END of numTopoChanges definition.

        leaf totalNumTopoChanges  {
            type  cml_data_types:CML_UINT32_T;
            config false;
            description "";
        } // END of totalNumTopoChanges definition.

        leaf maxAgeCount  {
            type  cml_data_types:CML_UINT32_T;
            config false;
            description "";
        } // END of maxAgeCount definition.

        leaf bpduguard  {
            type  cml_data_types:CML_BOOL_T;
            default false;
            description "";
        } // END of bpduguard definition.

        leaf errdisableTimeoutInterval  {
            type  cml_data_types:CML_INT32_T {
                 range "10..1000000";
            }
            default "300";
            description "";
        } // END of errdisableTimeoutInterval definition.

        leaf errdisableTimeoutEnable  {
            type  cml_data_types:CML_BOOL_T;
            default false;
            description "";
        } // END of errdisableTimeoutEnable definition.

        leaf bpduFilter  {
            type  cml_data_types:CML_BOOL_T;
            default false;
            description "";
        } // END of bpduFilter definition.

        leaf operCisco  {
            type  cml_data_types:CML_UINT8_T;
            config false;
            description "";
        } // END of operCisco definition.

        leaf topologyType  {
            type  cml_data_types:CML_BRIDGE_TOPOLOGY_T;
            config false;
            description "";
        } // END of topologyType definition.

        leaf tcFlag  {
            type  cml_data_types:CML_UINT8_T;
            config false;
            description "";
        } // END of tcFlag definition.

        leaf tcInitiator  {
            type  cml_data_types:CML_UINT8_T;
            config false;
            description "";
        } // END of tcInitiator definition.

        leaf tclastRcvdFrom  {
            type  cml_data_types:CML_STRING_T {
                length "0..255";
            }
            config false;
            description "";
        } // END of tclastRcvdFrom definition.

        leaf-list vlanInstanceMap  {
            if-feature feature_list:HAVE_RPVST_PLUS;
            type  cml_data_types:CML_UINT16_T;
            config false;
            description "";
        } // END of vlanInstanceMap definition.

        leaf custBpduProcess  {
            if-feature feature_list:HAVE_RPVST_PLUS;
            type  cml_data_types:CML_UINT8_T;
            config false;
            description "";
        } // END of custBpduProcess definition.

        leaf brType  {
            type  cml_data_types:CML_BRIDGE_TYPE_T;
            description "";
        } // END of brType definition.

        leaf mstpEnable  {
            type  cml_data_types:CML_INT32_T;
            default "1";
            description "";
        } // END of mstpEnable definition.


        list rpvstVlanTable {
            if-feature feature_list:HAVE_RPVST_PLUS;
            key "vlanId";
            description
                "rpvstVlanTable";
            leaf vlanId  {
                type  cml_data_types:CML_STRING_T {
                    length "0..255";
                }
                description "";
            } // END of vlanId definition.

            leaf rpvstPlusFlag  {
                type  cml_data_types:CML_UINT16_T;
                mandatory true;
                description "";
            } // END of rpvstPlusFlag definition.

            leaf vlanPriority  {
                if-feature feature_list:HAVE_RPVST_PLUS;
                type  cml_data_types:CML_UINT32_T {
                     range "0..61440";
                }
                default "32768";
                description "";
            } // END of vlanPriority definition.

        } // End of rpvstVlanTable-list

        list mstpBridgeInstance {
            key "instanceId";
            description
                "mstpBridgeInstance";
            leaf instanceId  {
                type  cml_data_types:CML_MSTP_INSTANCE_T;
                description "";
            } // END of instanceId definition.


            list mstpInstancePort {
                key "ifName";
                description
                    "Group of mstp attribute having interface property";
                leaf ifName  {
                    type  cml_data_types:CML_STRING_T {
                        length "0..255";
                    }
                    description "";
                } // END of ifName definition.

                leaf mstiPriority  {
                    type  cml_data_types:CML_INT16_T {
                         range "0..240";
                    }
                    default "128";
                    description "";
                } // END of mstiPriority definition.

                leaf mstppathCost  {
                    type  cml_data_types:CML_UINT32_T {
                         range "1..200000000";
                    }
                    default "20000000";
                    description "";
                } // END of mstppathCost definition.

                leaf instrestrictedTCN  {
                    type  cml_data_types:CML_BOOL_T;
                    default false;
                    description "";
                } // END of instrestrictedTCN definition.

                leaf instrestrictedRole  {
                    type  cml_data_types:CML_BOOL_T;
                    default false;
                    description "";
                } // END of instrestrictedRole definition.

                uses mstpInstancePortRuntimeAttrs;
            } // End of mstpInstancePort-list
            uses mstpBridgeInstanceAttrs;
            uses mstpInstanceRuntimeAttr;
        } // End of mstpBridgeInstance-list
        container mstpConfigInfo {
            description
                "mstp configuration info";
            leaf cfgFormatId  {
                type  cml_data_types:CML_UINT8_T;
                config false;
                description "";
            } // END of cfgFormatId definition.

            leaf cfgName  {
                type  cml_data_types:CML_STRING_T {
                    length "0..255";
                }
                default "Default";
                description "";
            } // END of cfgName definition.

            leaf cfgRevisionLvl  {
                type  cml_data_types:CML_UINT16_T {
                     range "0..65535";
                }
                description "";
            } // END of cfgRevisionLvl definition.

            leaf cfgDigest  {
                type  cml_data_types:CML_STRING_T {
                    length "0..255";
                }
                config false;
                description "";
            } // END of cfgDigest definition.

        } // END of mstpConfigInfo-container definition.
        uses mstpBridgeAttrs;
        uses mstpBridgeruntimeAttrs;
    } // END of mstpbridge-container definition.
    } // END of mstpbridge-container definition.

    grouping  mstpSpanningTree-grouping {
    description
        "mstpSpanningTree";
    container mstpSpanningTree {
        if-feature feature_list:HAVE_DEFAULT_BRIDGE;
        description
            "mstpSpanningTree";
        leaf mstpEnable  {
            type  cml_data_types:CML_BOOL_T;
            default true;
            description "";
        } // END of mstpEnable definition.

        leaf forceVersion  {
            type  cml_data_types:CML_UINT8_T {
                 range "0..3";
            }
            default "0";
            description "";
        } // END of forceVersion definition.

        leaf pathCostMethod  {
            type  cml_data_types:CML_PATHCOST_METHOD_T;
            description "";
        } // END of pathCostMethod definition.

        leaf errdisableTimeoutEnable  {
            type  cml_data_types:CML_BOOL_T;
            default false;
            description "";
        } // END of errdisableTimeoutEnable definition.

        leaf errdisableTimeoutInterval  {
            type  cml_data_types:CML_INT32_T {
                 range "10..1000000";
            }
            default "300";
            description "";
        } // END of errdisableTimeoutInterval definition.

        leaf bpduFilter  {
            type  cml_data_types:CML_BOOL_T;
            default false;
            description "";
        } // END of bpduFilter definition.

        leaf bpduguard  {
            type  cml_data_types:CML_BOOL_T;
            default false;
            description "";
        } // END of bpduguard definition.


        list rpvstVlanTable {
            if-feature feature_list:HAVE_RPVST_PLUS;
            key "vlanId";
            description
                "rpvstVlanTable";
            leaf vlanId  {
                type  cml_data_types:CML_STRING_T {
                    length "0..255";
                }
                description "";
            } // END of vlanId definition.

            leaf rpvstPlusFlag  {
                type  cml_data_types:CML_UINT16_T;
                description "";
            } // END of rpvstPlusFlag definition.

        } // End of rpvstVlanTable-list

        list spanInstance {
            if-feature feature_list:HAVE_DEFAULT_BRIDGE;
            key "instanceId";
            description
                "spanInstance";
            leaf instanceId  {
                type  cml_data_types:CML_INT32_T {
                     range "1..63";
                }
                description "";
            } // END of instanceId definition.


            list spanningInterface {
                if-feature feature_list:HAVE_DEFAULT_BRIDGE;
                key "ifName";
                description
                    "Group of mstp attribute having interface property";
                leaf ifName  {
                    type  cml_data_types:CML_STRING_T {
                        length "0..255";
                    }
                    description "";
                } // END of ifName definition.

                leaf mstiPriority  {
                    type  cml_data_types:CML_INT16_T {
                         range "0..240";
                    }
                    default "128";
                    description "";
                } // END of mstiPriority definition.

                leaf mstppathCost  {
                    type  cml_data_types:CML_UINT32_T {
                         range "1..200000000";
                    }
                    default "20000000";
                    description "";
                } // END of mstppathCost definition.

                uses mstpInstancePortRuntimeAttrs;
            } // End of spanningInterface-list
            uses mstpBridgeInstanceAttrs;
            uses mstpInstanceRuntimeAttr;
        } // End of spanInstance-list
        container mstpConfigInfo {
            description
                "mstp configuration info";
            leaf cfgFormatId  {
                type  cml_data_types:CML_UINT8_T;
                config false;
                description "";
            } // END of cfgFormatId definition.

            leaf cfgName  {
                type  cml_data_types:CML_STRING_T {
                    length "0..255";
                }
                default "Default";
                description "";
            } // END of cfgName definition.

            leaf cfgRevisionLvl  {
                type  cml_data_types:CML_UINT16_T {
                     range "0..65535";
                }
                description "";
            } // END of cfgRevisionLvl definition.

            leaf cfgDigest  {
                type  cml_data_types:CML_STRING_T {
                    length "0..255";
                }
                config false;
                description "";
            } // END of cfgDigest definition.

        } // END of mstpConfigInfo-container definition.
        uses mstpBridgeAttrs;
        uses mstpBridgeruntimeAttrs;
    } // END of mstpSpanningTree-container definition.
    } // END of mstpSpanningTree-container definition.

    grouping  backboneBridge-grouping {
    description
        "backboneBridge";
    container backboneBridge {
        description
            "backboneBridge";
        leaf priority  {
            type  cml_data_types:CML_UINT32_T {
                 range "0..61440";
            }
            default "32768";
            description "";
        } // END of priority definition.

    } // END of backboneBridge-container definition.
    } // END of backboneBridge-container definition.

    grouping  mstpDebugMode-grouping {
    description
        "mstpDebugMode";
    container mstpDebugMode {
        description
            "mstpDebugMode";
        leaf configDebugMstp  {
            type  cml_data_types:CML_MSTP_DEBUG_T;
            description "";
        } // END of configDebugMstp definition.

    } // END of mstpDebugMode-container definition.
    } // END of mstpDebugMode-container definition.

    grouping  mstpExecMode-grouping {
    description
        "mstpExecMode";
    container mstpExecMode {
        description
            "mstpExecMode";
        leaf execDebugMstp  {
            type  cml_data_types:CML_MSTP_DEBUG_T;
            description "";
        } // END of execDebugMstp definition.

    } // END of mstpExecMode-container definition.
    } // END of mstpExecMode-container definition.


}
