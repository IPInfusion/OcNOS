/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ldap.yang
*
*/

submodule ldap {

    belongs-to  ZebOS { prefix ZebOS; }

    import cml_data_types {
        prefix cml_data_types;
    }

    organization
        "IP Infusion Inc.";

    contact
        "Address: 3965 Freedom Circle, Suite 200, Santa Clara, CA 95054
        Phone: +1 408-400-1900
        E-mail: support@ipinfusion.com
        Web: http://www.ipinfusion.com/";

    description
        "Layer-3 ldap configurations";


    revision "2018-01-02" {
        description "Revisied on 2018-01-02.";    }

    revision "2017-11-27" {
        description "Revisied on 2017-11-27.";    }

    revision "2017-11-10" {
        description "Revisied on 2017-11-10.";    }

    revision "2017-11-09" {
        description "Revisied on 2017-11-09.";    }

    revision "2017-11-03" {
        description "Revisied on 2017-11-03.";    }

    revision "2017-11-02" {
        description "Revisied on 2017-11-02.";    }

    revision "2017-10-26" {
        description "Revisied on 2017-10-26.";    }

    revision "2017-10-23" {
        description "Revisied on 2017-10-23.";    }

    revision "2017-10-18" {
        description "Revisied on 2017-10-18.";    }

    revision "2017-10-11" {
        description "Revisied on 2017-10-11.";    }

    revision "2017-10-10" {
        description "Revisied on 2017-10-10.";    }

    revision "2017-09-28" {
        description "Revisied on 2017-09-28.";    }

    revision "2017-09-19" {
        description "Revisied on 2017-09-19.";    }

    revision "2017-09-14" {
        description "Revisied on 2017-09-14.";    }

    revision "2017-09-13" {
        description "Revisied on 2017-09-13.";    }

    revision "2017-09-04" {
        description "Revisied on 2017-09-04.";    }

    revision "2017-08-22" {
        description "Revisied on 2017-08-22.";    }

    revision "2017-08-09" {
        description "Revisied on 2017-08-09.";    }

    revision "2017-08-08" {
        description "Revisied on 2017-08-08.";    }

    revision "2017-08-07" {
        description "Revisied on 2017-08-07.";    }

    revision "2017-07-29" {
        description "Revisied on 2017-07-29.";    }

    revision "2017-07-27" {
        description "Revisied on 2017-07-27.";    }

    revision "2017-07-26" {
        description "Revisied on 2017-07-26.";    }

    revision "2017-07-24" {
        description "Revisied on 2017-07-24.";    }

    revision "2017-07-14" {
        description "Revisied on 2017-07-14.";    }

    revision "2017-07-11" {
        description "Revisied on 2017-07-11.";    }

    revision "2017-07-10" {
        description "Revisied on 2017-07-10.";    }

    revision "2017-07-05" {
        description "Revisied on 2017-07-05.";    }

    revision "2017-07-04" {
        description "Revisied on 2017-07-04.";    }

    revision "2017-07-03" {
        description "Revisied on 2017-07-03.";    }

    revision "2017-06-29" {
        description "Revisied on 2017-06-29.";    }

    revision "2017-06-28" {
        description "Revisied on 2017-06-28.";    }

    revision "2017-06-12" {
        description "Revisied on 2017-06-12.";    }

    revision "2017-06-09" {
        description "Revisied on 2017-06-09.";    }

    revision "2017-06-08" {
        description "Revisied on 2017-06-08.";    }

    revision "2017-06-07" {
        description "Revisied on 2017-06-07.";    }

    revision "2017-06-06" {
        description "Revisied on 2017-06-06.";    }

    revision "2017-06-02" {
        description "Revisied on 2017-06-02.";    }

    revision "2017-05-31" {
        description "Revisied on 2017-05-31.";    }

    revision "2017-05-30" {
        description "Revisied on 2017-05-30.";    }

    revision "2017-05-29" {
        description "Revisied on 2017-05-29.";    }

    revision "2017-05-26" {
        description "Revisied on 2017-05-26.";    }

    revision "2017-05-23" {
        description "Revisied on 2017-05-23.";    }

    revision "2017-05-19" {
        description "Revisied on 2017-05-19.";    }

    revision "2017-05-18" {
        description "Revisied on 2017-05-18.";    }

    revision "2017-05-16" {
        description "Revisied on 2017-05-16.";    }

    revision "2017-05-15" {
        description "Revisied on 2017-05-15.";    }

    revision "2017-05-11" {
        description "Revisied on 2017-05-11.";    }

    revision "2017-05-10" {
        description "Revisied on 2017-05-10.";    }

    revision "2017-05-04" {
        description "Revisied on 2017-05-04.";    }

    revision "2017-04-29" {
        description "Revisied on 2017-04-29.";    }

    revision "2017-04-28" {
        description "Revisied on 2017-04-28.";    }

    revision "2017-04-27" {
        description "Revisied on 2017-04-27.";    }

    revision "2017-04-26" {
        description "Revisied on 2017-04-26.";    }

    revision "2017-04-25" {
        description "Revisied on 2017-04-25.";    }

    revision "2017-04-21" {
        description "Revisied on 2017-04-21.";    }

    revision "2017-04-20" {
        description "Revisied on 2017-04-20.";    }

    revision "2017-04-19" {
        description "Revisied on 2017-04-19.";    }

    revision "2017-04-14" {
        description "Revisied on 2017-04-14.";    }

    revision "2017-04-13" {
        description "Revisied on 2017-04-13.";    }

    revision "2017-04-11" {
        description "Revisied on 2017-04-11.";    }

    revision "2017-04-09" {
        description "Revisied on 2017-04-09.";    }

    revision "2017-04-06" {
        description "Revisied on 2017-04-06.";    }

    revision "2017-03-25" {
        description "Revisied on 2017-03-25.";    }

    revision "2017-03-24" {
        description "Revisied on 2017-03-24.";    }

    revision "2017-03-21" {
        description "Revisied on 2017-03-21.";    }

    revision "2017-03-09" {
        description "Revisied on 2017-03-09.";    }

    revision "2017-03-05" {
        description "Revisied on 2017-03-05.";    }

    revision "2017-03-03" {
        description "Revisied on 2017-03-03.";    }

    revision "2017-02-27" {
        description "Revisied on 2017-02-27.";    }

    revision "2017-02-25" {
        description "Revisied on 2017-02-25.";    }

    revision "2017-02-24" {
        description "Revisied on 2017-02-24.";    }

    revision "2017-02-23" {
        description "Revisied on 2017-02-23.";    }

    revision "2017-02-22" {
        description "Revisied on 2017-02-22.";    }

    revision "2017-02-21" {
        description "Revisied on 2017-02-21.";    }

    revision "2017-02-20" {
        description "Revisied on 2017-02-20.";    }

    revision "2017-02-14" {
        description "Revisied on 2017-02-14.";    }

    revision "2017-02-13" {
        description "Revisied on 2017-02-13.";    }

    revision "2017-02-11" {
        description "Revisied on 2017-02-11.";    }

    revision "2017-02-10" {
        description "Revisied on 2017-02-10.";    }

    revision "2017-02-08" {
        description "Revisied on 2017-02-08.";    }

    revision "2017-02-07" {
        description "Revisied on 2017-02-07.";    }

    revision "2017-02-03" {
        description "Revisied on 2017-02-03.";    }

    revision "2017-02-02" {
        description "Revisied on 2017-02-02.";    }

    revision "2017-01-31" {
        description "Revisied on 2017-01-31.";    }

    revision "2017-01-30" {
        description "Revisied on 2017-01-30.";    }

    revision "2017-01-28" {
        description "Revisied on 2017-01-28.";    }

    revision "2017-01-27" {
        description "Revisied on 2017-01-27.";    }

    revision "2017-01-25" {
        description "Revisied on 2017-01-25.";    }

    revision "2017-01-23" {
        description "Revisied on 2017-01-23.";    }

    revision "2017-01-20" {
        description "Revisied on 2017-01-20.";    }

    revision "2017-01-19" {
        description "Revisied on 2017-01-19.";    }

    revision "2017-01-16" {
        description "Revisied on 2017-01-16.";    }

    revision "2017-01-12" {
        description "Revisied on 2017-01-12.";    }

    revision "2017-01-11" {
        description "Revisied on 2017-01-11.";    }

    revision "2017-01-10" {
        description "Revisied on 2017-01-10.";    }

    revision "2017-01-04" {
        description "Revisied on 2017-01-04.";    }

    revision "2016-12-30" {
        description "Revisied on 2016-12-30.";    }

    revision "2016-12-29" {
        description "Revisied on 2016-12-29.";    }

    revision "2016-12-28" {
        description "Revisied on 2016-12-28.";    }

    revision "2016-12-26" {
        description "Revisied on 2016-12-26.";    }

    revision "2016-12-22" {
        description "Revisied on 2016-12-22.";    }

    revision "2016-12-17" {
        description "Revisied on 2016-12-17.";    }

    revision "2016-10-28" {
        description "Revisied on 2016-10-28.";    }

    revision "2016-01-29" {
        description "Revisied on 2016-01-29.";    }


    grouping  ldap-grouping {
    container ldap {
        description
            "ldap";
        leaf featureLdap  {
            type  cml_data_types:CML_BOOL_T;
        } // END of featureLdap definition.

        leaf port  {
            type  cml_data_types:CML_UINT16_T {
                 range "1..65535";
            }
        } // END of port definition.

        leaf timeout  {
            type  cml_data_types:CML_UINT16_T {
                 range "1..60";
            }
        } // END of timeout definition.


        list ldap {
            key "hostAddr";
            description
                "ldap";
            leaf hostAddr  {
                type  cml_data_types:CML_HOSTNAME_T;
            } // END of hostAddr definition.

            leaf EnableSsl  {
                type  cml_data_types:CML_BOOL_T;
            } // END of EnableSsl definition.

            leaf hostPort  {
                type  cml_data_types:CML_UINT16_T {
                     range "1..65535";
                }
            } // END of hostPort definition.

            leaf hostDNPort  {
                type  cml_data_types:CML_UINT16_T {
                     range "1..65535";
                }
                default "389";
            } // END of hostDNPort definition.

            leaf hostTimeout  {
                type  cml_data_types:CML_UINT16_T {
                     range "1..60";
                }
                default "5";
            } // END of hostTimeout definition.

            leaf hostPTimeout  {
                type  cml_data_types:CML_UINT16_T {
                     range "1..60";
                }
            } // END of hostPTimeout definition.

            leaf rootDN  {
                type  cml_data_types:CML_STRING_T {
                    length "0..255";
                }
            } // END of rootDN definition.

        } // End of ldap-list
    } // END of ldap-container definition.
    } // END of ldap-container definition.


}
