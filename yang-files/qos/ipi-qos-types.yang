/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-qos-types.yang
*
*/

module ipi-qos-types {

    yang-version 1.1;

    namespace   "http://www.ipinfusion.com/yang/ocnos/ipi-qos-types";

    prefix "ipi-qos-types";

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "Quality of Service (QoS) types";


    revision "2022-06-01" {
        description "Updated the yang file with feature";
        reference "Initial Version";
    }

    revision "2021-06-30" {
        description "Modify enumeration values descriptions for QOS_RATE_UNIT_T type.";
        reference "Initial Version";
    }

    revision "2021-06-09" {
        description "Removed the option bps from QOS_SHAPE_RATE_UNIT_EXTENDED_T type";
        reference "Initial Version";
    }

    revision "2021-06-07" {
        description "Changed type qos default to type all from QOS_CLEAR_STATS_T type";
        reference "Initial Version";
    }

    revision "2021-05-28" {
        description "Removed QOS_POLICY_MAP_DEFAULT_T type";
        reference "Initial Version";
    }

    revision "2021-05-21" {
        description "Replaced HAVE_TRIDENT2 and HAVE_TRIDENT2PLUS with HAVE_CUSTOM1_QOS";
        reference "Initial Version";
    }

    revision "2021-05-20" {
        description "Added QOS_POLICY_MAP_DEFAULT_T and QOS_CLASS_MAP_DEFAULT_T types";
        reference "Initial Version";
    }

    revision "2021-05-19" {
        description "Removed QOS_PRECEDENCE_T, QOS_PRECEDENCE_EXTENDED_T, QOS_PRECEDENCE_VAL_T, QOS_DSCP_T, QOS_DSCP_EXTENDED_T and QOS_DSCP_VAL_T types";
        reference "Initial Version";
    }

    revision "2021-05-05" {
        description "Added QOS_COLOR_KEY_T and removed option all from QOS_COLOR_T type";
        reference "Initial Version";
    }

    revision "2021-04-06" {
        description "Added QOS_MAC_ADDRESS_T type";
        reference "Initial Version";
    }

    revision "2021-03-15" {
        description "Removed qos-default and match-default options from its enum";
        reference "Initial Version";
    }

    revision "2020-12-04" {
        description "Restructured module as per open-config style";
        reference "Initial Version";
    }

    revision "2018-06-21" {
        description "Initial Version";
        reference "Initial Version";
    }



    typedef  qos_rate_unit_t {
        type enumeration {
            enum kbps {
                value 2;
                description "Specifies the unit of kilobits per second";
            }
            enum mbps {
                value 3;
                description "Specifies the unit of megabits per second";
            }
            enum gbps {
                value 4;
                description "Specifies the unit of gigabits per second";
            }
            enum percent {
                value 6;
                description "Specifies the unit in percentage 1 to 100";
            }
        }
        description "type definition for QOS_RATE_UNIT_T";
    }

    typedef  qos_burst_rate_unit_t {
        type enumeration {
            enum none {
                value 0;
                description "default value";
            }
            enum kbytes {
                value 2;
                description "Specifies the units of kilobytes per second";
            }
            enum mbytes {
                value 3;
                description "Specifies the units of megabytes per second";
            }
            enum ms {
                value 4;
                description "Specifies the units of milliseconds";
            }
            enum us {
                value 5;
                description "Specifies the units of microseconds";
            }
        }
        description "type definition for QOS_BURST_RATE_UNIT_T";
    }

    typedef  qos_shape_rate_unit_t {
        type enumeration {
            enum kbps {
                value 2;
                description "Specifies the unit of kilobits per second";
            }
            enum mbps {
                value 3;
                description "Specifies the unit of megabits per second";
            }
            enum gbps {
                value 4;
                description "Specifies the unit of gigabits per second";
            }
        }
        description "type definition for QOS_SHAPE_RATE_UNIT_T";
    }

    typedef  qos_shape_rate_unit_extended_t {
        type enumeration {
            enum kbps {
                value 2;
                description "Specifies the unit of kilobits per second";
            }
            enum mbps {
                value 3;
                description "Specifies the unit of megabits per second";
            }
            enum gbps {
                value 4;
                description "Specifies the unit of gigabits per second";
            }
            enum percent {
                value 6;
                description "Specifies the unit in percentage";
            }
        }
        description "type definition for QOS_SHAPE_RATE_UNIT_EXTENDED_T";
    }

    typedef  qos_policy_map_t {
        type enumeration {
            enum qos {
                value 1;
                description "QoS is ingress/egress policy-map";
            }
            enum queuing {
                value 2;
                description "Queuing is egress policy-map";
            }
            enum queuing-default {
                value 3;
                description "Queuing is egress policy-map,Default queue of port";
            }
            enum vlan-queuing {
                value 4;
                if-feature feature-list:HAVE_CUSTOM1_QOS;
                description "Vlan-Queuing is egress policy-map";
            }
            enum hybrid-queuing {
                value 6;
                if-feature feature-list:HAVE_CUSTOM1_QOS;
                description "Hybrid-Queuing is egress policy-map";
            }
        }
        description "type definition for QOS_POLICY_MAP_T";
    }

    typedef  qos_policy_map_class_default_t {
        type string;
        description "type definition for QOS_POLICY_MAP_CLASS_DEFAULT_T";
    }

    typedef  qos_policy_map_class_t {
        type union {
            type string {

            }
            type qos_policy_map_class_default_t {

            }
        }
        description "type definition for QOS_POLICY_MAP_CLASS_T";
    }

    typedef  qos_police_t {
        type enumeration {
            enum none {
                value 0;
                description "No policer. Default to colour blind policer";
            }
            enum colour-blind {
                value 1;
                description "Colour blind policer";
            }
            enum colour-aware {
                value 2;
                description "Colour aware policer";
            }
        }
        description "type definition for QOS_POLICE_T";
    }

    typedef  qos_port_action_t {
        type enumeration {
            enum redirect-to-port {
                value 5;
                description "Redirect packet to new interface";
            }
            enum mirror-to-port {
                value 6;
                description "Mirror packet to new interface";
            }
        }
        description "type definition for QOS_PORT_ACTION_T";
    }

    typedef  qos_dei_t {
        type enumeration {
            enum 0 {
                value 0;
                description "Reset DEI";
            }
            enum 1 {
                value 1;
                description "Set DEI";
            }
            enum all {
                value 2;
                description "all DEI";
            }
        }
        description "type definition for QOS_DEI_T";
    }

    typedef  qos_color_key_t {
        type enumeration {
            enum green {
                value 0;
                description "Set mapping for green packets";
            }
            enum yellow {
                value 1;
                description "Set mapping for yellow packets";
            }
            enum red {
                value 2;
                description "Set mapping for red packets";
            }
            enum all {
                value 3;
                description "Set mapping for all packets";
            }
        }
        description "type definition for QOS_COLOR_KEY_T";
    }

    typedef  qos_color_t {
        type enumeration {
            enum green {
                value 0;
                description "Set mapping for green packets";
            }
            enum yellow {
                value 1;
                description "Set mapping for yellow packets";
            }
            enum red {
                value 2;
                description "Set mapping for red packets";
            }
        }
        description "type definition for QOS_COLOR_T";
    }

    typedef  qos_clear_stats_t {
        type enumeration {
            enum type-qos {
                value 0;
                description "Type of qos,QoS statistics";
            }
            enum type-qos-input {
                value 1;
                description "Type of qos,QoS statistics,Input direction";
            }
            enum type-qos-output {
                value 2;
                description "Type of qos,QoS statistics,Output direction";
            }
            enum type-queuing {
                value 3;
                description "Type of qos,Queuing statistics";
            }
            enum type-all {
                value 255;
                description "Type of qos,Clear all statistics from QoS and Queuing";
            }
        }
        description "type definition for QOS_CLEAR_STATS_T";
    }

    typedef  qos_class_map_t {
        type enumeration {
            enum qos {
                value 1;
                description "qos is ingress/egress class-map";
            }
            enum queuing {
                value 2;
                description "Match on Egress Queuing class";
            }
            enum queuing-default {
                value 3;
                description "Default queuing";
            }
            enum vlan-queuing {
                value 4;
                if-feature feature-list:HAVE_CUSTOM1_QOS;
                description "Match on Egress Vlan Queuing class";
            }
        }
        description "type definition for QOS_CLASS_MAP_T";
    }

    typedef  qos_class_map_default_t {
        type enumeration {
            enum qos {
                value 1;
                description "qos is ingress/egress class-map";
            }
            enum queuing {
                value 2;
                description "Match on Egress Queuing class";
            }
            enum queuing-default {
                value 3;
                description "Default queuing";
            }
            enum vlan-queuing {
                value 4;
                description "Match on Egress VlanQueuing class";
            }
        }
        description "type definition for QOS_CLASS_MAP_DEFAULT_T";
    }

    typedef  qos_threshold_t {
        type enumeration {
            enum mbytes {
                value 4;
                if-feature feature-list:HAVE_CUSTOM2_QOS;
                description "mega-bytes (min 1 - max 600)";
            }
            enum ms {
                value 6;
                if-feature feature-list:HAVE_CUSTOM2_QOS;
                description "milli-seconds (min 1 - max 50)";
            }
            enum us {
                value 7;
                if-feature feature-list:HAVE_CUSTOM2_QOS;
                description "micro-seconds (min 1 - max 50000)";
            }
            enum packets {
                if-feature feature-list:NOT_HAVE_CUSTOM2_QOS;
                description "Number of Packets (min 1 - max 600)";
            }
            enum bytes {
                if-feature feature-list:NOT_HAVE_CUSTOM2_QOS;
                description "bytes (min 1024 - max 524288)";
            }
            enum kbytes {
                if-feature feature-list:NOT_HAVE_CUSTOM2_QOS;
                description "kilo-bytes (min 1 - max 512)";
            }
        }
        description "type definition for QOS_THRESHOLD_T";
    }

    typedef  qos_profile_name_default_t {
        type enumeration {
            enum default {
                value 0;
                description "default";
            }
        }
        description "type definition for QOS_PROFILE_NAME_DEFAULT_T";
    }

    typedef  qos_conform_action_t {
        type enumeration {
            enum none {
                value 0;
                description "Sets the action to take when the data rate is within bounds";
            }
            enum transmit {
                value 1;
                description "Specifies the action of transmitting packets";
            }
            enum set-dscp-transmit {
                value 2;
                description "Specify the IP DSCP value 0 to 63";
            }
            enum set-prec-transmit {
                value 3;
                description "Specify the IP Precedence value 0 to 7";
            }
            enum set-cos-transmit {
                value 4;
                description "Specify the cos value 0 to 7";
            }
            enum set-mpls-class {
                value 5;
                description "Set the mpls class filed to the give value and tx the packet";
            }
            enum set-qos-transmit {
                value 6;
                description "Specify the qos value";
            }
        }
        description "type definition for QOS_CONFORM_ACTION_T";
    }

    typedef  qos_exceed_action_t {
        type enumeration {
            enum none {
                value 0;
                description "default value";
            }
            enum drop {
                value 1;
                description "Sets the action to take when the data rate is exceeded. Default is drop";
            }
            enum set-dscp-transmit {
                value 2;
                description "Specify the IP DSCP value 0 to 63";
            }
            enum set-prec-transmit {
                value 3;
                description "Specify the IP Precedence value 0 to 7";
            }
            enum set-cos-transmit {
                value 4;
                description "Specify the cos value 0 to 7";
            }
            enum set-mpls-class {
                value 5;
                description "Set the mpls class filed to the give value and tx the packet";
            }
            enum set-flow-control {
                value 6;
                description "Send a pause frame on the ingress port and pass the packet";
            }
            enum set-axe-ret {
                value 7;
                description "Send a pause frame on the ingress port and pass the packet";
            }
            enum transmit {
                value 8;
                description "Pass the packet by setting DEI";
            }
        }
        description "type definition for QOS_EXCEED_ACTION_T";
    }

    typedef  qos_violate_action_t {
        type enumeration {
            enum none {
                value 0;
                description "default value";
            }
            enum drop {
                value 1;
                description "Sets the action to take when the data rate is exceeded. Default is drop";
            }
            enum set-dscp-transmit {
                value 2;
                description "Specify the IP DSCP value 0 to 63";
            }
            enum set-cos-transmit {
                value 3;
                description "Specify the cos value 0 to 7";
            }
            enum set-mpls-class {
                value 4;
                description "Set the mpls class filed to the give value and tx the packet";
            }
            enum transmit {
                value 5;
                description "Pass the packet by setting DEI";
            }
        }
        description "type definition for QOS_VIOLATE_ACTION_T";
    }

    typedef  qos_match_criteria_t {
        type enumeration {
            enum match-all {
                value 1;
                description "match all";
            }
            enum match-any {
                value 2;
                description "match any";
            }
        }
        description "type definition for QOS_MATCH_CRITERIA_T";
    }

    typedef  qos_traffic_type_t {
        type enumeration {
            enum l2-uc {
                value 1;
                if-feature feature-list:NOT_HAVE_CUSTOM2_QOS;
                description "L2 Unicast";
            }
            enum l2-uc-unknown {
                value 2;
                if-feature feature-list:NOT_HAVE_CUSTOM2_QOS;
                description "Unknown L2 Unicast";
            }
            enum l2-mc {
                value 3;
                if-feature feature-list:HAVE_CUSTOM2_QOS;
                description "L2 Multicast";
            }
            enum l2-bc {
                value 5;
                if-feature feature-list:HAVE_CUSTOM2_QOS;
                description "L2 Broadcast";
            }
            enum default {
                value 6;
                description "L2 traffic-type all";
            }
            enum l2-unknown {
                value 7;
                if-feature feature-list:HAVE_CUSTOM2_QOS;
                description "Unknown L2 traffic";
            }
        }
        description "type definition for QOS_TRAFFIC_TYPE_T";
    }

    typedef  qos_layer4_protocol_t {
        type enumeration {
            enum any {
                value 0;
                description "Specify ANY protocol- TCP/UDP";
            }
            enum tcp {
                value 1;
                description "Specify TCP protocol";
            }
            enum udp {
                value 2;
                description "Specify UDP protocol";
            }
        }
        description "type definition for QOS_LAYER4_PROTOCOL_T";
    }

    typedef  qos_layer4_port_t {
        type enumeration {
            enum source-port {
                value 1;
                description "Specify source TCP/UDP port";
            }
            enum destination-port {
                value 2;
                description "Specify destination TCP/UDP port";
            }
        }
        description "type definition for QOS_LAYER4_PORT_T";
    }

    typedef  cml_remark_state_t {
        type enumeration {
            enum disable {
                value 1;
                description "Disable remarking";
            }
            enum enable {
                value 2;
                description "Enable remarking";
            }
        }
        description "type definition for CML_REMARK_STATE_T";
    }

    typedef  qos_proto_type_t {
        type enumeration {
            enum arp {
                value 0;
                description "Address Resolution protocol";
            }
            enum bridging {
                value 1;
                description "Bridging";
            }
            enum cdp {
                value 2;
                description "CISCO Discovery Protocol";
            }
            enum clns {
                value 3;
                description "connectionless network service";
            }
            enum clns-es {
                value 4;
                description "CLNS END systems";
            }
            enum clns-is {
                value 5;
                description "CLNS Intermediate systems";
            }
            enum dhcp {
                value 6;
                description "Dynamic host configuration";
            }
            enum isis {
                value 7;
                description "Intermediate system to Intermedaite system";
            }
            enum ldp {
                value 8;
                description "Label Distrubution protocol";
            }
            enum netbios {
                value 9;
                description "NetBIOS Extended User Interface";
            }
        }
        description "type definition for QOS_PROTO_TYPE_T";
    }

    typedef  qos_mac_address_t {
        type string {
            pattern "[0-9a-fA-F]{2}(:[0-9a-fA-F]{2}){5}|[0-9a-fA-F]{2}(-[0-9a-fA-F]{2}){5}|[0-9a-fA-F]{4}(\\.[0-9a-fA-F]{4}){2}";
        }
        description "MAC(XX-XX-XX-XX-XX-XX) address (Option 1) or MAC(XX:XX:XX:XX:XX:XX)
                    address (Option 2) or MAC(XXXX.XXXX.XXXX) address (Option 3).";
    }

}
