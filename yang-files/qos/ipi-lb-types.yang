/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-lb-types.yang
*
*/

module ipi-lb-types {

    yang-version 1.1;

    namespace   "http://www.ipinfusion.com/yang/ocnos/ipi-lb-types";

    prefix "ipi-lb-types";

    organization
        "IP Infusion Inc.";

    contact
        "Address: 3965 Freedom Circle, Suite 200, Santa Clara, CA 95054
         Phone: +1 408-400-1900
         E-mail: support@ipinfusion.com
         Web: http://www.ipinfusion.com/";

    description
        "Link Bonding types";


    revision "2021-07-10" {
        description "Initial Version";
        reference "Initial Version";
    }



    typedef  lb_segment_size_t {
        type enumeration {
            enum 128 {
                value 0;
                description "128";
            }
            enum 128Eh {
                value 1;
                description "128Eh";
            }
            enum 192 {
                value 2;
                description "192";
            }
            enum 192Eh {
                value 3;
                description "192Eh";
            }
        }
        description "type definition for LB_SEGMENT_SIZE_T";
    }

}
