/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-qos.yang
*
*/

module ipi-qos {

    yang-version 1.1;

    namespace   "http://www.ipinfusion.com/yang/ocnos/ipi-qos";

    prefix "ipi-qos";

    import cml-data-types {
        prefix cml-data-types;
        revision-date 2022-09-30;
    }

    import ipi-qos-types {
        prefix ipi-qos-types;
        revision-date 2022-06-01;
    }

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "Quality of Service (QoS)";


    revision "2022-08-24" {
        description "Changed helpstring from queeu to Traffic-Class";
        reference " 2.0.3.";
    }

    revision "2022-07-28" {
        description "Added dependentObject for qos-enable in all qos configuration";
        reference " 2.0.2.";
    }

    revision "2022-07-19" {
        description "Removed autoPopulate from qos container";
        reference " 2.0.1.";
    }

    revision "2022-07-11" {
        description "Removed implicit-delete from queue-mode config";
        reference " 2.0.0.";
    }

    revision "2022-06-27" {
        description "Updated when expressions in yang file";
        reference " 1.0.0.";
    }

    revision "2022-06-01" {
        description "Updated the yang file with feature";
        reference "Initial Version";
    }

    revision "2022-01-13" {
        description "Added the new objectlist queue-color-to-exp in queues-to-exp container";
        reference "Initial Version";
    }

    revision "2021-12-15" {
        description "Added color option in egress exp-map";
        reference "Initial Version";
    }

    revision "2021-12-10" {
        description "Added remark-queue-value option in ingress exp-map";
        reference "Initial Version";
    }

    revision "2021-10-08" {
        description "Added remark-queue option in ingress cos-map";
        reference "Initial Version";
    }

    revision "2021-07-29" {
        description "Do not trigger hardware specific events for Software Forwarder Feature.";
        reference "Initial Version";
    }

    revision "2021-07-12" {
        description "Add attribute 'reference-description' on class-map and policy-map profile to help configuration translation process to Open Config model.";
        reference "Initial Version";
    }

    revision "2021-07-06" {
        description "Add support to IP precedence(TOS) related profile.";
        reference "Initial Version";
    }

    revision "2021-06-30" {
        description "Modify CIR attribute description and enumeration values descriptions for QOS_RATE_UNIT_T type.";
        reference "Initial Version";
    }

    revision "2021-06-24" {
        description "Return back leaves block-size and child-service-policy-name";
        reference "Initial Version";
    }

    revision "2021-06-10" {
        description "Changed data type to CML_RANGE_T for attributes 'port', 'vlan', 'inner-vlan', 'rtp'.";
        reference "Initial Version";
    }

    revision "2021-06-08" {
        description "Add a limit of 32 entries on leaf-list used for destination-mac and source-mac attributes.";
        reference "Initial Version";
    }

    revision "2021-06-07" {
        description "Changed value on QOS_CLEAR_STATS_T used on objectaction qos-clear-statistics";
        reference "Initial Version";
    }

    revision "2021-06-04" {
        description "Changed type of attributes 'precedence-remark', 'precedence-remark-only-bridged', 'dscp-value-remark' and 'dscp-remark-only-bridged'. Attribute 'dscp-value' from 'qos-mode' have name changed to 'dscp-value-remark'.";
        reference "Initial Version";
    }

    revision "2021-05-28" {
        description "Removed whole policy-maps-default container";
        reference "Initial Version";
    }

    revision "2021-05-26" {
        description "Changed data type for attributes dscp-all, ipv6-dscp-all, precedence-all, ipv6-precedence-all";
        reference "Initial Version";
    }

    revision "2021-05-21" {
        description "Added match cos and qos-group, set qos-group, and support for hierarchical QoS and VLAN shaping for DC platforms";
        reference "Initial Version";
    }

    revision "2021-05-20" {
        description "Changed type of attributes with name 'type' of containers 'class-map-default' and 'policy-map-default'";
        reference "Initial Version";
    }

    revision "2021-05-19" {
        description "Changed types QOS_PRECEDENCE_EXTENDED_T and QOS_DSCP_EXTENDED_T to CML_UINT8_T and types QOS_PRECEDENCE_VAL_T and QOS_DSCP_VAL_T to CML_RANGE_T";
        reference "Initial Version";
    }

    revision "2021-05-14" {
        description "Removed vxlan-qos clis for DC platforms";
        reference "Initial Version";
    }

    revision "2021-05-11" {
        description "Remove unsupported leaves block-size and child-service-policy-name";
        reference "Initial Version";
    }

    revision "2021-05-07" {
        description "Add weight and drop-probability options for DC platforms";
        reference "Initial Version";
    }

    revision "2021-05-06" {
        description "Updated color and dei overall the model to include 'all' when it is the key, otherwise to be optional";
        reference "Initial Version";
    }

    revision "2021-05-05" {
        description "Added length in policies and classes names";
        reference "Initial Version";
    }

    revision "2021-04-13" {
        description "Enable weighted-round-robin and strict-priority unicast/non-unicast weight configuration for DC platforms";
        reference "Initial Version";
    }

    revision "2021-04-06" {
        description "Updated mac address leaves to new type";
        reference "Initial Version";
    }

    revision "2021-03-24" {
        description "Renamed precedence and vxlan-queue-color-to-dscp-profiles objects";
        reference "Initial Version";
    }

    revision "2021-03-23" {
        description "Removed mutation-map related objects";
        reference "Initial Version";
    }

    revision "2021-03-18" {
        description "Created a separated struct for class-map type queue";
        reference "Initial Version";
    }

    revision "2021-03-15" {
        description "Removed qos-default and match-default options from its enum";
        reference "Initial Version";
    }

    revision "2020-12-04" {
        description "Restructured module as per open-config style";
        reference "Initial Version";
    }

    revision "2018-06-21" {
        description "Initial Version";
        reference "Initial Version";
    }

    grouping qos-class-map-default-top {
        description
            "Grouping for QoS class-map-default";
        container class-maps-default {
            config false;
            description
                "State data for QoS class-map-default";

            list class-map-default {
            when " /ipi-qos:qos/ipi-qos:global/ipi-qos:config/ipi-qos:enable-qos ";
                key "name";
                config false;
                description
                    "State data list for QoS class-map-default";
                leaf name  {
                    type  leafref {
                        path  "../state/name";
                    }
                    description "Use this attribute to show the class-map-default name";
                } // END of name definition.

                container state {
                    config false;
                    description
                        "Operational state data for QoS class-map-default";
                    uses qos-class-map-default-state;
                } // END of state-container definition.
            } // End of class-map-default-list
        } // END of class-maps-default-container definition.
    } // END of qos-class-map-default-top definition.
    grouping qos-class-map-default-state {
        description
            "Grouping for QoS class-default match state";
        leaf name  {
            type  string {
                length "1..1965";
                pattern "[^?' =,>|]+";
            }
            description "Use this attribute to show the class-map-default name";
        } // END of name definition.

        leaf type  {
            type  ipi-qos-types:qos_class_map_default_t;
            description "Use this attribute to show the class-map-default type.";
        } // END of type definition.

        leaf match-criteria  {
            type  ipi-qos-types:qos_match_criteria_t;
            description "Use this attribute to show the class-map-default match-criteria.";
        } // END of match-criteria definition.

    } // END of qos-class-map-default-state definition.
    grouping qos-class-map-top {
        description
            "Grouping for QoS class-map";
        container class-maps {
            description
                "Configuration data for QoS class-map";

            list class-map {
            when " /ipi-qos:qos/ipi-qos:global/ipi-qos:config/ipi-qos:enable-qos ";
                key "name";
                description
                    "Configuration data list for QoS class-map";
                leaf name  {
                    type  leafref {
                        path  "../config/name";
                    }
                    description "Use this attribute to set the class-map name";
                } // END of name definition.

                container config {
                    description
                        "Configuration data for QoS class-map";
                    uses qos-class-map-config;
                } // END of config-container definition.
                container state {
                    config false;
                    description
                        "Operational state data for QoS class-map";
                    uses qos-class-map-config;
                } // END of state-container definition.
                container match-any-conditions {
                    when " ../config/match-criteria='match-any' ";
                    description
                        "Configuration data for QoS class match-any";
                    container config {
                        description
                            "Configuration data for QoS class match-any";
                        uses qos-class-match-any-config;
                    } // END of config-container definition.
                    container state {
                        config false;
                        description
                            "Operational state data for QoS class match-any";
                        uses qos-class-match-any-config;
                    } // END of state-container definition.
                    container ipv4 {
                        description
                            "Configuration data for QoS class match-any";

                        list layer4-match {
                            key "protocol port-type";
                            max-elements 1;
                            description
                                "Configuration data for QoS class layer 4 match";
                            leaf protocol  {
                                type  leafref {
                                    path  "../config/protocol";
                                }
                                description "Use this attribute to classify traffic based on the layer 4 protocol";
                            } // END of protocol definition.

                            leaf port-type  {
                                type  leafref {
                                    path  "../config/port-type";
                                }
                                description "Use this attribute to classify traffic based on layer 4 source port or
                                            destination port";
                            } // END of port-type definition.

                            container config {
                                description
                                    "Configuration data for QoS class layer 4 match";
                                uses qos-layer4-match-config;
                            } // END of config-container definition.
                            container state {
                                config false;
                                description
                                    "Operational state data for QoS class layer 4 match";
                                uses qos-layer4-match-config;
                            } // END of state-container definition.
                        } // End of layer4-match-list
                    } // END of ipv4-container definition.
                    container ipv6 {
                        description
                            "Configuration data for QoS class match-any";

                        list layer4-match {
                            if-feature feature-list:HAVE_CUSTOM2_QOS;
                            key "protocol port-type";
                            max-elements 1;
                            description
                                "Configuration data for QoS class ipv6 layer 4 match";
                            leaf protocol  {
                                type  leafref {
                                    path  "../config/protocol";
                                }
                                description "Use this attribute to classify traffic based on the layer 4 protocol";
                            } // END of protocol definition.

                            leaf port-type  {
                                type  leafref {
                                    path  "../config/port-type";
                                }
                                description "Use this attribute to classify traffic based on layer 4 source port or
                                            destination port";
                            } // END of port-type definition.

                            container config {
                                description
                                    "Configuration data for QoS class ipv6 layer 4 match";
                                uses qos-layer4-match-config;
                            } // END of config-container definition.
                            container state {
                                config false;
                                description
                                    "Operational state data for QoS class layer 4 match";
                                uses qos-layer4-match-config;
                            } // END of state-container definition.
                        } // End of layer4-match-list
                    } // END of ipv6-container definition.
                } // END of match-any-conditions-container definition.
                container match-all-conditions {
                    when " ../config/match-criteria='match-all' ";
                    description
                        "Configuration data for QoS class match-all";

                    list layer4-match-ipv4 {
                        key "protocol-all port-type-all port-all";
                        max-elements 1;
                        description
                            "Configuration data for QoS class layer 4 match";
                        leaf protocol-all  {
                            type  leafref {
                                path  "../config/protocol-all";
                            }
                            description "Use this attribute to classify traffic based on the layer 4 protocol";
                        } // END of protocol-all definition.

                        leaf port-type-all  {
                            type  leafref {
                                path  "../config/port-type-all";
                            }
                            description "Use this attribute to classify traffic based on layer 4 source port or
                                        destination port";
                        } // END of port-type-all definition.

                        leaf port-all  {
                            type  leafref {
                                path  "../config/port-all";
                            }
                            description "Use this attribute to classify traffic based on the port";
                        } // END of port-all definition.

                        container config {
                            description
                                "Configuration data for QoS class layer 4 match";
                            uses qos-layer4-match-all-config;
                        } // END of config-container definition.
                        container state {
                            config false;
                            description
                                "Operational state data for QoS class layer 4 match";
                            uses qos-layer4-match-all-config;
                        } // END of state-container definition.
                    } // End of layer4-match-ipv4-list

                    list layer4-match-ipv6 {
                        if-feature feature-list:HAVE_CUSTOM2_QOS;
                        key "protocol-all port-type-all port-all";
                        max-elements 1;
                        description
                            "Configuration data for QoS class ipv6 layer 4 match";
                        leaf protocol-all  {
                            type  leafref {
                                path  "../config/protocol-all";
                            }
                            description "Use this attribute to classify traffic based on the layer 4 protocol";
                        } // END of protocol-all definition.

                        leaf port-type-all  {
                            type  leafref {
                                path  "../config/port-type-all";
                            }
                            description "Use this attribute to classify traffic based on layer 4 source port or
                                        destination port";
                        } // END of port-type-all definition.

                        leaf port-all  {
                            type  leafref {
                                path  "../config/port-all";
                            }
                            description "Use this attribute to classify traffic based on the port";
                        } // END of port-all definition.

                        container config {
                            description
                                "Configuration data for QoS class ipv6 layer 4 match";
                            uses qos-layer4-match-all-config;
                        } // END of config-container definition.
                        container state {
                            config false;
                            description
                                "Operational state data for QoS class layer 4 match";
                            uses qos-layer4-match-all-config;
                        } // END of state-container definition.
                    } // End of layer4-match-ipv6-list
                    container config {
                        description
                            "Configuration data for QoS class match-all";
                        uses qos-class-match-all-config;
                    } // END of config-container definition.
                    container state {
                        config false;
                        description
                            "Operational state data for QoS class match-all";
                        uses qos-class-match-all-config;
                    } // END of state-container definition.
                } // END of match-all-conditions-container definition.
            } // End of class-map-list
        } // END of class-maps-container definition.
    } // END of qos-class-map-top definition.
    grouping qos-class-map-config {
        description
            "Grouping for QoS class match configuration";
        leaf name  {
            type  string {
                length "1..32";
                pattern "[^?' =,>|]+";
            }
            description "Use this attribute to set the class-map name";
        } // END of name definition.

        leaf type  {
            type  ipi-qos-types:qos_class_map_t;
            mandatory true;
            description "Use this attribute to set the class-map type. Default value is 1.";
        } // END of type definition.

        leaf match-criteria  {
            type  ipi-qos-types:qos_match_criteria_t;
            mandatory true;
            description "Use this attribute to set the class-map match-criteria. Default value
                        is 1.";
        } // END of match-criteria definition.

        leaf reference-description  {
            type  cml-data-types:cml_line_t {
                length "1..64";
            }
            description "This attribute configures reference description message on class-map
                        profile for QoS type.";
        } // END of reference-description definition.

    } // END of qos-class-map-config definition.
    grouping qos-layer4-match-config {
        description
            "Grouping for QoS class layer 4 match configuration";
        leaf protocol  {
            type  ipi-qos-types:qos_layer4_protocol_t;
            description "Use this attribute to classify traffic based on the layer 4 protocol";
        } // END of protocol definition.

        leaf port-type  {
            type  ipi-qos-types:qos_layer4_port_t;
            description "Use this attribute to classify traffic based on layer 4 source port or
                        destination port";
        } // END of port-type definition.

        leaf port  {
            type  cml-data-types:cml_range_t;
            mandatory true;
            description "Use this attribute to classify traffic based on the port. Enter
                        TCP/UDP port value 1-65535 or range of values.";
        } // END of port definition.

    } // END of qos-layer4-match-config definition.
    grouping qos-layer4-match-all-config {
        description
            "Grouping for QoS class layer 4 match configuration";
        leaf protocol-all  {
            type  ipi-qos-types:qos_layer4_protocol_t;
            description "Use this attribute to classify traffic based on the layer 4 protocol";
        } // END of protocol-all definition.

        leaf port-type-all  {
            type  ipi-qos-types:qos_layer4_port_t;
            description "Use this attribute to classify traffic based on layer 4 source port or
                        destination port";
        } // END of port-type-all definition.

        leaf port-all  {
            type  uint16 {
                 range "1..65535"  {
                    description "1..65535: Supported range 1 - 65535";
                 }
            }
            description "Use this attribute to classify traffic based on the port";
        } // END of port-all definition.

    } // END of qos-layer4-match-all-config definition.
    grouping qos-class-match-any-config {
        description
            "Grouping for QoS class match-any configuration";
        leaf access-control-list-name  {
            type  string {
                length "1..64";
                pattern "[^?' =,>|]+";
            }
            description "Use this attribute to classify traffic based on the Access Control
                        List (ACL)";
        } // END of access-control-list-name definition.

        leaf-list ethertype  {
            when " not(/ipi-qos:qos/ipi-qos:global/ipi-qos:class-maps/ipi-qos:class-map/ipi-qos:match-any-conditions/ipi-qos:config/ipi-qos:access-control-list-name) ";
            if-feature feature-list:HAVE_CUSTOM2_QOS;
            type  string {
                length "1..1965";
                pattern "0x[^?' =,>]+";
            }
            description "Use this attribute to classify traffic based on the EtherType value(s)";
        } // END of ethertype definition.

        leaf-list traffic-type  {
            when " not(/ipi-qos:qos/ipi-qos:global/ipi-qos:class-maps/ipi-qos:class-map/ipi-qos:match-any-conditions/ipi-qos:config/ipi-qos:access-control-list-name) ";
            type  ipi-qos-types:qos_traffic_type_t;
            description "Use this attribute to classify traffic based on the traffic type value";
        } // END of traffic-type definition.

        leaf cos  {
            when " not(/ipi-qos:qos/ipi-qos:global/ipi-qos:class-maps/ipi-qos:class-map/ipi-qos:match-any-conditions/ipi-qos:config/ipi-qos:access-control-list-name) ";
            type  cml-data-types:cml_range_t;
            description "Use this attribute to classify traffic based on the Class of Service
                        (CoS) value";
        } // END of cos definition.

        leaf inner-cos  {
            when " not(/ipi-qos:qos/ipi-qos:global/ipi-qos:class-maps/ipi-qos:class-map/ipi-qos:match-any-conditions/ipi-qos:config/ipi-qos:access-control-list-name) ";
            type  cml-data-types:cml_range_t;
            description "Use this attribute to classify traffic based on inner Class of Service
                        (CoS) value";
        } // END of inner-cos definition.

        leaf vlan  {
            when " not(/ipi-qos:qos/ipi-qos:global/ipi-qos:class-maps/ipi-qos:class-map/ipi-qos:match-any-conditions/ipi-qos:config/ipi-qos:access-control-list-name) ";
            type  cml-data-types:cml_range_t;
            description "Use this attribute to classify traffic based on VLAN ID. Enter VLAN ID
                        1-4094 or range of VLAN ID's.";
        } // END of vlan definition.

        leaf inner-vlan  {
            when " not(/ipi-qos:qos/ipi-qos:global/ipi-qos:class-maps/ipi-qos:class-map/ipi-qos:match-any-conditions/ipi-qos:config/ipi-qos:access-control-list-name) ";
            type  cml-data-types:cml_range_t;
            description "Use this attribute to classify traffic based on inner VLAN ID. Enter
                        VLAN ID 1-4094 or range of VLAN ID's.";
        } // END of inner-vlan definition.

        leaf rtp  {
            when " not(/ipi-qos:qos/ipi-qos:global/ipi-qos:class-maps/ipi-qos:class-map/ipi-qos:match-any-conditions/ipi-qos:config/ipi-qos:access-control-list-name) ";
            type  cml-data-types:cml_range_t;
            description "Use this attribute to classify traffic based on the Real-time
                        Transport Protocol (RTP). The rtp value 2000-65535 or range of rtp
                        values.";
        } // END of rtp definition.

        leaf mpls-exp  {
            when " not(/ipi-qos:qos/ipi-qos:global/ipi-qos:class-maps/ipi-qos:class-map/ipi-qos:match-any-conditions/ipi-qos:config/ipi-qos:access-control-list-name) ";
            if-feature feature-list:HAVE_DIFFSERV;
            type  cml-data-types:cml_range_t;
            description "Use this attribute to classify traffic based on the MPLS experimental
                        (EXP) value";
        } // END of mpls-exp definition.

        leaf dscp  {
            when " not(/ipi-qos:qos/ipi-qos:global/ipi-qos:class-maps/ipi-qos:class-map/ipi-qos:match-any-conditions/ipi-qos:config/ipi-qos:access-control-list-name) ";
            type  cml-data-types:cml_range_t;
            description "Use this attribute to classify traffic based on the Differentiated
                        Services Control Protocol (DSCP) value.
                        Warning: In CLI show running, DSCP values with well-known names (ex.:
                        af11, cs0) will be displayed as such.
                        On Netconf, DSCP values will always be numeric.";
        } // END of dscp definition.

        leaf ipv6-dscp  {
            when " not(/ipi-qos:qos/ipi-qos:global/ipi-qos:class-maps/ipi-qos:class-map/ipi-qos:match-any-conditions/ipi-qos:config/ipi-qos:access-control-list-name) ";
            if-feature feature-list:HAVE_CUSTOM2_QOS;
            type  cml-data-types:cml_range_t;
            description "Use this attribute to classify traffic based on the Differentiated
                        Services Control Protocol (DSCP) value.
                        Warning: In CLI show running, DSCP values with well-known names (ex.:
                        af11, cs0) will be displayed as such.
                        On Netconf, DSCP values will always be numeric.";
        } // END of ipv6-dscp definition.

        leaf precedence  {
            when " not(/ipi-qos:qos/ipi-qos:global/ipi-qos:class-maps/ipi-qos:class-map/ipi-qos:match-any-conditions/ipi-qos:config/ipi-qos:access-control-list-name) ";
            type  cml-data-types:cml_range_t;
            description "Use this attribute to classify traffic based on the precedence value.
                        Warning: In CLI show running, precedence values with well-known names
                        (ex.: priority, immediate) will be displayed as such.
                        On Netconf, precedence values will always be numeric.";
        } // END of precedence definition.

        leaf ipv6-precedence  {
            when " not(/ipi-qos:qos/ipi-qos:global/ipi-qos:class-maps/ipi-qos:class-map/ipi-qos:match-any-conditions/ipi-qos:config/ipi-qos:access-control-list-name) ";
            if-feature feature-list:HAVE_CUSTOM2_QOS;
            type  cml-data-types:cml_range_t;
            description "Use this attribute to classify IPv6 traffic based on the precedence
                        value.
                        Warning: In CLI show running, precedence values with well-known names
                        (ex.: priority, immediate) will be displayed as such.
                        On Netconf, precedence values will always be numeric.";
        } // END of ipv6-precedence definition.

        leaf-list packet-protocol  {
            when " not(/ipi-qos:qos/ipi-qos:global/ipi-qos:class-maps/ipi-qos:class-map/ipi-qos:match-any-conditions/ipi-qos:config/ipi-qos:access-control-list-name) ";
            if-feature feature-list:HAVE_CUSTOM1_QOS;
            type  ipi-qos-types:qos_proto_type_t;
            description "Use this attribute to classify traffic based on the protocol";
        } // END of packet-protocol definition.

        leaf-list source-mac  {
            when " not(/ipi-qos:qos/ipi-qos:global/ipi-qos:class-maps/ipi-qos:class-map/ipi-qos:match-any-conditions/ipi-qos:config/ipi-qos:access-control-list-name) ";
            if-feature feature-list:HAVE_CUSTOM1_QOS;
            type  ipi-qos-types:qos_mac_address_t {
                length "1..17";
            }
            max-elements 32;
            description "Use this attribute to classify traffic based on the source MAC
                        address. The MAC address value allow up to 17 characters.";
        } // END of source-mac definition.

        leaf-list destination-mac  {
            when " not(/ipi-qos:qos/ipi-qos:global/ipi-qos:class-maps/ipi-qos:class-map/ipi-qos:match-any-conditions/ipi-qos:config/ipi-qos:access-control-list-name) ";
            if-feature feature-list:HAVE_CUSTOM1_QOS;
            type  ipi-qos-types:qos_mac_address_t {
                length "1..17";
            }
            max-elements 32;
            description "Use this attribute to classify traffic based on the destination MAC
                        address. The MAC address value allow up to 17 characters.";
        } // END of destination-mac definition.

    } // END of qos-class-match-any-config definition.
    grouping qos-class-match-all-config {
        description
            "Grouping for QoS class match-all configuration";
        leaf ethertype-all  {
            if-feature feature-list:HAVE_CUSTOM2_QOS;
            type  string {
                length "1..1965";
                pattern "[^?' =,>|]+";
            }
            description "Use this attribute to classify traffic based on the EtherType value";
        } // END of ethertype-all definition.

        leaf traffic-type-all  {
            type  ipi-qos-types:qos_traffic_type_t;
            description "Use this attribute to classify traffic based on the traffic type";
        } // END of traffic-type-all definition.

        leaf cos-all  {
            type  uint8 {
                 range "0..7"  {
                    description "0..7: Supported range 0 - 7";
                 }
            }
            description "Use this attribute to classify traffic based on the Class of Service
                        (CoS) value";
        } // END of cos-all definition.

        leaf inner-cos-all  {
            type  uint8 {
                 range "0..7"  {
                    description "0..7: Supported range 0 - 7";
                 }
            }
            description "Use this attribute to classify traffic based on the inner Class of
                        Service (CoS) value";
        } // END of inner-cos-all definition.

        leaf vlan-all  {
            type  uint16 {
                 range "1..4094"  {
                    description "1..4094: Supported range 1 - 4094";
                 }
            }
            description "Use this attribute to classify traffic based on the VLAN ID";
        } // END of vlan-all definition.

        leaf inner-vlan-all  {
            type  uint16 {
                 range "1..4094"  {
                    description "1..4094: Supported range 1 - 4094";
                 }
            }
            description "Use this attribute to classify traffic based on the inner VLAN ID";
        } // END of inner-vlan-all definition.

        leaf rtp-all  {
            type  uint32 {
                 range "2000..65535"  {
                    description "2000..65535: Supported range 2000 - 65535";
                 }
            }
            description "Use this attribute to classify traffic based on the Real-time
                        Transport Protocol (RTP)";
        } // END of rtp-all definition.

        leaf mpls-exp-all  {
            if-feature feature-list:HAVE_DIFFSERV;
            type  uint8 {
                 range "0..7"  {
                    description "0..7: Supported range 0 - 7";
                 }
            }
            description "Use this attribute to classify traffic based on the MPLS experimental
                        (EXP) value";
        } // END of mpls-exp-all definition.

        leaf dscp-all  {
            type  string {
                length "1..8";
                pattern "[^?' =,>|]+";
            }
            description "Use this attribute to classify traffic based on the Differentiated
                        Services Control Protocol (DSCP) value. The DSCP value range is 0-63.
                        Warning: In CLI show running, DSCP values with well-known names (ex.:
                        af11, cs0) will be displayed as such.
                        On Netconf, DSCP values will always be numeric. The string type allow
                        up to 8 characters on well-known name.";
        } // END of dscp-all definition.

        leaf ipv6-dscp-all  {
            if-feature feature-list:HAVE_CUSTOM2_QOS;
            type  string {
                length "1..8";
                pattern "[^?' =,>|]+";
            }
            description "Use this attribute to classify traffic based on the Differentiated
                        Services Control Protocol (DSCP) value upon IPv6 packet. The DSCP
                        value range is 0-63.
                        Warning: In CLI show running, DSCP values with well-known names (ex.:
                        af11, cs0) will be displayed as such.
                        On Netconf, DSCP values will always be numeric. The string type allow
                        up to 8 characters on well-known name.";
        } // END of ipv6-dscp-all definition.

        leaf precedence-all  {
            type  string {
                length "1..13";
                pattern "[^?' =,>|]+";
            }
            description "Use this attribute to classify traffic based on the precedence value.
                        The precedence value range is 0-7.
                        Warning: In CLI show running, precedence values with well-known names
                        (ex.: priority, immediate) will be displayed as such.
                        On Netconf, precedence values will always be numeric. The string type
                        allow up to 13 characters on well-known name.";
        } // END of precedence-all definition.

        leaf ipv6-precedence-all  {
            if-feature feature-list:HAVE_CUSTOM2_QOS;
            type  string {
                length "1..13";
                pattern "[^?' =,>|]+";
            }
            description "Use this attribute to classify traffic based on the precedence value
                        upon IPv6 packet. The precedence value range is 0-7.
                        Warning: In CLI show running, precedence values with well-known names
                        (ex.: priority, immediate) will be displayed as such.
                        On Netconf, precedence values will always be numeric. The string type
                        allow up to 13 characters on well-known name.";
        } // END of ipv6-precedence-all definition.

        leaf packet-protocol-all  {
            if-feature feature-list:HAVE_CUSTOM1_QOS;
            type  ipi-qos-types:qos_proto_type_t;
            description "Use this attribute to classify traffic based on the protocol";
        } // END of packet-protocol-all definition.

        leaf source-mac-all  {
            if-feature feature-list:HAVE_CUSTOM1_QOS;
            type  ipi-qos-types:qos_mac_address_t {
                length "1..17";
            }
            description "Use this attribute to classify traffic based on the source MAC
                        address. The MAC address value allow up to 17 characters.";
        } // END of source-mac-all definition.

        leaf destination-mac-all  {
            if-feature feature-list:HAVE_CUSTOM1_QOS;
            type  ipi-qos-types:qos_mac_address_t {
                length "1..17";
            }
            description "Use this attribute to classify traffic based on the destination MAC
                        address. The MAC address value allow up to 17 characters.";
        } // END of destination-mac-all definition.

    } // END of qos-class-match-all-config definition.
    grouping qos-class-map-queuing-match-condition-config {
        description
            "Grouping for QoS class-map-queuing configuration";
        leaf vlan-queue  {
            type  uint16 {
                 range "1..4094"  {
                    description "1..4094: Supported range 1 - 4094";
                 }
            }
            description "Use this attribute to classify traffic based on the VLAN ID";
        } // END of vlan-queue definition.

        leaf-list queue  {
            if-feature feature-list:HAVE_SERVICE_QUEUING_2;
            type  uint8 {
                 range "0..7"  {
                    description "0..7: Supported range 0 - 7";
                 }
            }
            description "Use this attribute to classify traffic based on queue value";
        } // END of queue definition.

        leaf service-template-name  {
            if-feature feature-list:HAVE_SERVICE_QUEUING_2;
            type  string {
                length "1..1965";
                pattern "[^?' =,>|]+";
            }
            description "Use this attribute to classify traffic based on service template";
        } // END of service-template-name definition.

        leaf interface  {
            if-feature feature-list:HAVE_SERVICE_QUEUING_2;
            type  string {
                length "1..1965";
                pattern "[^?' =,>|]+";
            }
            description "Use this attribute to classify traffic based on the subinterface or
                        vlan interface name";
        } // END of interface definition.

        leaf cos  {
            if-feature feature-list:HAVE_CUSTOM1_QOS;
            type  cml-data-types:cml_range_t;
            description "Use this attribute to classify traffic based on the Class of Service
                        (CoS) value";
        } // END of cos definition.

        leaf qos-group  {
            if-feature feature-list:HAVE_CUSTOM1_QOS;
            type  uint32 {
                 range "1..2000"  {
                    description "1..2000: Supported range 1 - 2000";
                 }
            }
            description "Use this attribute to classify traffic QoS group";
        } // END of qos-group definition.

    } // END of qos-class-map-queuing-match-condition-config definition.
    grouping qos-class-map-queuing-match-condition {
        description
            "Grouping for class-map-queuing matching condition";
        container match-conditions {
            when " /ipi-qos:qos/ipi-qos:global/ipi-qos:class-maps-queuing/ipi-qos:class-map-queuing/ipi-qos:config/ipi-qos:type = 'queuing' ";
            description
                "Configuration data for class-map-queuing matching condition";
            container config {
                description
                    "Configuration data for class-map-queuing matching conditions";
                uses qos-class-map-queuing-match-condition-config;
            } // END of config-container definition.
            container state {
                config false;
                description
                    "Operational state data for class-map-queuing matching conditions";
                uses qos-class-map-queuing-match-condition-config;
            } // END of state-container definition.
        } // END of match-conditions-container definition.
    } // END of qos-class-map-queuing-match-condition definition.
    grouping qos-class-map-queuing-config {
        description
            "Grouping for QoS class-map-queuing configuration";
        leaf name  {
            type  string {
                length "1..32";
                pattern "[^?' =,>|]+";
            }
            description "Use this attribute to set the class-map name";
        } // END of name definition.

        leaf type  {
            type  ipi-qos-types:qos_class_map_t;
            mandatory true;
            description "Use this attribute to set the class-map type. Default value is 1.";
        } // END of type definition.

        leaf reference-description  {
            type  cml-data-types:cml_line_t {
                length "1..64";
            }
            description "This attribute configures reference description message on class-map
                        profile for queuing.";
        } // END of reference-description definition.

    } // END of qos-class-map-queuing-config definition.
    grouping qos-class-map-queuing-top {
        description
            "Grouping for QoS class-map-queuing";
        container class-maps-queuing {
            description
                "Configuration data for class-maps-queuing";

            list class-map-queuing {
            when " /ipi-qos:qos/ipi-qos:global/ipi-qos:config/ipi-qos:enable-qos ";
                key "name";
                description
                    "List of class-maps-queuing";
                leaf name  {
                    type  leafref {
                        path  "../config/name";
                    }
                    description "Use this attribute to set the class-map-queuing name";
                } // END of name definition.

                container config {
                    description
                        "Configuration data for class-map-queuing";
                    uses qos-class-map-queuing-config;
                } // END of config-container definition.
                container state {
                    config false;
                    description
                        "Operational state data for class-map-queuing";
                    uses qos-class-map-queuing-config;
                } // END of state-container definition.
                uses qos-class-map-queuing-match-condition;
            } // End of class-map-queuing-list
        } // END of class-maps-queuing-container definition.
    } // END of qos-class-map-queuing-top definition.
    grouping qos-cos-to-queue-config {
        description
            "Grouping for QoS CoS to Traffic-Class configuration";
        leaf cos-value  {
            type  uint8 {
                 range "0..7"  {
                    description "0..7: Supported range 0 - 7";
                 }
            }
            description "Use this attribute to map a Class of Service (CoS) value to a
                        particular Traffic-Class";
        } // END of cos-value definition.

        leaf queue-id  {
            type  uint8 {
                 range "0..7"  {
                    description "0..7: Supported range 0 - 7";
                 }
            }
            mandatory true;
            description "Use this attribute to select the Traffic-Class CoS is mapped to";
        } // END of queue-id definition.

        leaf remark-queue-id  {
            if-feature feature-list:HAVE_CUSTOM3_QOS;
            type  uint8 {
                 range "0..7"  {
                    description "0..7: Supported range 0 - 7";
                 }
            }
            description "Use this attribute to select the remarked Traffic-Class cos is mapped
                        to";
        } // END of remark-queue-id definition.

    } // END of qos-cos-to-queue-config definition.
    grouping qos-cos-to-queue {
        description
            "Grouping for QoS CoS to Traffic-Class";
        container cos-to-queues {
            if-feature feature-list:HAVE_CUSTOM2_QOS;
            description
                "Configuration data for QoS CoS to Traffic-Class";

            list cos-to-queue {
                key "cos-value";
                description
                    "Configuration data list for QoS CoS to Traffic-Class";
                leaf cos-value  {
                    type  leafref {
                        path  "../config/cos-value";
                    }
                    description "Use this attribute to map a Class of Service (CoS) value to a
                                particular Traffic-Class";
                } // END of cos-value definition.

                container config {
                    description
                        "Configuration data for QoS CoS to Traffic-Class";
                    uses qos-cos-to-queue-config;
                } // END of config-container definition.
                container state {
                    config false;
                    description
                        "Operational state data for QoS CoS to Traffic-Class";
                    uses qos-cos-to-queue-config;
                } // END of state-container definition.
            } // End of cos-to-queue-list
        } // END of cos-to-queues-container definition.
    } // END of qos-cos-to-queue definition.
    grouping qos-cos-to-queue-profile-top {
        description
            "Grouping for QoS CoS DEI to Traffic-Class profile";
        container cos-to-queue-profiles {
            description
                "Configuration data for QoS CoS DEI to Traffic-Class profile";

            list cos-to-queue-profile {
                key "name";
                description
                    "Configuration data list for QoS CoS DEI to Traffic-Class profile";
                leaf name  {
                    type  leafref {
                        path  "../config/name";
                    }
                    description "Use this attribute to set a name to CoS to Traffic-Class profile";
                } // END of name definition.

                container config {
                    description
                        "Configuration data for QoS CoS DEI to Traffic-Class profile";
                    uses qos-cos-to-queue-profile-config;
                } // END of config-container definition.
                container state {
                    config false;
                    description
                        "Operational state data for QoS CoS DEI to Traffic-Class profile";
                    uses qos-cos-to-queue-profile-config;
                } // END of state-container definition.
                uses qos-cos-dei-to-queue;
                uses qos-cos-to-queue;
            } // End of cos-to-queue-profile-list
        } // END of cos-to-queue-profiles-container definition.
    } // END of qos-cos-to-queue-profile-top definition.
    grouping qos-cos-to-queue-profile-config {
        description
            "Grouping for QoS CoS DEI to Traffic-Class profile configuration";
        leaf name  {
            type  string {
                length "1..31";
                pattern "[^?' =,>|]+";
            }
            description "Use this attribute to set a name to CoS to Traffic-Class profile";
        } // END of name definition.

    } // END of qos-cos-to-queue-profile-config definition.
    grouping qos-cos-dei-to-queue {
        description
            "Grouping for QoS CoS DEI to Traffic-Class";
        container cos-dei-to-queues {
            if-feature feature-list:NOT_HAVE_CUSTOM2_QOS;
            description
                "Configuration data for QoS CoS DEI to Traffic-Class";

            list cos-dei-to-queue {
                key "cos-value dei-value";
                description
                    "Configuration data list for QoS CoS DEI to Traffic-Class";
                leaf cos-value  {
                    type  leafref {
                        path  "../config/cos-value";
                    }
                    description "Use this attribute to map a Class of Service (CoS) value to a
                                particular Traffic-Class";
                } // END of cos-value definition.

                leaf dei-value  {
                    type  leafref {
                        path  "../config/dei-value";
                    }
                    description "Use this attribute to map a Discard Eligibility Indicator (DEI) value
                                to a particular Traffic-Class. Default value is 2.";
                } // END of dei-value definition.

                container config {
                    description
                        "Configuration data for QoS CoS DEI to Traffic-Class";
                    uses qos-cos-dei-to-queue-config;
                } // END of config-container definition.
                container state {
                    config false;
                    description
                        "Operational state data for QoS CoS DEI to Traffic-Class";
                    uses qos-cos-dei-to-queue-config;
                } // END of state-container definition.
            } // End of cos-dei-to-queue-list
        } // END of cos-dei-to-queues-container definition.
    } // END of qos-cos-dei-to-queue definition.
    grouping qos-cos-dei-to-queue-config {
        description
            "Grouping for QoS CoS DEI to Traffic-Class configuration";
        leaf cos-value  {
            type  uint8 {
                 range "0..7"  {
                    description "0..7: Supported range 0 - 7";
                 }
            }
            description "Use this attribute to map a Class of Service (CoS) value to a
                        particular Traffic-Class";
        } // END of cos-value definition.

        leaf dei-value  {
            type  ipi-qos-types:qos_dei_t;
            default "all";
            description "Use this attribute to map a Discard Eligibility Indicator (DEI) value
                        to a particular Traffic-Class";
        } // END of dei-value definition.

        leaf queue-id  {
            type  uint8 {
                 range "0..7"  {
                    description "0..7: Supported range 0 - 7";
                 }
            }
            mandatory true;
            description "Use this attribute to select the Traffic-Class CoS DEI is mapped to";
        } // END of queue-id definition.

        leaf color  {
            type  ipi-qos-types:qos_color_t;
            description "Use this attribute to select the color CoS DEI is mapped to.";
        } // END of color definition.

    } // END of qos-cos-dei-to-queue-config definition.
    grouping qos-dscp-to-dscp-profile-top {
        description
            "Grouping for QoS DSCP to DSCP profile";
        container dscp-to-dscp-profiles {
            if-feature feature-list:HAVE_CUSTOM2_QOS;
            description
                "Configuration data for QoS DSCP to DSCP profile";

            list dscp-to-dscp-profile {
                key "name";
                description
                    "Configuration data list for QoS DSCP to DSCP profile";
                leaf name  {
                    type  leafref {
                        path  "../config/name";
                    }
                    description "Use this attribute to set a name to DSCP to DSCP profile";
                } // END of name definition.

                container config {
                    description
                        "Configuration data for QoS DSCP to DSCP profile";
                    uses qos-dscp-to-dscp-profile-config;
                } // END of config-container definition.
                container state {
                    config false;
                    description
                        "Operational state data for QoS DSCP to DSCP profile";
                    uses qos-dscp-to-dscp-profile-config;
                } // END of state-container definition.
                uses qos-dscp-to-dscp;
            } // End of dscp-to-dscp-profile-list
        } // END of dscp-to-dscp-profiles-container definition.
    } // END of qos-dscp-to-dscp-profile-top definition.
    grouping qos-dscp-to-dscp-profile-config {
        description
            "Grouping for QoS DSCP to DSCP profile configuration";
        leaf name  {
            type  string {
                length "1..31";
                pattern "[^?' =,>|]+";
            }
            description "Use this attribute to set a name to DSCP to DSCP profile";
        } // END of name definition.

    } // END of qos-dscp-to-dscp-profile-config definition.
    grouping qos-dscp-to-dscp {
        description
            "Grouping for QoS DSCP to DSCP";
        container dscp-to-dscps {
            description
                "Configuration data for QoS DSCP to DSCP";

            list dscp-to-dscp {
                key "dscp-value color";
                description
                    "Configuration data list for QoS DSCP to DSCP";
                leaf dscp-value  {
                    type  leafref {
                        path  "../config/dscp-value";
                    }
                    description "Use this attribute to select Differentiated Services Control Protocol
                                (DSCP) value in";
                } // END of dscp-value definition.

                leaf color  {
                    type  leafref {
                        path  "../config/color";
                    }
                    description "Use this attribute to select the color to map. Default value is 3.";
                } // END of color definition.

                container config {
                    description
                        "Configuration data for QoS DSCP to DSCP";
                    uses qos-dscp-to-dscp-config;
                } // END of config-container definition.
                container state {
                    config false;
                    description
                        "Operational state data for QoS DSCP to DSCP";
                    uses qos-dscp-to-dscp-config;
                } // END of state-container definition.
            } // End of dscp-to-dscp-list
        } // END of dscp-to-dscps-container definition.
    } // END of qos-dscp-to-dscp definition.
    grouping qos-dscp-to-dscp-config {
        description
            "Grouping for QoS DSCP to DSCP configuration";
        leaf dscp-value  {
            type  uint8 {
                 range "0..63"  {
                    description "0..63: Supported range 0 - 63";
                 }
            }
            description "Use this attribute to select Differentiated Services Control Protocol
                        (DSCP) value in";
        } // END of dscp-value definition.

        leaf color  {
            type  ipi-qos-types:qos_color_key_t;
            default "all";
            description "Use this attribute to select the color to map";
        } // END of color definition.

        leaf remark-dscp-value  {
            type  uint8 {
                 range "0..63"  {
                    description "0..63: Supported range 0 - 63";
                 }
            }
            mandatory true;
            description "Use this attribute to select Differentiated Services Control Protocol
                        (DSCP) value out";
        } // END of remark-dscp-value definition.

    } // END of qos-dscp-to-dscp-config definition.
    grouping qos-precedence-to-precedence-profile-top {
        description
            "Grouping for QoS Precedence to Precedence profile";
        container precedence-to-precedence-profiles {
            if-feature feature-list:HAVE_CUSTOM2_QOS;
            description
                "Configuration data for QoS Precedence to Precedence profile";

            list precedence-to-precedence-profile {
                key "name";
                description
                    "Configuration data list for QoS Precedence to Precedence profile";
                leaf name  {
                    type  leafref {
                        path  "../config/name";
                    }
                    description "Use this attribute to set a name to Precedence to Precedence profile";
                } // END of name definition.

                container config {
                    description
                        "Configuration data for QoS Precedence to Precedence profile";
                    uses qos-precedence-to-precedence-profile-config;
                } // END of config-container definition.
                container state {
                    config false;
                    description
                        "Operational state data for QoS Precedence to Precedence profile";
                    uses qos-precedence-to-precedence-profile-config;
                } // END of state-container definition.
                uses qos-precedence-to-precedence;
            } // End of precedence-to-precedence-profile-list
        } // END of precedence-to-precedence-profiles-container definition.
    } // END of qos-precedence-to-precedence-profile-top definition.
    grouping qos-precedence-to-precedence-profile-config {
        description
            "Grouping for QoS Precedence to Precedence profile configuration";
        leaf name  {
            type  string {
                length "1..31";
                pattern "[^?' =,>|]+";
            }
            description "Use this attribute to set a name to Precedence to Precedence profile";
        } // END of name definition.

    } // END of qos-precedence-to-precedence-profile-config definition.
    grouping qos-precedence-to-precedence {
        description
            "Grouping for QoS Precedence to Precedence";
        container precedence-to-precedences {
            description
                "Configuration data for QoS Precedence to Precedence";

            list precedence-to-precedence {
                key "precedence-value";
                description
                    "Configuration data list for QoS Precedence to Precedence";
                leaf precedence-value  {
                    type  leafref {
                        path  "../config/precedence-value";
                    }
                    description "Use this attribute to select IP Precedence value in";
                } // END of precedence-value definition.

                container config {
                    description
                        "Configuration data for QoS Precedence to Precedence";
                    uses qos-precedence-to-precedence-config;
                } // END of config-container definition.
                container state {
                    config false;
                    description
                        "Operational state data for QoS Precedence to Precedence";
                    uses qos-precedence-to-precedence-config;
                } // END of state-container definition.
            } // End of precedence-to-precedence-list
        } // END of precedence-to-precedences-container definition.
    } // END of qos-precedence-to-precedence definition.
    grouping qos-precedence-to-precedence-config {
        description
            "Grouping for QoS Precedence to Precedence configuration";
        leaf precedence-value  {
            type  uint8 {
                 range "0..7"  {
                    description "0..7: Supported range 0 - 7";
                 }
            }
            description "Use this attribute to select IP Precedence value in";
        } // END of precedence-value definition.

        leaf remark-precedence-value  {
            type  uint8 {
                 range "0..7"  {
                    description "0..7: Supported range 0 - 7";
                 }
            }
            mandatory true;
            description "Use this attribute to select IP Precedence value out";
        } // END of remark-precedence-value definition.

    } // END of qos-precedence-to-precedence-config definition.
    grouping qos-dscp-to-queue-profile-top {
        description
            "Grouping for QoS DSCP to Traffic-Class profile";
        container dscp-to-queue-profiles {
            description
                "Configuration data for QoS DSCP to Traffic-Class profile";

            list dscp-to-queue-profile {
                key "name";
                description
                    "Configuration data list for QoS DSCP to Traffic-Class profile";
                leaf name  {
                    type  leafref {
                        path  "../config/name";
                    }
                    description "Use this attribute to set a name to DSCP to Traffic-Class profile";
                } // END of name definition.

                container config {
                    description
                        "Configuration data for QoS DSCP to Traffic-Class profile";
                    uses qos-dscp-to-queue-profile-config;
                } // END of config-container definition.
                container state {
                    config false;
                    description
                        "Operational state data for QoS DSCP to Traffic-Class profile";
                    uses qos-dscp-to-queue-profile-config;
                } // END of state-container definition.
                uses qos-dscp-to-queue;
            } // End of dscp-to-queue-profile-list
        } // END of dscp-to-queue-profiles-container definition.
    } // END of qos-dscp-to-queue-profile-top definition.
    grouping qos-dscp-to-queue-profile-config {
        description
            "Grouping for QoS DSCP to Traffic-Class profile configuration";
        leaf name  {
            type  string {
                length "1..31";
                pattern "[^?' =,>|]+";
            }
            description "Use this attribute to set a name to DSCP to Traffic-Class profile";
        } // END of name definition.

    } // END of qos-dscp-to-queue-profile-config definition.
    grouping qos-dscp-to-queue {
        description
            "Grouping for QoS DSCP to Traffic-Class";
        container dscp-to-queues {
            description
                "Configuration data for QoS DSCP to Traffic-Class";

            list dscp-to-queue {
                key "dscp-value";
                description
                    "Configuration data list for QoS DSCP to Traffic-Class";
                leaf dscp-value  {
                    type  leafref {
                        path  "../config/dscp-value";
                    }
                    description "Use this attribute to map a Differentiated Services Control Protocol
                                (DSCP) value to a particular Traffic-Class";
                } // END of dscp-value definition.

                container config {
                    description
                        "Configuration data for QoS DSCP to Traffic-Class";
                    uses qos-dscp-to-queue-config;
                } // END of config-container definition.
                container state {
                    config false;
                    description
                        "Operational state data for QoS DSCP to Traffic-Class";
                    uses qos-dscp-to-queue-config;
                } // END of state-container definition.
            } // End of dscp-to-queue-list
        } // END of dscp-to-queues-container definition.
    } // END of qos-dscp-to-queue definition.
    grouping qos-dscp-to-queue-config {
        description
            "Grouping for QoS DSCP to Traffic-Class configuration";
        leaf dscp-value  {
            type  uint8 {
                 range "0..63"  {
                    description "0..63: Supported range 0 - 63";
                 }
            }
            description "Use this attribute to map a Differentiated Services Control Protocol
                        (DSCP) value to a particular Traffic-Class";
        } // END of dscp-value definition.

        leaf queue-id  {
            type  uint8 {
                 range "0..7"  {
                    description "0..7: Supported range 0 - 7";
                 }
            }
            mandatory true;
            description "Use this attribute to select the Traffic-Class DSCP is mapped to";
        } // END of queue-id definition.

        leaf color  {
            type  ipi-qos-types:qos_color_t;
            description "Use this attribute to select the color to map.";
        } // END of color definition.

        leaf remark-dscp-value  {
            if-feature feature-list:HAVE_CUSTOM2_QOS;
            type  uint8 {
                 range "0..63"  {
                    description "0..63: Supported range 0 - 63";
                 }
            }
            description "Use this attribute to select Differentiated Services Control Protocol
                        (DSCP) value out.";
        } // END of remark-dscp-value definition.

    } // END of qos-dscp-to-queue-config definition.
    grouping qos-precedence-to-queue-profile-top {
        description
            "Grouping for QoS Precedence to Traffic-Class profile";
        container precedence-to-queue-profiles {
            description
                "Configuration data for QoS Precedence to Traffic-Class profile";

            list precedence-to-queue-profile {
                key "name";
                description
                    "Configuration data list for QoS Precedence to Traffic-Class profile";
                leaf name  {
                    type  leafref {
                        path  "../config/name";
                    }
                    description "Use this attribute to set a name to Precedence to Traffic-Class
                                profile";
                } // END of name definition.

                container config {
                    description
                        "Configuration data for QoS Precedence to Traffic-Class profile";
                    uses qos-precedence-to-queue-profile-config;
                } // END of config-container definition.
                container state {
                    config false;
                    description
                        "Operational state data for QoS Precedence to Traffic-Class profile";
                    uses qos-precedence-to-queue-profile-config;
                } // END of state-container definition.
                uses qos-precedence-to-queue;
            } // End of precedence-to-queue-profile-list
        } // END of precedence-to-queue-profiles-container definition.
    } // END of qos-precedence-to-queue-profile-top definition.
    grouping qos-precedence-to-queue-profile-config {
        description
            "Grouping for QoS Precedence to Traffic-Class profile configuration";
        leaf name  {
            type  string {
                length "1..31";
                pattern "[^?' =,>|]+";
            }
            description "Use this attribute to set a name to Precedence to Traffic-Class
                        profile";
        } // END of name definition.

    } // END of qos-precedence-to-queue-profile-config definition.
    grouping qos-precedence-to-queue {
        description
            "Grouping for QoS Precedence to Traffic-Class";
        container precedence-to-queues {
            description
                "Configuration data for QoS Precedence to Traffic-Class";

            list precedence-to-queue {
                key "precedence-value";
                description
                    "Configuration data list for QoS Precedence to Traffic-Class";
                leaf precedence-value  {
                    type  leafref {
                        path  "../config/precedence-value";
                    }
                    description "Use this attribute to map a IP Precedence value to a particular
                                Traffic-Class";
                } // END of precedence-value definition.

                container config {
                    description
                        "Configuration data for QoS Precedence to Traffic-Class";
                    uses qos-precedence-to-queue-config;
                } // END of config-container definition.
                container state {
                    config false;
                    description
                        "Operational state data for QoS Precedence to Traffic-Class";
                    uses qos-precedence-to-queue-config;
                } // END of state-container definition.
            } // End of precedence-to-queue-list
        } // END of precedence-to-queues-container definition.
    } // END of qos-precedence-to-queue definition.
    grouping qos-precedence-to-queue-config {
        description
            "Grouping for QoS Precedence to Traffic-Class configuration";
        leaf precedence-value  {
            type  uint8 {
                 range "0..7"  {
                    description "0..7: Supported range 0 - 7";
                 }
            }
            description "Use this attribute to map a IP Precedence value to a particular
                        Traffic-Class";
        } // END of precedence-value definition.

        leaf queue-id  {
            type  uint8 {
                 range "0..7"  {
                    description "0..7: Supported range 0 - 7";
                 }
            }
            mandatory true;
            description "Use this attribute to select the Traffic-Class IP Precedence is mapped
                        to";
        } // END of queue-id definition.

        leaf remark-precedence-value  {
            if-feature feature-list:HAVE_CUSTOM2_QOS;
            type  uint8 {
                 range "0..7"  {
                    description "0..7: Supported range 0 - 7";
                 }
            }
            description "Use this attribute to select IP Precedence value out.";
        } // END of remark-precedence-value definition.

    } // END of qos-precedence-to-queue-config definition.
    grouping qos-exp-encap-profile-top {
        description
            "Grouping for QoS MPLS experimental encapsulation profile";
        container exp-encapsulation-profiles {
            if-feature feature-list:HAVE_DIFFSERV;
            if-feature feature-list:HAVE_CUSTOM2_QOS;
            if-feature feature-list:NOT_HAVE_CUSTOM3_QOS;
            description
                "Configuration data for QoS MPLS experimental encapsulation profile";

            list exp-encapsulation-profile {
                key "name";
                description
                    "Configuration data list for QoS MPLS experimental encapsulation
                                profile";
                leaf name  {
                    type  leafref {
                        path  "../config/name";
                    }
                    description "Use this attribute to set a name to MPLS experimental encapsulation
                                profile name";
                } // END of name definition.

                container config {
                    description
                        "Configuration data for QoS MPLS experimental encapsulation profile";
                    uses qos-exp-encapsulation-profile-config;
                } // END of config-container definition.
                container state {
                    config false;
                    description
                        "Operational state data for QoS MPLS experimental encapsulation profile";
                    uses qos-exp-encapsulation-profile-config;
                } // END of state-container definition.
                uses qos-exp-encap-layer-2;
                uses qos-exp-encap-layer-3;
            } // End of exp-encapsulation-profile-list
        } // END of exp-encapsulation-profiles-container definition.
    } // END of qos-exp-encap-profile-top definition.
    grouping qos-exp-encapsulation-profile-config {
        description
            "Grouping for QoS MPLS experimental encapsulation profile configuration";
        leaf name  {
            type  string {
                length "1..31";
                pattern "[^?' =,>|]+";
            }
            description "Use this attribute to set a name to MPLS experimental encapsulation
                        profile name";
        } // END of name definition.

    } // END of qos-exp-encapsulation-profile-config definition.
    grouping qos-exp-encap-layer-2 {
        description
            "Grouping for QoS L2 MPLS experimental encapsulation";
        container layer-2 {
            description
                "Configuration data for Qos L2 MPLS experimental encapsulation";
            uses qos-queue-color-to-exp;
        } // END of layer-2-container definition.
    } // END of qos-exp-encap-layer-2 definition.
    grouping qos-queue-color-to-exp {
        description
            "Grouping for QoS Traffic-Class color to MPLS experimental";
        container queue-color-to-exps {
            description
                "Configuration data for QoS Traffic-Class color to MPLS experimental";

            list queue-color-to-exp {
                key "queue-id color";
                description
                    "Configuration data list for QoS Traffic-Class color to MPLS
                                experimental";
                leaf queue-id  {
                    type  leafref {
                        path  "../config/queue-id";
                    }
                    description "Use this attribute to select the Traffic-Class to map";
                } // END of queue-id definition.

                leaf color  {
                    type  leafref {
                        path  "../config/color";
                    }
                    description "Use this attribute to select the color to map. Default value is 3.";
                } // END of color definition.

                container config {
                    description
                        "Configuration data for QoS Traffic-Class color to MPLS experimental";
                    uses qos-queue-color-to-exp-config;
                } // END of config-container definition.
                container state {
                    config false;
                    description
                        "Operational state data for QoS Traffic-Class color to MPLS
                                experimental";
                    uses qos-queue-color-to-exp-config;
                } // END of state-container definition.
            } // End of queue-color-to-exp-list
        } // END of queue-color-to-exps-container definition.
    } // END of qos-queue-color-to-exp definition.
    grouping qos-queue-color-to-exp-config {
        description
            "Grouping for QoS Traffic-Class color to MPLS experimental
                        configuration";
        leaf queue-id  {
            type  uint8 {
                 range "0..7"  {
                    description "0..7: Supported range 0 - 7";
                 }
            }
            description "Use this attribute to select the Traffic-Class to map";
        } // END of queue-id definition.

        leaf color  {
            type  ipi-qos-types:qos_color_key_t;
            default "all";
            description "Use this attribute to select the color to map";
        } // END of color definition.

        leaf exp-value  {
            type  uint8 {
                 range "0..7"  {
                    description "0..7: Supported range 0 - 7";
                 }
            }
            mandatory true;
            description "Use this attribute to select the MPLS experimental (EXP) value mapped
                        to";
        } // END of exp-value definition.

    } // END of qos-queue-color-to-exp-config definition.
    grouping qos-exp-encap-layer-3 {
        description
            "Grouping for QoS L3 MPLS experimental encapsulation";
        container layer-3 {
            description
                "Configuration data for Qos L3 MPLS experimental encapsulation";
            uses qos-dscp-to-exp;
        } // END of layer-3-container definition.
    } // END of qos-exp-encap-layer-3 definition.
    grouping qos-dscp-to-exp {
        description
            "Grouping for QoS DSCP to MPLS experimental";
        container dscp-to-exps {
            description
                "Configuration data for QoS DSCP to MPLS experimental";

            list dscp-to-exp {
                key "dscp-value";
                description
                    "Configuration data list for QoS DSCP to MPLS experimental";
                leaf dscp-value  {
                    type  leafref {
                        path  "../config/dscp-value";
                    }
                    description "Use this attribute to map a Differentiated Services Control Protocol
                                (DSCP) value";
                } // END of dscp-value definition.

                container config {
                    description
                        "Configuration data for QoS DSCP to MPLS experimental";
                    uses qos-dscp-to-exp-config;
                } // END of config-container definition.
                container state {
                    config false;
                    description
                        "Operational state data for QoS DSCP to MPLS experimental";
                    uses qos-dscp-to-exp-config;
                } // END of state-container definition.
            } // End of dscp-to-exp-list
        } // END of dscp-to-exps-container definition.
    } // END of qos-dscp-to-exp definition.
    grouping qos-dscp-to-exp-config {
        description
            "Grouping for QoS DSCP to MPLS experimental configuration";
        leaf dscp-value  {
            type  uint8 {
                 range "0..63"  {
                    description "0..63: Supported range 0 - 63";
                 }
            }
            description "Use this attribute to map a Differentiated Services Control Protocol
                        (DSCP) value";
        } // END of dscp-value definition.

        leaf exp-value  {
            type  uint8 {
                 range "0..7"  {
                    description "0..7: Supported range 0 - 7";
                 }
            }
            mandatory true;
            description "Use this attribute to select the MPLS experimental (EXP) value mapped
                        to";
        } // END of exp-value definition.

    } // END of qos-dscp-to-exp-config definition.
    grouping qos-dscp-encap-profile-top {
        description
            "Grouping for QoS dscp encapsulation profile";
        container dscp-encapsulation-profiles {
            if-feature feature-list:HAVE_CUSTOM2_QOS;
            description
                "Configuration data for QoS dscp encapsulation profile";

            list dscp-encapsulation-profile {
                key "name";
                description
                    "Configuration data list for QoS dscp encapsulation profile";
                leaf name  {
                    type  leafref {
                        path  "../config/name";
                    }
                    description "Use this attribute to set a name to VxLAN dscp encapsulation profile
                                name";
                } // END of name definition.

                container config {
                    description
                        "Configuration data for QoS dscp encapsulation profile";
                    uses qos-dscp-encapsulation-profile-config;
                } // END of config-container definition.
                container state {
                    config false;
                    description
                        "Operational state data for QoS dscp encapsulation profile";
                    uses qos-dscp-encapsulation-profile-config;
                } // END of state-container definition.
                uses qos-dscp-encap-layer-2;
                uses qos-dscp-encap-layer-3;
            } // End of dscp-encapsulation-profile-list
        } // END of dscp-encapsulation-profiles-container definition.
    } // END of qos-dscp-encap-profile-top definition.
    grouping qos-dscp-encapsulation-profile-config {
        description
            "Grouping for QoS VxLAN dscp encapsulation profile configuration";
        leaf name  {
            type  string {
                length "1..31";
                pattern "[^?' =,>|]+";
            }
            description "Use this attribute to set a name to dscp encapsulation profile name";
        } // END of name definition.

    } // END of qos-dscp-encapsulation-profile-config definition.
    grouping qos-dscp-encap-layer-2 {
        description
            "Grouping for QoS L2 dscp encapsulation";
        container layer-2 {
            description
                "Configuration data for Qos L2 dscp encapsulation";
            uses qos-l2-queue-color-to-dscp;
        } // END of layer-2-container definition.
    } // END of qos-dscp-encap-layer-2 definition.
    grouping qos-l2-queue-color-to-dscp {
        description
            "Grouping for QoS Traffic-Class color to dscp encapsulation";
        container queue-color-to-dscps {
            description
                "Configuration data for QoS Traffic-Class color to dscp encapsulation";

            list queue-color-to-dscp {
                key "queue-id color";
                description
                    "Configuration data list for QoS Traffic-Class color to dscp
                                encapsulation";
                leaf queue-id  {
                    type  leafref {
                        path  "../config/queue-id";
                    }
                    description "Use this attribute to select the Traffic-Class to map";
                } // END of queue-id definition.

                leaf color  {
                    type  leafref {
                        path  "../config/color";
                    }
                    description "Use this attribute to select the color to map. Default value is 3.";
                } // END of color definition.

                container config {
                    description
                        "Configuration data for QoS Traffic-Class color to dscp encapsulation";
                    uses qos-l2-queue-color-to-dscp-config;
                } // END of config-container definition.
                container state {
                    config false;
                    description
                        "Operational state data for QoS Traffic-Class color to dscp
                                encapsulation";
                    uses qos-l2-queue-color-to-dscp-config;
                } // END of state-container definition.
            } // End of queue-color-to-dscp-list
        } // END of queue-color-to-dscps-container definition.
    } // END of qos-l2-queue-color-to-dscp definition.
    grouping qos-l2-queue-color-to-dscp-config {
        description
            "Grouping for QoS Traffic-Class color to dscpEncap configuration";
        leaf queue-id  {
            type  uint8 {
                 range "0..7"  {
                    description "0..7: Supported range 0 - 7";
                 }
            }
            description "Use this attribute to select the Traffic-Class to map";
        } // END of queue-id definition.

        leaf color  {
            type  ipi-qos-types:qos_color_key_t;
            default "all";
            description "Use this attribute to select the color to map";
        } // END of color definition.

        leaf dscp-value  {
            type  uint8 {
                 range "0..63"  {
                    description "0..63: Supported range 0 - 63";
                 }
            }
            mandatory true;
            description "Use this attribute to select the VxLAN dscp-encap value mapped to";
        } // END of dscp-value definition.

    } // END of qos-l2-queue-color-to-dscp-config definition.
    grouping qos-dscp-encap-layer-3 {
        description
            "Grouping for QoS L3 dscp encapsulation";
        container layer-3 {
            description
                "Configuration data for Qos L3 dscp encapsulation";
            uses qos-l3-dscp-to-dscp-encap;
        } // END of layer-3-container definition.
    } // END of qos-dscp-encap-layer-3 definition.
    grouping qos-l3-dscp-to-dscp-encap {
        description
            "Grouping for QoS DSCP to dscp encapsulation";
        container dscp-to-dscp-encaps {
            description
                "Configuration data for QoS DSCP to dscp encapsulation";

            list dscp-to-dscp-encap {
                key "dscp-value";
                description
                    "Configuration data list for QoS DSCP to dscp encapsulation";
                leaf dscp-value  {
                    type  leafref {
                        path  "../config/dscp-value";
                    }
                    description "Use this attribute to map a Differentiated Services Control Protocol
                                (DSCP) value";
                } // END of dscp-value definition.

                container config {
                    description
                        "Configuration data for QoS DSCP to dscp encapsulation";
                    uses qos-l3-dscp-to-dscp-encap-config;
                } // END of config-container definition.
                container state {
                    config false;
                    description
                        "Operational state data for QoS DSCP to dscp encapsulation";
                    uses qos-l3-dscp-to-dscp-encap-config;
                } // END of state-container definition.
            } // End of dscp-to-dscp-encap-list
        } // END of dscp-to-dscp-encaps-container definition.
    } // END of qos-l3-dscp-to-dscp-encap definition.
    grouping qos-l3-dscp-to-dscp-encap-config {
        description
            "Grouping for QoS DSCP to dscp encap configuration";
        leaf dscp-value  {
            type  uint8 {
                 range "0..63"  {
                    description "0..63: Supported range 0 - 63";
                 }
            }
            description "Use this attribute to map a Differentiated Services Control Protocol
                        (DSCP) value";
        } // END of dscp-value definition.

        leaf dscp-encap-value  {
            type  uint8 {
                 range "0..63"  {
                    description "0..63: Supported range 0 - 63";
                 }
            }
            mandatory true;
            description "Use this attribute to select the VxLAN dscp-encap value mapped to";
        } // END of dscp-encap-value definition.

    } // END of qos-l3-dscp-to-dscp-encap-config definition.
    grouping qos-exp-to-queue-profile-top {
        description
            "Grouping for QoS MPLS experimental to Traffic-Class profile";
        container exp-to-queue-profiles {
            if-feature feature-list:HAVE_DIFFSERV;
            description
                "Configuration data for QoS MPLS experimental to Traffic-Class profile";

            list exp-to-queue-profile {
                key "profile-id";
                description
                    "Configuration data list for QoS MPLS experimental to Traffic-Class
                                profile";
                leaf profile-id  {
                    type  leafref {
                        path  "../config/profile-id";
                    }
                    description "Use this attribute to set a name to MPLS experimental (EXP) to
                                Traffic-Class profile name. Default value is 0.";
                } // END of profile-id definition.

                container config {
                    description
                        "Configuration data for QoS MPLS experimental to Traffic-Class profile";
                    uses qos-exp-to-queue-profile-config;
                } // END of config-container definition.
                container state {
                    config false;
                    description
                        "Operational state data for QoS MPLS experimental to Traffic-Class
                                profile";
                    uses qos-exp-to-queue-profile-config;
                } // END of state-container definition.
                uses qos-exp-to-queue;
            } // End of exp-to-queue-profile-list
        } // END of exp-to-queue-profiles-container definition.
    } // END of qos-exp-to-queue-profile-top definition.
    grouping qos-exp-to-queue-profile-config {
        description
            "Grouping for QoS MPLS experimental to Traffic-Class profile
                        configuration";
        leaf profile-id  {
            type  ipi-qos-types:qos_profile_name_default_t;
            description "Use this attribute to set a name to MPLS experimental (EXP) to
                        Traffic-Class profile name";
        } // END of profile-id definition.

    } // END of qos-exp-to-queue-profile-config definition.
    grouping qos-exp-to-queue {
        description
            "Grouping for QoS MPLS experimental to Traffic-Class";
        container exp-to-queues {
            description
                "Configuration data for QoS MPLS experimental to Traffic-Class";

            list exp-to-queue {
                key "exp-value";
                description
                    "Configuration data list for QoS MPLS experimental to Traffic-Class";
                leaf exp-value  {
                    type  leafref {
                        path  "../config/exp-value";
                    }
                    description "Use this attribute to select the MPLS experimental (EXP) value to map";
                } // END of exp-value definition.

                container config {
                    description
                        "Configuration data for QoS MPLS experimental to Traffic-Class";
                    uses qos-exp-to-queue-config;
                } // END of config-container definition.
                container state {
                    config false;
                    description
                        "Operational state data for QoS MPLS experimental to Traffic-Class";
                    uses qos-exp-to-queue-config;
                } // END of state-container definition.
            } // End of exp-to-queue-list
        } // END of exp-to-queues-container definition.
    } // END of qos-exp-to-queue definition.
    grouping qos-exp-to-queue-config {
        description
            "Grouping for QoS MPLS experimental to Traffic-Class configuration";
        leaf exp-value  {
            type  uint8 {
                 range "0..7"  {
                    description "0..7: Supported range 0 - 7";
                 }
            }
            description "Use this attribute to select the MPLS experimental (EXP) value to map";
        } // END of exp-value definition.

        leaf queue-id  {
            type  uint8 {
                 range "0..7"  {
                    description "0..7: Supported range 0 - 7";
                 }
            }
            mandatory true;
            description "Use this attribute to select the Traffic-Class mapped to";
        } // END of queue-id definition.

        leaf color  {
            type  ipi-qos-types:qos_color_t;
            description "Use this attribute to select the color mapped to.";
        } // END of color definition.

        leaf remark-queue-value  {
            if-feature feature-list:HAVE_CUSTOM3_QOS;
            type  uint8 {
                 range "0..7"  {
                    description "0..7: Supported range 0 - 7";
                 }
            }
            description "Use this attribute to select the remark Traffic-Class is mapped to";
        } // END of remark-queue-value definition.

    } // END of qos-exp-to-queue-config definition.
    grouping qos-queue-to-exp-profile-top {
        description
            "Grouping for QoS MPLS Traffic-Class to exp profile";
        container queue-to-exp-profiles {
            if-feature feature-list:HAVE_DIFFSERV;
            if-feature feature-list:HAVE_CUSTOM1_QOS_OR_HAVE_CUSTOM3_QOS;
            description
                "Configuration data for QoS MPLS Traffic-Class to exp profile";

            list queue-to-exp-profile {
                key "name";
                description
                    "Configuration data list for QoS MPLS Traffic-Class to exp profile";
                leaf name  {
                    type  leafref {
                        path  "../config/name";
                    }
                    description "Use this attribute to set a name to MPLS experimental (EXP) to
                                Traffic-Class profile name";
                } // END of name definition.

                container config {
                    description
                        "Configuration data for QoS MPLS Traffic-Class to exp profile";
                    uses qos-queue-to-exp-profile-config;
                } // END of config-container definition.
                container state {
                    config false;
                    description
                        "Operational state data for QoS MPLS Traffic-Class to exp profile";
                    uses qos-queue-to-exp-profile-config;
                } // END of state-container definition.
                uses qos-queue-to-exp;
            } // End of queue-to-exp-profile-list
        } // END of queue-to-exp-profiles-container definition.
    } // END of qos-queue-to-exp-profile-top definition.
    grouping qos-queue-to-exp-profile-config {
        description
            "Grouping for QoS MPLS Traffic-Class to exp profile configuration";
        leaf name  {
            type  string {
                length "1..31";
                pattern "[^?' =,>|]+";
            }
            description "Use this attribute to set a name to MPLS Traffic-Class to exp profile
                        name";
        } // END of name definition.

    } // END of qos-queue-to-exp-profile-config definition.
    grouping qos-queue-to-exp {
        description
            "Grouping for QoS MPLS Traffic-Class to exp";
        container queues-to-exp {
            description
                "Configuration data for QoS MPLS Traffic-Class to exp";

            list queue-to-exp {
                if-feature feature-list:HAVE_CUSTOM1_QOS;
                key "queue-id";
                description
                    "Configuration data list for QoS MPLS Traffic-Class to exp";
                leaf queue-id  {
                    type  leafref {
                        path  "../config/queue-id";
                    }
                    description "Use this attribute to select the Traffic-Class to map";
                } // END of queue-id definition.

                container config {
                    description
                        "Configuration data for QoS MPLS Traffic-Class to exp";
                    uses qos-queue-to-exp-config;
                } // END of config-container definition.
                container state {
                    config false;
                    description
                        "Operational state data for QoS MPLS Traffic-Class to exp";
                    uses qos-queue-to-exp-config;
                } // END of state-container definition.
            } // End of queue-to-exp-list

            list queue-color-to-exp {
                if-feature feature-list:HAVE_CUSTOM3_QOS;
                key "queue-id color";
                description
                    "Configuration data list for QoS MPLS Traffic-Class to exp";
                leaf queue-id  {
                    type  leafref {
                        path  "../config/queue-id";
                    }
                    description "Use this attribute to select the Traffic-Class to map";
                } // END of queue-id definition.

                leaf color  {
                    type  leafref {
                        path  "../config/color";
                    }
                    description "Use this attribute to select the color to map. Default value is 3.";
                } // END of color definition.

                container config {
                    description
                        "Configuration data for QoS MPLS Traffic-Class to exp";
                    uses qos-queue-color-to-exp-config;
                } // END of config-container definition.
                container state {
                    config false;
                    description
                        "Operational state data for QoS MPLS Traffic-Class to exp";
                    uses qos-queue-color-to-exp-config;
                } // END of state-container definition.
            } // End of queue-color-to-exp-list
        } // END of queues-to-exp-container definition.
    } // END of qos-queue-to-exp definition.
    grouping qos-queue-to-exp-config {
        description
            "Grouping for QoS MPLS Traffic-Class to exp configuration";
        leaf queue-id  {
            type  uint8 {
                 range "0..7"  {
                    description "0..7: Supported range 0 - 7";
                 }
            }
            description "Use this attribute to select the Traffic-Class to map";
        } // END of queue-id definition.

        leaf exp-value  {
            type  uint8 {
                 range "0..7"  {
                    description "0..7: Supported range 0 - 7";
                 }
            }
            mandatory true;
            description "Use this attribute to select the MPLS experimental (EXP) value mapped
                        to";
        } // END of exp-value definition.

    } // END of qos-queue-to-exp-config definition.
    grouping qos-queue-color-to-cos-profile-top {
        description
            "Grouping for QoS Traffic-Class color to CoS profile";
        container queue-color-to-cos-profiles {
            description
                "Configuration data for QoS Traffic-Class color to CoS profile";

            list queue-color-to-cos-profile {
                key "name";
                description
                    "Configuration data list for QoS Traffic-Class color to CoS profile";
                leaf name  {
                    type  leafref {
                        path  "../config/name";
                    }
                    description "Use this attribute to select the Traffic-Class color to CoS profile
                                name";
                } // END of name definition.

                container config {
                    description
                        "Configuration data for QoS Traffic-Class color to CoS profile";
                    uses qos-queue-color-to-cos-profile-config;
                } // END of config-container definition.
                container state {
                    config false;
                    description
                        "Operational state data for QoS Traffic-Class color to CoS profile";
                    uses qos-queue-color-to-cos-profile-config;
                } // END of state-container definition.
                uses qos-queue-color-to-cos;
            } // End of queue-color-to-cos-profile-list
        } // END of queue-color-to-cos-profiles-container definition.
    } // END of qos-queue-color-to-cos-profile-top definition.
    grouping qos-queue-color-to-cos-profile-config {
        description
            "Grouping for QoS Traffic-Class color to CoS profile configuration";
        leaf name  {
            type  string {
                length "1..31";
                pattern "[^?' =,>|]+";
            }
            description "Use this attribute to select the Traffic-Class color to CoS profile
                        name";
        } // END of name definition.

    } // END of qos-queue-color-to-cos-profile-config definition.
    grouping qos-queue-color-to-cos {
        description
            "Grouping for QoS Traffic-Class color to CoS";
        container queue-color-to-coses {
            description
                "Configuration data for QoS Traffic-Class color to CoS";

            list queue-color-to-cos {
                key "queue-id color";
                description
                    "Configuration data list for QoS Traffic-Class color to CoS";
                leaf queue-id  {
                    type  leafref {
                        path  "../config/queue-id";
                    }
                    description "Use this attribute to select the Traffic-Class to map";
                } // END of queue-id definition.

                leaf color  {
                    type  leafref {
                        path  "../config/color";
                    }
                    description "Use this attribute to select the color to map. Default value is 3.";
                } // END of color definition.

                container config {
                    description
                        "Configuration data for QoS Traffic-Class color to CoS";
                    uses qos-queue-color-to-cos-config;
                } // END of config-container definition.
                container state {
                    config false;
                    description
                        "Operational state data for QoS Traffic-Class color to CoS";
                    uses qos-queue-color-to-cos-config;
                } // END of state-container definition.
            } // End of queue-color-to-cos-list
        } // END of queue-color-to-coses-container definition.
    } // END of qos-queue-color-to-cos definition.
    grouping qos-queue-color-to-cos-config {
        description
            "Grouping for QoS Traffic-Class color to CoS configuration";
        leaf queue-id  {
            type  uint8 {
                 range "0..7"  {
                    description "0..7: Supported range 0 - 7";
                 }
            }
            description "Use this attribute to select the Traffic-Class to map";
        } // END of queue-id definition.

        leaf color  {
            type  ipi-qos-types:qos_color_key_t;
            default "all";
            description "Use this attribute to select the color to map";
        } // END of color definition.

        leaf cos-value  {
            type  uint8 {
                 range "0..7"  {
                    description "0..7: Supported range 0 - 7";
                 }
            }
            mandatory true;
            description "Use this attribute to map a Class of Service (CoS) value mapped to";
        } // END of cos-value definition.

    } // END of qos-queue-color-to-cos-config definition.
    grouping qos-queue-color-to-dscp-profile-config {
        description
            "Grouping for QoS Traffic-Class color to DSCP profile configuraation";
        leaf name  {
            type  string {
                length "1..31";
                pattern "[^?' =,>|]+";
            }
            description "Use this attribute to select the Traffic-Class color to DSCP profile
                        name";
        } // END of name definition.

    } // END of qos-queue-color-to-dscp-profile-config definition.
    grouping qos-queue-color-to-dscp-profile-top {
        description
            "Grouping for QoS Traffic-Class color to DSCP profile";
        container queue-color-to-dscp-profiles {
            description
                "Configuration data for QoS Traffic-Class color to DSCP profile";

            list queue-color-to-dscp-profile {
                key "name";
                description
                    "Configuration data list for QoS Traffic-Class color to DSCP profile";
                leaf name  {
                    type  leafref {
                        path  "../config/name";
                    }
                    description "Use this attribute to select the Traffic-Class color to DSCP profile
                                name";
                } // END of name definition.

                container config {
                    description
                        "Configuration data for QoS Traffic-Class color to DSCP profile";
                    uses qos-queue-color-to-dscp-profile-config;
                } // END of config-container definition.
                container state {
                    config false;
                    description
                        "Operational state data for QoS Traffic-Class color to DSCP profile";
                    uses qos-queue-color-to-dscp-profile-config;
                } // END of state-container definition.
                uses qos-queue-color-to-dscp;
            } // End of queue-color-to-dscp-profile-list
        } // END of queue-color-to-dscp-profiles-container definition.
    } // END of qos-queue-color-to-dscp-profile-top definition.
    grouping qos-queue-color-to-dscp {
        description
            "Grouping for QoS Traffic-Class color to DSCP";
        container queue-color-to-dscps {
            description
                "Configuration data for QoS Traffic-Class color to DSCP";

            list queue-color-to-dscp {
                key "queue-id color";
                description
                    "Configuration data list for QoS Traffic-Class color to DSCP";
                leaf queue-id  {
                    type  leafref {
                        path  "../config/queue-id";
                    }
                    description "Use this attribute to select the Traffic-Class to map";
                } // END of queue-id definition.

                leaf color  {
                    type  leafref {
                        path  "../config/color";
                    }
                    description "Use this attribute to select the color to map. Default value is 3.";
                } // END of color definition.

                container config {
                    description
                        "Configuration data for QoS Traffic-Class color to DSCP";
                    uses qos-queue-color-to-dscp-config;
                } // END of config-container definition.
                container state {
                    config false;
                    description
                        "Operational state data for QoS Traffic-Class color to DSCP";
                    uses qos-queue-color-to-dscp-config;
                } // END of state-container definition.
            } // End of queue-color-to-dscp-list
        } // END of queue-color-to-dscps-container definition.
    } // END of qos-queue-color-to-dscp definition.
    grouping qos-queue-color-to-dscp-config {
        description
            "Grouping for QoS Traffic-Class color to DSCP configuration";
        leaf queue-id  {
            type  uint8 {
                 range "0..7"  {
                    description "0..7: Supported range 0 - 7";
                 }
            }
            description "Use this attribute to select the Traffic-Class to map";
        } // END of queue-id definition.

        leaf color  {
            type  ipi-qos-types:qos_color_key_t;
            default "all";
            description "Use this attribute to select the color to map";
        } // END of color definition.

        leaf dscp-value  {
            type  uint8 {
                 range "0..63"  {
                    description "0..63: Supported range 0 - 63";
                 }
            }
            mandatory true;
            description "Use this attribute to map a Differentiated Services Control Protocol
                        (DSCP) value mapped to";
        } // END of dscp-value definition.

    } // END of qos-queue-color-to-dscp-config definition.
    grouping qos-queue-to-precedence-profile-top {
        description
            "Grouping for QoS Traffic-Class to Precedence profile";
        container queue-to-precedence-profiles {
            description
                "Configuration data for QoS Traffic-Class to Precedence profile";

            list queue-to-precedence-profile {
                key "name";
                description
                    "Configuration data list for QoS Traffic-Class to Precedence profile";
                leaf name  {
                    type  leafref {
                        path  "../config/name";
                    }
                    description "Use this attribute to select the Traffic-Class to Precedence profile
                                name";
                } // END of name definition.

                container config {
                    description
                        "Configuration data for QoS Traffic-Class to Precedence profile";
                    uses qos-queue-to-precedence-profile-config;
                } // END of config-container definition.
                container state {
                    config false;
                    description
                        "Operational state data for QoS Traffic-Class to Precedence profile";
                    uses qos-queue-to-precedence-profile-config;
                } // END of state-container definition.
                uses qos-queue-to-precedence;
            } // End of queue-to-precedence-profile-list
        } // END of queue-to-precedence-profiles-container definition.
    } // END of qos-queue-to-precedence-profile-top definition.
    grouping qos-queue-to-precedence-profile-config {
        description
            "Grouping for QoS Traffic-Class to Precedence profile configuraation";
        leaf name  {
            type  string {
                length "1..31";
                pattern "[^?' =,>|]+";
            }
            description "Use this attribute to select the Traffic-Class to Precedence profile
                        name";
        } // END of name definition.

    } // END of qos-queue-to-precedence-profile-config definition.
    grouping qos-queue-to-precedence {
        description
            "Grouping for QoS Traffic-Class to Precedence";
        container queue-to-precedences {
            description
                "Configuration data for QoS Traffic-Class to Precedence";

            list queue-to-precedence {
                key "queue-id";
                description
                    "Configuration data list for QoS Traffic-Class to Precedence";
                leaf queue-id  {
                    type  leafref {
                        path  "../config/queue-id";
                    }
                    description "Use this attribute to select the Traffic-Class to map";
                } // END of queue-id definition.

                container config {
                    description
                        "Configuration data for QoS Traffic-Class to Precedence";
                    uses qos-queue-to-precedence-config;
                } // END of config-container definition.
                container state {
                    config false;
                    description
                        "Operational state data for QoS Traffic-Class to Precedence";
                    uses qos-queue-to-precedence-config;
                } // END of state-container definition.
            } // End of queue-to-precedence-list
        } // END of queue-to-precedences-container definition.
    } // END of qos-queue-to-precedence definition.
    grouping qos-queue-to-precedence-config {
        description
            "Grouping for QoS Traffic-Class to Precedence configuration";
        leaf queue-id  {
            type  uint8 {
                 range "0..7"  {
                    description "0..7: Supported range 0 - 7";
                 }
            }
            description "Use this attribute to select the Traffic-Class to map";
        } // END of queue-id definition.

        leaf precedence-value  {
            type  uint8 {
                 range "0..7"  {
                    description "0..7: Supported range 0 - 7";
                 }
            }
            mandatory true;
            description "Use this attribute to map a IP Precedence value mapped to";
        } // END of precedence-value definition.

    } // END of qos-queue-to-precedence-config definition.
    grouping qos-map-profile-top {
        description
            "Grouping for QoS map profile";
        container map-profile {
            when " /ipi-qos:qos/ipi-qos:global/ipi-qos:config/ipi-qos:enable-qos ";
            if-feature feature-list:HAVE_QOS_MAPPING_PROFILE;
            description
                "Configuration data for QoS map profile";
            uses qos-cos-to-queue-profile-top;
            uses qos-dscp-to-dscp-profile-top;
            uses qos-precedence-to-precedence-profile-top;
            uses qos-dscp-to-queue-profile-top;
            uses qos-dscp-encap-profile-top;
            uses qos-exp-encap-profile-top;
            uses qos-exp-to-queue-profile-top;
            uses qos-queue-to-exp-profile-top;
            uses qos-queue-color-to-cos-profile-top;
            uses qos-queue-to-precedence-profile-top;
            uses qos-precedence-to-queue-profile-top;
            uses qos-queue-color-to-dscp-profile-top;
        } // END of map-profile-container definition.
    } // END of qos-map-profile-top definition.
    grouping qos-map-class {
        description
            "Grouping for QoS map class";
        container classes {
            if-feature feature-list:HAVE_DIFFSERV;
            description
                "Configuration data for QoS map class";

            list class {
                key "class-value";
                description
                    "Configuration data list for QoS map class";
                leaf class-value  {
                    type  leafref {
                        path  "../config/class-value";
                    }
                    description "Use this attribute to map a class value to a particular MPLS
                                experimental (EXP)";
                } // END of class-value definition.

                container config {
                    description
                        "Configuration data for QoS map class";
                    uses qos-map-class-config;
                } // END of config-container definition.
                container state {
                    config false;
                    description
                        "Operational state data for QoS map class";
                    uses qos-map-class-config;
                } // END of state-container definition.
            } // End of class-list
        } // END of classes-container definition.
    } // END of qos-map-class definition.
    grouping qos-map-class-config {
        description
            "Grouping for QoS map class configuration";
        leaf class-value  {
            type  uint8 {
                 range "0..7"  {
                    description "0..7: Supported range 0 - 7";
                 }
            }
            description "Use this attribute to map a class value to a particular MPLS
                        experimental (EXP)";
        } // END of class-value definition.

        leaf exp-value  {
            type  uint8 {
                 range "0..7"  {
                    description "0..7: Supported range 0 - 7";
                 }
            }
            mandatory true;
            description "Use this attribute to select the EXP class is mapped to";
        } // END of exp-value definition.

    } // END of qos-map-class-config definition.
    grouping qos-queue-wrr-unicast-non-unicast {
        description
            "Grouping for QoS queue weighted round robin unicast/non-unicast";
        container weighted-round-robins {
            when " not(/ipi-qos:qos/ipi-qos:global/ipi-qos:scheduler-mode/ipi-qos:strict-priority/ipi-qos:config/ipi-qos:enabled) ";
            description
                "Configuration data for QoS queue weighted round robin
                        unicast/non-unicast";

            list weighted-round-robin {
                key "unicast-queue-weight non-unicast-queue-weight";
                max-elements 1;
                description
                    "Configuration data list for WRR weights";
                leaf unicast-queue-weight  {
                    type  leafref {
                        path  "../config/unicast-queue-weight";
                    }
                    description "Use this attribute to set action as change qos wrr weigth for uc queue
                                in the egress to the defined value for matched packets";
                } // END of unicast-queue-weight definition.

                leaf non-unicast-queue-weight  {
                    type  leafref {
                        path  "../config/non-unicast-queue-weight";
                    }
                    description "Use this attribute to set action as change qos wrr weigth for non-uc
                                queue in the egress to the defined value for matched packets";
                } // END of non-unicast-queue-weight definition.

                container config {
                    description
                        "Configuration data for QoS queue weighted round robin
                                unicast/non-unicast";
                    uses qos-queue-wrr-unicast-non-unicast-config;
                } // END of config-container definition.
                container state {
                    config false;
                    description
                        "Operational state data for QoS queue weighted round robin
                                unicast/non-unicast";
                    uses qos-queue-wrr-unicast-non-unicast-config;
                } // END of state-container definition.
            } // End of weighted-round-robin-list
        } // END of weighted-round-robins-container definition.
    } // END of qos-queue-wrr-unicast-non-unicast definition.
    grouping qos-queue-wrr-unicast-non-unicast-config {
        description
            "Grouping for QoS queue weighted round robin unicast/non-unicast
                        configuration";
        leaf unicast-queue-weight  {
            type  uint8 {
                 range "1..127"  {
                    description "1..127: Supported range 1 - 127";
                 }
            }
            description "Use this attribute to set action as change qos wrr weigth for uc queue
                        in the egress to the defined value for matched packets";
        } // END of unicast-queue-weight definition.

        leaf non-unicast-queue-weight  {
            type  uint8 {
                 range "1..127"  {
                    description "1..127: Supported range 1 - 127";
                 }
            }
            description "Use this attribute to set action as change qos wrr weigth for non-uc
                        queue in the egress to the defined value for matched packets";
        } // END of non-unicast-queue-weight definition.

    } // END of qos-queue-wrr-unicast-non-unicast-config definition.
    grouping qos-queue-sp-config {
        description
            "Grouping for QoS queue strict priority configuration";
        leaf enabled  {
            type  empty;
            description "Use this attribute to set strict-priority for scheduler mode of L1
                        node to WRR";
        } // END of enabled definition.

    } // END of qos-queue-sp-config definition.
    grouping qos-queue-sp {
        description
            "Grouping for QoS queue strict priority";
        container strict-priority {
            when " not(/ipi-qos:qos/ipi-qos:global/ipi-qos:scheduler-mode/ipi-qos:weighted-round-robins/ipi-qos:weighted-round-robin/ipi-qos:config/ipi-qos:unicast-queue-weight) ";
            description
                "Configuration data for QoS queue strict priority";
            container config {
                description
                    "Configuration data for QoS queue strict priority";
                uses qos-queue-sp-config;
            } // END of config-container definition.
            container state {
                config false;
                description
                    "Operational state data for QoS queue strict priority";
                uses qos-queue-sp-config;
            } // END of state-container definition.
        } // END of strict-priority-container definition.
    } // END of qos-queue-sp definition.
    grouping qos-queue-scheduler-top {
        description
            "Grouping for QoS queue scheduler";
        container scheduler-mode {
            when " /ipi-qos:qos/ipi-qos:global/ipi-qos:config/ipi-qos:enable-qos ";
            if-feature feature-list:HAVE_CUSTOM1_QOS;
            description
                "Configuration data for QoS queue scheduler";
            uses qos-queue-wrr-unicast-non-unicast;
            uses qos-queue-sp;
        } // END of scheduler-mode-container definition.
    } // END of qos-queue-scheduler-top definition.
    grouping qos-policy-map-top {
        description
            "Grouping for QoS policy-map";
        container policy-maps {
            when " /ipi-qos:qos/ipi-qos:global/ipi-qos:config/ipi-qos:enable-qos ";
            description
                "Configuration data for QoS policy-map";

            list policy-map {
                key "policy-map-name";
                description
                    "Configuration data list for QoS policy-map";
                leaf policy-map-name  {
                    type  leafref {
                        path  "../config/policy-map-name";
                    }
                    description "Use this attribute to set the policy-map name";
                } // END of policy-map-name definition.

                container config {
                    description
                        "Configuration data for QoS policy-map";
                    uses qos-policy-map-config;
                } // END of config-container definition.
                container state {
                    config false;
                    description
                        "Operational state data for QoS policy-map";
                    uses qos-policy-map-config;
                } // END of state-container definition.
                uses qos-policy-map-class;
            } // End of policy-map-list
        } // END of policy-maps-container definition.
    } // END of qos-policy-map-top definition.
    grouping qos-policy-map-config {
        description
            "Grouping for QoS policy-map configuration";
        leaf policy-map-name  {
            type  string {
                length "1..32";
                pattern "[^?' =,>|]+";
            }
            description "Use this attribute to set the policy-map name";
        } // END of policy-map-name definition.

        leaf type  {
            type  ipi-qos-types:qos_policy_map_t;
            mandatory true;
            description "Use this attribute to set the policy-map type. Default value is 1.";
        } // END of type definition.

        leaf reference-description  {
            type  cml-data-types:cml_line_t {
                length "1..64";
            }
            description "This attribute configures reference description message on policy-map
                        profile";
        } // END of reference-description definition.

    } // END of qos-policy-map-config definition.
    grouping qos-policy-map-class {
        description
            "Grouping for QoS policy-map class configuration";
        container classes {
            description
                "Configuration data for QoS policy-map class configuration";

            list class {
                key "class-map-name";
                description
                    "Configuration data list for QoS policy-map class configuration";
                leaf class-map-name  {
                    type  leafref {
                        path  "../config/class-map-name";
                    }
                    description "Use this attribute to attach a class-map of type qos or queue to the
                                policy-map";
                } // END of class-map-name definition.

                container config {
                    description
                        "Configuration data for QoS policy-map class configuration";
                    uses qos-policy-map-class-config;
                } // END of config-container definition.
                container state {
                    config false;
                    description
                        "Operational state data for QoS policy-map class configuration";
                    uses qos-policy-map-class-config;
                } // END of state-container definition.
                uses qos-queue-mode-top;
                uses qos-qos-mode;
            } // End of class-list
        } // END of classes-container definition.
    } // END of qos-policy-map-class definition.
    grouping qos-policy-map-class-config {
        description
            "Grouping for QoS policy-map class configuration";
        leaf class-map-name  {
            type  ipi-qos-types:qos_policy_map_class_t;
            description "Use this attribute to attach a class-map of type qos or queue to the
                        policy-map";
        } // END of class-map-name definition.

        leaf type  {
            type  ipi-qos-types:qos_policy_map_t;
            mandatory true;
            description "Use this attribute to set the class-map type. Default value is 1.";
        } // END of type definition.

        leaf child-service-policy-name  {
            type  leafref {
                path  "/qos/global/policy-maps/policy-map/policy-map-name";
            }
            description "Use this attribute to attach a child service-policy to the policy-map";
        } // END of child-service-policy-name definition.

        leaf reference-description  {
            type  cml-data-types:cml_line_t {
                length "1..64";
            }
            description "This attribute configures reference description message on the
                        association between policy-map profile and class-map profile.";
        } // END of reference-description definition.

    } // END of qos-policy-map-class-config definition.
    grouping qos-queue-mode-top {
        description
            "Grouping for QoS queue";
        container queue-mode {
            when " /ipi-qos:qos/ipi-qos:global/ipi-qos:policy-maps/ipi-qos:policy-map/ipi-qos:classes/ipi-qos:class/ipi-qos:config/ipi-qos:type = 'queuing' or /ipi-qos:qos/ipi-qos:global/ipi-qos:policy-maps/ipi-qos:policy-map/ipi-qos:classes/ipi-qos:class/ipi-qos:config/ipi-qos:type = 'queuing-default' ";
            description
                "Configuration data for QoS queue";
            container config {
                description
                    "Configuration data for QoS queue";
                uses qos-queue-mode-config;
            } // END of config-container definition.
            container state {
                config false;
                description
                    "Operational state data for QoS queue";
                uses qos-queue-mode-config;
            } // END of state-container definition.
            uses qos-queue-mode-red-top;
            uses qos-queue-mode-tail-drop-top;
            uses qos-queue-mode-bandwidth-top;
            uses qos-queue-mode-shape-top;
        } // END of queue-mode-container definition.
    } // END of qos-queue-mode-top definition.
    grouping qos-queue-mode-config {
        description
            "Grouping for QoS queue configuration";
        leaf byte-compensation  {
            if-feature feature-list:HAVE_CUSTOM2_QOS;
            type  int8 {
                 range "-64..64"  {
                    description "-64..64: Supported range -64 - 64";
                 }
            }
            description "Use this attribute to set the compensation used to adjust this byte
                        difference in order to achieve the expected egress queue rate.";
        } // END of byte-compensation definition.

        leaf delay-tolerance  {
            if-feature feature-list:HAVE_CUSTOM2_QOS;
            type  empty;
            description "Use this attribute to set the low delay tolerance profile.";
        } // END of delay-tolerance definition.

        leaf weighted-round-robin-queue-weight  {
            if-feature feature-list:NOT_HAVE_CUSTOM2_QOS;
            type  uint8 {
                 range "1..127"  {
                    description "1..127:Feature : HAVE_WRR_MAX_WEIGHT_63 Supported range 1 - 63Not
                            Feature : HAVE_WRR_MAX_WEIGHT_63  Supported range 1 - 127";
                 }
            }
            description "Use this attribute to set the weight for Weighted Round Robin queue
                        scheduling algorithm";
        } // END of weighted-round-robin-queue-weight definition.

        leaf strict-priority-enabled  {
            if-feature feature-list:NOT_HAVE_CUSTOM2_QOS;
            type  empty;
            description "Use this attibute to set Strict Priority as queue scheduling algorithm";
        } // END of strict-priority-enabled definition.

        leaf priority-level  {
            when " not(/ipi-qos:qos/ipi-qos:global/ipi-qos:policy-maps/ipi-qos:policy-map/ipi-qos:classes/ipi-qos:class/ipi-qos:queue-mode/ipi-qos:config/ipi-qos:weighted-fair-queueing-queue-weight) ";
            if-feature feature-list:HAVE_CUSTOM2_QOS;
            type  uint8 {
                 range "0..7"  {
                    description "0..7: Supported range 0 - 7";
                 }
            }
            description "Use this attribute to set the class traffic level for Priority queue
                        scheduling algorithm";
        } // END of priority-level definition.

        leaf weighted-fair-queueing-queue-weight  {
            when " not(/ipi-qos:qos/ipi-qos:global/ipi-qos:policy-maps/ipi-qos:policy-map/ipi-qos:classes/ipi-qos:class/ipi-qos:queue-mode/ipi-qos:config/ipi-qos:priority-level) ";
            if-feature feature-list:HAVE_CUSTOM2_QOS;
            type  uint8 {
                 range "1..63"  {
                    description "1..63: Supported range 1 - 63";
                 }
            }
            description "Use this attribute to set the weight for Weighted Fair Queueing queue
                        scheduling algorithm";
        } // END of weighted-fair-queueing-queue-weight definition.

    } // END of qos-queue-mode-config definition.
    grouping qos-queue-mode-red-top {
        description
            "Grouping for QoS queue random early detection";
        container red {
            description
                "Configuration data for QoS queue random early detection";
            container config {
                description
                    "Configuration data for QoS queue random early detection";
                uses qos-queue-mode-red-config;
            } // END of config-container definition.
            container state {
                config false;
                description
                    "Operational state data for QoS queue random early detection";
                uses qos-queue-mode-red-config;
            } // END of state-container definition.
            uses qos-queue-mode-wred-top;
            uses qos-queue-mode-random-detect-top;
        } // END of red-container definition.
    } // END of qos-queue-mode-red-top definition.
    grouping qos-queue-mode-red-config {
        description
            "Grouping for QoS queue random early detection";
        leaf weight  {
            type  uint8 {
                 range "0..31"  {
                    description "0..31:Feature : HAVE_CUSTOM1_QOS Supported range 0 - 15Feature :
                            HAVE_CUSTOM2_QOS Supported range 0 - 31";
                 }
            }
            description "Use this attribute to set weight for Weighted Random Early Detection";
        } // END of weight definition.

    } // END of qos-queue-mode-red-config definition.
    grouping qos-queue-mode-wred-top {
        description
            "Grouping for QoS queue weighted random early detection";
        container wreds {
            if-feature feature-list:HAVE_CUSTOM2_QOS;
            description
                "Configuration data for QoS queue weighted random early detection";

            list wred {
                key "color";
                description
                    "Configuration data list for QoS queue weighted random early detection";
                leaf color  {
                    type  leafref {
                        path  "../config/color";
                    }
                    description "Use this attribute to set Weighted Random Early Detection color.
                                Default value is 3.";
                } // END of color definition.

                container config {
                    description
                        "Configuration data for QoS queue weighted random early detection";
                    uses qos-queue-mode-wred-config;
                } // END of config-container definition.
                container state {
                    config false;
                    description
                        "Operational state data for QoS queue weighted random early detection";
                    uses qos-queue-mode-wred-config;
                } // END of state-container definition.
            } // End of wred-list
        } // END of wreds-container definition.
    } // END of qos-queue-mode-wred-top definition.
    grouping qos-queue-mode-wred-config {
        description
            "Grouping for QoS queue weighted random early detection configuration";
        leaf color  {
            type  ipi-qos-types:qos_color_key_t;
            default "all";
            description "Use this attribute to set Weighted Random Early Detection color";
        } // END of color definition.

        leaf min-threshold  {
            type  uint32 {
                 range "1..629145600"  {
                    description "1..629145600: Supported range 1 - 629145600";
                 }
            }
            mandatory true;
            description "Use this attribute to set Weighted Random Early Detection minimum
                        threshold";
        } // END of min-threshold definition.

        leaf min-threshold-unit  {
            type  ipi-qos-types:qos_threshold_t;
            mandatory true;
            description "Use this attribute to set minimum threshold unit";
        } // END of min-threshold-unit definition.

        leaf max-threshold  {
            type  uint32 {
                 range "1..629145600"  {
                    description "1..629145600: Supported range 1 - 629145600";
                 }
            }
            mandatory true;
            description "Use this attribute to set maximum threshold unit";
        } // END of max-threshold definition.

        leaf max-threshold-unit  {
            type  ipi-qos-types:qos_threshold_t;
            mandatory true;
            description "Use this attribute to set Weighted Random Early Detection maximum
                        threshold";
        } // END of max-threshold-unit definition.

        leaf drop-probability  {
            type  uint8 {
                 range "1..100"  {
                    description "1..100: Supported range 1 - 100";
                 }
            }
            mandatory true;
            description "Use this attribute to set the percentage of packet drops when average
                        queue length reaches maximum threshold. Default value is 80.";
        } // END of drop-probability definition.

    } // END of qos-queue-mode-wred-config definition.
    grouping qos-queue-mode-random-detect-top {
        description
            "Grouping for QoS queue weighted random early detection";
        container wred {
            if-feature feature-list:HAVE_CUSTOM1_QOS;
            description
                "Configuration data for QoS queue weighted random early detection";
            container config {
                description
                    "Configuration data for QoS queue weighted random early detection";
                uses qos-queue-mode-random-detect-config;
            } // END of config-container definition.
            container state {
                config false;
                description
                    "Operational state data for QoS queue weighted random early detection";
                uses qos-queue-mode-random-detect-config;
            } // END of state-container definition.
        } // END of wred-container definition.
    } // END of qos-queue-mode-random-detect-top definition.
    grouping qos-queue-mode-random-detect-config {
        description
            "Grouping for QoS queue weighted random early detection configuration";
        leaf min-threshold  {
            type  uint32 {
                 range "1..524288"  {
                    description "1..524288:Not Feature : HAVE_CUSTOM2_QOS  Supported range 1 - 524288";
                 }
            }
            mandatory true;
            description "Use this attribute to set Weighted Random Early Detection minimum
                        threshold";
        } // END of min-threshold definition.

        leaf threshold-unit  {
            type  ipi-qos-types:qos_threshold_t;
            mandatory true;
            description "Use this attribute to set minimum threshold unit";
        } // END of threshold-unit definition.

        leaf max-threshold  {
            type  uint32 {
                 range "1..524288"  {
                    description "1..524288: Supported range 1 - 524288";
                 }
            }
            mandatory true;
            description "Use this attribute to set maximum threshold unit";
        } // END of max-threshold definition.

        leaf drop-probability  {
            type  uint8 {
                 range "1..100"  {
                    description "1..100: Supported range 1 - 100";
                 }
            }
            mandatory true;
            description "Use this attribute to set the percentage of packet drops when average
                        queue length reaches maximum threshold. Default value is 80.";
        } // END of drop-probability definition.

        leaf min-threshold-yellow  {
            type  uint32 {
                 range "1..524288"  {
                    description "1..524288: Supported range 1 - 524288";
                 }
            }
            description "Use this attribute to set Weighted Random Early Detection minimum
                        threshold";
        } // END of min-threshold-yellow definition.

        leaf max-threshold-yellow  {
            type  uint32 {
                 range "1..524288"  {
                    description "1..524288: Supported range 1 - 524288";
                 }
            }
            description "Use this attribute to set maximum threshold unit";
        } // END of max-threshold-yellow definition.

        leaf drop-probability-yellow  {
            type  uint8 {
                 range "1..100"  {
                    description "1..100: Supported range 1 - 100";
                 }
            }
            description "Use this attribute to set the percentage of packet drops when average
                        queue length reaches maximum threshold. Default value is 80.";
        } // END of drop-probability-yellow definition.

        leaf min-threshold-red  {
            type  uint32 {
                 range "1..524288"  {
                    description "1..524288: Supported range 1 - 524288";
                 }
            }
            description "Use this attribute to set Weighted Random Early Detection minimum
                        threshold";
        } // END of min-threshold-red definition.

        leaf max-threshold-red  {
            type  uint32 {
                 range "1..524288"  {
                    description "1..524288: Supported range 1 - 524288";
                 }
            }
            description "Use this attribute to set maximum threshold unit";
        } // END of max-threshold-red definition.

        leaf drop-probability-red  {
            type  uint8 {
                 range "1..100"  {
                    description "1..100: Supported range 1 - 100";
                 }
            }
            description "Use this attribute to set the percentage of packet drops when average
                        queue length reaches maximum threshold. Default value is 80.";
        } // END of drop-probability-red definition.

        leaf explicit-congestion-notification  {
            type  empty;
            description "Use this attribute to set explicit congestion notification.";
        } // END of explicit-congestion-notification definition.

    } // END of qos-queue-mode-random-detect-config definition.
    grouping qos-queue-mode-tail-drop-top {
        description
            "Grouping for QoS queue tail-drop";
        container tail-drops {
            description
                "Configuration data for QoS queue tail-drop";

            list tail-drop {
                key "max-threshold max-threshold-type";
                max-elements 1;
                description
                    "Configuration data for QoS queue tail-drop";
                leaf max-threshold  {
                    type  leafref {
                        path  "../config/max-threshold";
                    }
                    description "Use this attribute to set tail drop limits on egress queue";
                } // END of max-threshold definition.

                leaf max-threshold-type  {
                    type  leafref {
                        path  "../config/max-threshold-type";
                    }
                    description "Use this attribute to set tail drop limits on egress queue";
                } // END of max-threshold-type definition.

                container config {
                    description
                        "Configuration data for QoS queue tail-drop";
                    uses qos-queue-mode-tail-drop-config;
                } // END of config-container definition.
                container state {
                    config false;
                    description
                        "Operational state data for QoS queue tail-drop";
                    uses qos-queue-mode-tail-drop-config;
                } // END of state-container definition.
            } // End of tail-drop-list
        } // END of tail-drops-container definition.
    } // END of qos-queue-mode-tail-drop-top definition.
    grouping qos-queue-mode-tail-drop-config {
        description
            "Grouping for QoS queue tail-drop configuration";
        leaf max-threshold  {
            type  uint32 {
                 range "1..629145600"  {
                    description "1..629145600:Not Feature : HAVE_CUSTOM2_QOS  Supported range 1 -
                            524288Feature : HAVE_CUSTOM2_QOS Supported range 1 - 629145600";
                 }
            }
            description "Use this attribute to set tail drop limits on egress queue";
        } // END of max-threshold definition.

        leaf max-threshold-type  {
            type  ipi-qos-types:qos_threshold_t;
            description "Use this attribute to set the tail drop unit";
        } // END of max-threshold-type definition.

    } // END of qos-queue-mode-tail-drop-config definition.
    grouping qos-queue-mode-bandwidth-top {
        description
            "Grouping for QoS queue bandwidth";
        container bandwidths {
            if-feature feature-list:NOT_HAVE_CUSTOM2_QOS;
            description
                "Configuration data for QoS queue bandwidth";

            list bandwidth {
                key "rate-value rate-type";
                max-elements 1;
                description
                    "Configuration data for QoS queue bandwidth";
                leaf rate-value  {
                    type  leafref {
                        path  "../config/rate-value";
                    }
                    description "Use this attribute to set a minimum bandwidth rate on the egress queue";
                } // END of rate-value definition.

                leaf rate-type  {
                    type  leafref {
                        path  "../config/rate-type";
                    }
                    description "Use this attribute to set the bandwidth rate unit";
                } // END of rate-type definition.

                container config {
                    description
                        "Configuration data for QoS queue bandwidth";
                    uses qos-queue-mode-bandwidth-config;
                } // END of config-container definition.
                container state {
                    config false;
                    description
                        "Operational state data for QoS queue bandwidth";
                    uses qos-queue-mode-bandwidth-config;
                } // END of state-container definition.
            } // End of bandwidth-list
        } // END of bandwidths-container definition.
    } // END of qos-queue-mode-bandwidth-top definition.
    grouping qos-queue-mode-bandwidth-config {
        description
            "Grouping for QoS queue bandwidth configuration";
        leaf rate-value  {
            type  uint32;
            description "Use this attribute to set a minimum bandwidth rate on the egress queue";
        } // END of rate-value definition.

        leaf rate-type  {
            type  ipi-qos-types:qos_shape_rate_unit_extended_t;
            description "Use this attribute to set the bandwidth rate unit";
        } // END of rate-type definition.

    } // END of qos-queue-mode-bandwidth-config definition.
    grouping qos-queue-mode-shape-top {
        description
            "Grouping for QoS queue shape";
        container shapes {
            description
                "Configuration data for QoS queue shape";

            list shape {
                key "rate-value rate-unit";
                max-elements 1;
                description
                    "Configuration data for QoS queue shape";
                leaf rate-value  {
                    type  leafref {
                        path  "../config/rate-value";
                    }
                    description "Use this attribute to set a maximum shaping rate on the egress queue";
                } // END of rate-value definition.

                leaf rate-unit  {
                    type  leafref {
                        path  "../config/rate-unit";
                    }
                    description "Use this attribute to set the shape rate unit";
                } // END of rate-unit definition.

                container config {
                    description
                        "Configuration data for QoS queue shape";
                    uses qos-queue-mode-shape-config;
                } // END of config-container definition.
                container state {
                    config false;
                    description
                        "Operational state data for QoS queue shape";
                    uses qos-queue-mode-shape-config;
                } // END of state-container definition.
            } // End of shape-list
        } // END of shapes-container definition.
    } // END of qos-queue-mode-shape-top definition.
    grouping qos-queue-mode-shape-config {
        description
            "Grouping for QoS queue shape configuration";
        leaf rate-value  {
            type  uint32;
            description "Use this attribute to set a maximum shaping rate on the egress queue";
        } // END of rate-value definition.

        leaf rate-unit  {
            type  ipi-qos-types:qos_shape_rate_unit_extended_t;
            description "Use this attribute to set the shape rate unit";
        } // END of rate-unit definition.

    } // END of qos-queue-mode-shape-config definition.
    grouping qos-qos-mode {
        description
            "Grouping for QoS qos";
        container qos-mode {
            when " /ipi-qos:qos/ipi-qos:global/ipi-qos:policy-maps/ipi-qos:policy-map/ipi-qos:classes/ipi-qos:class/ipi-qos:config/ipi-qos:type = 'qos' ";
            description
                "Configuration data for QoS qos";
            container config {
                description
                    "Configuration data for QoS qos mode";
                uses qos-qos-mode-config;
            } // END of config-container definition.
            container state {
                config false;
                description
                    "Operational state data for QoS qos";
                uses qos-qos-mode-config;
            } // END of state-container definition.
            uses qos-police;
        } // END of qos-mode-container definition.
    } // END of qos-qos-mode definition.
    grouping qos-qos-mode-config {
        description
            "Grouping for QoS qos";
        leaf priority  {
            type  uint16 {
                 range "1..1000"  {
                    description "1..1000: Supported range 1 - 1000";
                 }
            }
            description "Use this attribute to set the user priority for the class attached to
                        this policy-map";
        } // END of priority definition.

        choice set-option {
            description
                "Choice for options to be applied";
            case port-action {

                description
                    "Set port action";

            }
            case precedence {

                description
                    "Set precedence option";

                leaf precedence-remark  {
                    type  string {
                        length "1..13";
                        pattern "[^?' =,>|]+";
                    }
                    description "Use this attribute to match traffic classes set action as change
                                precedence in the egress packet to the defined value. The precedence
                                value range is 0-7.
                                Warning: In CLI show running, precedence values with well-known names
                                (ex.: priority, immediate) will be displayed as such.
                                On Netconf, precedence values will always be numeric. The string type
                                allow up to 13 characters on well-known name.";
                } // END of precedence-remark definition.

            }
            case bridge-precedence {

                description
                    "Set bridge precedence option";

            }
            case cos {

                description
                    "Set CoS option";

                leaf cos-value  {
                    type  uint8 {
                         range "0..7"  {
                            description "0..7: Supported range 0 - 7";
                         }
                    }
                    description "Use this attribute to match traffic classes set action as change CoS
                                in the egress packet to the defined value";
                } // END of cos-value definition.

            }
            case bridge-cos {

                description
                    "Set bridge CoS option";

                leaf cos-remark-only-bridged  {
                    if-feature feature-list:HAVE_CUSTOM1_QOS;
                    type  uint8 {
                         range "0..7"  {
                            description "0..7: Supported range 0 - 7";
                         }
                    }
                    description "Use this attribute to enable remarking only bridged packets";
                } // END of cos-remark-only-bridged definition.

            }
            case dscp {

                description
                    "Set DSCP option";

                leaf dscp-value-remark  {
                    type  string {
                        length "1..8";
                        pattern "[^?' =,>|]+";
                    }
                    description "Use this attribute to match traffic classes set action as change DSCP
                                in the egress packet to the defined value. The DSCP value range is
                                0-63.
                                Warning: In CLI show running, DSCP values with well-known names (ex.:
                                af11, cs0) will be displayed as such.
                                On Netconf, DSCP values will always be numeric. The string type allow
                                up to 8 characters on well-known name.";
                } // END of dscp-value-remark definition.

            }
            case bridge-dscp {

                description
                    "Set bridge DSCP option";

                leaf dscp-remark-only-bridged  {
                    if-feature feature-list:HAVE_CUSTOM1_QOS;
                    type  string {
                        length "1..8";
                        pattern "[^?' =,>|]+";
                    }
                    description "Use this attribute to enable remarking only bridged packets. The DSCP
                                value range is 0-63.
                                Warning: In CLI show running, DSCP values with well-known names (ex.:
                                af11, cs0) will be displayed as such.
                                On Netconf, DSCP values will always be numeric. The string type allow
                                up to 8 characters on well-known name.";
                } // END of dscp-remark-only-bridged definition.

            }
            case queue {

                description
                    "Set queue option";

                leaf queue-id  {
                    type  uint8 {
                         range "0..7"  {
                            description "0..7: Supported range 0 - 7";
                         }
                    }
                    description "Use this attribute to match traffic classes set action as change queue
                                in the egress packet to the defined value";
                } // END of queue-id definition.

            }
            case bridge-queue {

                description
                    "Set bridge queue option";

                leaf queue-remark-only-bridged  {
                    if-feature feature-list:HAVE_CUSTOM1_QOS;
                    type  uint8 {
                         range "0..7"  {
                            description "0..7: Supported range 0 - 7";
                         }
                    }
                    description "Use this attribute to enable remarking only bridged packets";
                } // END of queue-remark-only-bridged definition.

            }
            case qos-group {

                description
                    "Set QoS group option";

                leaf qos-group  {
                    if-feature feature-list:HAVE_CUSTOM1_QOS;
                    type  uint16 {
                         range "1..2000"  {
                            description "1..2000: Supported range 1 - 2000";
                         }
                    }
                    description "Use this attribute to set action as change QoS group in the egress
                                packet to the defined value";
                } // END of qos-group definition.

            }
        } // END of set-option-choice definition.
    } // END of qos-qos-mode-config definition.
    grouping qos-police {
        description
            "Grouping for QoS police";
        container police {
            description
                "Configuration data for QoS police";
            container config {
                description
                    "Configuration data for QoS police";
                uses qos-aggregate-police-ref;
                uses qos-police-config;
            } // END of config-container definition.
            container state {
                config false;
                description
                    "Operational state data for QoS police";
                uses qos-aggregate-police-ref;
                uses qos-police-config;
            } // END of state-container definition.
        } // END of police-container definition.
    } // END of qos-police definition.
    grouping qos-police-config {
        description
            "Grouping for QoS police configuration";
        leaf type  {
            type  ipi-qos-types:qos_police_t;
            description "Use this attribute to set policer type. Default value is 0.";
        } // END of type definition.

        leaf cir  {
            type  uint64 {
                 range "1..2000000000"  {
                    description "1..2000000000:Feature : HAVE_POLICE_MAX_RATE_500GBPS Supported range 1
                            - 500000000Not Feature : HAVE_POLICE_MAX_RATE_500GBPS  Supported range
                            1 - 720000000Not Feature : HAVE_CUSTOM2_QOS  Supported range 1 -
                            2000000000";
                 }
            }
            mandatory true;
            description "Use this attribute to set a Committed Information Rate. Default value
                        is 1.";
        } // END of cir definition.

        leaf cir-unit  {
            when " ../cir ";
            type  ipi-qos-types:qos_rate_unit_t;
            mandatory true;
            description "Use this attribute to set a Committed Information Rate unit.";
        } // END of cir-unit definition.

        leaf bc  {
            type  uint64 {
                 range "1..256000"  {
                    description "1..256000:Feature : HAVE_CUSTOM2_QOS Supported range 1 - 4161Not
                            Feature : HAVE_CUSTOM2_QOS  Supported range 1 - 256000";
                 }
            }
            description "Use this attribute to set a Committed Burst";
        } // END of bc definition.

        leaf bc-unit  {
            when " ../bc ";
            type  ipi-qos-types:qos_burst_rate_unit_t;
            description "Use this attribute to set a Committed Burst unit";
        } // END of bc-unit definition.

        leaf eir  {
            if-feature feature-list:HAVE_CUSTOM2_QOS;
            type  uint64 {
                 range "1..720000000"  {
                    description "1..720000000:Feature : HAVE_POLICE_MAX_RATE_500GBPS Supported range 1
                            - 500000000Not Feature : HAVE_POLICE_MAX_RATE_500GBPS  Supported range
                            1 - 720000000";
                 }
            }
            description "Use this attribute to set an Excess Information Rate";
        } // END of eir definition.

        leaf eir-unit  {
            when " ../eir ";
            if-feature feature-list:HAVE_CUSTOM2_QOS;
            type  ipi-qos-types:qos_rate_unit_t;
            description "Use this attribute to set an Excess Information Rate unit";
        } // END of eir-unit definition.

        leaf pir  {
            if-feature feature-list:HAVE_CUSTOM1_QOS;
            type  uint64 {
                 range "1..2000000000"  {
                    description "1..2000000000: Supported range 1 - 2000000000";
                 }
            }
            description "Use this attribute to set a Peak Information Rate";
        } // END of pir definition.

        leaf pir-unit  {
            when " ../pir ";
            if-feature feature-list:HAVE_CUSTOM1_QOS;
            type  ipi-qos-types:qos_rate_unit_t;
            description "Use this attribute to set a Peak Information Rate unit";
        } // END of pir-unit definition.

        leaf be  {
            type  uint32 {
                 range "1..256000"  {
                    description "1..256000:Feature : HAVE_CUSTOM2_QOS Supported range 1 - 4161Not
                            Feature : HAVE_CUSTOM2_QOS  Supported range 1 - 256000";
                 }
            }
            description "Use this attribute to set an Extended Burst";
        } // END of be definition.

        leaf be-unit  {
            when " ../be ";
            type  ipi-qos-types:qos_burst_rate_unit_t;
            description "Use this attribute to set an Extended Burst unit";
        } // END of be-unit definition.

        leaf set-conform-action  {
            if-feature feature-list:HAVE_CUSTOM1_QOS;
            type  ipi-qos-types:qos_conform_action_t;
            description "Use this attribute to set an action when queue traffic conforms with
                        defined policer values";
        } // END of set-conform-action definition.

        leaf conform-cos  {
            when " ../set-conform-action='set-cos-transmit' ";
            if-feature feature-list:HAVE_CUSTOM1_QOS;
            type  uint8 {
                 range "0..7"  {
                    description "0..7: Supported range 0 - 7";
                 }
            }
            description "CoS value to be set on packets that conform";
        } // END of conform-cos definition.

        leaf conform-dscp  {
            when " ../set-conform-action='set-dscp-transmit' ";
            if-feature feature-list:HAVE_CUSTOM1_QOS;
            type  uint8 {
                 range "0..63"  {
                    description "0..63: Supported range 0 - 63";
                 }
            }
            description "DSCP value to be set on packets that conform";
        } // END of conform-dscp definition.

        leaf conform-precedence  {
            when " ../set-conform-action='set-prec-transmit' ";
            if-feature feature-list:HAVE_CUSTOM1_QOS;
            type  uint8 {
                 range "0..7"  {
                    description "0..7: Supported range 0 - 7";
                 }
            }
            description "Precedence value to be set on packets that conform";
        } // END of conform-precedence definition.

        leaf conform-exp  {
            when " ../set-conform-action='set-mpls-class' ";
            if-feature feature-list:HAVE_CUSTOM1_QOS;
            if-feature feature-list:HAVE_DIFFSERV;
            type  uint8 {
                 range "0..7"  {
                    description "0..7: Supported range 0 - 7";
                 }
            }
            description "MPLS class value to be set on packets that conform";
        } // END of conform-exp definition.

        leaf set-exceed-action  {
            if-feature feature-list:HAVE_CUSTOM1_QOS;
            type  ipi-qos-types:qos_exceed_action_t;
            description "Use this attribute to set an action when queue traffic exceeds define
                        policer values";
        } // END of set-exceed-action definition.

        leaf exceed-cos  {
            when " ../set-exceed-action='set-cos-transmit' ";
            if-feature feature-list:HAVE_CUSTOM1_QOS;
            type  uint8 {
                 range "0..7"  {
                    description "0..7: Supported range 0 - 7";
                 }
            }
            description "CoS value to be set on packets that exceed";
        } // END of exceed-cos definition.

        leaf exceed-dscp  {
            when " ../set-exceed-action='set-dscp-transmit' ";
            if-feature feature-list:HAVE_CUSTOM1_QOS;
            type  uint8 {
                 range "0..63"  {
                    description "0..63: Supported range 0 - 63";
                 }
            }
            description "DSCP value to be set on packets that exceed";
        } // END of exceed-dscp definition.

        leaf exceed-exp  {
            when " ../set-exceed-action='set-mpls-class' ";
            if-feature feature-list:HAVE_CUSTOM1_QOS;
            if-feature feature-list:HAVE_DIFFSERV;
            type  uint8 {
                 range "0..7"  {
                    description "0..7: Supported range 0 - 7";
                 }
            }
            description "MPLS class value to be set on packets that exceed";
        } // END of exceed-exp definition.

        leaf set-violate-action  {
            if-feature feature-list:HAVE_CUSTOM1_QOS;
            type  ipi-qos-types:qos_violate_action_t;
            description "Use this attribute to set an action when queue traffic violates
                        defined policer values";
        } // END of set-violate-action definition.

        leaf violate-cos  {
            when " ../set-violate-action='set-cos-transmit' ";
            if-feature feature-list:HAVE_CUSTOM1_QOS;
            type  uint8 {
                 range "0..7"  {
                    description "0..7: Supported range 0 - 7";
                 }
            }
            description "CoS value to be set on packets that violate";
        } // END of violate-cos definition.

        leaf violate-dscp  {
            when " ../set-violate-action='set-dscp-transmit' ";
            if-feature feature-list:HAVE_CUSTOM1_QOS;
            type  uint8 {
                 range "0..63"  {
                    description "0..63: Supported range 0 - 63";
                 }
            }
            description "DSCP value to be set on packets that violate";
        } // END of violate-dscp definition.

        leaf violate-exp  {
            when " ../set-violate-action='set-mpls-class' ";
            if-feature feature-list:HAVE_CUSTOM1_QOS;
            if-feature feature-list:HAVE_DIFFSERV;
            type  uint8 {
                 range "0..7"  {
                    description "0..7: Supported range 0 - 7";
                 }
            }
            description "MPLS class value to be set on packets that violate";
        } // END of violate-exp definition.

    } // END of qos-police-config definition.
    grouping qos-police-action {
        description
            "Grouping for QoS police action";
    } // END of qos-police-action definition.
    grouping qos-police-actions-config {
        description
            "Grouping for QoS police action";
        leaf set-conform-action  {
            type  ipi-qos-types:qos_conform_action_t;
            description "Use this attribute to set an action when queue traffic conforms with
                        defined policer values";
        } // END of set-conform-action definition.

        leaf conform-cos  {
            when " ../set-conform-action=4 ";
            type  uint8 {
                 range "0..7"  {
                    description "0..7: Supported range 0 - 7";
                 }
            }
            description "CoS value to be set on packets that conform";
        } // END of conform-cos definition.

        leaf conform-dscp  {
            when " ../set-conform-action=2 ";
            type  uint8 {
                 range "0..63"  {
                    description "0..63: Supported range 0 - 63";
                 }
            }
            description "DSCP value to be set on packets that conform";
        } // END of conform-dscp definition.

        leaf conform-precedence  {
            when " ../set-conform-action=3 ";
            type  uint8 {
                 range "0..7"  {
                    description "0..7: Supported range 0 - 7";
                 }
            }
            description "Precedence value to be set on packets that conform";
        } // END of conform-precedence definition.

        leaf set-exceed-action  {
            type  ipi-qos-types:qos_exceed_action_t;
            description "Use this attribute to set an action when queue traffic exceeds define
                        policer values";
        } // END of set-exceed-action definition.

        leaf exceed-cos  {
            when " ../set-exceed-action=4 ";
            type  uint8 {
                 range "0..7"  {
                    description "0..7: Supported range 0 - 7";
                 }
            }
            description "CoS value to be set on packets that exceed";
        } // END of exceed-cos definition.

        leaf exceed-dscp  {
            when " ../set-exceed-action=2 ";
            type  uint8 {
                 range "0..63"  {
                    description "0..63: Supported range 0 - 63";
                 }
            }
            description "DSCP value to be set on packets that exceed";
        } // END of exceed-dscp definition.

        leaf set-violate-action  {
            type  ipi-qos-types:qos_violate_action_t;
            description "Use this attribute to set an action when queue traffic violates
                        defined policer values";
        } // END of set-violate-action definition.

        leaf violate-cos  {
            when " ../set-violate-action=4 ";
            type  uint8 {
                 range "0..7"  {
                    description "0..7: Supported range 0 - 7";
                 }
            }
            description "CoS value to be set on packets that violate";
        } // END of violate-cos definition.

        leaf violate-dscp  {
            when " ../set-violate-action=2 ";
            type  uint8 {
                 range "0..63"  {
                    description "0..63: Supported range 0 - 63";
                 }
            }
            description "DSCP value to be set on packets that violate";
        } // END of violate-dscp definition.

    } // END of qos-police-actions-config definition.
    grouping qos-aggregate-police-ref {
        description
            "Grouping for QoS aggregate police reference";
    } // END of qos-aggregate-police-ref definition.
    grouping qos-aggregate-police-config {
        description
            "Grouping for QoS aggregate police configuration";
        leaf name  {
            type  string {
                length "1..32";
                pattern "[^?' =,>|]+";
            }
            description "Use this attribute to aggregate policer to multiple classes";
        } // END of name definition.

        uses qos-police-config;
    } // END of qos-aggregate-police-config definition.
    grouping qos-aggregate-police-top {
        description
            "Grouping for QoS aggregate police";
    } // END of qos-aggregate-police-top definition.
    grouping qos-remark-config {
        description
            "Grouping for QoS remark configuration";
        leaf cos  {
            type  empty;
            description "Use this command to enable remarking of CoS set by the egress map";
        } // END of cos definition.

        leaf dei  {
            if-feature feature-list:NOT_HAVE_CUSTOM2_QOS;
            type  empty;
            description "Use this command to enable remarking of DEI set by the egress map";
        } // END of dei definition.

        leaf dscp  {
            type  empty;
            description "Use this command to enable remarking of DSCP set by the egress map";
        } // END of dscp definition.

    } // END of qos-remark-config definition.
    grouping qos-remark-top {
        description
            "Grouping for QoS remark";
        container remark {
            when " /ipi-qos:qos/ipi-qos:global/ipi-qos:config/ipi-qos:enable-qos ";
            description
                "Configuration data for QoS remark";
            container config {
                description
                    "Configuration data for QoS remark";
                uses qos-remark-config;
            } // END of config-container definition.
            container state {
                config false;
                description
                    "Operational state data for QoS remark";
                uses qos-remark-config;
            } // END of state-container definition.
        } // END of remark-container definition.
    } // END of qos-remark-top definition.
    grouping qos-global-config {
        description
            "Grouping for QoS global configuration";
        leaf enable-qos  {
            type  empty;
            description "Use this attribute to globally enable or disable QoS";
        } // END of enable-qos definition.

        leaf red-drop-disabled  {
            when " /ipi-qos:qos/ipi-qos:global/ipi-qos:config/ipi-qos:enable-qos ";
            if-feature feature-list:HAVE_CUSTOM2_QOS;
            type  empty;
            description "Use this attribute to disable red packet drop in the system. Red
                        packets are dropped in the system by default to
                        achieve ingress rate limiting via policer and storm control. However,
                        this command is used when there is no use-case
                        for rate limiting traffic and red packets need to be allowed in the
                        system";
        } // END of red-drop-disabled definition.

        leaf statistics-enabled  {
            when " /ipi-qos:qos/ipi-qos:global/ipi-qos:config/ipi-qos:enable-qos ";
            type  empty;
            description "Use this attribute to enable QoS statistics";
        } // END of statistics-enabled definition.

        leaf block-size  {
            when " /ipi-qos:qos/ipi-qos:global/ipi-qos:config/ipi-qos:enable-qos ";
            if-feature feature-list:HAVE_FLEXPORT;
            if-feature feature-list:HAVE_CUSTOM1_QOS;
            type  uint8 {
                 range "1..8"  {
                    description "1..8: Supported range 1 - 8";
                 }
            }
            default "1";
            description "Use this attribute to configure block-size for vlan-queuing";
        } // END of block-size definition.

    } // END of qos-global-config definition.
    grouping qos-global-top {
        description
            "Top-level grouping for QoS";
        container global {
            description
                "Configuration data for global QoS";
            container config {
                description
                    "Configuration data for global QoS";
                uses qos-global-config;
            } // END of config-container definition.
            container state {
                config false;
                description
                    "Operational state data fot global QoS";
                uses qos-global-config;
            } // END of state-container definition.
            uses qos-map-profile-top;
            uses qos-remark-top;
            uses qos-class-map-default-top;
            uses qos-class-map-top;
            uses qos-class-map-queuing-top;
            uses qos-policy-map-top;
            uses qos-aggregate-police-top;
            uses qos-queue-scheduler-top;
        } // END of global-container definition.
    } // END of qos-global-top definition.

    grouping  qos-grouping {
    description
        "Quality of Service (QoS)";
    container qos {
        if-feature feature-list:HAVE_QOS;
        description
            "Quality of Service (QoS)";
        uses qos-global-top;
    } // END of qos-container definition.
    } // END of qos-grouping definition.

    uses qos-grouping;

    rpc qos-clear-statistics {
        if-feature feature-list:HAVE_QOS;
        description "Clears QoS statistics";
        input  {
            leaf interface-name  {
                type string;
                default "NULL";
                description "Specify the interface name for which statistics should be cleared";
            }
            leaf type  {
                type ipi-qos-types:qos_clear_stats_t;
                default "type-all";
                description "Specify the type of statistics that should be cleared";
            }
        }
    }

}
