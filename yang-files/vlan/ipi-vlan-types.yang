/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-vlan-types.yang
*
*/

module ipi-vlan-types {

    yang-version 1.1;

    namespace   "http://www.ipinfusion.com/yang/ocnos/ipi-vlan-types";

    prefix "ipi-vlan-types";

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "This module defines types related to the vlan model";


    revision "2022-06-01" {
        description "Updated the yang file with feature";
        reference " 0.6.0.";
    }

    revision "2021-09-07" {
        description "Fix for JIRA-50146";
        reference " 0.5.1.";
    }

    revision "2021-08-01" {
        description "Update helpstrings as part of OCMP-809";
        reference " 0.5.0.";
    }

    revision "2021-04-08" {
        description "Data model changes done for OCMP-608";
        reference " 0.4.0.";
    }

    revision "2021-01-27" {
        description "Private vlan data types modified";
        reference " 0.3.0.";
    }

    revision "2020-12-15" {
        description "Change to have data-types in lower case instead of camel case";
        reference " 0.2.0.";
    }

    revision "2018-06-21" {
        description "Initial Version";
        reference " 0.1.0.";
    }



    typedef  vlan_state_t {
        type enumeration {
            enum disable {
                value 1;
                description "Disable VLAN status on the bridge";
            }
            enum enable {
                value 2;
                description "Enable VLAN status on the bridge";
            }
        }
        description "type definition for VLAN_STATE_T";
    }

    typedef  vlan_allowed_forbidden_t {
        type enumeration {
            enum forbidden {
                value 0;
                description "Forbidden list";
            }
            enum allowed {
                value 1;
                description "Allowed list";
            }
        }
        description "type definition for VLAN_ALLOWED_FORBIDDEN_T";
    }

    typedef  cvlan_type_t {
        type enumeration {
            enum customer {
                value 4;
                description "Customer VLAN";
            }
        }
        description "type definition for CVLAN_TYPE_T";
    }

    typedef  svlan_type_t {
        type enumeration {
            enum point-point {
                value 16;
                if-feature feature-list:HAVE_PROVIDER_BRIDGE;
                description "Service Point-to-Point Service VLAN";
            }
            enum multipoint-multipoint {
                value 32;
                if-feature feature-list:HAVE_PROVIDER_BRIDGE;
                description "Service Multipoint to Multipoint Service VLAN";
            }
            enum rooted-multipoint {
                value 2048;
                if-feature feature-list:HAVE_PROVIDER_BRIDGE;
                description "Service Rooted Multipoint Service VLAN";
            }
        }
        description "type definition for SVLAN_TYPE_T";
    }

    typedef  vlan_oper_status_t {
        type enumeration {
            enum Up {
                value 1;
                description "Operational state UP";
            }
            enum Down {
                value 2;
                description "Operational state DOWN";
            }
        }
        description "type definition for VLAN_OPER_STATUS_T";
    }

    typedef  vlan_pvlan_type_t {
        type enumeration {
            enum community {
                value 1;
                description "VLAN type to community";
            }
            enum isolated {
                value 2;
                description "VLAN type to isolated";
            }
            enum primary {
                value 3;
                description "VLAN type to primary";
            }
        }
        description "type definition for VLAN_PVLAN_TYPE_T";
    }

    typedef  vlan_oepvlan_type_t {
        type enumeration {
            enum cvlan {
                value 1;
                description "Configure CVLAN oep-mapping table entry";
            }
            enum svlan {
                value 2;
                description "Configure SVLAN oep-mapping table entry";
            }
        }
        description "type definition for VLAN_OEPVLAN_TYPE_T";
    }

    typedef  vlan_preserve_type_t {
        type bits {
            bit preserve-cos {
                position 0;
                description "Preserve COS";
            }
            bit preserve-vlanid {
                position 1;
                description "Preserve VLAN ID";
            }
        }
        description "type definition for VLAN_PRESERVE_TYPE_T";
    }

    typedef  vlan_acltype_t {
        type enumeration {
            enum mac {
                value 1;
                description "MAC access-list";
            }
            enum ip {
                value 3;
                description "IP access-list";
            }
            enum ipv6 {
                value 4;
                description "IPv6 access-list";
            }
        }
        description "type definition for VLAN_ACLTYPE_T";
    }

    typedef  vlan_actiontype_t {
        type enumeration {
            enum forward {
                value 101;
                description "Forward";
            }
            enum drop {
                value 102;
                description "Drop";
            }
            enum redirect {
                value 103;
                description "Redirect to";
            }
        }
        description "type definition for VLAN_ACTIONTYPE_T";
    }

    typedef  vlan_ethertype_t {
        type enumeration {
            enum ip {
                value 2048;
                description "IP (0x0800)";
            }
            enum x25 {
                value 2053;
                description "CCITT X.25 (0x0805)";
            }
            enum arp {
                value 2054;
                description "Address Resolution Protocol (0x0806)";
            }
            enum g8bpqx25 {
                value 2303;
                description "G8BPQ AX.25 (0x08FF)";
            }
            enum ieeepup {
                value 2560;
                description "Xerox IEEE802.3 PUP (0x0a00)";
            }
            enum ieeeaddrtrans {
                value 2561;
                description "Xerox IEEE802.3 PUP Address Translation (0x0a01)";
            }
            enum dec {
                value 24576;
                description "DEC Assigned (0x6000)";
            }
            enum decdnadumpload {
                value 24577;
                description "DEC DNA Dump/Load (0x6001)";
            }
            enum decdnaremoteconsole {
                value 24578;
                description "DEC DNA Remote Console (0x6002)";
            }
            enum decdnarouting {
                value 24579;
                description "DEC DNA Routing (0x6003)";
            }
            enum declat {
                value 24580;
                description "DEC LAT (0x6004)";
            }
            enum decdiagnostics {
                value 24581;
                description "DEC Diagnostics (0x6005)";
            }
            enum rarp {
                value 32821;
                description "Reverse Address Resolution Protocol (0x8035)";
            }
            enum atalkddp {
                value 32923;
                description "Appletalk DDP (0x809B)";
            }
            enum atalkaarp {
                value 33011;
                description "Appletalk AARP (0x80F3)";
            }
            enum ipx {
                value 33079;
                description "IPX (0x8137)";
            }
            enum ipv6 {
                value 34525;
                description "IPv6 (0x86DD)";
            }
            enum atmmulti {
                value 34892;
                description "MultiProtocol Over ATM (0x884c)";
            }
            enum pppdiscovery {
                value 34915;
                description "PPPoE discovery (0x8863)";
            }
            enum pppsession {
                value 34916;
                description "PPPoE session (0x8864)";
            }
            enum atmtransport {
                value 34948;
                description "Frame-based ATM Transport (0x8884)";
            }
        }
        description "type definition for VLAN_ETHERTYPE_T";
    }

    typedef  vlan_classifier_ethertype_string_t {
        type string {
            length 5..6;
            pattern "0x[0-9a-fA-F]+";
        }
        description "type definition for VLAN_CLASSIFIER_ETHERTYPE_STRING_T";
    }

    typedef  vlan_classifier_ethertype_t {
        type union {
            type vlan_classifier_ethertype_string_t {

            }
            type vlan_ethertype_t {

            }
        }
        description "type definition for VLAN_CLASSIFIER_ETHERTYPE_T";
    }

    typedef  vlan_ce_svlan_t {
        type enumeration {
            enum ce-vlan {
                value 1;
                description "Preservation for Customer Edge VLAN";
            }
            enum svlan {
                value 2;
                description "Preservation for Service VLAN";
            }
        }
        description "type definition for VLAN_CE_SVLAN_T";
    }

    typedef  cvlan_config_t {
        type bits {
            bit default {
                position 0;
                description "Default value";
            }
            bit untagged-pep {
                position 1;
                description "Configure PEP as Untagged for this CVLAN";
            }
            bit untagged-cep {
                position 2;
                description "Configure CEP as Untagged for this CVLAN";
            }
        }
        description "type definition for CVLAN_CONFIG_T";
    }

    typedef  cml_add_remove_t {
        type enumeration {
            enum remove {
                value 0;
                description "Deletes the interface from the VLAN list";
            }
            enum add {
                value 1;
                description "Adds the interface in the VLAN list";
            }
        }
        description "type definition for CML_ADD_REMOVE_T";
    }

}
