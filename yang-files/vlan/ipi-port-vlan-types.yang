/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-port-vlan-types.yang
*
*/

module ipi-port-vlan-types {

    yang-version 1.1;

    namespace   "http://www.ipinfusion.com/yang/ocnos/ipi-port-vlan-types";

    prefix "ipi-port-vlan-types";

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "This module defines types related to the port vlan model";


    revision "2022-07-13" {
        description "Enabling Provider-bridging functionality for customer-network";
        reference " 0.6.1.";
    }

    revision "2022-06-01" {
        description "Updated the yang file with feature";
        reference " 0.6.0.";
    }

    revision "2022-01-13" {
        description "Added if-feature for data types";
        reference " 0.5.0.";
    }

    revision "2021-09-03" {
        description "Update descriptions of attribute";
        reference " 0.4.0.";
    }

    revision "2021-08-01" {
        description "Update helpstring commands";
        reference " 0.3.0.";
    }

    revision "2021-05-20" {
        description "Update helpstring for interface level switchport commands.";
        reference " 0.2.1.";
    }

    revision "2020-12-15" {
        description "Change to have data-types in lower case instead of camel case";
        reference " 0.2.0.";
    }

    revision "2018-06-21" {
        description "Initial Version";
        reference " 0.1.0.";
    }



    typedef  port_vlan_stack_t {
        type enumeration {
            enum customer-edge-port {
                value 4;
                description "Set the switching characteristics of the Layer-2 interface to Customer-edge port";
            }
            enum provider-port {
                value 6;
                description "Set the switching characteristics of the Layer-2 interface to Provider port";
            }
        }
        description "type definition for PORT_VLAN_STACK_T";
    }

    typedef  port_vlan_uni_enni_type_t {
        type enumeration {
            enum leaf {
                value 1;
                description "Leaf";
            }
            enum root {
                value 2;
                description "Root";
            }
            enum trunk {
                value 3;
                description "Trunk";
            }
        }
        description "type definition for PORT_VLAN_UNI_ENNI_TYPE_T";
    }

    typedef  port_vlan_uni_service_t {
        type enumeration {
            enum bundle {
                value 1;
                description "UNI supports bundling without multiplexing";
            }
            enum all-to-one {
                value 2;
                description "UNI supports all to one bundling";
            }
            enum multiplex {
                value 3;
                description "UNI supports multiplexing without bundling";
            }
        }
        description "type definition for PORT_VLAN_UNI_SERVICE_T";
    }

    typedef  port_vlan_uni_enable_disable_t {
        type enumeration {
            enum disable {
                value 0;
                description "uni type disable will set the default uni type";
            }
            enum enable {
                value 1;
                description "uni type enable will update the uni type";
            }
        }
        description "type definition for PORT_VLAN_UNI_ENABLE_DISABLE_T";
    }

    typedef  port_vlan_frame_type_t {
        type enumeration {
            enum vlan-tagged {
                value 1;
                description "Set VLAN-tagged frames can only be received";
            }
            enum all {
                value 2;
                description "Set all frames can be received";
            }
        }
        description "type definition for PORT_VLAN_FRAME_TYPE_T";
    }

    typedef  port_vlan_allowed_type_t {
        type enumeration {
            enum remove {
                value 1;
                description "Remove a VLAN to Tx/Rx through the Layer-2 interface";
            }
            enum except {
                value 2;
                description "Allow all VLANs except VID to Tx/Rx through the Layer2 interface";
            }
            enum all {
                value 3;
                description "Allow all VLANs to Tx/Rx through the Layer-2 interface";
            }
            enum add {
                value 4;
                description "Allow specified VLANs to Tx/Rx through the Layer-2 interface";
            }
            enum none {
                value 5;
                description "Allow none of the VLANs to Tx/Rx through the Layer-2 interface";
            }
        }
        description "type definition for PORT_VLAN_ALLOWED_TYPE_T";
    }

    typedef  port_vlan_port_sec_mode_t {
        type enumeration {
            enum static {
                value 1;
                description "Static mode";
            }
            enum default {
                value 2;
                description "Dynamic mode";
            }
        }
        description "type definition for PORT_VLAN_PORT_SEC_MODE_T";
    }

    typedef  port_vlan_pvlan_mode_t {
        type enumeration {
            enum host {
                value 1;
                description "host port";
            }
            enum promiscuous {
                value 2;
                description "promiscuous port";
            }
            enum trunk {
                value 3;
                if-feature feature-list:HAVE_PVLAN_TRUNK;
                description "pvlan-trunk port";
            }
        }
        description "type definition for PORT_VLAN_PVLAN_MODE_T";
    }

    typedef  port_vlan_oep_map_type_t {
        type enumeration {
            enum uni-oep {
                value 2;
                description "Configure OVC endpoint map";
            }
            enum enni-oep {
                value 4;
                description "Configure OEP mapping table";
            }
        }
        description "type definition for PORT_VLAN_OEP_MAP_TYPE_T";
    }

    typedef  port_vlan_switch_port_mode_t {
        type enumeration {
            enum access {
                value 1;
                description "Set the Layer-2 interface as access";
            }
            enum hybrid {
                value 2;
                description "Set the Layer-2 interface as hybrid";
            }
            enum trunk {
                value 3;
                description "Set the Layer-2 interface as trunk";
            }
            enum customer-network {
                value 5;
                description "Set the Layer-2 interface as customer network";
            }
            enum provider-network {
                value 6;
                description "Set the Layer-2 interface as provider network";
            }
            enum sbp {
                value 20;
                if-feature feature-list:HAVE_DCB;
                description "Station-facing Bridge-Port";
            }
            enum uap {
                value 21;
                if-feature feature-list:HAVE_DCB;
                description "Uplink Access Port";
            }
            enum customer-edge-access {
                value 41;
                if-feature feature-list:HAVE_PROVIDER_BRIDGE;
                description "Set the Layer-2 interface as customer edge,Set the Layer-2 interface as access";
            }
            enum customer-edge-hybrid {
                value 42;
                if-feature feature-list:HAVE_PROVIDER_BRIDGE;
                description "Set the Layer-2 interface as customer edge,Set the Layer-2 interface as hybrid";
            }
            enum customer-edge-trunk {
                value 43;
                if-feature feature-list:HAVE_PROVIDER_BRIDGE;
                description "Set the Layer-2 interface as customer edge,Set the Layer-2 interface as trunk";
            }
        }
        description "type definition for PORT_VLAN_SWITCH_PORT_MODE_T";
    }

    typedef  port_vlan_l2_fdb_action_t {
        type enumeration {
            enum discard {
                value 0;
                description "Specifies to discard frames";
            }
            enum forward {
                value 1;
                description "Specifies to forward frames";
            }
        }
        description "type definition for PORT_VLAN_L2_FDB_ACTION_T";
    }

}
