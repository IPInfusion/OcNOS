/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-aaa-types.yang
*
*/

module ipi-aaa-types {

    yang-version 1.1;

    namespace   "http://www.ipinfusion.com/yang/ocnos/ipi-aaa-types";

    prefix "ipi-aaa-types";

    organization
        "IP Infusion Inc.";

    contact
        "Address: 3965 Freedom Circle, Suite 200, Santa Clara, CA 95054
         Phone: +1 408-400-1900
         E-mail: support@ipinfusion.com
         Web: http://www.ipinfusion.com/";

    description
        "This defines types related to AAA model";


    revision "2022-06-01" {
        description "Updated the yang file with feature";
        reference " 0.3.0.";
    }

    revision "2021-09-03" {
        description "Update descriptions of attribute";
        reference " 0.2.0.";
    }

    revision "2021-07-01" {
        description "Initial Version";
        reference " 0.1.0.";
    }



    typedef  aaa_server_grp_type_t {
        type enumeration {
            enum tacacs+ {
                value 1;
                description "TACACS+ server group definition";
            }
            enum radius {
                value 2;
                description "RADIUS server group definition";
            }
        }
        description "type definition for AAA_SERVER_GRP_TYPE_T";
    }

}
