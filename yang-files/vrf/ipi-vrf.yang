/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-vrf.yang
*
*/

module ipi-vrf {

    yang-version 1.1;

    namespace   "http://www.ipinfusion.com/yang/ocnos/ipi-vrf";

    prefix "ipi-vrf";

    import ipi-network-instance {
        prefix ipi-network-instance;
        revision-date 2022-06-01;
    }

    import ietf-inet-types {
        prefix inet;
        revision-date 2013-07-15;
    }

    import cml-data-types {
        prefix cml-data-types;
        revision-date 2022-09-30;
    }

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "IPI VRF";


    revision "2022-07-13" {
        description "Deleted DB-triggers that add lo.vrf interfaces on creation of VRF";
        reference " 0.6.1.";
    }

    revision "2022-06-01" {
        description "Updated the yang file with feature";
        reference " 0.6.0.";
    }

    revision "2022-04-28" {
        description "Support for EVPN-MPLS IRB";
        reference " 0.5.0.";
    }

    revision "2021-09-03" {
        description "Update descriptions of attribute";
        reference " 0.4.0.";
    }

    revision "2021-01-27" {
        description "layer-3 network id attribute enabled";
        reference " 0.3.0.";
    }

    revision "2020-12-15" {
        description "Change to have data-types in lower case instead of camel case";
        reference " 0.2.0.";
    }

    revision "2020-08-11" {
        description "Datamodel restructuring";
        reference " 0.1.0.";
    }

    grouping network-instance-vrf-config {
        description
            "Configuration item grouping for VRF";
        leaf vrf-name  {
            type  leafref {
                path  "/ipi-network-instance:network-instances/ipi-network-instance:network-instance/ipi-network-instance:instance-name";
            }
            description "VRF Name";
        } // END of vrf-name definition.

        leaf description  {
            type  cml-data-types:cml_line_t {
                length "1..1965";
            }
            description "VRF-specific description";
        } // END of description definition.

        leaf tunnel-select-policy  {
            if-feature feature-list:HAVE_SERVICE_MAPPING_OR_HAVE_SRV6;
            type  string {
                length "1..127";
                pattern "[^?' =,>|]+";
            }
            description "tunnel policy to be configured";
        } // END of tunnel-select-policy definition.

        leaf router-id  {
            type  inet:ipv4-address;
            description "VRF Router ID";
        } // END of router-id definition.

        leaf evpn-layer3-network-id  {
            if-feature feature-list:HAVE_BGP_EVPN;
            if-feature feature-list:HAVE_NVO;
            type  uint32 {
                 range "1..16777215"  {
                    description "1..16777215: Supported range 1 - 16777215";
                 }
            }
            description "L3 EVPN Identifier";
        } // END of evpn-layer3-network-id definition.

        leaf mvpn-spmsi-ipv4-prefix  {
            if-feature feature-list:HAVE_BGP_MVPN;
            type  inet:ipv4-prefix;
            description "This attribute is used to configure IP address prefix for S-PMSI
                        static IP addresses per VRF.";
        } // END of mvpn-spmsi-ipv4-prefix definition.

    } // END of network-instance-vrf-config definition.
    grouping network-instance-vrf-state {
        description
            "State item grouping for VRF";
        leaf vrf-id  {
            type  uint32;
            description "VRF ID";
        } // END of vrf-id definition.

        leaf fib-id  {
            type  uint32;
            description "VRF FIB ID";
        } // END of fib-id definition.

    } // END of network-instance-vrf-state definition.

    grouping  vrf-grouping {
    description
        "Top level container for VRF";
    container vrf {
        if-feature feature-list:HAVE_VRF;
        description
            "Top level container for VRF";
        container config {
            description
                "Config container for VRF";
            uses network-instance-vrf-config;
        } // END of config-container definition.
        container state {
            config false;
            description
                "State container for VRF";
            uses network-instance-vrf-config;
            uses network-instance-vrf-state;
        } // END of state-container definition.
    } // END of vrf-container definition.
    } // END of vrf-grouping definition.

    augment /ipi-network-instance:network-instances/ipi-network-instance:network-instance {
    when " /ipi-network-instance:network-instances/ipi-network-instance:network-instance/ipi-network-instance:instance-type = 'vrf' or /ipi-network-instance:network-instances/ipi-network-instance:network-instance/ipi-network-instance:instance-type = 'mac-vrf' ";
        description
            "Top level container for VRF";
        uses vrf-grouping;
    }


    rpc clear-default-router-id {
        if-feature feature-list:HAVE_L3;
        if-feature feature-list:HAVE_VRF;
        description "Use this RPC to update default VRF router ID for all routing processes
                    in the System";
    }

    rpc clear-vrf-router-id {
        if-feature feature-list:HAVE_VRF;
        description "Use this RPC to reset the VRF Router-id";
        input  {
            leaf vrfName  {
                type string;
                mandatory true;
                description "VRF Name";
            }
        }
    }

}
