/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ospf.yang
*
*/

submodule ospf {

    belongs-to  ZebOS { prefix ZebOS; }
    include interface;


    import cml_data_types {
        prefix cml_data_types;
    }

    import feature_list {
        prefix feature_list;
    }

    description
        "Layer-3 ospf configurations";


    revision "2017-03-05" {
        description "Added implicit_delete for Interface tables.";
    }

    revision "2017-01-25" {
        description "Fix for JIRA-13037,JIRA-13021,JIRA-13019.";
    }

    revision "2017-01-23" {
        description "Fix for JIRA-12899 (graceful-restart).";
    }

    revision "2017-01-10" {
        description "Fix for JIRA-12271,12211,12385.";
    }

    revision "2016-12-22" {
        description "Added support for OSPF SMI auto generation.";
    }

    revision "2016-09-29" {
        description "Initial version of datamodel with Backend mapping.";
    }

    revision "2016-02-25" {
        description "Ospf vlink get-api implementation.";
    }

    revision "2016-02-11" {
        description "Ported changes from XP-master to ocnos-master.";
    }

    revision "2016-02-03" {
        description "Added utils function for encryption cases.";
    }

    revision "2016-01-26" {
        description "Addition of snmp oid for both IfTable and NeigborTable.";
    }



    grouping ospfMaster-grouping {
        list ospfMaster {
             
            description
                "OSPF Master commands";

            config true;
            key "vrId";

            
            leaf vrId  {
                type  cml_data_types:CML_UINT32_T;  
            } // END of vrId definition.

            leaf multiInstanceSet  {
                if-feature feature_list:HAVE_OSPF_MULTI_INST;
                type  cml_data_types:CML_BOOL_T;  
            } // END of multiInstanceSet definition.

            leaf graceperiod  {
                if-feature feature_list:HAVE_RESTART;
                type  cml_data_types:CML_UINT16_T {
                     range "1..1800";
                }
                description "grace period for graceful restart";
            } // END of graceperiod definition.

            leaf plannedOnly  {
                if-feature feature_list:HAVE_RESTART;
                type  cml_data_types:CML_BOOL_T;  
                description "ospf global config restart planned only";
            } // END of plannedOnly definition.

            leaf-list helperId  {
                type  cml_data_types:CML_IPV4_ADDR_T;  
                description "OSPF Helper Never Router-ID list";
            } // END of helperId definition.

            container ospfDebug {
                                config true;

                description
                    "OSPF global debug flags";

                leaf ospfDebugAllType  {
                    type  cml_data_types:CML_OSPF_ALL_DEBUG_T;  
                    description "debug packet type for ospf";
                } // END of ospfDebugAllType definition.

                leaf ospfPacketDebugType  {
                    type  cml_data_types:CML_OSPF_PACKET_TYPE_T;  
                    default "hello";
                    description "debug packet type for ospf";
                } // END of ospfPacketDebugType definition.

                leaf ospfEventFlags  {
                    type  cml_data_types:CML_OSPF_DEBUG_EVENT_TYPE_T;  
                    default "abr";
                    description "debug event flags for ospf";
                } // END of ospfEventFlags definition.

                leaf ospfIfsmFlags  {
                    type  cml_data_types:CML_OSPF_DEBUG_IFSM_T;  
                    default "status";
                    description "debug interface state machine flags for ospf";
                } // END of ospfIfsmFlags definition.

                leaf ospfNfsmFlags  {
                    type  cml_data_types:CML_OSPF_DEBUG_NFSM_T;  
                    default "status";
                    description "debug nsm state machine flags for ospf";
                } // END of ospfNfsmFlags definition.

                leaf ospfLsaFlags  {
                    type  cml_data_types:CML_OSPF_DEBUG_LSA_T;  
                    default "generate";
                    description "debug lsa flags for ospf";
                } // END of ospfLsaFlags definition.

                leaf ospfNsmFlags  {
                    type  cml_data_types:CML_OSPF_DEBUG_NSM_T;  
                    default "interface";
                    description "debug nsm flags for ospf";
                } // END of ospfNsmFlags definition.

                leaf ospfRibFlags  {
                    if-feature feature_list:HAVE_RIBD;
                    type  cml_data_types:CML_OSPF_DEBUG_RIB_T;  
                    default "interface";
                    description "debug flags for ribd";
                } // END of ospfRibFlags definition.

                leaf ospfRibClientFlags  {
                    if-feature feature_list:HAVE_RIBD;
                    type  cml_data_types:CML_OSPF_DEBUG_RIB_CLIENT_T;  
                    description "debug flags for ribd";
                } // END of ospfRibClientFlags definition.

                leaf ospfBfdFlags  {
                    if-feature feature_list:HAVE_BFD;
                    type  cml_data_types:CML_BOOL_T;  
                    description "debug bfd flags for ospf";
                } // END of ospfBfdFlags definition.

                leaf ospfRtCalcflags  {
                    type  cml_data_types:CML_OSPF_DEBUG_ROUTE_T;  
                    default "spf";
                    description "debug route cal flags for ospf";
                } // END of ospfRtCalcflags definition.

                leaf ospfDatabaseTimerflags  {
                    type  cml_data_types:CML_BOOL_T;  
                    description "debug database timer flags for ospf";
                } // END of ospfDatabaseTimerflags definition.

                leaf ospfRedistributeFlags  {
                    type  cml_data_types:CML_OSPF_DEBUG_REDIST_T;  
                    description "debug redistribute flags for ospf";
                } // END of ospfRedistributeFlags definition.

                leaf ospfGracefulRestartFlags  {
                    type  cml_data_types:CML_OSPF_DEBUG_GRACEFUL_T;  
                    description "debug graceful restart flags for ospf";
                } // END of ospfGracefulRestartFlags definition.

                leaf ospfPolicyFlags  {
                    type  cml_data_types:CML_BOOL_T;  
                    description "debug policy flags for ospf";
                } // END of ospfPolicyFlags definition.

                leaf ospfRetransmissionFlags  {
                    type  cml_data_types:CML_BOOL_T;  
                    description "debug retransmission flags for ospf";
                } // END of ospfRetransmissionFlags definition.

                leaf ospfLfaRouteFlags  {
                    if-feature feature_list:HAVE_OSPF_LFA;
                    type  cml_data_types:CML_BOOL_T;  
                    description "debug Lfa flags for ospf";
                } // END of ospfLfaRouteFlags definition.

                leaf ospfHaFlags  {
                    if-feature feature_list:HAVE_OSPF_SSO;
                    type  cml_data_types:CML_BOOL_T;  
                    description "debug HA flags for ospf";
                } // END of ospfHaFlags definition.

                leaf ospfSrFlags  {
                    if-feature feature_list:HAVE_SR_MPLS;
                    type  cml_data_types:CML_BOOL_T;  
                    description "debug segment routing flags for ospf";
                } // END of ospfSrFlags definition.

            } // END of ospfDebug-container definition.
            container helperPOlicy {
                                config true;

                description
                    "Helper policy for Graceful Restart";

                leaf MaxGracePeriod  {
                    type  cml_data_types:CML_UINT16_T {
                         range "1..1800";
                    }
                    description "Helper limit grace period for Graceful Restart";
                } // END of MaxGracePeriod definition.

            } // END of helperPOlicy-container definition.
        } // End of ospfMaster-list
    } // END of ospfMaster-grouping definition.


    grouping ospf-grouping {
        list ospf {
             
            description
                "OSPF attributes for each ospf process id";

            config true;
            key "ospfProcessId";

            
            leaf ospfUpTime  {
                type  cml_data_types:CML_STRING_T {
                    length "0..255";
                }
                config false;
            } // END of ospfUpTime definition.

            leaf ddCountIn  {
                type  cml_data_types:CML_UINT16_T;  
                config false;
            } // END of ddCountIn definition.

            leaf ddCountOut  {
                type  cml_data_types:CML_UINT16_T;  
                config false;
            } // END of ddCountOut definition.

            leaf externalLsaCount  {
                type  cml_data_types:CML_INT32_T;  
                config false;
            } // END of externalLsaCount definition.

            leaf externalLsaChecksum  {
                type  cml_data_types:CML_STRING_T {
                    length "0..255";
                }
                config false;
            } // END of externalLsaChecksum definition.

            leaf opaqueLsaCount  {
                type  cml_data_types:CML_INT32_T;  
                config false;
            } // END of opaqueLsaCount definition.

            leaf opaqueLsaChecksum  {
                type  cml_data_types:CML_STRING_T {
                    length "0..255";
                }
                config false;
            } // END of opaqueLsaChecksum definition.

            leaf nonDefaulExternalLsaCount  {
                type  cml_data_types:CML_INT32_T;  
                config false;
            } // END of nonDefaulExternalLsaCount definition.

            leaf lsdbExceedOverflowInterval  {
                type  cml_data_types:CML_UINT32_T;  
                config false;
            } // END of lsdbExceedOverflowInterval definition.

            leaf lsaOriginateCount  {
                type  cml_data_types:CML_UINT32_T;  
                config false;
            } // END of lsaOriginateCount definition.

            leaf lsaRecievedCount  {
                type  cml_data_types:CML_UINT32_T;  
                config false;
            } // END of lsaRecievedCount definition.

            leaf areaCount  {
                type  cml_data_types:CML_INT32_T;  
                config false;
            } // END of areaCount definition.

            leaf dsteStatus  {
                if-feature feature_list:HAVE_DSTE;
                type  cml_data_types:CML_STRING_T {
                    length "0..255";
                }
                config false;
            } // END of dsteStatus definition.

            leaf ospfPacketSendBuffer  {
                type  cml_data_types:CML_UINT32_T;  
                config false;
            } // END of ospfPacketSendBuffer definition.

            leaf ospfLsaBuffer  {
                type  cml_data_types:CML_UINT32_T;  
                config false;
            } // END of ospfLsaBuffer definition.

            leaf ospfPacketUnusedCount  {
                type  cml_data_types:CML_UINT32_T;  
                config false;
            } // END of ospfPacketUnusedCount definition.

            leaf ospfTotalPacketUnusedCount  {
                type  cml_data_types:CML_UINT32_T;  
                config false;
            } // END of ospfTotalPacketUnusedCount definition.

            leaf ospfStatsUpTime  {
                type  cml_data_types:CML_STRING_T {
                    length "0..255";
                }
                config false;
            } // END of ospfStatsUpTime definition.

            leaf ospfRouterIdChanges  {
                type  cml_data_types:CML_UINT32_T;  
                config false;
            } // END of ospfRouterIdChanges definition.

            leaf ospfDRElectionCounter  {
                type  cml_data_types:CML_UINT32_T;  
                config false;
            } // END of ospfDRElectionCounter definition.

            leaf ospfOlderLsaReceived  {
                type  cml_data_types:CML_UINT32_T;  
                config false;
            } // END of ospfOlderLsaReceived definition.

            leaf ospfNbrStateChangeCount  {
                type  cml_data_types:CML_UINT32_T;  
                config false;
            } // END of ospfNbrStateChangeCount definition.

            leaf ospfNbrExpirationCount  {
                type  cml_data_types:CML_UINT32_T;  
                config false;
            } // END of ospfNbrExpirationCount definition.

            leaf ospfNbrBadLsReqsCount  {
                type  cml_data_types:CML_UINT32_T;  
                config false;
            } // END of ospfNbrBadLsReqsCount definition.

            leaf ospfNbrSeqNumMismatchCount  {
                type  cml_data_types:CML_UINT32_T;  
                config false;
            } // END of ospfNbrSeqNumMismatchCount definition.

            leaf ospfSpfFull  {
                type  cml_data_types:CML_UINT32_T;  
                config false;
            } // END of ospfSpfFull definition.

            leaf ospfSpfSummary  {
                type  cml_data_types:CML_UINT32_T;  
                config false;
            } // END of ospfSpfSummary definition.

            leaf ospfSpfExternal  {
                type  cml_data_types:CML_UINT32_T;  
                config false;
            } // END of ospfSpfExternal definition.

            leaf defaultRouterId  {
                type  cml_data_types:CML_STRING_T {
                    length "0..255";
                }
                config false;
            } // END of defaultRouterId definition.

            leaf vrId  {
                type  cml_data_types:CML_UINT32_T;  
                default "0";
            } // END of vrId definition.

            leaf ospfProcessId  {
                type  cml_data_types:CML_UINT16_T {
                     range "0..65535";
                }
            } // END of ospfProcessId definition.

            leaf vrfName  {
                type  cml_data_types:CML_STRING_T {
                    length "0..255";
                }
            } // END of vrfName definition.

            leaf routerId  {
                type  cml_data_types:CML_STRING_T {
                    length "0..255";
                }
                default "NULL";
            } // END of routerId definition.

            leaf floodReduction  {
                type  cml_data_types:CML_BOOL_T;  
            } // END of floodReduction definition.

            leaf isCompitableRfc1583  {
                type  cml_data_types:CML_BOOL_T;  
            } // END of isCompitableRfc1583 definition.

            leaf isdbSummary  {
                type  cml_data_types:CML_BOOL_T;  
            } // END of isdbSummary definition.

            leaf bfdEnabled  {
                if-feature feature_list:HAVE_BFD;
                type  cml_data_types:CML_BOOL_T;  
            } // END of bfdEnabled definition.

            leaf cspfEnabled  {
                if-feature feature_list:HAVE_OSPF_CSPF;
                type  cml_data_types:CML_BOOL_T;  
            } // END of cspfEnabled definition.

            leaf cspfTieBreak  {
                if-feature feature_list:HAVE_OSPF_CSPF;
                type  cml_data_types:CML_OSPF6_CSPF_TYPE_T;  
            } // END of cspfTieBreak definition.

            leaf cspfDefRetryInterval  {
                if-feature feature_list:HAVE_OSPF_CSPF;
                type  cml_data_types:CML_UINT16_T {
                     range "1..3600";
                }
            } // END of cspfDefRetryInterval definition.

            leaf cspfBetterProtection  {
                if-feature feature_list:HAVE_OSPF_CSPF;
                if-feature feature_list:HAVE_GMPLS;
                type  cml_data_types:CML_BOOL_T;  
            } // END of cspfBetterProtection definition.

            leaf vrfLiteEnable  {
                if-feature feature_list:HAVE_VRF_OSPF;
                type  cml_data_types:CML_BOOL_T;  
            } // END of vrfLiteEnable definition.

            leaf logAdjacencyDebugType  {
                type  cml_data_types:CML_STRING_T {
                    length "0..255";
                }
            } // END of logAdjacencyDebugType definition.

            leaf shutDown  {
                type  cml_data_types:CML_BOOL_T;  
            } // END of shutDown definition.

            leaf areaBorderType  {
                type  cml_data_types:CML_OSPF_ABR_TYPE_T;  
            } // END of areaBorderType definition.

            leaf spfMinDelay  {
                type  cml_data_types:CML_UINT32_T {
                     range "0..2147483647";
                }
                default "500";
            } // END of spfMinDelay definition.

            leaf spfMaxDelay  {
                type  cml_data_types:CML_UINT32_T {
                     range "0..2147483647";
                }
                default "5000";
            } // END of spfMaxDelay definition.

            leaf throttleTimersStartDelay  {
                type  cml_data_types:CML_UINT32_T {
                     range "0..600000";
                }
                default "0";
            } // END of throttleTimersStartDelay definition.

            leaf throttleMinInterval  {
                type  cml_data_types:CML_UINT32_T {
                     range "1..600000";
                }
                default "5000";
            } // END of throttleMinInterval definition.

            leaf throttleTimersMaxDelay  {
                type  cml_data_types:CML_UINT32_T {
                     range "1..600000";
                }
                default "5000";
            } // END of throttleTimersMaxDelay definition.

            leaf lsaMinArrival  {
                type  cml_data_types:CML_UINT32_T {
                     range "0..600000";
                }
                default "1";
            } // END of lsaMinArrival definition.

            leaf referenceBandwidth  {
                type  cml_data_types:CML_INT32_T {
                     range "1..4294967";
                }
                default "100000";
            } // END of referenceBandwidth definition.

            leaf maxDBDescriptor  {
                type  cml_data_types:CML_UINT16_T {
                     range "1..65535";
                }
                default "5000";
            } // END of maxDBDescriptor definition.

            leaf restartMethod  {
                if-feature feature_list:HAVE_RESTART;
                type  cml_data_types:CML_BOOL_T;  
            } // END of restartMethod definition.

            leaf restartMethodlls  {
                if-feature feature_list:HAVE_RESTART;
                type  cml_data_types:CML_BOOL_T;  
            } // END of restartMethodlls definition.

            leaf isCapabilityOpaque  {
                if-feature feature_list:HAVE_OPAQUE_LSA;
                type  cml_data_types:CML_BOOL_T;  
            } // END of isCapabilityOpaque definition.

            leaf isCapabilityTe  {
                if-feature feature_list:HAVE_OSPF_TE;
                type  cml_data_types:CML_OSPF_CAPABILITY_TE_T;  
            } // END of isCapabilityTe definition.

            leaf metricValue  {
                type  cml_data_types:CML_UINT32_T {
                     range "1..16777214";
                }
                default "2";
            } // END of metricValue definition.

            leaf lsdbExternalLimit  {
                if-feature feature_list:HAVE_OSPF_DB_OVERFLOW;
                type  cml_data_types:CML_UINT32_T {
                     range "0..2147483647";
                }
                default "100000";
            } // END of lsdbExternalLimit definition.

            leaf exitOverflowInterval  {
                if-feature feature_list:HAVE_OSPF_DB_OVERFLOW;
                type  cml_data_types:CML_UINT32_T {
                     range "0..65535";
                }
                default "0";
            } // END of exitOverflowInterval definition.

            leaf lsdbLimit  {
                type  cml_data_types:CML_UINT32_T {
                     range "0..4294967294";
                }
                default "0";
            } // END of lsdbLimit definition.

            leaf lsdbLimitType  {
                type  cml_data_types:CML_OSPF_ACTION_TYPE_T;  
                default "hard";
            } // END of lsdbLimitType definition.

            leaf maxAreaLimit  {
                type  cml_data_types:CML_UINT32_T {
                     range "1..4294967294";
                }
            } // END of maxAreaLimit definition.

            leaf ospfmaxUnusePackets  {
                type  cml_data_types:CML_UINT32_T {
                     range "0..65535";
                }
                default "200";
            } // END of ospfmaxUnusePackets definition.

            leaf lsaunuseMax  {
                type  cml_data_types:CML_UINT16_T {
                     range "0..65535";
                }
            } // END of lsaunuseMax definition.

            leaf refreshTimer  {
                type  cml_data_types:CML_UINT32_T {
                     range "10..1800";
                }
                default "10";
            } // END of refreshTimer definition.

            leaf isFrrSet  {
                if-feature feature_list:HAVE_OSPF_LFA;
                type  cml_data_types:CML_BOOL_T;  
            } // END of isFrrSet definition.

            leaf adminDistance  {
                type  cml_data_types:CML_INT32_T {
                     range "1..255";
                }
            } // END of adminDistance definition.


            list passiveInterface {
                 
                description
                    "OSPF Passive Interface list";

                config true;
                key "passiveIfName";

                
                leaf passiveIfName  {
                    type  cml_data_types:CML_STRING_T {
                        length "0..255";
                    }
                } // END of passiveIfName definition.

                leaf-list passiveIfAddr  {
                    type  cml_data_types:CML_IPV4_ADDR_T;  
                } // END of passiveIfAddr definition.

            } // End of passiveInterface-list

            list default-information {
                 
                description
                    "Default external route Information";

                config true;
                key "defaultInformationOriginate";

                
                leaf defaultInformationOriginate  {
                    type  cml_data_types:CML_BOOL_T;  
                } // END of defaultInformationOriginate definition.

                container default-information-always {
                                        config true;

                    description
                        "Default external route Information Always";

                    leaf metric  {
                        type  cml_data_types:CML_UINT32_T {
                             range "0..16777214";
                        }
                    } // END of metric definition.

                    leaf metricType  {
                        type  cml_data_types:CML_OSPF_METRIC_TYPE_T;  
                    } // END of metricType definition.

                    leaf routeMap  {
                        type  cml_data_types:CML_STRING_T {
                            length "0..255";
                        }
                    } // END of routeMap definition.

                    leaf alwaysSet  {
                        type  cml_data_types:CML_BOOL_T;  
                        default true;
                    } // END of alwaysSet definition.

                } // END of default-information-always-container definition.
            } // End of default-information-list

            list frr_pref {
                                 if-feature feature_list:HAVE_OSPF_LFA;

                description
                    "Keeps user preferences, lower index in the array is higher priority";

                config true;
                key "frrPrefIndex";

                
                leaf frrPrefIndex  {
                    type  cml_data_types:CML_UINT32_T {
                         range "1..10";
                    }
                } // END of frrPrefIndex definition.

                leaf frrPrefVal  {
                    mandatory true;
                    if-feature feature_list:HAVE_OSPF_LFA;
                    type  cml_data_types:CML_OSPF_FRR_TIE_BREAK_VAL_T;  
                } // END of frrPrefVal definition.

            } // End of frr_pref-list

            list srcDistance {
                 
                description
                    "srcDistance";

                config true;
                key "distprefix";

                
                leaf distprefix  {
                    type  cml_data_types:CML_IPV4_ADDR_PREFIX_T;  
                } // END of distprefix definition.

                leaf aclDistance  {
                    type  cml_data_types:CML_UINT8_T {
                         range "1..255";
                    }
                } // END of aclDistance definition.

                leaf accessListName  {
                    mandatory true;
                    type  cml_data_types:CML_STRING_T {
                        length "0..255";
                    }
                } // END of accessListName definition.

            } // End of srcDistance-list

            list distributeList {
                                 if-feature feature_list:HAVE_ACL;

                description
                    "Distribute list for OSPF Protocol";

                config true;
                key "distAccessListName";

                
                leaf distAccessListName  {
                    type  cml_data_types:CML_STRING_T {
                        length "0..255";
                    }
                } // END of distAccessListName definition.

                leaf ospfDistIn  {
                    type  cml_data_types:CML_BOOL_T;  
                } // END of ospfDistIn definition.


                list distributeListProtocol {
                     
                    description
                        "Distribute list for OSPF Protocol";

                    config true;
                    key "ospfdistProtocol";

                    
                    leaf ospfdistProtocol  {
                        type  cml_data_types:CML_OSPF_DIST_ROUTE_SOURCE_TYPE_T;  
                    } // END of ospfdistProtocol definition.

                } // End of distributeListProtocol-list

                list distributeListOspf {
                     
                    description
                        "Distribute list for OSPF Protocol";

                    config true;
                    key "ospfdistOspfProtocol";

                    
                    leaf ospfdistOspfProtocol  {
                        type  cml_data_types:CML_INT32_T {
                             range "1..65535";
                        }
                    } // END of ospfdistOspfProtocol definition.

                } // End of distributeListOspf-list
            } // End of distributeList-list

            list redistributeProc {
                 
                description
                    "reditribute routes internally to other ospf process id";

                config true;
                key "secondaryOspfProcessId";

                
                leaf secondaryOspfProcessId  {
                    type  cml_data_types:CML_INT32_T {
                         range "1..65535";
                    }
                } // END of secondaryOspfProcessId definition.

                leaf redistOspfMetricType  {
                    type  cml_data_types:CML_OSPF_METRIC_TYPE_T;  
                    default "2";
                } // END of redistOspfMetricType definition.

                leaf redistOspfMetricValue  {
                    type  cml_data_types:CML_INT32_T {
                         range "0..16777214";
                    }
                    default "0";
                } // END of redistOspfMetricValue definition.

                leaf redistOspfTag  {
                    type  cml_data_types:CML_UINT32_T {
                         range "0..4294967295";
                    }
                    default "0";
                } // END of redistOspfTag definition.

                leaf ospfrouteMapName  {
                    type  cml_data_types:CML_STRING_T {
                        length "0..255";
                    }
                    default "";
                } // END of ospfrouteMapName definition.

            } // End of redistributeProc-list

            list redistribute {
                 
                description
                    "redistribute routes to external process (bgp/static etc.)";

                config true;
                key "routeSourceType";

                
                leaf routeSourceType  {
                    type  cml_data_types:CML_OSPF_ROUTE_SOURCE_TYPE_T;  
                } // END of routeSourceType definition.

                leaf redistMetricType  {
                    type  cml_data_types:CML_OSPF_METRIC_TYPE_T;  
                } // END of redistMetricType definition.

                leaf redistMetricValue  {
                    type  cml_data_types:CML_INT32_T {
                         range "0..16777214";
                    }
                } // END of redistMetricValue definition.

                leaf redistTag  {
                    type  cml_data_types:CML_UINT32_T {
                         range "0..4294967295";
                    }
                } // END of redistTag definition.

                leaf routeMapName  {
                    type  cml_data_types:CML_STRING_T {
                        length "0..255";
                    }
                    default "";
                } // END of routeMapName definition.

            } // End of redistribute-list

            list neighbor {
                 
                description
                    "ospf neighbour";

                config true;
                key "neighborIpAddr";

                
                leaf neighborIpAddr  {
                    type  cml_data_types:CML_IPV4_ADDR_T;  
                } // END of neighborIpAddr definition.

                leaf neighborCost  {
                    type  cml_data_types:CML_UINT16_T {
                         range "1..65535";
                    }
                    default "10";
                } // END of neighborCost definition.

                leaf ospfNbmaNbrStatus  {
                    type  cml_data_types:CML_OSPF_NBMA_ROW_STATUS;  
                } // END of ospfNbmaNbrStatus definition.

                container nbrOptions {
                                        config true;

                    description
                        "nbrOptions";

                    leaf neighborStaticPriority  {
                        type  cml_data_types:CML_UINT8_T {
                             range "0..255";
                        }
                        default "0";
                    } // END of neighborStaticPriority definition.

                    leaf neighborPollInterval  {
                        type  cml_data_types:CML_INT32_T {
                             range "1..2147483647";
                        }
                        default "120";
                    } // END of neighborPollInterval definition.

                } // END of nbrOptions-container definition.
            } // End of neighbor-list

            list summary {
                 
                description
                    "ospf summary";

                config true;
                key "summaryAddr";

                
                leaf summaryAddr  {
                    type  cml_data_types:CML_IPV4_PREFIX_T;  
                } // END of summaryAddr definition.

                leaf summaryAddressNotAdvertise  {
                    type  cml_data_types:CML_BOOL_T;  
                } // END of summaryAddressNotAdvertise definition.

                leaf addressTag  {
                    type  cml_data_types:CML_UINT32_T {
                         range "0..4294967295";
                    }
                } // END of addressTag definition.

            } // End of summary-list

            list area {
                 
                description
                    "ospf area";

                config true;
                key "areaId";

                
                leaf AreaInterfaceCount  {
                    type  cml_data_types:CML_INT32_T;  
                    config false;
                } // END of AreaInterfaceCount definition.

                leaf AreaNeighborCount  {
                    type  cml_data_types:CML_INT32_T;  
                    config false;
                } // END of AreaNeighborCount definition.

                leaf spfLastExexTime  {
                    type  cml_data_types:CML_STRING_T {
                        length "0..255";
                    }
                    config false;
                } // END of spfLastExexTime definition.

                leaf spfExecCount  {
                    type  cml_data_types:CML_UINT32_T;  
                    config false;
                } // END of spfExecCount definition.

                leaf areaLsaCount  {
                    type  cml_data_types:CML_INT32_T;  
                    config false;
                } // END of areaLsaCount definition.

                leaf areaLsaChecksum  {
                    type  cml_data_types:CML_STRING_T {
                        length "0..255";
                    }
                    config false;
                } // END of areaLsaChecksum definition.

                leaf nssaTranslatorCount  {
                    if-feature feature_list:HAVE_NSSA;
                    type  cml_data_types:CML_INT32_T;  
                    config false;
                } // END of nssaTranslatorCount definition.

                leaf nssaTranslatorState  {
                    if-feature feature_list:HAVE_NSSA;
                    type  cml_data_types:CML_STRING_T {
                        length "0..255";
                    }
                    config false;
                } // END of nssaTranslatorState definition.

                leaf areaId  {
                    type  cml_data_types:CML_STRING_T {
                        length "0..255";
                    }
                } // END of areaId definition.

                leaf areaAuthType  {
                    type  cml_data_types:CML_OSPF_AREA_AUTHENTICATION_TYPE_T;  
                } // END of areaAuthType definition.

                leaf areaShortcutType  {
                    type  cml_data_types:CML_OSPF_AREA_SHORTCUT_TYPE_T;  
                    default "default";
                } // END of areaShortcutType definition.

                leaf exportListName  {
                    if-feature feature_list:HAVE_ACL;
                    type  cml_data_types:CML_STRING_T {
                        length "0..255";
                    }
                    default "NULL";
                } // END of exportListName definition.

                leaf importListName  {
                    if-feature feature_list:HAVE_ACL;
                    type  cml_data_types:CML_STRING_T {
                        length "0..255";
                    }
                    default "NULL";
                } // END of importListName definition.


                list filterPrefixList {
                                         if-feature feature_list:HAVE_ACL;

                    description
                        "filterPrefixList";

                    config true;
                    key "prefixType";

                    
                    leaf prefixName  {
                        mandatory true;
                        type  cml_data_types:CML_STRING_T {
                            length "0..255";
                        }
                    } // END of prefixName definition.

                    leaf prefixType  {
                        type  cml_data_types:CML_OSPF_AREA_FILTER_LIST_PREFIX_T;  
                    } // END of prefixType definition.

                } // End of filterPrefixList-list

                list filterAccessList {
                                         if-feature feature_list:HAVE_ACL;

                    description
                        "filterAccessList";

                    config true;
                    key "accessType";

                    
                    leaf accessName  {
                        mandatory true;
                        type  cml_data_types:CML_STRING_T {
                            length "0..255";
                        }
                    } // END of accessName definition.

                    leaf accessType  {
                        type  cml_data_types:CML_OSPF_AREA_FILTER_LIST_PREFIX_T;  
                    } // END of accessType definition.

                } // End of filterAccessList-list

                list hostAddr {
                     
                    description
                        "ospf host entries";

                    config true;
                    key "hostIpAddr";

                    
                    leaf hostIpAddr  {
                        type  cml_data_types:CML_IPV4_ADDR_T;  
                    } // END of hostIpAddr definition.

                    leaf hostEntryCost  {
                        type  cml_data_types:CML_INT32_T {
                             range "0..65535";
                        }
                        default "0";
                    } // END of hostEntryCost definition.

                } // End of hostAddr-list

                list network {
                     
                    description
                        "ospf network";

                    config true;
                    key "networkPrefix";

                    
                    leaf networkPrefix  {
                        type  cml_data_types:CML_IPV4_PREFIX_T;  
                    } // END of networkPrefix definition.

                    leaf networkMask  {
                        type  cml_data_types:CML_INT32_T;  
                    } // END of networkMask definition.

                    leaf InstanceId  {
                        mandatory true;
                        if-feature feature_list:HAVE_OSPF_MULTI_INST;
                        type  cml_data_types:CML_INT16_T {
                             range "0..255";
                        }
                    } // END of InstanceId definition.


                    list ospfInterfaceNeighbor {
                         
                        description
                            "ospfInterfaceNeighbor";

                        config false;
                        key "ospfNbrIfname";

                        
                        leaf ospfNbrIfname  {
                            type  cml_data_types:CML_STRING_T {
                                length "0..255";
                            }
                        } // END of ospfNbrIfname definition.


                        list ospfNeighborRuntime {
                             
                            description
                                "ospfNeighborRuntime";

                            config false;
                            key "ospfNbrRouterId";

                            
                            leaf ospfNbrRouterId  {
                                type  cml_data_types:CML_STRING_T {
                                    length "0..255";
                                }
                            } // END of ospfNbrRouterId definition.

                            leaf ospfNbrOptions  {
                                type  cml_data_types:CML_STRING_T {
                                    length "0..255";
                                }
                            } // END of ospfNbrOptions definition.

                            leaf ospfNeighborState  {
                                type  cml_data_types:CML_STRING_T {
                                    length "0..255";
                                }
                            } // END of ospfNeighborState definition.

                            leaf ospfNbrEvents  {
                                type  cml_data_types:CML_UINT32_T;  
                            } // END of ospfNbrEvents definition.

                            leaf ospfNbrAddressLessIndex  {
                                type  cml_data_types:CML_UINT32_T;  
                            } // END of ospfNbrAddressLessIndex definition.

                            leaf ospfNbrLsRetransQLen  {
                                type  cml_data_types:CML_UINT32_T;  
                            } // END of ospfNbrLsRetransQLen definition.

                            leaf ospfNbmaNbrPermanence  {
                                type  cml_data_types:CML_UINT32_T;  
                            } // END of ospfNbmaNbrPermanence definition.

                            leaf ospfNbrHelloSuppressed  {
                                type  cml_data_types:CML_UINT32_T;  
                            } // END of ospfNbrHelloSuppressed definition.

                            leaf ospfNbrRestartHelperStatus  {
                                if-feature feature_list:HAVE_RESTART;
                                type  cml_data_types:CML_UINT32_T;  
                            } // END of ospfNbrRestartHelperStatus definition.

                            leaf ospfNbrRestartHelperAge  {
                                if-feature feature_list:HAVE_RESTART;
                                type  cml_data_types:CML_UINT32_T;  
                            } // END of ospfNbrRestartHelperAge definition.

                            leaf ospfNbrRestartHelperExitReason  {
                                if-feature feature_list:HAVE_RESTART;
                                type  cml_data_types:CML_UINT32_T;  
                            } // END of ospfNbrRestartHelperExitReason definition.

                            leaf ospfLsDbCount  {
                                type  cml_data_types:CML_UINT32_T;  
                            } // END of ospfLsDbCount definition.

                            leaf ospfLsRequestCount  {
                                type  cml_data_types:CML_UINT32_T;  
                            } // END of ospfLsRequestCount definition.

                            leaf ospfLsRetransmitCount  {
                                type  cml_data_types:CML_UINT32_T;  
                            } // END of ospfLsRetransmitCount definition.

                            leaf llsOptions  {
                                if-feature feature_list:HAVE_RESTART;
                                type  cml_data_types:CML_STRING_T {
                                    length "0..255";
                                }
                            } // END of llsOptions definition.

                            leaf llsExtendedOption  {
                                if-feature feature_list:HAVE_RESTART;
                                type  cml_data_types:CML_STRING_T {
                                    length "0..255";
                                }
                            } // END of llsExtendedOption definition.

                            leaf lastOobResyncTime  {
                                if-feature feature_list:HAVE_RESTART;
                                type  cml_data_types:CML_STRING_T {
                                    length "0..255";
                                }
                            } // END of lastOobResyncTime definition.

                            leaf oobResyncTimeout  {
                                if-feature feature_list:HAVE_RESTART;
                                type  cml_data_types:CML_STRING_T {
                                    length "0..255";
                                }
                            } // END of oobResyncTimeout definition.

                            leaf deadTimerDueTime  {
                                type  cml_data_types:CML_STRING_T {
                                    length "0..255";
                                }
                            } // END of deadTimerDueTime definition.

                            leaf ospfPollTimerDueIn  {
                                type  cml_data_types:CML_STRING_T {
                                    length "0..255";
                                }
                            } // END of ospfPollTimerDueIn definition.

                            leaf ospfNeighborUpTime  {
                                type  cml_data_types:CML_STRING_T {
                                    length "0..255";
                                }
                            } // END of ospfNeighborUpTime definition.

                            leaf ospfCryptSeqNum  {
                                if-feature feature_list:HAVE_MD5;
                                type  cml_data_types:CML_UINT32_T;  
                            } // END of ospfCryptSeqNum definition.

                            leaf ospfDesignatedRouter  {
                                type  cml_data_types:CML_STRING_T {
                                    length "0..255";
                                }
                            } // END of ospfDesignatedRouter definition.

                            leaf ospfBackDesignatedRouter  {
                                type  cml_data_types:CML_STRING_T {
                                    length "0..255";
                                }
                            } // END of ospfBackDesignatedRouter definition.

                        } // End of ospfNeighborRuntime-list
                    } // End of ospfInterfaceNeighbor-list
                } // End of network-list

                list virtLink {
                     
                    description
                        "ospf virtual link";

                    config true;
                    key "peerId";

                    
                    leaf peerId  {
                        type  cml_data_types:CML_IPV4_ADDR_T;  
                    } // END of peerId definition.

                    leaf vlinkAuthType  {
                        type  cml_data_types:CML_OSPF_VLINK_AUTH_TYPE_T;  
                        default "authentication-null";
                    } // END of vlinkAuthType definition.

                    leaf vlinkMsgDigestKeyId  {
                        type  cml_data_types:CML_UINT8_T {
                             range "1..255";
                        }
                    } // END of vlinkMsgDigestKeyId definition.

                    leaf vlinkMsgDigestKey  {
                        type  cml_data_types:CML_STRING_T {
                            length "0..255";
                        }
                        default "";
                    } // END of vlinkMsgDigestKey definition.

                    leaf vlinkAuthKey  {
                        type  cml_data_types:CML_STRING_T {
                            length "0..255";
                        }
                        default "";
                    } // END of vlinkAuthKey definition.

                    leaf vlinkRetransIntvl  {
                        type  cml_data_types:CML_INT32_T {
                             range "1..1800";
                        }
                        default "5";
                    } // END of vlinkRetransIntvl definition.

                    leaf vlinkTransmitDelay  {
                        type  cml_data_types:CML_INT32_T {
                             range "1..3600";
                        }
                        default "1";
                    } // END of vlinkTransmitDelay definition.

                    leaf vlinkHelloInterval  {
                        type  cml_data_types:CML_INT32_T {
                             range "1..65535";
                        }
                        default "10";
                    } // END of vlinkHelloInterval definition.

                    leaf vlinkDeadInterval  {
                        type  cml_data_types:CML_INT32_T {
                             range "1..65535";
                        }
                        default "40";
                    } // END of vlinkDeadInterval definition.

                    leaf vlinkWaitInterval  {
                        type  cml_data_types:CML_INT32_T;  
                        config false;
                        description "wait timer interval";
                    } // END of vlinkWaitInterval definition.

                    leaf vlinkName  {
                        type  cml_data_types:CML_STRING_T {
                            length "0..255";
                        }
                        config false;
                        description "Virtual Link Name";
                    } // END of vlinkName definition.

                    leaf vlinkStatus  {
                        type  cml_data_types:CML_OSPF_VLINK_STATUS_T;  
                        config false;
                        description "Virtual Link Status";
                    } // END of vlinkStatus definition.

                    leaf vlinkInterface  {
                        type  cml_data_types:CML_STRING_T {
                            length "0..255";
                        }
                        config false;
                        description "Virtual Link Interface";
                    } // END of vlinkInterface definition.

                    leaf vlinkLocalAddress  {
                        type  cml_data_types:CML_STRING_T {
                            length "0..255";
                        }
                        config false;
                        description "Virtual Link Local address";
                    } // END of vlinkLocalAddress definition.

                    leaf vlinkRemoteAddress  {
                        type  cml_data_types:CML_STRING_T {
                            length "0..255";
                        }
                        config false;
                        description "Virtual Link Remote address";
                    } // END of vlinkRemoteAddress definition.

                    leaf vlinkHelloDue  {
                        type  cml_data_types:CML_STRING_T {
                            length "0..255";
                        }
                        config false;
                        description "Virtual Link Hello due";
                    } // END of vlinkHelloDue definition.

                    leaf vlinkInterfaceState  {
                        type  cml_data_types:CML_OSPF_VLINK_INTERFACE_STATE_T;  
                        config false;
                        description "Virtual Link Interface State";
                    } // END of vlinkInterfaceState definition.

                    leaf vlinkAdjState  {
                        type  cml_data_types:CML_OSPF_VLINK_ADJ_STATE_T;  
                        config false;
                        description "Virtual Link Adjacency state";
                    } // END of vlinkAdjState definition.

                    container vlinkbfd {
                                                config true;

                        description
                            "Bidirectional Forwarding Detection";

                        leaf vlinkFallOverBfd  {
                            if-feature feature_list:HAVE_BFD;
                            type  cml_data_types:CML_BOOL_T;  
                        } // END of vlinkFallOverBfd definition.

                    } // END of vlinkbfd-container definition.
                } // End of virtLink-list

                list range {
                     
                    description
                        "ospf range";

                    config true;
                    key "rangeId";

                    
                    leaf rangeId  {
                        type  cml_data_types:CML_IPV4_PREFIX_T;  
                    } // END of rangeId definition.

                    leaf rangeAdvertise  {
                        type  cml_data_types:CML_OSPF_AREA_RANGE_ADVERTISE_T;  
                    } // END of rangeAdvertise definition.

                    leaf substituteAddr  {
                        type  cml_data_types:CML_IPV4_PREFIX_T;  
                    } // END of substituteAddr definition.

                    leaf subAddrPrefix  {
                        type  cml_data_types:CML_UINT8_T;  
                    } // END of subAddrPrefix definition.

                } // End of range-list
                container stubNssa {
                                        config true;

                    description
                        "ospf area stub/nssa configuration";

                    leaf isStubArea  {
                        type  cml_data_types:CML_BOOL_T;  
                    } // END of isStubArea definition.

                    leaf isNssaArea  {
                        type  cml_data_types:CML_BOOL_T;  
                    } // END of isNssaArea definition.

                    leaf stubAreaNoSummary  {
                        type  cml_data_types:CML_BOOL_T;  
                    } // END of stubAreaNoSummary definition.

                    leaf nssaStabilityInterval  {
                        type  cml_data_types:CML_INT32_T {
                             range "0..2147483647";
                        }
                        default "40";
                    } // END of nssaStabilityInterval definition.

                    leaf nssaTranslatorRole  {
                        type  cml_data_types:CML_OSPF_TRANSLATOR_ROLE_T;  
                        default "candidate";
                    } // END of nssaTranslatorRole definition.

                    leaf nssaDefaultOriginMetric  {
                        type  cml_data_types:CML_INT32_T {
                             range "0..16777214";
                        }
                        default "0";
                    } // END of nssaDefaultOriginMetric definition.

                    leaf nssaDefaultOriginMetricType  {
                        type  cml_data_types:CML_INT32_T {
                             range "1..2";
                        }
                        default "2";
                    } // END of nssaDefaultOriginMetricType definition.

                    leaf isNssaNoDist  {
                        type  cml_data_types:CML_BOOL_T;  
                    } // END of isNssaNoDist definition.

                    leaf isNssaDefaultOriginate  {
                        type  cml_data_types:CML_BOOL_T;  
                    } // END of isNssaDefaultOriginate definition.

                    leaf nssaAreaNoSummary  {
                        type  cml_data_types:CML_BOOL_T;  
                    } // END of nssaAreaNoSummary definition.

                    leaf areaCost  {
                        type  cml_data_types:CML_UINT32_T {
                             range "0..16777215";
                        }
                        default "1";
                    } // END of areaCost definition.

                    leaf nssarouteMap  {
                        type  cml_data_types:CML_STRING_T {
                            length "0..255";
                        }
                    } // END of nssarouteMap definition.

                } // END of stubNssa-container definition.
            } // End of area-list
            container distance {
                                config true;

                description
                    "Define an administrative distance";

                leaf distanceIntra  {
                    type  cml_data_types:CML_UINT32_T {
                         range "1..255";
                    }
                } // END of distanceIntra definition.

                leaf distanceInter  {
                    type  cml_data_types:CML_UINT32_T {
                         range "1..255";
                    }
                } // END of distanceInter definition.

                leaf distanceExternal  {
                    type  cml_data_types:CML_UINT32_T {
                         range "1..255";
                    }
                } // END of distanceExternal definition.

            } // END of distance-container definition.
            container domain-id {
                                config true;

                description
                    "domainCMLSEPid";

                leaf domainPrimaryAddr  {
                    if-feature feature_list:HAVE_VRF_OSPF;
                    type  cml_data_types:CML_IPV4_ADDR_T;  
                } // END of domainPrimaryAddr definition.

                leaf domainNull  {
                    if-feature feature_list:HAVE_VRF_OSPF;
                    type  cml_data_types:CML_STRING_T {
                        length "0..255";
                    }
                } // END of domainNull definition.

                leaf domainType  {
                    if-feature feature_list:HAVE_VRF_OSPF;
                    type  cml_data_types:CML_OSPF_DOMAIN_TYPE_T;  
                } // END of domainType definition.

                leaf domainHexValue  {
                    if-feature feature_list:HAVE_VRF_OSPF;
                    type  cml_data_types:CML_STRING_T {
                        length "0..255";
                    }
                } // END of domainHexValue definition.

                leaf domainTypeSecondary  {
                    if-feature feature_list:HAVE_VRF_OSPF;
                    type  cml_data_types:CML_BOOL_T;  
                } // END of domainTypeSecondary definition.


                list domainIdSecondary {
                                         if-feature feature_list:HAVE_VRF_OSPF;

                    description
                        "domainIdSecondary";

                    config true;
                    key "domainSecondaryAddr";

                    
                    leaf domainSecondaryAddr  {
                        type  cml_data_types:CML_IPV4_ADDR_T;  
                    } // END of domainSecondaryAddr definition.

                } // End of domainIdSecondary-list
            } // END of domain-id-container definition.
            uses TrafficStats;
        } // End of ospf-list
    } // END of ospf-grouping definition.


    grouping ospfInterface-grouping {
        list ospfInterface {
             
            description
                "OSPF interface related operations";

            config true;
            key "ifName";

            
            leaf ifName  {
                type  cml_data_types:CML_STRING_T {
                    length "0..255";
                }
            } // END of ifName definition.

            leaf ifTEMetric  {
                if-feature feature_list:HAVE_OSPF_TE;
                type  cml_data_types:CML_UINT32_T {
                     range "1..65535";
                }
                default "1";
            } // END of ifTEMetric definition.

            leaf ifBfdEnable  {
                if-feature feature_list:HAVE_BFD;
                type  cml_data_types:CML_OSPF_BFD_STATE;  
            } // END of ifBfdEnable definition.

            leaf ifNetworkType  {
                type  cml_data_types:CML_OSPF_NETWORK_T;  
            } // END of ifNetworkType definition.

            leaf ospfProcess  {
                type  cml_data_types:CML_UINT16_T {
                     range "0..65535";
                }
            } // END of ospfProcess definition.

            leaf multiAreaId  {
                if-feature feature_list:HAVE_BFD;
                type  cml_data_types:CML_STRING_T {
                    length "0..255";
                }
            } // END of multiAreaId definition.

            leaf neighborAddr  {
                type  cml_data_types:CML_IPV4_ADDR_T;  
            } // END of neighborAddr definition.

            leaf ifMtu  {
                type  cml_data_types:CML_UINT16_T {
                     range "576..65535";
                }
                default "576";
            } // END of ifMtu definition.

            leaf ifDisableAll  {
                type  cml_data_types:CML_BOOL_T;  
            } // END of ifDisableAll definition.

            leaf fastRerouteIfSet  {
                type  cml_data_types:CML_BOOL_T;  
            } // END of fastRerouteIfSet definition.

            leaf ifFloodReduction  {
                type  cml_data_types:CML_BOOL_T;  
            } // END of ifFloodReduction definition.

            leaf ifDemandCircuit  {
                if-feature feature_list:HAVE_OSPF_OD;
                if-feature feature_list:HAVE_OSPF_MULTI_INST;
                type  cml_data_types:CML_BOOL_T;  
            } // END of ifDemandCircuit definition.


            list ospfInterfaceAddr {
                 
                description
                    "OSPF interface addr related operations";

                config true;
                key "ipOspfAddr";

                
                leaf ipOspfAddr  {
                    type  cml_data_types:CML_STRING_T {
                        length "0..255";
                    }
                } // END of ipOspfAddr definition.

                leaf ifAuthTypeAddr  {
                    type  cml_data_types:CML_OSPF_AUTH_TYPE_T;  
                    default "simple";
                } // END of ifAuthTypeAddr definition.

                leaf ifAuthKeyAddr  {
                    type  cml_data_types:CML_STRING_T {
                        length "1..8";
                    }
                } // END of ifAuthKeyAddr definition.

                leaf ospfIfAdminStat  {
                    type  cml_data_types:CML_OSPF_IF_STATE;  
                } // END of ospfIfAdminStat definition.

                leaf authKeyEncryptionAddr  {
                    type  cml_data_types:CML_OSPF_MD5_T;  
                } // END of authKeyEncryptionAddr definition.

                leaf ospfIfAreaId  {
                    if-feature feature_list:HAVE_OSPF_MULTI_INST;
                    type  cml_data_types:CML_STRING_T {
                        length "0..255";
                    }
                } // END of ospfIfAreaId definition.

                leaf ifStatus  {
                    if-feature feature_list:HAVE_OSPF_MULTI_INST;
                    type  cml_data_types:CML_OSPF_ROW_STATUS;  
                } // END of ifStatus definition.

                leaf ospfIfMulticastForwarding  {
                    if-feature feature_list:HAVE_OSPF_MULTI_INST;
                    type  cml_data_types:CML_UINT32_T;  
                } // END of ospfIfMulticastForwarding definition.

                leaf ospfIfDemand  {
                    if-feature feature_list:HAVE_OSPF_MULTI_INST;
                    type  cml_data_types:CML_UINT32_T;  
                } // END of ospfIfDemand definition.

                leaf ospfAddressLessIf  {
                    type  cml_data_types:CML_UINT32_T;  
                    config false;
                } // END of ospfAddressLessIf definition.

                leaf ospfIfState  {
                    type  cml_data_types:CML_UINT32_T;  
                    config false;
                } // END of ospfIfState definition.

                leaf ospfIfEvents  {
                    type  cml_data_types:CML_UINT32_T;  
                    config false;
                } // END of ospfIfEvents definition.

                leaf ospfIfLsaCount  {
                    type  cml_data_types:CML_UINT32_T;  
                    config false;
                } // END of ospfIfLsaCount definition.

                leaf ospfIfLsaCksumSum  {
                    type  cml_data_types:CML_UINT32_T;  
                    config false;
                } // END of ospfIfLsaCksumSum definition.

                leaf ospfIfDesignatedRouter  {
                    type  cml_data_types:CML_STRING_T {
                        length "0..255";
                    }
                    config false;
                } // END of ospfIfDesignatedRouter definition.

                leaf ospfIfBackupDesignatedRouter  {
                    type  cml_data_types:CML_STRING_T {
                        length "0..255";
                    }
                    config false;
                } // END of ospfIfBackupDesignatedRouter definition.

                leaf ospfIfDesignatedRouterId  {
                    type  cml_data_types:CML_STRING_T {
                        length "0..255";
                    }
                    config false;
                } // END of ospfIfDesignatedRouterId definition.

                leaf ospfIfBackupDesignatedRouterId  {
                    type  cml_data_types:CML_STRING_T {
                        length "0..255";
                    }
                    config false;
                } // END of ospfIfBackupDesignatedRouterId definition.

                leaf ifPriorityAddr  {
                    type  cml_data_types:CML_UINT8_T {
                         range "0..255";
                    }
                    default "1";
                } // END of ifPriorityAddr definition.

                leaf ifCostAddr  {
                    type  cml_data_types:CML_UINT32_T {
                         range "1..65535";
                    }
                    default "10";
                } // END of ifCostAddr definition.

                leaf ifDeadIntervalAddr  {
                    type  cml_data_types:CML_UINT32_T {
                         range "1..65535";
                    }
                    default "40";
                } // END of ifDeadIntervalAddr definition.

                leaf ifHelloIntervalAddr  {
                    type  cml_data_types:CML_UINT32_T {
                         range "1..65535";
                    }
                    default "10";
                } // END of ifHelloIntervalAddr definition.

                leaf ifRetransmitIntervalAddr  {
                    type  cml_data_types:CML_UINT32_T {
                         range "1..65535";
                    }
                    default "5";
                } // END of ifRetransmitIntervalAddr definition.

                leaf ifTransmitDelayAddr  {
                    type  cml_data_types:CML_UINT32_T {
                         range "1..3600";
                    }
                    default "1";
                } // END of ifTransmitDelayAddr definition.

                leaf ifDatabaseFilterAddr  {
                    type  cml_data_types:CML_BOOL_T;  
                } // END of ifDatabaseFilterAddr definition.

                leaf isMtuIgnoreAddr  {
                    type  cml_data_types:CML_BOOL_T;  
                } // END of isMtuIgnoreAddr definition.

                leaf ifResyncTimeoutAddr  {
                    type  cml_data_types:CML_UINT32_T {
                         range "1..65535";
                    }
                    default "40";
                } // END of ifResyncTimeoutAddr definition.


                list ospfInterfaceMessageDigestKey {
                     
                    description
                        "OSPF message-digest-key related operations";

                    config true;
                    key "msgDigestKeyIdAddr";

                    
                    leaf msgDigestKeyIdAddr  {
                        type  cml_data_types:CML_UINT32_T {
                             range "1..255";
                        }
                    } // END of msgDigestKeyIdAddr definition.

                    leaf msgDigestKeyEncryptionAddr  {
                        mandatory true;
                        type  cml_data_types:CML_OSPF_MD5_T;  
                    } // END of msgDigestKeyEncryptionAddr definition.

                    leaf msgifAuthKeyAddr  {
                        mandatory true;
                        type  cml_data_types:CML_STRING_T {
                            length "1..16";
                        }
                    } // END of msgifAuthKeyAddr definition.

                } // End of ospfInterfaceMessageDigestKey-list
            } // End of ospfInterfaceAddr-list
            uses TrafficStats;
        } // End of ospfInterface-list
    } // END of ospfInterface-grouping definition.


    grouping teLinkOspf-grouping {
        list teLinkOspf {
                         if-feature feature_list:HAVE_GMPLS;
            if-feature feature_list:HAVE_OSPF_TE;

            description
                "teLinkOspf";

            config true;
            key "teName";

            
            leaf teName  {
                type  cml_data_types:CML_STRING_T {
                    length "0..255";
                }
            } // END of teName definition.

            leaf teLinkOspfInstance  {
                type  cml_data_types:CML_UINT16_T {
                     range "0..65535";
                }
            } // END of teLinkOspfInstance definition.

            leaf teLinkAreaId  {
                type  cml_data_types:CML_STRING_T {
                    length "0..255";
                }
            } // END of teLinkAreaId definition.

            leaf teLinkTEMetric  {
                if-feature feature_list:HAVE_OSPF_TE;
                if-feature feature_list:HAVE_GMPLS;
                type  cml_data_types:CML_UINT32_T {
                     range "1..65535";
                }
                default "1";
            } // END of teLinkTEMetric definition.

            leaf telinkLocalEnable  {
                if-feature feature_list:HAVE_OSPF_TE;
                if-feature feature_list:HAVE_GMPLS;
                type  cml_data_types:CML_BOOL_T;  
            } // END of telinkLocalEnable definition.

        } // End of teLinkOspf-list
    } // END of teLinkOspf-grouping definition.
    grouping TrafficStats {
                leaf trafficTimeStamp  {
            type  cml_data_types:CML_STRING_T {
                length "0..255";
            }
            config false;
        } // END of trafficTimeStamp definition.

        leaf totalStatsIn  {
            type  cml_data_types:CML_INT32_T;  
            config false;
        } // END of totalStatsIn definition.

        leaf totalStatsOut  {
            type  cml_data_types:CML_INT32_T;  
            config false;
        } // END of totalStatsOut definition.

        leaf errorsDropIn  {
            type  cml_data_types:CML_INT32_T;  
            config false;
        } // END of errorsDropIn definition.

        leaf errorsDropOut  {
            type  cml_data_types:CML_INT32_T;  
            config false;
        } // END of errorsDropOut definition.

        leaf errorsHellosIn  {
            type  cml_data_types:CML_INT32_T;  
            config false;
        } // END of errorsHellosIn definition.

        leaf dbdsIn  {
            type  cml_data_types:CML_INT32_T;  
            config false;
        } // END of dbdsIn definition.

        leaf lsreqIn  {
            type  cml_data_types:CML_INT32_T;  
            config false;
        } // END of lsreqIn definition.

        leaf lsuIn  {
            type  cml_data_types:CML_INT32_T;  
            config false;
        } // END of lsuIn definition.

        leaf lsacksIn  {
            type  cml_data_types:CML_INT32_T;  
            config false;
        } // END of lsacksIn definition.

        leaf unknownIn  {
            type  cml_data_types:CML_INT32_T;  
            config false;
        } // END of unknownIn definition.

        leaf unknownOut  {
            type  cml_data_types:CML_INT32_T;  
            config false;
        } // END of unknownOut definition.

        leaf badVersion  {
            type  cml_data_types:CML_INT32_T;  
            config false;
        } // END of badVersion definition.

        leaf badCrc  {
            type  cml_data_types:CML_INT32_T;  
            config false;
        } // END of badCrc definition.

        leaf invalidSrc  {
            type  cml_data_types:CML_INT32_T;  
            config false;
        } // END of invalidSrc definition.

        leaf invalidDSt  {
            type  cml_data_types:CML_INT32_T;  
            config false;
        } // END of invalidDSt definition.

        leaf noNbr  {
            type  cml_data_types:CML_INT32_T;  
            config false;
        } // END of noNbr definition.

        leaf passive  {
            type  cml_data_types:CML_INT32_T;  
            config false;
        } // END of passive definition.

        leaf wrongArea  {
            type  cml_data_types:CML_INT32_T;  
            config false;
        } // END of wrongArea definition.

        leaf pktLength  {
            type  cml_data_types:CML_INT32_T;  
            config false;
        } // END of pktLength definition.

        leaf badAuth  {
            type  cml_data_types:CML_INT32_T;  
            config false;
        } // END of badAuth definition.

        leaf statsHelloIn  {
            type  cml_data_types:CML_INT32_T;  
            config false;
        } // END of statsHelloIn definition.

        leaf statsDbDescIn  {
            type  cml_data_types:CML_INT32_T;  
            config false;
        } // END of statsDbDescIn definition.

        leaf statsLsReqIn  {
            type  cml_data_types:CML_INT32_T;  
            config false;
        } // END of statsLsReqIn definition.

        leaf statsLsUpdIn  {
            type  cml_data_types:CML_INT32_T;  
            config false;
        } // END of statsLsUpdIn definition.

        leaf statsLsAckIn  {
            type  cml_data_types:CML_INT32_T;  
            config false;
        } // END of statsLsAckIn definition.

        leaf statsHelloOut  {
            type  cml_data_types:CML_INT32_T;  
            config false;
        } // END of statsHelloOut definition.

        leaf statsDbDescOut  {
            type  cml_data_types:CML_INT32_T;  
            config false;
        } // END of statsDbDescOut definition.

        leaf statsLsReqOut  {
            type  cml_data_types:CML_INT32_T;  
            config false;
        } // END of statsLsReqOut definition.

        leaf statsLsUpdOut  {
            type  cml_data_types:CML_INT32_T;  
            config false;
        } // END of statsLsUpdOut definition.

        leaf statsLsAckOut  {
            type  cml_data_types:CML_INT32_T;  
            config false;
        } // END of statsLsAckOut definition.

    } // END of TrafficStats definition.


}
