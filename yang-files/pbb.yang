/*
* Copyright (C) 2016 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : pbb.yang
*
*/

submodule pbb {

    belongs-to  ZebOS { prefix ZebOS; }
    include vlan;
    include bridge;
    include interface;


    import cml_data_types {
        prefix cml_data_types;
    }

    import feature_list {
        prefix feature_list;
    }

    description
        "provider back bone";


    revision "2016-10-14" {
        description "Revisied on 2016-10-14.";
    }



    grouping bebBridge-grouping {
        list bebBridge {
             
            description
                "bebBridge";

            config true;
            key "vrId";

            
            leaf vrId  {
                type  cml_data_types:CML_UINT32_T;  
            } // END of vrId definition.

            leaf bridgeId  {
                type  cml_data_types:CML_BRIDGE_BACKBONE_T;  
            } // END of bridgeId definition.


            list nsmMsgVlan {
                 
                description
                    "nsmMsgVlan";

                config true;
                key "vlanId";

                
                leaf vlanInstOper  {
                    type  cml_data_types:CML_VLAN_OPT_TYPE_T;  
                } // END of vlanInstOper definition.

                leaf vlanId  {
                    type  cml_data_types:CML_UINT32_T {
                         range "2..4094";
                    }
                } // END of vlanId definition.

                leaf bridgeId  {
                    type  cml_data_types:CML_BRIDGE_BACKBONE_T;  
                } // END of bridgeId definition.

                leaf cindex  {
                    type  cml_data_types:CML_UINT16_T;  
                    config false;
                } // END of cindex definition.

                leaf flags  {
                    type  cml_data_types:CML_UINT16_T;  
                    config false;
                } // END of flags definition.

                leaf ifName  {
                    type  cml_data_types:CML_STRING_T {
                        length "0..255";
                    }
                    config false;
                } // END of ifName definition.

                leaf brInstance  {
                    type  cml_data_types:CML_UINT16_T;  
                    config false;
                } // END of brInstance definition.

            } // End of nsmMsgVlan-list

            list nsmMsgVlanRange {
                 
                description
                    "nsmMsgVlanRange";

                config true;
                key "vlanStart";

                
                leaf vlanInstOper  {
                    type  cml_data_types:CML_VLAN_OPT_TYPE_T;  
                } // END of vlanInstOper definition.

                leaf vlanStart  {
                    type  cml_data_types:CML_UINT16_T {
                         range "2..4094";
                    }
                } // END of vlanStart definition.

                leaf vlanEnd  {
                    type  cml_data_types:CML_UINT16_T {
                         range "2..4094";
                    }
                } // END of vlanEnd definition.

                leaf bridgeId  {
                    type  cml_data_types:CML_BRIDGE_BACKBONE_T;  
                } // END of bridgeId definition.

            } // End of nsmMsgVlanRange-list

            list pbbTeInstEntry {
                 
                description
                    "pbbTeInstEntry";

                config true;
                key "teSid";

                
                leaf teSid  {
                    type  cml_data_types:CML_UINT32_T;  
                } // END of teSid definition.

                leaf teTrunkName  {
                    type  cml_data_types:CML_STRING_T {
                        length "0..255";
                    }
                    default "";
                } // END of teTrunkName definition.

                leaf tesiState  {
                    type  cml_data_types:CML_STRING_T {
                        length "0..255";
                    }
                    config false;
                } // END of tesiState definition.

                leaf tesiRefCount  {
                    type  cml_data_types:CML_STRING_T {
                        length "0..255";
                    }
                    config false;
                } // END of tesiRefCount definition.

                leaf currentEspIndex  {
                    type  cml_data_types:CML_UINT32_T;  
                    config false;
                } // END of currentEspIndex definition.

                leaf storageType  {
                    type  cml_data_types:CML_UINT8_T;  
                    config false;
                } // END of storageType definition.

                leaf pbbRowStatus  {
                    type  cml_data_types:CML_UINT8_T;  
                    config false;
                } // END of pbbRowStatus definition.

                leaf tesiMode  {
                    type  cml_data_types:CML_TESI_MODE_T;  
                } // END of tesiMode definition.

                leaf tesiType  {
                    type  cml_data_types:CML_TESI_TYPE_T;  
                } // END of tesiType definition.


                list cbpInterface {
                                         if-feature feature_list:HAVE_I_BEB;

                    description
                        "cbpInterface";

                    config true;
                    key "cbpIfp";

                    
                    leaf cbpIfp  {
                        type  cml_data_types:CML_STRING_T {
                            length "0..255";
                        }
                    } // END of cbpIfp definition.

                } // End of cbpInterface-list
                container nsmMsgPbbEspPnp {
                    if-feature feature_list:HAVE_I_BEB;
                                        config true;

                    description
                        "nsmMsgPbbEspPnp";

                    leaf espPnpTesid  {
                        type  cml_data_types:CML_UINT32_T;  
                        config false;
                    } // END of espPnpTesid definition.

                    leaf pnpAddDel  {
                        type  cml_data_types:CML_PNPADDDEL_T;  
                    } // END of pnpAddDel definition.

                    leaf pnpIfindex  {
                        type  cml_data_types:CML_STRING_T {
                            length "0..255";
                        }
                    } // END of pnpIfindex definition.

                    leaf cbpIfindex  {
                        type  cml_data_types:CML_UINT32_T;  
                        config false;
                    } // END of cbpIfindex definition.

                } // END of nsmMsgPbbEspPnp-container definition.
            } // End of pbbTeInstEntry-list

            list bebVlanPort {
                 
                description
                    "bebVlanPort";

                config true;
                key "pvid";

                
                leaf ifName  {
                    mandatory true;
                    type  cml_data_types:CML_STRING_T {
                        length "0..255";
                    }
                } // END of ifName definition.

                leaf pvid  {
                    type  cml_data_types:CML_UINT16_T {
                         range "2..4094";
                    }
                } // END of pvid definition.

                leaf mode  {
                    type  cml_data_types:CML_NSMVLANPORT_MODE_T;  
                } // END of mode definition.

                leaf subMode  {
                    type  cml_data_types:CML_UINT16_T;  
                    config false;
                } // END of subMode definition.

                leaf pvlanMode  {
                    type  cml_data_types:CML_UINT16_T;  
                    config false;
                } // END of pvlanMode definition.

                leaf pvlanConfigured  {
                    type  cml_data_types:CML_BOOL_T;  
                    config false;
                } // END of pvlanConfigured definition.

                leaf defaultVlanMode  {
                    type  cml_data_types:CML_BOOL_T;  
                    config false;
                } // END of defaultVlanMode definition.

                leaf vlanStacking  {
                    type  cml_data_types:CML_STRING_T {
                        length "0..255";
                    }
                    config false;
                } // END of vlanStacking definition.

                leaf stackMode  {
                    type  cml_data_types:CML_UINT16_T;  
                    config false;
                } // END of stackMode definition.

                leaf tagEthtype  {
                    type  cml_data_types:CML_UINT16_T;  
                    config false;
                } // END of tagEthtype definition.

                leaf flags  {
                    type  cml_data_types:CML_STRING_T {
                        length "0..255";
                    }
                    config false;
                } // END of flags definition.

                leaf config  {
                    type  cml_data_types:CML_STRING_T {
                        length "0..255";
                    }
                    config false;
                } // END of config definition.

                leaf portConfig  {
                    type  cml_data_types:CML_UINT16_T;  
                    config false;
                } // END of portConfig definition.

                leaf defaultUserPriority  {
                    type  cml_data_types:CML_INT32_T;  
                    config false;
                } // END of defaultUserPriority definition.

                leaf uniDefaultEvc  {
                    type  cml_data_types:CML_INT16_T;  
                    config false;
                } // END of uniDefaultEvc definition.

            } // End of bebVlanPort-list

            list svlanId {
                 
                description
                    "svlanId";

                config true;
                key "ifName";

                
                leaf ifName  {
                    type  cml_data_types:CML_STRING_T {
                        length "0..255";
                    }
                } // END of ifName definition.

                leaf svlanId  {
                    type  cml_data_types:CML_INT16_T {
                         range "2..4094";
                    }
                } // END of svlanId definition.

                leaf svlanLow  {
                    type  cml_data_types:CML_INT16_T {
                         range "2..4094";
                    }
                } // END of svlanLow definition.

                leaf svidHigh  {
                    type  cml_data_types:CML_INT16_T {
                         range "2..4094";
                    }
                } // END of svidHigh definition.

                leaf svlanInsName  {
                    type  cml_data_types:CML_SVLAN_INSTANCE_NAME_T;  
                } // END of svlanInsName definition.

                leaf serviceType  {
                    type  cml_data_types:CML_INT16_T;  
                    config false;
                } // END of serviceType definition.

                leaf bundleStatus  {
                    type  cml_data_types:CML_INT16_T;  
                    config false;
                } // END of bundleStatus definition.

                leaf svlanrefPortNum  {
                    type  cml_data_types:CML_STRING_T {
                        length "0..255";
                    }
                } // END of svlanrefPortNum definition.

            } // End of svlanId-list
            container g8031ProtectionGroup {
                if-feature feature_list:HAVE_G8031;
                                config true;

                description
                    "g8031ProtectionGroup";

                leaf gbridgeId  {
                    if-feature feature_list:HAVE_G8031;
                    type  cml_data_types:CML_BRIDGE_BACKBONE_T;  
                } // END of gbridgeId definition.

                leaf ifindexW  {
                    if-feature feature_list:HAVE_G8031;
                    type  cml_data_types:CML_UINT32_T;  
                } // END of ifindexW definition.

                leaf ifindexP  {
                    if-feature feature_list:HAVE_G8031;
                    type  cml_data_types:CML_UINT32_T;  
                } // END of ifindexP definition.

                leaf epsId  {
                    if-feature feature_list:HAVE_G8031;
                    type  cml_data_types:CML_UINT32_T;  
                } // END of epsId definition.

                leaf g8031InstanceId  {
                    if-feature feature_list:HAVE_G8031;
                    type  cml_data_types:CML_UINT32_T;  
                    config false;
                } // END of g8031InstanceId definition.

                leaf primaryVidg8031  {
                    if-feature feature_list:HAVE_G8031;
                    type  cml_data_types:CML_UINT32_T;  
                    config false;
                } // END of primaryVidg8031 definition.

                leaf instance  {
                    if-feature feature_list:HAVE_G8031;
                    type  cml_data_types:CML_UINT32_T {
                         range "1..64";
                    }
                } // END of instance definition.

            } // END of g8031ProtectionGroup-container definition.
            container nsmG8032Ring {
                if-feature feature_list:HAVE_G8032;
                                config true;

                description
                    "nsmG8032Ring";

                leaf ringbridgeId  {
                    if-feature feature_list:HAVE_G8032;
                    type  cml_data_types:CML_BRIDGE_BACKBONE_T;  
                } // END of ringbridgeId definition.

                leaf g8032RingId  {
                    if-feature feature_list:HAVE_G8032;
                    type  cml_data_types:CML_UINT32_T;  
                } // END of g8032RingId definition.

                leaf ringInstance  {
                    if-feature feature_list:HAVE_G8032;
                    type  cml_data_types:CML_UINT32_T {
                         range "1..64";
                    }
                } // END of ringInstance definition.

                leaf ringIfindexE  {
                    if-feature feature_list:HAVE_G8032;
                    type  cml_data_types:CML_UINT32_T;  
                } // END of ringIfindexE definition.

                leaf ringIfindexW  {
                    if-feature feature_list:HAVE_G8032;
                    type  cml_data_types:CML_UINT32_T;  
                } // END of ringIfindexW definition.

                leaf primaryvidg8032  {
                    if-feature feature_list:HAVE_G8032;
                    type  cml_data_types:CML_UINT32_T;  
                    config false;
                } // END of primaryvidg8032 definition.

                leaf g8032InstanceId  {
                    if-feature feature_list:HAVE_G8032;
                    type  cml_data_types:CML_UINT32_T;  
                    config false;
                } // END of g8032InstanceId definition.

            } // END of nsmG8032Ring-container definition.
        } // End of bebBridge-list
    } // END of bebBridge-grouping definition.


    grouping pbbInterface-grouping {
        list pbbInterface {
             
            description
                " Group of bridge attribute having interface property";

            config true;
            key "ifName";

            
            leaf ifName  {
                type  cml_data_types:CML_STRING_T {
                    length "0..255";
                }
                description "interface status";
            } // END of ifName definition.


            list providerNwBvlan {
                 
                description
                    "providerNwBvlan";

                config true;
                key "pbbBvid";

                
                leaf pbbBvid  {
                    type  cml_data_types:CML_UINT32_T {
                         range "2..4094";
                    }
                } // END of pbbBvid definition.

            } // End of providerNwBvlan-list

            list vipTbl {
                 
                description
                    "vipTbl";

                config true;
                key "srvInsName";

                
                leaf srvInsName  {
                    type  cml_data_types:CML_CMBCKBONE_INSTANCE_T;  
                } // END of srvInsName definition.

                leaf defaultDstBmac  {
                    type  cml_data_types:CML_STRING_T {
                        length "0..255";
                    }
                } // END of defaultDstBmac definition.

                leaf srvType  {
                    type  cml_data_types:CML_VIP_TRAFFIC_T;  
                } // END of srvType definition.

            } // End of vipTbl-list

            list cbpSrvinstTbl {
                                 if-feature feature_list:HAVE_I_BEB;

                description
                    "cbpSrvinstTbl";

                config true;
                key "cbpInsStart";

                
                leaf cbpInsStart  {
                    type  cml_data_types:CML_UINT32_T {
                         range "1..16777214";
                    }
                } // END of cbpInsStart definition.

                leaf cbpInsEnd  {
                    type  cml_data_types:CML_UINT32_T {
                         range "1..16777214";
                    }
                } // END of cbpInsEnd definition.

                leaf bvid  {
                    type  cml_data_types:CML_UINT32_T {
                         range "2..4094";
                    }
                } // END of bvid definition.

                leaf defaultDstBmac  {
                    type  cml_data_types:CML_STRING_T {
                        length "0..255";
                    }
                } // END of defaultDstBmac definition.

                leaf ptMptType  {
                    type  cml_data_types:CML_BOOL_T;  
                } // END of ptMptType definition.

                leaf localSid  {
                    type  cml_data_types:CML_UINT32_T {
                         range "2..16777214";
                    }
                } // END of localSid definition.

                leaf edge  {
                    type  cml_data_types:CML_UINT8_T;  
                } // END of edge definition.

                leaf mode  {
                    type  cml_data_types:CML_BEB_MODE_T;  
                    default "none";
                } // END of mode definition.

                leaf status  {
                    type  cml_data_types:CML_UINT32_T;  
                    config false;
                } // END of status definition.

            } // End of cbpSrvinstTbl-list

            list pbbTeInstEntryIf {
                                 if-feature feature_list:HAVE_I_BEB;

                description
                    "pbbTeInstEntryIf";

                config true;
                key "teSid";

                
                leaf teSid  {
                    type  cml_data_types:CML_UINT32_T;  
                } // END of teSid definition.

                leaf remoteMac  {
                    if-feature feature_list:HAVE_GMPLS;
                    if-feature feature_list:HAVE_GELS;
                    type  cml_data_types:CML_STRING_T {
                        length "0..255";
                    }
                } // END of remoteMac definition.

                leaf espVid  {
                    type  cml_data_types:CML_UINT16_T {
                         range "2..4094";
                    }
                } // END of espVid definition.

                leaf multicast  {
                    type  cml_data_types:CML_BOOL_T;  
                    default false;
                } // END of multicast definition.

                leaf mcastRxMac  {
                    type  cml_data_types:CML_STRING_T {
                        length "0..255";
                    }
                } // END of mcastRxMac definition.

                leaf egress  {
                    type  cml_data_types:CML_BOOL_T;  
                } // END of egress definition.

                leaf ingress  {
                    type  cml_data_types:CML_BOOL_T;  
                } // END of ingress definition.

            } // End of pbbTeInstEntryIf-list
            container pipTbl {
                                config true;

                description
                    "pipTbl";

                leaf pipSrcBmac  {
                    type  cml_data_types:CML_STRING_T {
                        length "0..255";
                    }
                } // END of pipSrcBmac definition.

                leaf pipPortName  {
                    type  cml_data_types:CML_STRING_T {
                        length "0..255";
                    }
                    config false;
                } // END of pipPortName definition.

                leaf pipVipMap  {
                    type  cml_data_types:CML_STRING_T {
                        length "0..255";
                    }
                    config false;
                } // END of pipVipMap definition.

            } // END of pipTbl-container definition.
            container pbbTeApsGrp {
                                config true;

                description
                    "pbbTeApsGrp";

                leaf apsGrpId  {
                    type  cml_data_types:CML_UINT32_T;  
                } // END of apsGrpId definition.

                leaf instance  {
                    type  cml_data_types:CML_UINT32_T;  
                    config false;
                } // END of instance definition.

                leaf tesidW  {
                    type  cml_data_types:CML_UINT32_T;  
                } // END of tesidW definition.

                leaf tesidB  {
                    type  cml_data_types:CML_UINT32_T;  
                } // END of tesidB definition.

                leaf storageType  {
                    type  cml_data_types:CML_UINT8_T;  
                    config false;
                } // END of storageType definition.

                leaf pbbTeApsRowStatus  {
                    type  cml_data_types:CML_UINT8_T;  
                    config false;
                } // END of pbbTeApsRowStatus definition.

            } // END of pbbTeApsGrp-container definition.
            container pbbTeIsid {
                                config true;

                description
                    "pbbTeIsid";

                leaf apsGrpId  {
                    type  cml_data_types:CML_UINT32_T;  
                } // END of apsGrpId definition.

                leaf isidOptType  {
                    type  cml_data_types:CML_ASPTEISID_T;  
                } // END of isidOptType definition.

                leaf teIsid  {
                    type  cml_data_types:CML_UINT32_T;  
                } // END of teIsid definition.

                leaf storageType  {
                    type  cml_data_types:CML_UINT8_T;  
                    config false;
                } // END of storageType definition.

                leaf pbbTeRowStatus  {
                    type  cml_data_types:CML_UINT8_T;  
                    config false;
                } // END of pbbTeRowStatus definition.

            } // END of pbbTeIsid-container definition.
            container cnpSrvTblKey {
                                config true;

                description
                    "cnpSrvTblKey";

                leaf cnpSid  {
                    type  cml_data_types:CML_CNP_INSTANCE_T;  
                } // END of cnpSid definition.

                leaf icompId  {
                    type  cml_data_types:CML_INT32_T;  
                    config false;
                } // END of icompId definition.

                leaf icompPortNum  {
                    type  cml_data_types:CML_INT32_T;  
                    config false;
                } // END of icompPortNum definition.

                leaf refPortNum  {
                    type  cml_data_types:CML_STRING_T {
                        length "0..255";
                    }
                } // END of refPortNum definition.

            } // END of cnpSrvTblKey-container definition.
        } // End of pbbInterface-list
    } // END of pbbInterface-grouping definition.


}
