/*
 * Copyright (C) 2024 IP Infusion, Inc.
 * All rights reserved.
 *
 * Unless required by applicable law or agreed to in writing,
 * software distributed under the License is distributed on an
 * "AS IS" BASIS, WITHOUT WARRANTIES OR CONDITIONS OF ANY
 * KIND, either express or implied.
 *
 * File name: ipi-oc-terminal-device-properties-augments.yang
 */

module ipi-oc-terminal-device-properties-augments {
  namespace "http://www.ipinfusion.com/yang/ocnos/ipi-oc-terminal-device-properties-augments";
  prefix "ipi-oc-opt-term-properties-augments";

  import openconfig-terminal-device-property-types { prefix oc-opt-term-prop-types; }

  revision "2024-05-06" {
    description "Initial Revision";
  }

  identity MODULATION_FORMAT_NRZ {
    base oc-opt-term-prop-types:MODULATION_FORMAT;
    description
      "Two voltage levels to represent logic 0/1 (NZR) modulation format identity";
  }

  identity MODULATION_FORMAT_PAM5 {
    base oc-opt-term-prop-types:MODULATION_FORMAT;
    description
      "5-level Pulse Amplitude Modulation (PAM)";
  }

  identity MODULATION_FORMAT_PAM16 {
    base oc-opt-term-prop-types:MODULATION_FORMAT;
    description
      "16-level Pulse Amplitude Modulation (PAM)";
  }

  identity G_33GHZ {
    base oc-opt-term-prop-types:ADJUSTMENT_GRANULARITY;
    description
      "Adjustment granularity value of 33 gigahertz.";
  }

  identity G_75GHZ {
    base oc-opt-term-prop-types:ADJUSTMENT_GRANULARITY;
    description
      "Adjustment granularity value of 75 gigahertz.";
  }

}
