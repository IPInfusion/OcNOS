/*
 * Copyright (C) 2024 IP Infusion, Inc.
 * All rights reserved.
 *
 * Unless required by applicable law or agreed to in writing,
 * software distributed under the License is distributed on an
 * "AS IS" BASIS, WITHOUT WARRANTIES OR CONDITIONS OF ANY
 * KIND, either express or implied.
 *
 * File name: ipi-oc-ni-augments.yang
 */

module ipi-oc-ni-augments {
  namespace   "http://www.ipinfusion.com/yang/ocnos/ipi-oc-ni-augments";
  prefix "ipi-oc-ni-augments";

  import openconfig-network-instance { prefix oc-netinst; }
  import openconfig-network-instance-types { prefix oc-ni-types; }
  import openconfig-mpls-types { prefix oc-mplst; }


  revision "2024-04-08" {
    description "Add new identities to LSP_ROLE";
  }

  revision "2024-03-18" {
    description "Add protection-role leaf for RSVP-TE tunnels in config and state container";
  }

  revision "2024-02-23" {
    description "Add enabled leaf for RSVP-TE in interface-attributes container";
  }

  revision "2024-01-30" {
    description "Add enabled leaf for RSVP-TE in config and state container";
  }

  revision "2023-07-25" {
    description "Add enabled leaf for LDP in config and state container";
  }

  revision "2023-06-06" {
    description "Add missing bridge-protocol leaf for state container";
  }

  revision "2023-02-14" {
    description "Remove route-target configuration due support on network-instance 'inter-instance-policies' container";
  }

  revision "2021-04-26" {
    description "Add route-target configuration";
  }

  revision "2021-04-10" {
    description "Add bridge protocol";
  }

  revision "2021-02-25" {
    description "Initial Revision";
  }

  grouping bridge-protocol-leaf {
    leaf bridge-protocol {
      description "Bridge protocol type";
      when "../oc-netinst:type = 'oc-ni-types:L2L3'";
      default "ieee-vlan-bridge";

      type enumeration {
        enum ieee {
          value 1;
          description "IEEE 801.1Q spanning-tree protocol";
        }
        enum ieee-vlan-bridge {
          value 2;
          description "IEEE 801.1Q spanning-tree protocol,Vlan aware bridge";
        }
        enum rstp {
          value 3;
          description "IEEE 801.1w rapid spanning-tree protocol";
        }
        enum rstp-vlan-bridge {
          value 4;
          description "IEEE 801.1w rapid spanning-tree protocol,Vlan aware bridge";
        }
        enum mstp {
          value 5;
          description "IEEE 802.1s multiple spanning-tree protocol";
        }
        enum provider-rstp {
          value 6;
          description "IEEE 802.1s multiple spanning-tree protocol";
        }
        enum provider-mstp {
          value 7;
          description "IEEE 802.1s rapid spanning-tree protocol";
        }
        enum rpvst+ {
          value 8;
          description "IEEE 801.1w rapid per vlan spanning-tree protocol";
        }
        enum rstp-ring {
          value 10;
          description "IEEE 801.1w rapid spanning-tree protocol,Enable Rapid Ring spanning-tree";
        }
        enum mstp-ring {
          value 11;
          description "IEEE 802.1s multiple spanning-tree protocol,Enable Rapid Ring spanning-tree";
        }
        enum provider-rstp-edge {
          value 12;
          description "IEEE 802.1s multiple spanning-tree protocol,Configure as Edge bridge";
        }
        enum provider-mstp-edge {
          value 13;
          description "IEEE 802.1s rapid spanning-tree protocol,Configure as Edge bridge";
        }
        enum rstp-vlan-bridge-ring {
          value 14;
          description "IEEE 801.1w rapid spanning-tree protocol,Vlan aware bridge,Enable Rapid Ring spanning-tree";
        }
        enum trill {
          value 20;
          description "Transparent Interconnection of Lots of Link";
        }
        enum evb {
          value 97;
          description "evb";
        }
        enum svlan-evb {
          value 98;
          description "Svlan aware evb";
        }
      }
    }
  }

  augment "/oc-netinst:network-instances/oc-netinst:network-instance/oc-netinst:table-connections/oc-netinst:table-connection/oc-netinst:config" {

    description "Adds protocol instance id support for table connections";

    leaf dst-instance {
        type string;
        description "Instance ID of the destination protocol instance";
    }
  }

  augment "/oc-netinst:network-instances/oc-netinst:network-instance/oc-netinst:config" {
    uses bridge-protocol-leaf;
  }

  augment "/oc-netinst:network-instances/oc-netinst:network-instance/oc-netinst:state" {
    uses bridge-protocol-leaf;
  }

  grouping ldp-config {
    leaf enabled {
      type boolean;
      default "true";
      must "(. = 'true')" {
        error-message "The value must be true";
      }
      description "When set to true it indicates the LDP functionality is enabled and when set to false it is explicitly disabled";
    }
  }

  augment "/oc-netinst:network-instances/oc-netinst:network-instance/oc-netinst:mpls/oc-netinst:signaling-protocols/oc-netinst:ldp" {

    container config {
      description "LDP configuration attributes";
      uses ldp-config;
    }

    container state {
      description "LDP state attributes";
      uses ldp-config;
      config false;
    }
  }

  grouping rsvp-te-config {
    leaf enabled {
      type empty;
      description "When this leaf is present, it signifies that the RSVP functionality is active; conversely, its absence explicitly deactivates the feature";
    }
  }

  augment "/oc-netinst:network-instances/oc-netinst:network-instance/oc-netinst:mpls/oc-netinst:signaling-protocols/oc-netinst:rsvp-te" {

    container config {
      description "RSVP-TE configuration attributes";
      uses rsvp-te-config;
    }

    container state {
      description "RSVP-TE state attributes";
      uses rsvp-te-config;
      config false;
    }
  }

  grouping rsvp-te-if-config {
    leaf enabled {
      type boolean;
      default "true";
      must "(. = 'true')" {
        error-message "The value must be true";
      }
      description "Use this attribute to enable control adjacency to send and receive RSVP-TE control messages for MPLS and GMPLS";
    }
  }

  augment "/oc-netinst:network-instances/oc-netinst:network-instance/oc-netinst:mpls/oc-netinst:signaling-protocols/oc-netinst:rsvp-te/oc-netinst:interface-attributes/oc-netinst:interface/oc-netinst:config" {
      uses rsvp-te-if-config;
  }

  augment "/oc-netinst:network-instances/oc-netinst:network-instance/oc-netinst:mpls/oc-netinst:signaling-protocols/oc-netinst:rsvp-te/oc-netinst:interface-attributes/oc-netinst:interface/oc-netinst:state" {
      uses rsvp-te-if-config;
  }

  identity PROTECTION_ROLE {
    description
      "Base identity for protection role.";
  }

  identity ONE_TO_ONE {
    base PROTECTION_ROLE;
    description
      "Tunnel will use one-to-one protection mechanism.";
  }

  identity FACILITY {
    base PROTECTION_ROLE;
    description
      "Primary tunnel will use another tunnel as N:1 protection.";
  }

  identity BYPASS {
    base PROTECTION_ROLE;
    description
      "Tunnel is the protecting tunnel.";
  }

  grouping te-tunnels-config {
    leaf protection-role {
      type identityref {
        base PROTECTION_ROLE;
      }
      default ONE_TO_ONE;
      description "Specifies the tunnel protection mode: can be one-to-one, facility or bypass.";
    }
  }

  augment "/oc-netinst:network-instances/oc-netinst:network-instance/oc-netinst:mpls/oc-netinst:lsps/oc-netinst:constrained-path/oc-netinst:tunnels/oc-netinst:tunnel/oc-netinst:config" {
    uses te-tunnels-config;
  }

  augment "/oc-netinst:network-instances/oc-netinst:network-instance/oc-netinst:mpls/oc-netinst:lsps/oc-netinst:constrained-path/oc-netinst:tunnels/oc-netinst:tunnel/oc-netinst:state" {
    uses te-tunnels-config;
  }

  identity NON_INGRESS {
    base oc-mplst:LSP_ROLE;
    description
      "Label switched path role is a non ingress LSP";
  }

  identity NONE {
    base oc-mplst:LSP_ROLE;
    description
      "Label switched path role is invalid";
  }

}
