/*
 * Copyright (C) 2024 IP Infusion, Inc.
 * All rights reserved.
 *
 * Unless required by applicable law or agreed to in writing,
 * software distributed under the License is distributed on an
 * "AS IS" BASIS, WITHOUT WARRANTIES OR CONDITIONS OF ANY
 * KIND, either express or implied.
 *
 * File name: ipi-oc-sys-deviations.yang
 */

module ipi-oc-sys-deviations {
  namespace   "http://www.ipinfusion.com/yang/ocnos/ipi-oc-sys-deviations";
  prefix "ipi-oc-sys-deviations";

  import openconfig-system { prefix oc-sys; }

  revision "2024-08-12" {
    description "Fix translation to support user VRF to the logging";
  }

  revision "2023-05-17" {
    description "Add deviations for not-supported paths";
  }

  revision "2022-07-07" {
    description "Removed the deviation to support boot-time";
  }

  revision "2022-01-19" {
    description "Added new deviations for not supported trees";
  }

  revision "2021-05-04" {
    description "Date/time notation is wrong for OpenConfig,
                 see https://github.com/openconfig/public/issues/166";
  }

  revision "2020-11-24";
  deviation /oc-sys:system/oc-sys:logging/oc-sys:console {
    deviate not-supported;
  }

  deviation /oc-sys:system/oc-sys:logging/oc-sys:remote-servers/oc-sys:remote-server/oc-sys:selectors {
    description
      "Only one selector object is support, and cannot be deleted.";
    deviate add {
      must "count(selector)=1";
    }
  }

  deviation /oc-sys:system/oc-sys:state/oc-sys:current-datetime {
    deviate replace {
      type string;
    }
  }

  augment /oc-sys:system/oc-sys:alarms/oc-sys:alarm/oc-sys:state {
    leaf alarm-reported-timestamp {
      type string;
    }
  }

  deviation /oc-sys:system/oc-sys:config/oc-sys:login-banner {
    deviate not-supported;
  }

  deviation /oc-sys:system/oc-sys:state/oc-sys:login-banner {
    deviate not-supported;
  }

  deviation /oc-sys:system/oc-sys:config/oc-sys:motd-banner {
    deviate not-supported;
  }

  deviation /oc-sys:system/oc-sys:state/oc-sys:motd-banner {
    deviate not-supported;
  }

  deviation /oc-sys:system/oc-sys:aaa {
    deviate not-supported;
  }

  deviation /oc-sys:system/oc-sys:dns {
    deviate not-supported;
  }

  deviation /oc-sys:system/oc-sys:ntp {
    deviate not-supported;
  }

  deviation /oc-sys:system/oc-sys:ssh-server {
    deviate not-supported;
  }

  deviation /oc-sys:system/oc-sys:telnet-server {
    deviate not-supported;
  }

  deviation /oc-sys:system/oc-sys:memory {
    deviate not-supported;
  }

  deviation /oc-sys:system/oc-sys:cpus {
    deviate not-supported;
  }

  deviation /oc-sys:system/oc-sys:processes {
    deviate not-supported;
  }

  deviation /oc-sys:system/oc-sys:messages {
    deviate not-supported;
  }

  deviation /oc-sys:system/oc-sys:license {
    deviate not-supported;
  }

  deviation /oc-sys:system/oc-sys:config/oc-sys:domain-name {
    deviate not-supported;
  }

  deviation /oc-sys:system/oc-sys:logging/oc-sys:remote-servers/oc-sys:remote-server/oc-sys:config/oc-sys:source-address {
    deviate not-supported;
  }

  deviation /oc-sys:system/oc-sys:logging/oc-sys:remote-servers/oc-sys:remote-server/oc-sys:state/oc-sys:source-address {
    deviate not-supported;
  }

  deviation /oc-sys:system/oc-sys:mac-address {
    deviate not-supported;
  }

  deviation /oc-sys:system/oc-sys:mount-points {
    deviate not-supported;
  }

  deviation /oc-sys:system/oc-sys:state/oc-sys:domain-name {
    deviate not-supported;
  }

  deviation /oc-sys:system/oc-sys:state/oc-sys:last-configuration-timestamp {
    deviate not-supported;
  }

  deviation /oc-sys:system/oc-sys:state/oc-sys:software-version {
    deviate not-supported;
  }

}
