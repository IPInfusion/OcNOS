/*
 * Copyright (C) 2024 IP Infusion, Inc.
 * All rights reserved.
 *
 * Unless required by applicable law or agreed to in writing,
 * software distributed under the License is distributed on an
 * "AS IS" BASIS, WITHOUT WARRANTIES OR CONDITIONS OF ANY
 * KIND, either express or implied.
 *
 * File name: ipi-oc-platform-types-deviations.yang
 */

module ipi-oc-platform-types-deviations {
    namespace "http://www.ipinfusion.com/yang/ocnos/ipi-oc-platform-types-deviations";
    prefix "ipi-oc-platform-types-deviations";

    import openconfig-platform-types {
        prefix oc-platform-types;
    }

    revision "2024-08-30" {
        description
          "Removed FAN_TRAY as it is added in openconfig-platform-fan";
    }
    revision "2021-01-29" {
        description
          "First release: add new identities that OcNOS supports";
    }

    identity NA {
        base oc-platform-types:COMPONENT_OPER_STATUS;
        description
          "Not Applicable";
    }

    identity HW_NA {
        base oc-platform-types:OPENCONFIG_HARDWARE_COMPONENT;
        description
          "Not Applicable";
    }

    identity POWER_RAIL {
        base oc-platform-types:OPENCONFIG_HARDWARE_COMPONENT;
        description
          "Power rail component";
    }

    identity RAM {
        base oc-platform-types:OPENCONFIG_HARDWARE_COMPONENT;
        description
          "Ram Memory component";
    }

    identity PTP_CLOCK {
        base oc-platform-types:OPENCONFIG_HARDWARE_COMPONENT;
        description
          "PTP clock component";
    }
}
