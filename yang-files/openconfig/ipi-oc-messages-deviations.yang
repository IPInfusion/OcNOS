/*
 * Copyright (C) 2024 IP Infusion, Inc.
 * All rights reserved.
 *
 * Unless required by applicable law or agreed to in writing,
 * software distributed under the License is distributed on an
 * "AS IS" BASIS, WITHOUT WARRANTIES OR CONDITIONS OF ANY
 * KIND, either express or implied.
 *
 * File name: ipi-oc-messages-deviations.yang
 */

module ipi-oc-messages-deviations {
  namespace   "http://www.ipinfusion.com/yang/ocnos/ipi-oc-messages-deviations";
  prefix "ipi-oc-messages-deviations";

  import openconfig-messages { prefix oc-messages; }

  revision "2022-01-19" {
    description "Messages deviations";
  }

  deviation /oc-messages:messages {
    deviate not-supported;
  }

}
