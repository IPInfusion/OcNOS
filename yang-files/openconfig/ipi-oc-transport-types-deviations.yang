/*
 * Copyright (C) 2024 IP Infusion, Inc.
 * All rights reserved.
 *
 * Unless required by applicable law or agreed to in writing,
 * software distributed under the License is distributed on an
 * "AS IS" BASIS, WITHOUT WARRANTIES OR CONDITIONS OF ANY
 * KIND, either express or implied.
 *
 * File name: ipi-oc-transport-types-deviations.yang
 */

module ipi-oc-transport-types-deviations {
    namespace "http://www.ipinfusion.com/yang/ocnos/ipi-oc-transport-types-deviations";
    prefix "ipi-oc-transport-types-deviations";

    import openconfig-transport-types {
        prefix oc-opt-types;
    }

    revision "2021-05-07" {
        description
          "First release: add new identities that OcNOS supports";
    }

    identity UNKNOWN {
        base oc-opt-types:FIBER_CONNECTOR_TYPE;
        description
          "Unknown type connector";
    }

    identity FIBRE_CHANNEL_STYLE1_COPPER_CONNECTOR {
        base oc-opt-types:FIBER_CONNECTOR_TYPE;
        description
          "Fibre channel style 1 copper type connector";
    }

    identity FIBRE_CHANNEL_STYLE2_COPPER_CONNECTOR {
        base oc-opt-types:FIBER_CONNECTOR_TYPE;
        description
          "Fibre channel style 2 copper type connector";
    }

    identity BNC_TNC_CONNECTOR {
        base oc-opt-types:FIBER_CONNECTOR_TYPE;
        description
          "Bayonet or Threaded Neill Concelman type connector";
    }

    identity FIBRE_CHANNEL_COAXIAL_HEADERS_CONNECTOR {
        base oc-opt-types:FIBER_CONNECTOR_TYPE;
        description
          "Fibre channel coaxial headers type connector";
    }

    identity FIBER_JACK_CONNECTOR {
        base oc-opt-types:FIBER_CONNECTOR_TYPE;
        description
          "Fiber jack type connector";
    }

    identity MT_RJ_CONNECTOR {
        base oc-opt-types:FIBER_CONNECTOR_TYPE;
        description
          "Mechanical transfer registered jack type connector";
    }

    identity MU_CONNECTOR {
        base oc-opt-types:FIBER_CONNECTOR_TYPE;
        description
          "Multiple optical type connector";
    }

    identity SG_CONNECTOR {
        base oc-opt-types:FIBER_CONNECTOR_TYPE;
        description
          "SG type connector";
    }

    identity OPTICAL_PIGTAIL_CONNECTOR {
        base oc-opt-types:FIBER_CONNECTOR_TYPE;
        description
          "Optical pigtail type connector";
    }

    identity MPO_16_CONNECTOR {
        base oc-opt-types:FIBER_CONNECTOR_TYPE;
        description
          "MPO (multi-fiber push-on/pull-off) type fiber connector
            1x16 fibers";
    }

    identity HSSDC_II_CONNECTOR {
        base oc-opt-types:FIBER_CONNECTOR_TYPE;
        description
          "HSSDC II type connector";
    }

    identity COPPER_PIGTAIL_CONNECTOR {
        base oc-opt-types:FIBER_CONNECTOR_TYPE;
        description
          "Copper pigtail type connector";
    }

    identity RJ_45_CONNECTOR {
        base oc-opt-types:FIBER_CONNECTOR_TYPE;
        description
          "RJ45 type connector";
    }

    identity NO_SEPARABLE_CONNECTOR {
        base oc-opt-types:FIBER_CONNECTOR_TYPE;
        description
          "No separable connector type connector";
    }

    identity MXC2_X16_CONNECTOR {
        base oc-opt-types:FIBER_CONNECTOR_TYPE;
        description
          "MXC2 x16 type connector";
    }

    identity RESERVED_CONNECTOR {
        base oc-opt-types:FIBER_CONNECTOR_TYPE;
        description
          "Reserved type connector";
    }

    identity VENDOR_SPECIFIC_CONNECTOR {
        base oc-opt-types:FIBER_CONNECTOR_TYPE;
        description
          "Vendor specific type connector";
    }

    identity ETH_1000BASE_SX {
        base oc-opt-types:ETHERNET_PMD_TYPE;
        description
          "Ethernet compliance code: 1000BASE_SX";
    }

    identity ETH_1000BASE_LX {
        base oc-opt-types:ETHERNET_PMD_TYPE;
        description
          "Ethernet compliance code: 1000BASE_LX";
    }

    identity ETH_1000BASE_CX {
        base oc-opt-types:ETHERNET_PMD_TYPE;
        description
          "Ethernet compliance code: 1000BASE_CX";
    }

    identity ETH_1000BASE_T {
        base oc-opt-types:ETHERNET_PMD_TYPE;
        description
          "Ethernet compliance code: 1000BASE_T";
    }

    identity ETH_100BASE_LX_LX10 {
        base oc-opt-types:ETHERNET_PMD_TYPE;
        description
          "Ethernet compliance code: 100BASE_LX_LX10";
    }

    identity ETH_100BASE_FX {
        base oc-opt-types:ETHERNET_PMD_TYPE;
        description
          "Ethernet compliance code: 100BASE_FX";
    }

    identity ETH_BASE_BX10 {
        base oc-opt-types:ETHERNET_PMD_TYPE;
        description
          "Ethernet compliance code: BASE_BX10";
    }

    identity ETH_BASE_PX {
        base oc-opt-types:ETHERNET_PMD_TYPE;
        description
          "Ethernet compliance code: BASE_PX";
    }

    identity ETH_40G_AOC {
        base oc-opt-types:ETHERNET_PMD_TYPE;
        description
          "Ethernet compliance code: 40G_AOC";
    }

    identity ETH_OBSOLETE {
        base oc-opt-types:ETHERNET_PMD_TYPE;
        description
          "Ethernet compliance code: Obsolete";
    }

    identity ETH_RESERVED {
        base oc-opt-types:ETHERNET_PMD_TYPE;
        description
          "Ethernet compliance code: Reserved";
    }

    identity ETH_25GBASE_CRCA_S {
        base oc-opt-types:ETHERNET_PMD_TYPE;
        description
          "Ethernet compliance code: 25GBASE_CRCA_S";
    }

    identity ETH_25GBASE_CRCA_N {
        base oc-opt-types:ETHERNET_PMD_TYPE;
        description
          "Ethernet compliance code: 25GBASE_CRCA_N";
    }

    identity ETH_G959_P1_I1_2D1 {
        base oc-opt-types:ETHERNET_PMD_TYPE;
        description
          "Ethernet compliance code: G959_P1_I1_2D1";
    }

    identity ETH_G959_P1_S1_2D2 {
        base oc-opt-types:ETHERNET_PMD_TYPE;
        description
          "Ethernet compliance code: G959_P1_S1_2D2";
    }

    identity ETH_G959_P1_L1_2D2 {
        base oc-opt-types:ETHERNET_PMD_TYPE;
        description
          "Ethernet compliance code: G959_P1_L1_2D2";
    }

    identity ETH_100GBASE_T_SFI_ELECTRICAL {
        base oc-opt-types:ETHERNET_PMD_TYPE;
        description
          "Ethernet compliance code: 100GBASE_T_SFI_ELECTRICAL";
    }

    identity ETH_100GE_DWDM2 {
        base oc-opt-types:ETHERNET_PMD_TYPE;
        description
          "Ethernet compliance code: 100GE_DWDM2";
    }

    identity FORM_FACTOR_UNKNOWN {
        base oc-opt-types:TRANSCEIVER_FORM_FACTOR_TYPE;
        description
          "Unknown form factor";
    }

    identity SONET_OC192_SR {
        base oc-opt-types:SONET_APPLICATION_CODE;
        description
          "SONET/SDH application code: SONET_OC192_SR";
    }

    identity SONET_REACH_SPECIFIER_BIT1 {
        base oc-opt-types:SONET_APPLICATION_CODE;
        description
          "SONET/SDH application code: SONET_REACH_SPECIFIER_BIT1";
    }

    identity SONET_REACH_SPECIFIER_BIT2 {
        base oc-opt-types:SONET_APPLICATION_CODE;
        description
          "SONET/SDH application code: SONET_REACH_SPECIFIER_BIT2";
    }

    identity SONET_OC48_LR {
        base oc-opt-types:SONET_APPLICATION_CODE;
        description
          "SONET/SDH application code: SONET_OC48_LR";
    }

    identity SONET_OC48_IR {
        base oc-opt-types:SONET_APPLICATION_CODE;
        description
          "SONET/SDH application code: SONET_OC48_IR";
    }

    identity SONET_OC48_SR {
        base oc-opt-types:SONET_APPLICATION_CODE;
        description
          "SONET/SDH application code: SONET_OC48_SR";
    }

    identity SONET_OC12_SM_LR {
        base oc-opt-types:SONET_APPLICATION_CODE;
        description
          "SONET/SDH application code: SONET_OC12_SM_LR";
    }

    identity SONET_OC12_SM_IR {
        base oc-opt-types:SONET_APPLICATION_CODE;
        description
          "SONET/SDH application code: SONET_OC12_SM_IR";
    }

    identity SONET_OC12_SM_SR {
        base oc-opt-types:SONET_APPLICATION_CODE;
        description
          "SONET/SDH application code: SONET_OC12_SM_SR";
    }

    identity SONET_OC3_SM_LR {
        base oc-opt-types:SONET_APPLICATION_CODE;
        description
          "SONET/SDH application code: SONET_OC3_SM_LR";
    }

    identity SONET_OC3_SM_IR {
        base oc-opt-types:SONET_APPLICATION_CODE;
        description
          "SONET/SDH application code: SONET_OC3_SM_IR";
    }

    identity SONET_OC3_SM_SR {
        base oc-opt-types:SONET_APPLICATION_CODE;
        description
          "SONET/SDH application code: SONET_OC3_SM_SR";
    }

    identity PROT_200GE {
        base oc-opt-types:TRIBUTARY_PROTOCOL_TYPE;
        description
          "200G Ethernet port protocol";
    }

}
