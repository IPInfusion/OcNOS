/*
 * Copyright (C) 2024 IP Infusion, Inc.
 * All rights reserved.
 *
 * Unless required by applicable law or agreed to in writing,
 * software distributed under the License is distributed on an
 * "AS IS" BASIS, WITHOUT WARRANTIES OR CONDITIONS OF ANY
 * KIND, either express or implied.
 *
 * File name: ipi-oc-lacp-deviations.yang
 */

module ipi-oc-lacp-deviations {
  namespace   "http://www.ipinfusion.com/yang/ocnos/ipi-oc-lacp-deviations";
  prefix "ipi-oc-lacp-deviations";

  import openconfig-lacp { prefix oc-lacp; }

  revision "2023-05-04" {
    description "Add deviations for not-supported paths";
  }

  revision "2021-03-01" {
    description
      "First release: add restrictions to LAG interface mode";
    reference "2.4.3";
  }

  deviation /oc-lacp:lacp/oc-lacp:interfaces {
    deviate not-supported;
  }

}
