/*
 * Copyright (C) 2024 IP Infusion, Inc.
 * All rights reserved.
 *
 * Unless required by applicable law or agreed to in writing,
 * software distributed under the License is distributed on an
 * "AS IS" BASIS, WITHOUT WARRANTIES OR CONDITIONS OF ANY
 * KIND, either express or implied.
 *
 * File name: ipi-oc-terminal-device-properties-deviations.yang
 */

module ipi-oc-terminal-device-properties-deviations {
  namespace "http://www.ipinfusion.com/yang/ocnos/ipi-oc-terminal-device-properties-deviations";
  prefix "ipi-oc-opt-term-properties-deviations";

  import openconfig-terminal-device-properties { prefix oc-opt-term-properties; }

  revision "2024-05-06" {
    description "Initial Revision";
  }

  deviation /oc-opt-term-properties:operational-modes/oc-opt-term-properties:mode-descriptor/oc-opt-term-properties:G.698.2 {
    deviate not-supported;
  }

  deviation /oc-opt-term-properties:operational-modes/oc-opt-term-properties:mode-descriptor/oc-opt-term-properties:explicit-mode/oc-opt-term-properties:operational-mode-capabilities/oc-opt-term-properties:fec {
    deviate not-supported;
  }

  deviation /oc-opt-term-properties:operational-modes/oc-opt-term-properties:mode-descriptor/oc-opt-term-properties:explicit-mode/oc-opt-term-properties:operational-mode-capabilities/oc-opt-term-properties:filter {
    deviate not-supported;
  }

  deviation /oc-opt-term-properties:operational-modes/oc-opt-term-properties:mode-descriptor/oc-opt-term-properties:explicit-mode/oc-opt-term-properties:operational-mode-capabilities/oc-opt-term-properties:penalties {
    deviate not-supported;
  }

  deviation /oc-opt-term-properties:operational-modes/oc-opt-term-properties:mode-descriptor/oc-opt-term-properties:explicit-mode/oc-opt-term-properties:operational-mode-capabilities/oc-opt-term-properties:state/oc-opt-term-properties:baud-rate {
    deviate replace {
      type decimal64 {
        fraction-digits 9;
      }
    }
  }

  deviation /oc-opt-term-properties:operational-modes/oc-opt-term-properties:mode-descriptor/oc-opt-term-properties:explicit-mode/oc-opt-term-properties:operational-mode-capabilities/oc-opt-term-properties:state/oc-opt-term-properties:max-chromatic-dispersion {
    deviate not-supported;
  }

  deviation /oc-opt-term-properties:operational-modes/oc-opt-term-properties:mode-descriptor/oc-opt-term-properties:explicit-mode/oc-opt-term-properties:operational-mode-capabilities/oc-opt-term-properties:state/oc-opt-term-properties:max-differential-group-delay {
    deviate not-supported;
  }

  deviation /oc-opt-term-properties:operational-modes/oc-opt-term-properties:mode-descriptor/oc-opt-term-properties:explicit-mode/oc-opt-term-properties:operational-mode-capabilities/oc-opt-term-properties:state/oc-opt-term-properties:max-input-power {
    deviate not-supported;
  }

  deviation /oc-opt-term-properties:operational-modes/oc-opt-term-properties:mode-descriptor/oc-opt-term-properties:explicit-mode/oc-opt-term-properties:operational-mode-capabilities/oc-opt-term-properties:state/oc-opt-term-properties:max-polarization-dependent-loss {
    deviate not-supported;
  }

  deviation /oc-opt-term-properties:operational-modes/oc-opt-term-properties:mode-descriptor/oc-opt-term-properties:explicit-mode/oc-opt-term-properties:operational-mode-capabilities/oc-opt-term-properties:state/oc-opt-term-properties:min-input-power {
    deviate not-supported;
  }

  deviation /oc-opt-term-properties:operational-modes/oc-opt-term-properties:mode-descriptor/oc-opt-term-properties:explicit-mode/oc-opt-term-properties:operational-mode-capabilities/oc-opt-term-properties:state/oc-opt-term-properties:min-rx-osnr {
    deviate not-supported;
  }

  deviation /oc-opt-term-properties:operational-modes/oc-opt-term-properties:mode-descriptor/oc-opt-term-properties:explicit-mode/oc-opt-term-properties:operational-mode-capabilities/oc-opt-term-properties:state/oc-opt-term-properties:min-tx-osnr {
    deviate not-supported;
  }

  deviation /oc-opt-term-properties:operational-modes/oc-opt-term-properties:mode-descriptor/oc-opt-term-properties:explicit-mode/oc-opt-term-properties:operational-mode-capabilities/oc-opt-term-properties:state/oc-opt-term-properties:optical-channel-spectrum-width {
    deviate not-supported;
  }

  deviation /oc-opt-term-properties:operational-modes/oc-opt-term-properties:mode-descriptor/oc-opt-term-properties:explicit-mode/oc-opt-term-properties:optical-channel-config-value-constraints/oc-opt-term-properties:state/oc-opt-term-properties:grid-type {
    deviate not-supported;
  }

  deviation /oc-opt-term-properties:operational-modes/oc-opt-term-properties:mode-descriptor/oc-opt-term-properties:explicit-mode/oc-opt-term-properties:optical-channel-config-value-constraints/oc-opt-term-properties:state/oc-opt-term-properties:max-output-power {
    deviate replace {
      type decimal64 {
        fraction-digits 3;
      }
    }
  }

  deviation /oc-opt-term-properties:operational-modes/oc-opt-term-properties:mode-descriptor/oc-opt-term-properties:explicit-mode/oc-opt-term-properties:optical-channel-config-value-constraints/oc-opt-term-properties:state/oc-opt-term-properties:min-channel-spacing {
    deviate not-supported;
  }

  deviation /oc-opt-term-properties:operational-modes/oc-opt-term-properties:mode-descriptor/oc-opt-term-properties:explicit-mode/oc-opt-term-properties:optical-channel-config-value-constraints/oc-opt-term-properties:state/oc-opt-term-properties:min-output-power {
    deviate replace {
      type decimal64 {
        fraction-digits 3;
      }
    }
  }

}
