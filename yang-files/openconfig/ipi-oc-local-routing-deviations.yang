module ipi-oc-local-routing-deviations {
  namespace   "http://www.ipinfusion.com/yang/ocnos/ipi-oc-local-routing-deviations";
  prefix "ipi-oc-local-routing-deviations";

  import openconfig-local-routing { prefix oc-loc-rt; }

  revision "2022-01-19" {
    description "Local-routing deviations";
  }

  deviation /oc-loc-rt:local-routes {
    deviate not-supported;
  }
}
