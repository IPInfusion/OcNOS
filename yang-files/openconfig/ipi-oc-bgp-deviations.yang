module ipi-oc-bgp-deviations {
  namespace   "http://www.ipinfusion.com/yang/ocnos/ipi-oc-bgp-deviations";
  prefix "ipi-oc-bgp-deviations";

  import openconfig-bgp { prefix oc-bgp; }

  revision "2022-01-19" {
    description "BGP deviations";
  }

  deviation /oc-bgp:bgp {
    deviate not-supported;
  }

}
