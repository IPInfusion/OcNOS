/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-zebos-dhcpc.yang
*
*/

submodule ipi-zebos-dhcpc {

    belongs-to  ipi-zebos { prefix ipi-zebos; }

    import cml-data-types {
        prefix cml-data-types;
    }

    organization
        "IP Infusion Inc.";

    contact
        "Address: 3965 Freedom Circle, Suite 200, Santa Clara, CA 95054
        Phone: +1 408-400-1900
        E-mail: support@ipinfusion.com
        Web: http://www.ipinfusion.com/";

    description
        "dhcp_client_configuration";


    revision "2018-06-21" {
        description " Initial Version.";
        reference "";
    }


    grouping  dhcpClientInterface-grouping {
    description
        "DHCP interface related operations";
    container dhcpClientInterface {
        description
            "DHCP interface related operations";
        leaf address  {
            type  cml-data-types:CML_BOOL_T;
            description "";
        } // END of address definition.

        leaf nameserver  {
            type  cml-data-types:CML_BOOL_T;
            description "";
        } // END of nameserver definition.

        leaf logserver  {
            type  cml-data-types:CML_BOOL_T;
            description "";
        } // END of logserver definition.

        leaf hostname  {
            type  cml-data-types:CML_BOOL_T;
            description "";
        } // END of hostname definition.

        leaf ntpserver  {
            type  cml-data-types:CML_BOOL_T;
            description "";
        } // END of ntpserver definition.

        leaf ipv6address  {
            type  cml-data-types:CML_BOOL_T;
            description "";
        } // END of ipv6address definition.

        leaf ipv6nameserver  {
            type  cml-data-types:CML_BOOL_T;
            description "";
        } // END of ipv6nameserver definition.


        list prefixIpv6Addr {
            key "prefixName";
            description
                "IPv6 address configured using learnt Prefix from DHCP Server";
            leaf prefixName  {
                type  cml-data-types:CML_STRING_T;
                description "";
            } // END of prefixName definition.

            leaf-list suffixIpv6Addr  {
                type  cml-data-types:CML_STRING_T;
                description "";
            } // END of suffixIpv6Addr definition.

        } // End of prefixIpv6Addr-list
        container PrefixLearning {
            description
                "Learnt prefix parameters";
            leaf learnPrefix  {
                type  cml-data-types:CML_STRING_T {
                    length "1..255";
                }
                description "";
            } // END of learnPrefix definition.

            leaf learntPrefix  {
                type  cml-data-types:CML_IPV6_PREFIX_T;
                config false;
                description "Learnt prefix addr from DHCP server";
            } // END of learntPrefix definition.

            leaf maxLifeTime  {
                type  cml-data-types:CML_UINT32_T;
                config false;
                description "Learnt Prefix Max lifetime in secs";
            } // END of maxLifeTime definition.

            leaf prefferedLifeTime  {
                type  cml-data-types:CML_UINT32_T;
                config false;
                description "Learnt Prefix Preffered life time in secs";
            } // END of prefferedLifeTime definition.

        } // END of PrefixLearning-container definition.
    } // END of dhcpClientInterface-container definition.
    } // END of dhcpClientInterface-container definition.


}
