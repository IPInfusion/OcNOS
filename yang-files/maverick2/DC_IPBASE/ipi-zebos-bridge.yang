/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-zebos-bridge.yang
*
*/

submodule ipi-zebos-bridge {

    belongs-to  ipi-zebos { prefix ipi-zebos; }

    import cml-data-types {
        prefix cml-data-types;
    }

    import feature-list {
        prefix feature-list;
    }

    include ipi-zebos-interface;
    include ipi-zebos-vlan;
    include ipi-zebos-switchportinterface;
    include ipi-zebos-mstp;
    include ipi-zebos-lldpv2;
    include ipi-zebos-dcb;
    organization
        "IP Infusion Inc.";

    contact
        "Address: 3965 Freedom Circle, Suite 200, Santa Clara, CA 95054
        Phone: +1 408-400-1900
        E-mail: support@ipinfusion.com
        Web: http://www.ipinfusion.com/";

    description
        "Layer-2 bridge configurations";


    revision "2018-06-21" {
        description " Initial Version.";
        reference "";
    }



    grouping bridge-grouping {
    description
        "bridge";
        list bridge {
            key "bridgeId";
            description
                "bridge";
            leaf bridgeId  {
                type  cml-data-types:CML_STRING_T;
                description "";
            } // END of bridgeId definition.

            leaf bridgeType  {
                type  cml-data-types:CML_BRIDGE_PROTOCOL_T;
                mandatory true;
                description "";
            } // END of bridgeType definition.

            leaf providerType  {
                if-feature feature-list:HAVE_PROVIDER_BRIDGE;
                type  cml-data-types:CML_PROVIDER_EDGE_T;
                description "";
            } // END of providerType definition.

            leaf bridgeMac  {
                if-feature feature-list:HAVE_I_BEB;
                if-feature feature-list:HAVE_B_BEB;
                if-feature feature-list:HAVE_UDLD;
                type  cml-data-types:CML_MAC_ADDR_T;
                description "";
            } // END of bridgeMac definition.

            leaf learning  {
                type  cml-data-types:CML_BOOL_T;
                description "";
            } // END of learning definition.

            leaf topologyType  {
                type  cml-data-types:CML_BRIDGE_TOPOLOGY_T;
                mandatory true;
                description "";
            } // END of topologyType definition.

            leaf brType  {
                type  cml-data-types:CML_BRIDGE_TYPE_T;
                description "";
            } // END of brType definition.

            leaf mstpEnable  {
                type  cml-data-types:CML_INT32_T;
                default "1";
                description "";
            } // END of mstpEnable definition.

            leaf bridgeForward  {
                type  cml-data-types:CML_BRIDGE_FORWARD_T;
                description "";
            } // END of bridgeForward definition.

            leaf macType  {
                type  cml-data-types:CML_MACTYPE_T;
                description "";
            } // END of macType definition.


            list interface {
                key "ifName";
                description
                    " Group of bridge attribute having interface property";
                leaf ifName  {
                    type  cml-data-types:CML_STRING_T;
                    description "";
                } // END of ifName definition.

                leaf spanningTreeStatus  {
                    type  cml-data-types:CML_SPANNINGTREE_ENABLE_DISABLE_T;
                    mandatory true;
                    description "";
                } // END of spanningTreeStatus definition.

            } // End of interface-list

            list staticFdb {
                key "ifName";
                description
                    "static forwarding table entry for the bridge";
                leaf ifName  {
                    type  cml-data-types:CML_STRING_T;
                    description "";
                } // END of ifName definition.

                leaf-list macAddr  {
                    type  cml-data-types:CML_MAC_ADDR_T;
                    description "";
                } // END of macAddr definition.

                leaf discardForward  {
                    type  cml-data-types:CML_DISCARDFORWARD_T;
                    description "";
                } // END of discardForward definition.

                leaf macAddressTableLearning  {
                    type  cml-data-types:CML_ENABLE_DISABLE_T;
                    default "enable";
                    description "";
                } // END of macAddressTableLearning definition.

                leaf macLimit  {
                    if-feature feature-list:HAVE_CUSTOM_CLI_STYLE;
                    type  cml-data-types:CML_INT32_T;
                    description "";
                } // END of macLimit definition.

                leaf macLimitRange  {
                    if-feature feature-list:HAVE_CUSTOM_CLI_STYLE;
                    type  cml-data-types:CML_INT32_T {
                         range "5..32768";
                    }
                    description "";
                } // END of macLimitRange definition.

            } // End of staticFdb-list

            list oepMapTab {
                if-feature feature-list:HAVE_VLAN;
                key "oepTableName";
                description
                    "oepMapTab";
                leaf oepTableName  {
                    type  cml-data-types:CML_STRING_T;
                    description "";
                } // END of oepTableName definition.

                leaf oepType  {
                    type  cml-data-types:CML_UINT32_T;
                    config false;
                    description "";
                } // END of oepType definition.


                list oepvlan {
                    key "oepId";
                    description
                        "oepvlan";
                    leaf oepvlanTypeId  {
                        type  cml-data-types:CML_OEP_VLAN_TYPE_T;
                        description "";
                    } // END of oepvlanTypeId definition.

                    leaf-list oepvlanId  {
                        type  cml-data-types:CML_UINT16_T;
                        description "";
                    } // END of oepvlanId definition.

                    leaf oepId  {
                        type  cml-data-types:CML_STRING_T;
                        description "";
                    } // END of oepId definition.

                } // End of oepvlan-list
            } // End of oepMapTab-list

            list cvlanRegTab {
                if-feature feature-list:HAVE_VLAN;
                key "tablename";
                description
                    "cvlanRegTab";
                leaf tablename  {
                    type  cml-data-types:CML_STRING_T;
                    description "";
                } // END of tablename definition.


                list svlanReg {
                    if-feature feature-list:HAVE_PROVIDER_BRIDGE;
                    key "svlanRegId";
                    description
                        "svlanReg";
                    leaf svlanRegId  {
                        type  cml-data-types:CML_UINT16_T {
                             range "1..4094";
                        }
                        description "";
                    } // END of svlanRegId definition.


                    list cvlanReg {
                        key "cvlanRegId";
                        description
                            "cvlanReg";
                        leaf cvlanRegId  {
                            type  cml-data-types:CML_RANGE_T;
                            description "";
                        } // END of cvlanRegId definition.

                        leaf cvlanPepConfig  {
                            type  cml-data-types:CML_CVLAN_CONFIG_T;
                            description "";
                        } // END of cvlanPepConfig definition.

                        leaf Tcvid  {
                            type  cml-data-types:CML_UINT16_T {
                                 range "1..4094";
                            }
                            description "";
                        } // END of Tcvid definition.

                        leaf svlanCos  {
                            type  cml-data-types:CML_INT8_T {
                                 range "0..7";
                            }
                            description "";
                        } // END of svlanCos definition.

                        leaf svlanCfi  {
                            type  cml-data-types:CML_INT8_T {
                                 range "0..1";
                            }
                            description "";
                        } // END of svlanCfi definition.

                        leaf cvlanCos  {
                            type  cml-data-types:CML_INT8_T {
                                 range "0..7";
                            }
                            description "";
                        } // END of cvlanCos definition.

                        leaf cvlanCfi  {
                            type  cml-data-types:CML_INT8_T {
                                 range "0..1";
                            }
                            description "";
                        } // END of cvlanCfi definition.

                    } // End of cvlanReg-list
                } // End of svlanReg-list
            } // End of cvlanRegTab-list
            uses bridgeRuntimeAttrs;
            uses vlan-grouping;
            uses nsmEvcInfo-grouping;
            uses nsmOvcInfo-grouping;
            uses ovcVlanType-grouping;
            uses vlanDtag-grouping;
            uses staticMac-grouping;
            uses backboneBridgeInstance-grouping;
            uses mstpbridge-grouping;
            uses backboneBridge-grouping;
            uses evbbridge-grouping;
            uses nsmDcbBridge-grouping;
        } // End of bridge-list
    } // END of bridge-grouping definition.


    grouping spanningTree-grouping {
    description
        "spanningTree";
        list spanningTree {
            if-feature feature-list:HAVE_DEFAULT_BRIDGE;
            key "bridgeId";
            description
                "spanningTree";
            leaf bridgeId  {
                type  cml-data-types:CML_STRING_T;
                description "";
            } // END of bridgeId definition.

            leaf spanningTreeMode  {
                type  cml-data-types:CML_BRIDGE_SPANMODE_T;
                description "";
            } // END of spanningTreeMode definition.

            leaf learning  {
                type  cml-data-types:CML_BOOL_T;
                description "";
            } // END of learning definition.

            leaf edgeFlag  {
                type  cml-data-types:CML_BOOL_T;
                default false;
                description "";
            } // END of edgeFlag definition.


            list staticFdb {
                key "ifName";
                description
                    "static forwarding table entry for the bridge";
                leaf ifName  {
                    type  cml-data-types:CML_STRING_T;
                    description "";
                } // END of ifName definition.

                leaf-list macAddr  {
                    type  cml-data-types:CML_MAC_ADDR_T;
                    description "";
                } // END of macAddr definition.

                leaf discardForward  {
                    type  cml-data-types:CML_DISCARDFORWARD_T;
                    description "";
                } // END of discardForward definition.

                leaf vlanId  {
                    if-feature feature-list:HAVE_PROVIDER_BRIDGE;
                    type  cml-data-types:CML_UINT32_T {
                         range "2..4094";
                    }
                    description "";
                } // END of vlanId definition.

                leaf sVlanId  {
                    if-feature feature-list:HAVE_PROVIDER_BRIDGE;
                    type  cml-data-types:CML_UINT32_T {
                         range "2..4094";
                    }
                    description "";
                } // END of sVlanId definition.

                leaf macAddressTableLearning  {
                    type  cml-data-types:CML_ENABLE_DISABLE_T;
                    default "enable";
                    description "";
                } // END of macAddressTableLearning definition.

                leaf macLimit  {
                    if-feature feature-list:HAVE_CUSTOM_CLI_STYLE;
                    type  cml-data-types:CML_INT32_T;
                    description "";
                } // END of macLimit definition.

                leaf macLimitRange  {
                    if-feature feature-list:HAVE_CUSTOM_CLI_STYLE;
                    type  cml-data-types:CML_INT32_T {
                         range "5..32768";
                    }
                    description "";
                } // END of macLimitRange definition.

            } // End of staticFdb-list

            list spanningTreeinterface {
                key "ifName";
                description
                    " Group of bridge attribute having interface property";
                leaf ifName  {
                    type  cml-data-types:CML_STRING_T;
                    description "";
                } // END of ifName definition.

                leaf spanningState  {
                    type  cml-data-types:CML_SPANNINGTREE_ENABLE_DISABLE_T;
                    default "enable";
                    description "";
                } // END of spanningState definition.

            } // End of spanningTreeinterface-list
            uses bridgeRuntimeAttrs;
            uses mstpSpanningTree-grouping;
            uses nsmDcbDefaultBridge-grouping;
        } // End of spanningTree-list
    } // END of spanningTree-grouping definition.
    grouping bridgeRuntimeAttrs {
        description
            "bridgeRuntimeAttrs";
        leaf ageingTime  {
            type  cml-data-types:CML_UINT32_T;
            config false;
            description "";
        } // END of ageingTime definition.

        leaf spanningTreeEnable  {
            type  cml-data-types:CML_UINT32_T;
            config false;
            description "";
        } // END of spanningTreeEnable definition.

        leaf backboneEdge  {
            if-feature feature-list:HAVE_I_BEB;
            if-feature feature-list:HAVE_B_BEB;
            if-feature feature-list:HAVE_UDLD;
            type  cml-data-types:CML_UINT32_T;
            config false;
            description "";
        } // END of backboneEdge definition.

        leaf vlanNumDeletes  {
            if-feature feature-list:HAVE_PROVIDER_BRIDGE;
            type  cml-data-types:CML_UINT32_T;
            config false;
            description "";
        } // END of vlanNumDeletes definition.

        leaf trafficClassEnabled  {
            if-feature feature-list:HAVE_PROVIDER_BRIDGE;
            type  cml-data-types:CML_UINT32_T;
            config false;
            description "";
        } // END of trafficClassEnabled definition.

        leaf numCosq  {
            if-feature feature-list:HAVE_QOS;
            type  cml-data-types:CML_UINT32_T;
            config false;
            description "";
        } // END of numCosq definition.

        leaf maxMstInstances  {
            type  cml-data-types:CML_UINT16_T;
            config false;
            description "";
        } // END of maxMstInstances definition.

        leaf uniTypeMode  {
            type  cml-data-types:CML_UINT16_T;
            config false;
            description "";
        } // END of uniTypeMode definition.

    } // END of bridgeRuntimeAttrs definition.


}
