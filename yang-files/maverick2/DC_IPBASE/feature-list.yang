/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : feature-list.yang
*
*/

module feature-list {

    namespace "http://ipinfusion.com/ns/feature-list";

    prefix "feature-list";

    organization
        "IP Infusion Inc.";

    contact
        "3965 Freedom Circle, Suite 200
        Santa Clara, CA 95054 +1 408-400-1900
        E-mail: support@ipinfusion.com
        Web: http://www.ipinfusion.com/";

    description "List of features used in Zebos Module";

    revision "2015-10-15" {
        description "initial version: revisied on 2015-10-15.";
        reference "";
    }

    feature HAVE_VR {
        description "Virtual Router feature";
    }

    feature HAVE_VRF {
        description "VRF feature";
    }

    feature HAVE_BGP_EVPN {
        description "BGP EVPN feature";
    }

    feature HAVE_NVO {
        description "NVO feature";
    }

    feature HAVE_L3 {
        description "L3 feature";
    }

    feature HAVE_IPV6 {
        description "IPV6 feature";
    }

    feature HAVE_NSM_IF_ARBITER {
        description "NSM Interface Arbiter";
    }

    feature HAVE_ACL {
        description "acl feature";
    }

    feature HAVE_DHCP_CLIENT {
        description "dhcp feature";
    }

    feature HAVE_LDPD {
        description "LDP feature";
    }

    feature HAVE_TE {
        description "TE feature";
    }

    feature HAVE_AXELX {
        description "Axelx feature enabled";
    }

    feature HAVE_CUSTOM_CLI_STYLE {
        description "custom cli style";
    }

    feature HAVE_DSTE {
        description "dste feature";
    }

    feature HAVE_MPLS_RIB {
        description "dste feature";
    }

    feature HAVE_NDD {
        description "NDD feature";
    }

    feature HAVE_SR {
        description "sr mpls feature";
    }

    feature HAVE_NSM_IF_UNNUMBERED {
        description "nsm interface unnumbered feature";
    }

    feature HAVE_TDM_VC {
        description "TDM VC mpls feature";
    }

    feature HAVE_INTERFACE_NAME_MAPPING {
        description "original ifname feature";
    }

    feature HAVE_VRX {
        description "vrx  feature";
    }

    feature HAVE_L2 {
        description "l2  feature";
    }

    feature HAVE_QOS {
        description "qos  feature";
    }

    feature HAVE_TFO {
        description "tfo  feature";
    }

    feature HAVE_UDLD {
        description "udld  feature";
    }

    feature HAVE_SNMP_AGENT {
        description "SNMP agentx feature";
    }

    feature HAVE_SNMP {
        description "snmp feature";
    }

    feature HAVE_MPLS {
        description "mpls feature";
    }

    feature HAVE_TRILLD {
        description "trill  feature";
    }

    feature HAVE_VXLAN {
        description "vxlan  feature";
    }

    feature HAVE_FLEXPORT {
        description "Flexport Feature";
    }

    feature HAVE_TRIDENT2 {
        description "Trident2 Feature";
    }

    feature HAVE_TRIDENT2PLUS {
        description "Trident2plus Feature";
    }

    feature HAVE_TOMAHAWK {
        description "Tomahawk Feature";
    }

    feature HAVE_BROADCOM {
        description "broadcom feature";
    }

    feature HAVE_DUNE {
        description "dune feature";
    }

    feature HAVE_HAL {
        description "hal feature";
    }

    feature HAVE_MARVELL {
        description "marvell feature";
    }

    feature HAVE_SWFWDR {
        description "swfwdr feature";
    }

    feature HAVE_RATE_LIMIT {
        description "rate limit feature";
    }

    feature HAVE_LACP {
        description "lacp feature";
    }

    feature HAVE_BCM_UFT {
        description "bcm uft feature";
    }

    feature HAVE_ELK_TCAM {
        description "elk tcam feature";
    }

    feature HAVE_HELIX4 {
        description "helix feature";
    }

    feature ENABLE_HAL_PATH {
        description "hal path feature";
    }

    feature HAVE_GRE_KEY {
        description "hal path feature";
    }

    feature HAVE_TUNNEL {
        description "hal path feature";
    }

    feature HAVE_VPORT {
        description "vport feature";
    }

    feature HAVE_MPLS_STATS {
        description "mpls counters";
    }

    feature HAVE_TUNNEL_IPV6 {
        description "tunnel ipv6 feature";
    }

    feature HAVE_MCEC {
        description "mcec feature";
    }

    feature HAVE_PORT_BUNDLE {
        description "Port bundle feature";
    }

    feature HAVE_OBM_DROP_CNTRS {
        description "OBM drop counters feature";
    }

    feature HAVE_TOMAHAWK2 {
        description "Tomahawk2 chipset";
    }

    feature HAVE_CUSTOM1_HW_BFD {
        description "dune bfd hardware offload feature";
    }

    feature HAVE_CUSTOM2_HW_BFD {
        description "tomahawk, tomahawk2, trident3 bfd hardware offload feature";
    }

    feature HAVE_DEFAULT_BRIDGE {
        description "default bridge feature";
    }

    feature HAL_DEBUG_L2_PKT_H {
        description "layer2 hal pkt debug";
    }

    feature HAVE_PBB_TE {
        description "pbb te bridge feature";
    }

    feature HAVE_PVLAN {
        description "pvlan feature";
    }

    feature HAVE_PROVIDER_BRIDGE {
        description "provider feature";
    }

    feature HAVE_G8032V2 {
        description "g8032v2 feature";
    }

    feature HAVE_G8032 {
        description "g8032 feature";
    }

    feature NSM_VLAN_ERPS_CONF {
        description "vlan erps conf feature";
    }

    feature HAVE_SUBSCRIBER_INTERFACE {
        description "Subscriber Interface feature";
    }

    feature HAVE_HA {
        description "HA feature";
    }

    feature HAVE_IPSEC {
        description "IPSEC feature";
    }

    feature HAVE_BFD {
        description "BFD feature";
    }

    feature HAVE_HQOS {
        description "hqos feature enabled";
    }

    feature HAVE_INTELFM {
        description "intelfm feature enabled";
    }

    feature HAVE_I_BEB {
        description "beb feature enabled";
    }

    feature HAVE_VLAN {
        description "vlan feature";
    }

    feature HAVE_DCB {
        description "dcb feature";
    }

    feature HAVE_B_BEB {
        description "vlan feature";
    }

    feature HAVE_RPVST_PLUS {
        description "rpvst feature";
    }

    feature HAVE_SPBD {
        description "spbd feature";
    }

    feature HAVE_ASYNC {
        description "async feature";
    }

    feature HAVE_L2GP {
        description "l2gp feature";
    }

    feature HAVE_MSTPD {
        description "mstp feature";
    }

    feature HAVE_MLAG {
        description "MLAG feature";
    }

    feature HAVE_LACPV2 {
        description "LLDPV2 feature enabled";
    }

    feature HAVE_LLDPV2 {
        description "LLDPV2 feature";
    }

    feature HAVE_POE {
        description "poe feature";
    }

    feature HAVE_MULTIPATH {
        description "multipath feature";
    }

    feature HAVE_CUSTOM_CLI {
        description "custom cli feature";
    }

    feature HAVE_OSPF_MULTI_INST {
        description "OSPF Multi Instance feature";
    }

    feature HAVE_MD5 {
        description "MD5";
    }

    feature HAVE_VRF_OSPF {
        description "OSPF VRF";
    }

    feature HAVE_OSPF_TE {
        description "OSPF Traffic Engineering";
    }

    feature HAVE_OSPF_CSPF {
        description "OSPF-CSPF feature";
    }

    feature HAVE_GMPLS {
        description "GMPLS feature";
    }

    feature HAVE_RIBD {
        description "RIBD feature";
    }

    feature HAVE_OSPF_LFA {
        description "OSPF LFA";
    }

    feature HAVE_OSPF_SSO {
        description "OSPF stateful swithchover";
    }

    feature HAVE_SR_MPLS {
        description "OSPF segment route";
    }

    feature HAVE_RESTART {
        description "OSPF graceful restart";
    }

    feature HAVE_OSPF_DB_OVERFLOW {
        description "OSPF DB overflow feature";
    }

    feature HAVE_OPAQUE_LSA {
        description "OSPF-OPAQUE feature";
    }

    feature HAVE_OSPF_OD {
        description "Ospf OD feature";
    }

    feature HAVE_NSSA {
        description "Ospf nssa feature";
    }

    feature HAVE_OSPF_MULTI_AREA {
        description "Ospf Multi area feature";
    }

    feature HAVE_VRF_OSPF6 {
        description "VRF_OSPF6 feature ";
    }

    feature HAVE_OSPF6_LFA {
        description "OSPF6_LFA feature ";
    }

    feature HAVE_OSPF6_TE {
        description "OSPF6_TE feature ";
    }

    feature HAVE_OSPF6_CSPF {
        description "OSPF6_CSPF feature ";
    }

    feature HAVE_OSPF6_OD {
        description "OSPF6_OD feature ";
    }

    feature HAVE_VPN_ECMP {
        description "HAVE_VPN_ECMP feature enabled";
    }

    feature BGP_L2VPN_VPLS_MODE {
        description "l2vpn vpls feature enabled";
    }

    feature HAVE_EXT_CAP_ASN {
        description "EXT-CAP-ASN feature enabled";
    }

    feature HAVE_BGP_VPLS {
        description "bgp vpls feature enabled";
    }

    feature HAVE_BGP_LS {
        description "bgp link-state feature enabled";
    }

    feature HAVE_6PE {
        description "bgp 6PE feature enabled";
    }

    feature HAVE_BGP_TABLE_MAP {
        description "bgp table map feature enabled";
    }

    feature HAVE_TCP_MD5SIG {
        description "tcp md5 feature enabled";
    }

    feature HAVE_BGP_ADD_PATH {
        description "additional path feature enabled";
    }

    feature HAVE_BGP_AIGP {
        description "AIGP feature enabled";
    }

    feature HAVE_BGP_LU {
        description "bgp lu feature";
    }

    feature HAVE_BGP_MPLS_RESTART {
        description "bgp BGP-MPLS-RESTART feature enabled";
    }

    feature HAVE_BGP_PIC_CORE_EDGE {
        description "pic core feature";
    }

    feature HAVE_UNNUM {
        description "HAVE_UNNUM feature enabled";
    }

    feature HAVE_BFD_MAIN {
        description "BFD feature enabled";
    }

    feature HAVE_BFD_MONO {
        description "BFD-MONO feature enabled";
    }

    feature HAVE_MPLS_OAM {
        description "MPLS-OAM feature enabled";
    }

    feature HAVE_BFD_HW_OFFLOAD {
        description "BFD HW Offload feature";
    }

    feature HAVE_VRRP_V3 {
        description "VRRPV3 feature";
    }

    feature HAVE_ISIS_LFA {
        description "ISIS feature";
    }

    feature HAVE_MPLS_P2MP {
        description "MPLS P2MP feature";
    }

    feature HAVE_ISIS_MESH_GROUP {
        description "ISIS MESH GROUP feature";
    }

    feature HAVE_VRF_ISIS {
        description "ISIS VRF feature";
    }

    feature HAVE_ISIS_TE {
        description "ISIS-TE feature";
    }

    feature HAVE_WIDE_METRIC {
        description "wide metric feature";
    }

    feature HAVE_ISIS_CSPF {
        description "ISIS-CSPF feature";
    }

    feature HAVE_MULTI_TOPOLOGY {
        description "multi-topology feature";
    }

    feature HAVE_PROTOCOL_TOPOLOGY {
        description "Protocol topology feature";
    }

    feature HAVE_PIM_SMDM {
        description "PIM sparse dense mode";
    }

    feature HAVE_PIM_DM {
        description "PIM dense mode";
    }

    feature HAVE_PIM_SM {
        description "PIM sparse mode";
    }

    feature HAVE_PIM_SSM {
        description "PIM source specific multicast";
    }

    feature HAVE_PIM_MSDP_API {
        description "PIM Multicast Source Discovery Protocol";
    }

    feature HAVE_PIM_BIDIR {
        description "PIM Bidirectional";
    }

    feature HAVE_PIM_MSDP {
        description "PIM Multicast Source Discovery Protocol";
    }

    feature HAVE_PIM_ECMP_REDIRECT {
        description "PIM ECMP enabled";
    }

    feature HAVE_HOSTPD {
        description "HOSTP feature";
    }

    feature HAVE_SYSLOG {
        description "syslog feature";
    }

    feature HAVE_DEBUG_MODULE_SEVERITY {
        description "Module severity feature";
    }

    feature HAVE_SNMP_V3 {
        description "snmp version v3";
    }

    feature HAVE_AAA {
        description "aaa feature";
    }

    feature HAVE_TACACS_CLIENT {
        description "tacacs-client feature enabled";
    }

    feature HAVE_USER_MGMT {
        description "user management feature";
    }

    feature HAVE_RBAC {
        description "Role Based Access Control feature";
    }

    feature HAVE_SSH_SERVER {
        description "ssh server feature";
    }

    feature HAVE_TELNET_SERVER {
        description "telnet-server feature";
    }

    feature HAVE_HOSTP_NTP {
        description "ntp feature";
    }

    feature HAVE_RADIUS_CLIENT {
        description "radius feature";
    }

    feature HAVE_DNS_CLIENT {
        description "dns-client feature enabled";
    }

    feature HAVE_SFLOW {
        description "sFlow feature";
    }

    feature HAVE_UT {
        description "ut";
    }

    feature HAVE_COHERENT_OPTICS {
        description "Coherent Optics";
    }

    feature HAVE_FLEXLM {
        description "License feature enabled";
    }

    feature HAVE_PSERVD {
        description "PSERVD feature";
    }

    feature HAVE_ZEBOS_CORE_ANALYSER {
        description "Core file management";
    }

    feature HAVE_PBR {
        description "PBR feature";
    }

    feature HAVE_AGENTX {
        description "SNMP-AGENTX feature";
    }

    feature HAVE_DIFFSERV {
        description "enable diffserv flag";
    }

    feature HAVE_TRIDENT3 {
        description "Trident3 Feature";
    }

    feature HAVE_MAC_AUTH {
        description "MAC_AUTH feature";
    }

    feature HAVE_RIP_GR_SUPPORT {
        description "rip gr support";
    }

    feature HAVE_VRF_RIP {
        description "rip vrf support";
    }

    feature HAVE_CUSTOM2_ACL {
        description "Custom ACL options2";
    }

    feature HAVE_DEFAULT_FILTER {
        description "Default filter support";
    }

    feature HAVE_RPF {
        description "Reverse path forwarding feature";
    }

    feature HAVE_ADVANCE_MIRROR {
        description "advance mirror feature";
    }

    feature HAVE_RIPNGD {
        description "ripng support";
    }

    feature HAVE_VRF_RIPNG {
        description "ripng vrf support";
    }

    feature HAVE_VRF_ND {
        description "vrf nd feature";
    }

    feature HAVE_IMI {
        description "imi system features";
    }

    feature PNE_VERSION_6_9 {
        description "clear user feature";
    }

    feature HAVE_REBOOT {
        description "imi reboot feature";
    }

    feature HAVE_RTADV {
        description "rtadv feature";
    }

    feature HAVE_MIP6 {
        description "mip6 feature";
    }

    feature HAVE_NAT {
        description "NAT feature";
    }

    feature HAVE_GUEST_VM {
        description "Virtual Machine feature";
    }

    feature NOT_HAVE_DEBUG_MODULE_SEVERITY {
        description "It is negation of HAVE_DEBUG_MODULE_SEVERITY";
    }

    feature NOT_HAVE_SWFWDR {
        description "It is negation of HAVE_SWFWDR";
    }

    feature NOT_HAVE_ADVANCE_MIRROR {
        description "It is negation of HAVE_ADVANCE_MIRROR";
    }

    feature NOT_HAVE_DUNE {
        description "It is negation of HAVE_DUNE";
    }

    feature NOT_HAVE_TOMAHAWK {
        description "It is negation of HAVE_TOMAHAWK";
    }

    feature NOT_HAVE_BROADCOM {
        description "It is negation of HAVE_BROADCOM";
    }

    feature NOT_HAVE_MPLS {
        description "It is negation of HAVE_MPLS";
    }

    feature NOT_HAVE_HELIX4 {
        description "It is negation of HAVE_HELIX4";
    }

    feature NOT_HAVE_BFD_HW_OFFLOAD {
        description "It is negation of HAVE_BFD_HW_OFFLOAD";
    }

    feature NOT_HAVE_NDD {
        description "It is negation of HAVE_NDD";
    }

    feature NOT_HAVE_HQOS {
        description "It is negation of HAVE_HQOS";
    }

}
