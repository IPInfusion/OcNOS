/*
* Copyright (C) 2018 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-zebos-acl.yang
*
*/

submodule ipi-zebos-acl {

    belongs-to  ipi-zebos { prefix ipi-zebos; }

    import cml-data-types {
        prefix cml-data-types;
    }

    import feature-list {
        prefix feature-list;
    }

    organization
        "IP Infusion Inc.";

    contact
        "Address: 3965 Freedom Circle, Suite 200, Santa Clara, CA 95054
        Phone: +1 408-400-1900
        E-mail: support@ipinfusion.com
        Web: http://www.ipinfusion.com/";

    description
        "Access List Related Configurations";


    revision "2017-05-23" {
        description " Initial Version.";
        reference "";
    }

    grouping accessListAttr {
        description
            "accessListAttr";
        leaf remark  {
            type  cml-data-types:CML_LINE_T;
            description "";
        } // END of remark definition.

        leaf startSeqNum  {
            type  cml-data-types:CML_UINT32_T;
            description "";
        } // END of startSeqNum definition.

        leaf increment  {
            type  cml-data-types:CML_UINT64_T;
            description "";
        } // END of increment definition.

        leaf filterTypeDF  {
            type  cml-data-types:CML_ACL_FILTER_ACTION_T;
            default "deny-all";
            description "";
        } // END of filterTypeDF definition.

        leaf logDF  {
            if-feature feature-list:HAVE_SFLOW;
            type  cml-data-types:CML_BOOL_T;
            description "";
        } // END of logDF definition.

        leaf sampleDF  {
            if-feature feature-list:HAVE_SFLOW;
            type  cml-data-types:CML_BOOL_T;
            description "";
        } // END of sampleDF definition.


        list filterList {
            key "accessNumFL";
            description
                "filterList";
            leaf accessNumFL  {
                type  cml-data-types:CML_UINT32_T {
                     range "1..268435453";
                }
                description "";
            } // END of accessNumFL definition.

            leaf filterTypeFL  {
                type  cml-data-types:CML_ACL_FILTER_ACTION_T;
                description "";
            } // END of filterTypeFL definition.

            leaf logFL  {
                if-feature feature-list:HAVE_SFLOW;
                type  cml-data-types:CML_BOOL_T;
                description "";
            } // END of logFL definition.

            leaf sampleFL  {
                if-feature feature-list:HAVE_SFLOW;
                type  cml-data-types:CML_BOOL_T;
                description "";
            } // END of sampleFL definition.

            leaf redirectPortFL  {
                type  cml-data-types:CML_STRING_T;
                description "";
            } // END of redirectPortFL definition.

            leaf packetFormatFM  {
                type  cml-data-types:CML_ACL_ETHER_TYPE_T;
                description "";
            } // END of packetFormatFM definition.

            leaf cosFM  {
                type  cml-data-types:CML_INT32_T {
                     range "0..7";
                }
                description "";
            } // END of cosFM definition.

            leaf vlanFM  {
                type  cml-data-types:CML_INT32_T {
                     range "1..4094";
                }
                description "";
            } // END of vlanFM definition.

            leaf iVlanFM  {
                type  cml-data-types:CML_INT32_T {
                     range "1..4094";
                }
                description "";
            } // END of iVlanFM definition.

            leaf arpFM  {
                type  cml-data-types:CML_ACL_ARP_TYPE_T;
                description "";
            } // END of arpFM definition.

            leaf sMacFM  {
                type  cml-data-types:CML_STRING_T {
                    pattern "[0-9a-fA-F]{1,4}\\.[0-9a-fA-F]{1,4}\\.[0-9a-fA-F]{1,4}|[0-9a-fA-F]{2}\\-[0-9a-fA-F]{2}\\-[0-9a-fA-F]{2}\\-[0-9a-fA-F]{2}\\-[0-9a-fA-F]{2}\\-[0-9a-fA-F]{2}|[0-9a-fA-F]{2}:[0-9a-fA-F]{2}:[0-9a-fA-F]{2}:[0-9a-fA-F]{2}:[0-9a-fA-F]{2}:[0-9a-fA-F]{2}|any";
                    }
                    description "";
                } // END of sMacFM definition.

                leaf sMacMaskFM  {
                    type  cml-data-types:CML_STRING_T {
                        pattern "[0-9a-fA-F]{1,4}\\.[0-9a-fA-F]{1,4}\\.[0-9a-fA-F]{1,4}|[0-9a-fA-F]{2}\\-[0-9a-fA-F]{2}\\-[0-9a-fA-F]{2}\\-[0-9a-fA-F]{2}\\-[0-9a-fA-F]{2}\\-[0-9a-fA-F]{2}|[0-9a-fA-F]{2}:[0-9a-fA-F]{2}:[0-9a-fA-F]{2}:[0-9a-fA-F]{2}:[0-9a-fA-F]{2}:[0-9a-fA-F]{2}";
                        }
                        description "";
                    } // END of sMacMaskFM definition.

                    leaf dMacFM  {
                        type  cml-data-types:CML_STRING_T {
                            pattern "[0-9a-fA-F]{1,4}\\.[0-9a-fA-F]{1,4}\\.[0-9a-fA-F]{1,4}|[0-9a-fA-F]{2}\\-[0-9a-fA-F]{2}\\-[0-9a-fA-F]{2}\\-[0-9a-fA-F]{2}\\-[0-9a-fA-F]{2}\\-[0-9a-fA-F]{2}|[0-9a-fA-F]{2}:[0-9a-fA-F]{2}:[0-9a-fA-F]{2}:[0-9a-fA-F]{2}:[0-9a-fA-F]{2}:[0-9a-fA-F]{2}|any";
                            }
                            description "";
                        } // END of dMacFM definition.

                        leaf dMacMaskFM  {
                            type  cml-data-types:CML_STRING_T {
                                pattern "[0-9a-fA-F]{1,4}\\.[0-9a-fA-F]{1,4}\\.[0-9a-fA-F]{1,4}|[0-9a-fA-F]{2}\\-[0-9a-fA-F]{2}\\-[0-9a-fA-F]{2}\\-[0-9a-fA-F]{2}\\-[0-9a-fA-F]{2}\\-[0-9a-fA-F]{2}|[0-9a-fA-F]{2}:[0-9a-fA-F]{2}:[0-9a-fA-F]{2}:[0-9a-fA-F]{2}:[0-9a-fA-F]{2}:[0-9a-fA-F]{2}";
                                }
                                description "";
                            } // END of dMacMaskFM definition.

                            leaf sIpFC  {
                                type  cml-data-types:CML_ACL_ANY_IPV4_ADDR_T;
                                description "";
                            } // END of sIpFC definition.

                            leaf dIpFC  {
                                type  cml-data-types:CML_ACL_ANY_IPV4_ADDR_T;
                                description "";
                            } // END of dIpFC definition.

                            leaf protocolFC  {
                                type  cml-data-types:CML_ACL_IP_PROTO_T;
                                description "";
                            } // END of protocolFC definition.

                            leaf srcPortMinFC  {
                                type  cml-data-types:CML_UINT16_T {
                                     range "0..65535";
                                }
                                description "";
                            } // END of srcPortMinFC definition.

                            leaf srcPortMaxFC  {
                                type  cml-data-types:CML_UINT16_T {
                                     range "0..65535";
                                }
                                description "";
                            } // END of srcPortMaxFC definition.

                            leaf srcPortUdpFC  {
                                type  cml-data-types:CML_ACL_UDP_KEYWORD_T;
                                description "";
                            } // END of srcPortUdpFC definition.

                            leaf srcPortTcpFC  {
                                type  cml-data-types:CML_ACL_TCP_KEYWORD_T;
                                description "";
                            } // END of srcPortTcpFC definition.

                            leaf srcPortOperFC  {
                                type  cml-data-types:CML_ACL_PORT_OPERATIONS_T;
                                description "";
                            } // END of srcPortOperFC definition.

                            leaf destPortMinFC  {
                                type  cml-data-types:CML_UINT16_T {
                                     range "0..65535";
                                }
                                description "";
                            } // END of destPortMinFC definition.

                            leaf destPortMaxFC  {
                                type  cml-data-types:CML_UINT16_T {
                                     range "0..65535";
                                }
                                description "";
                            } // END of destPortMaxFC definition.

                            leaf destPortUdpFC  {
                                type  cml-data-types:CML_ACL_UDP_KEYWORD_T;
                                description "";
                            } // END of destPortUdpFC definition.

                            leaf destPortTcpFC  {
                                type  cml-data-types:CML_ACL_TCP_KEYWORD_T;
                                description "";
                            } // END of destPortTcpFC definition.

                            leaf destPortOperFC  {
                                type  cml-data-types:CML_ACL_PORT_OPERATIONS_T;
                                description "";
                            } // END of destPortOperFC definition.

                            leaf dscpFC  {
                                type  cml-data-types:CML_ACL_DSCP_T;
                                description "";
                            } // END of dscpFC definition.

                            leaf precedenceFC  {
                                type  cml-data-types:CML_ACL_PRECEDENCE_T;
                                description "";
                            } // END of precedenceFC definition.

                            leaf fragmentsFC  {
                                type  cml-data-types:CML_INT32_T;
                                description "";
                            } // END of fragmentsFC definition.

                            leaf vlanFC  {
                                type  cml-data-types:CML_INT32_T {
                                     range "1..4094";
                                }
                                description "";
                            } // END of vlanFC definition.

                            leaf iVlanFC  {
                                type  cml-data-types:CML_INT32_T {
                                     range "1..4094";
                                }
                                description "";
                            } // END of iVlanFC definition.

                            leaf tcpFlagFC  {
                                type  cml-data-types:CML_ACL_TCP_FLAGS_T;
                                description "";
                            } // END of tcpFlagFC definition.

                            leaf icmpMsgFC  {
                                type  cml-data-types:CML_ACL_ICMP_OPTIONS_T;
                                description "";
                            } // END of icmpMsgFC definition.

                            leaf icmpTypeFC  {
                                type  cml-data-types:CML_UINT8_T {
                                     range "0..255";
                                }
                                description "";
                            } // END of icmpTypeFC definition.

                            leaf icmpCodeFC  {
                                type  cml-data-types:CML_UINT8_T {
                                     range "0..255";
                                }
                                description "";
                            } // END of icmpCodeFC definition.

                            leaf arpFC  {
                                type  cml-data-types:CML_UINT8_T;
                                description "";
                            } // END of arpFC definition.

                            leaf protocolFZE  {
                                type  cml-data-types:CML_ACL_IPV6_PROTO_T;
                                description "";
                            } // END of protocolFZE definition.

                            leaf srcAddrFZE  {
                                if-feature feature-list:HAVE_IPV6;
                                type  cml-data-types:CML_ACL_ANY_IPV6_ADDR_T;
                                description "";
                            } // END of srcAddrFZE definition.

                            leaf srcPortOperFZE  {
                                type  cml-data-types:CML_ACL_PORT_OPERATIONS_T;
                                description "";
                            } // END of srcPortOperFZE definition.

                            leaf srcPortMaxFZE  {
                                type  cml-data-types:CML_UINT16_T {
                                     range "0..65535";
                                }
                                description "";
                            } // END of srcPortMaxFZE definition.

                            leaf srcPortMinFZE  {
                                type  cml-data-types:CML_UINT16_T {
                                     range "0..65535";
                                }
                                description "";
                            } // END of srcPortMinFZE definition.

                            leaf srcPortUdpFZE  {
                                type  cml-data-types:CML_ACL_UDP_KEYWORD_T;
                                description "";
                            } // END of srcPortUdpFZE definition.

                            leaf srcPortTcpFZE  {
                                type  cml-data-types:CML_ACL_TCP_KEYWORD_T;
                                description "";
                            } // END of srcPortTcpFZE definition.

                            leaf destAddrFZE  {
                                if-feature feature-list:HAVE_IPV6;
                                type  cml-data-types:CML_ACL_ANY_IPV6_ADDR_T;
                                description "";
                            } // END of destAddrFZE definition.

                            leaf destPortOperFZE  {
                                type  cml-data-types:CML_ACL_PORT_OPERATIONS_T;
                                description "";
                            } // END of destPortOperFZE definition.

                            leaf destPortMaxFZE  {
                                type  cml-data-types:CML_UINT16_T {
                                     range "0..65535";
                                }
                                description "";
                            } // END of destPortMaxFZE definition.

                            leaf destPortMinFZE  {
                                type  cml-data-types:CML_UINT16_T {
                                     range "0..65535";
                                }
                                description "";
                            } // END of destPortMinFZE definition.

                            leaf destPortUdpFZE  {
                                type  cml-data-types:CML_ACL_UDP_KEYWORD_T;
                                description "";
                            } // END of destPortUdpFZE definition.

                            leaf destPortTcpFZE  {
                                type  cml-data-types:CML_ACL_TCP_KEYWORD_T;
                                description "";
                            } // END of destPortTcpFZE definition.

                            leaf icmpMsgFZE  {
                                type  cml-data-types:CML_ACL_ICMPV6_OPTIONS_T;
                                description "";
                            } // END of icmpMsgFZE definition.

                            leaf icmpTypeFZE  {
                                type  cml-data-types:CML_UINT8_T {
                                     range "0..255";
                                }
                                description "";
                            } // END of icmpTypeFZE definition.

                            leaf icmpCodeFZE  {
                                type  cml-data-types:CML_UINT8_T {
                                     range "0..255";
                                }
                                description "";
                            } // END of icmpCodeFZE definition.

                            leaf flowLabelFZE  {
                                type  cml-data-types:CML_INT32_T {
                                     range "0..1048575";
                                }
                                description "";
                            } // END of flowLabelFZE definition.

                            leaf fragmentsFZE  {
                                type  cml-data-types:CML_INT32_T;
                                description "";
                            } // END of fragmentsFZE definition.

                            leaf dscpFZE  {
                                type  cml-data-types:CML_ACL_DSCP_T;
                                description "";
                            } // END of dscpFZE definition.

                            leaf tcpFlagFZE  {
                                type  cml-data-types:CML_ACL_TCP_FLAGS_T;
                                description "";
                            } // END of tcpFlagFZE definition.

                            leaf vlanFZE  {
                                type  cml-data-types:CML_INT32_T {
                                     range "1..4094";
                                }
                                description "";
                            } // END of vlanFZE definition.

                            leaf iVlanFZE  {
                                type  cml-data-types:CML_INT32_T {
                                     range "1..4094";
                                }
                                description "";
                            } // END of iVlanFZE definition.

        } // End of filterList-list
    } // END of accessListAttr definition.

    grouping  accessMasterIPv4-grouping {
    description
        "accessMasterIPv4";
    container accessMasterIPv4 {
        description
            "accessMasterIPv4";

        list accessListIPv4 {
            key "aclNameIPv4";
            description
                "accessListIPv4";
            leaf aclNameIPv4  {
                type  cml-data-types:CML_STRING_T {
                    length "1..64";
                }
                description "";
            } // END of aclNameIPv4 definition.

            uses accessListAttr;
        } // End of accessListIPv4-list

        list accessListIPv4Standard {
            key "aclNameIpv4Standard";
            description
                "accessListIPv4Standard";
            leaf aclNameIpv4Standard  {
                type  cml-data-types:CML_STRING_T {
                    length "1..64";
                }
                description "";
            } // END of aclNameIpv4Standard definition.


            list accessListIPv4StandardFilterlist {
                key "srcIpStd";
                description
                    "accessListIPv4StandardFilterlist";
                leaf srcIpStd  {
                    type  cml-data-types:CML_ACL_ANY_IPV4_ADDR_T;
                    description "";
                } // END of srcIpStd definition.

                leaf filterTypeStd  {
                    type  cml-data-types:CML_ACL_FILTER_TYPE_T;
                    mandatory true;
                    description "";
                } // END of filterTypeStd definition.

            } // End of accessListIPv4StandardFilterlist-list
        } // End of accessListIPv4Standard-list

        list accessListMac {
            key "aclNameMAC";
            description
                "accessListMac";
            leaf aclNameMAC  {
                type  cml-data-types:CML_STRING_T {
                    length "1..64";
                }
                description "";
            } // END of aclNameMAC definition.

            uses accessListAttr;
        } // End of accessListMac-list
    } // END of accessMasterIPv4-container definition.
    } // END of accessMasterIPv4-container definition.

    grouping  accessMasterARP-grouping {
    description
        "accessMasterARP";
    container accessMasterARP {
        if-feature feature-list:HAVE_CUSTOM2_ACL;
        description
            "accessMasterARP";

        list accessListARP {
            key "aclNameARP";
            description
                "accessListARP";
            leaf aclNameARP  {
                type  cml-data-types:CML_STRING_T {
                    length "1..64";
                }
                description "";
            } // END of aclNameARP definition.

            uses accessListAttr;
        } // End of accessListARP-list
    } // END of accessMasterARP-container definition.
    } // END of accessMasterARP-container definition.

    grouping  accessMasterIPv6-grouping {
    description
        "accessMasterIPv6";
    container accessMasterIPv6 {
        description
            "accessMasterIPv6";

        list accessListIPv6 {
            key "aclNameIPv6";
            description
                "accessListIPv6";
            leaf aclNameIPv6  {
                type  cml-data-types:CML_STRING_T {
                    length "1..64";
                }
                description "";
            } // END of aclNameIPv6 definition.

            uses accessListAttr;
        } // End of accessListIPv6-list

        list accessListIPv6Standard {
            if-feature feature-list:HAVE_IPV6;
            key "aclNameIpv6Standard";
            description
                "accessListIPv6Standard";
            leaf aclNameIpv6Standard  {
                type  cml-data-types:CML_STRING_T {
                    length "1..64";
                }
                description "";
            } // END of aclNameIpv6Standard definition.


            list accessListIPv6StandardFilterlist {
                if-feature feature-list:HAVE_IPV6;
                key "srcIpv6Std";
                description
                    "accessListIPv6StandardFilterlist";
                leaf srcIpv6Std  {
                    type  cml-data-types:CML_ACL_ANY_IPV6_ADDR_T;
                    description "";
                } // END of srcIpv6Std definition.

                leaf filterTypeStd  {
                    type  cml-data-types:CML_ACL_FILTER_TYPE_T;
                    mandatory true;
                    description "";
                } // END of filterTypeStd definition.

            } // End of accessListIPv6StandardFilterlist-list
        } // End of accessListIPv6Standard-list
    } // END of accessMasterIPv6-container definition.
    } // END of accessMasterIPv6-container definition.


}
