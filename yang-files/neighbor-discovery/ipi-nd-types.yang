/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-nd-types.yang
*
*/

module ipi-nd-types {

    yang-version 1.1;

    namespace   "http://www.ipinfusion.com/yang/ocnos/ipi-nd-types";

    prefix "ipi-nd-types";

    organization
        "IP Infusion Inc.";

    contact
        "Address: 3965 Freedom Circle, Suite 200, Santa Clara, CA 95054
         Phone: +1 408-400-1900
         E-mail: support@ipinfusion.com
         Web: http://www.ipinfusion.com/";

    description
        "YANG version of the ipi-nd-types";


    revision "2022-06-01" {
        description "Updated the yang file with feature";
        reference " 0.4.0.";
    }

    revision "2021-09-03" {
        description "Update descriptions of attribute";
        reference " 0.3.0.";
    }

    revision "2020-12-15" {
        description "Change to have data-types in lower case instead of camel case";
        reference " 0.2.0.";
    }

    revision "2020-07-30" {
        description "Initial Version";
        reference " 0.1.0.";
    }



    typedef  ndd_nd_state_t {
        type enumeration {
            enum INCOMPLETE {
                value 1;
                description "First ARP request sent, send ARP request.";
            }
            enum REACHABLE {
                value 2;
                description "Normal expiration reset use counter.";
            }
            enum STALE {
                value 4;
                description "Still usable, needs verification reset use counter, change state to delay";
            }
            enum DELAY {
                value 8;
                description " Schedule ARP request, needs verification reset use counter";
            }
            enum PROBE {
                value 16;
                description "ARP request reset use counter.";
            }
            enum FAILED {
                value 32;
                description "ARP requests response not received.";
            }
            enum PERMANENT {
                value 128;
                description "Never expires; never verified reset use counter";
            }
        }
        description "type definition for NDD_ND_STATE_T";
    }

    typedef  ndd_nd_if_type_t {
        type enumeration {
            enum down {
                value 0;
                description "Static Adjacencies attached to down interface";
            }
            enum up {
                value 1;
                description "Static Adjacencies attached to down interface";
            }
        }
        description "type definition for NDD_ND_IF_TYPE_T";
    }

    typedef  ndd_nd_src_type_t {
        type enumeration {
            enum static {
                value 0;
                description "Static source";
            }
            enum icmpv6 {
                value 1;
                description "dynamic source";
            }
        }
        description "type definition for NDD_ND_SRC_TYPE_T";
    }

}
