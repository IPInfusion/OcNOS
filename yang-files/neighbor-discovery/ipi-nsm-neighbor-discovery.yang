/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-nsm-neighbor-discovery.yang
*
*/

module ipi-nsm-neighbor-discovery {

    yang-version 1.1;

    namespace   "http://www.ipinfusion.com/yang/ocnos/ipi-nsm-neighbor-discovery";

    prefix "ipi-nsm-neighbor-discovery";

    import cml-data-types {
        prefix cml-data-types;
        revision-date 2022-09-30;
    }

    import ipi-interface {
        prefix ipi-interface;
        revision-date 2022-08-24;
    }

    import ietf-inet-types {
        prefix inet;
        revision-date 2013-07-15;
    }

    import feature-list {
        prefix feature-list;
        revision-date 2023-02-21;
    }

    organization
        "IP Infusion Inc.";

    contact
        "Address: 3965 Freedom Circle, Suite 200, Santa Clara, CA 95054
         Phone: +1 408-400-1900
         E-mail: support@ipinfusion.com
         Web: http://www.ipinfusion.com/";

    description
        "Neighbor Discovery";


    revision "2022-06-01" {
        description "Updated the yang file with feature";
        reference " 0.3.0.";
    }

    revision "2020-12-15" {
        description "Change to have data-types in lower case instead of camel case";
        reference " 0.2.0.";
    }

    revision "2020-07-10" {
        description "Initial Version";
        reference " 0.1.0.";
    }

    grouping global-ipv6-nd {
        description
            "Nd global level ipv6 neighbor information";

        list entry {
        when " /ipi-nsm-neighbor-discovery:neighbor-discovery/ipi-nsm-neighbor-discovery:entry/ipi-nsm-neighbor-discovery:config/ipi-nsm-neighbor-discovery:mac-address ";
            key "ipv6-address name";
            description
                "Nd global level ipv6 neighbor information";
            leaf ipv6-address  {
                type  leafref {
                    path  "../config/ipv6-address";
                }
                description "";
            } // END of ipv6-address definition.

            leaf name  {
                type  leafref {
                    path  "/ipi-interface:interfaces/ipi-interface:interface/ipi-interface:name";
                }
                description "";
            } // END of name definition.

            container config {
                description
                    "Nd ipv6 neighbor information";
                uses link-layer-ipv6-top;
            } // END of config-container definition.
            container state {
                config false;
                description
                    "Operational state data";
                uses link-layer-ipv6-top;
            } // END of state-container definition.
        } // End of entry-list
    } // END of global-ipv6-nd definition.
    grouping link-layer-ipv6-top {
        description
            "link-layer address information";
        leaf ipv6-address  {
            type  inet:ipv6-address;
            description "";
        } // END of ipv6-address definition.

        leaf mac-address  {
            type  cml-data-types:cml_mac_addr_t {
                length "1..1965";
            }
            mandatory true;
            description "";
        } // END of mac-address definition.

    } // END of link-layer-ipv6-top definition.

    grouping  neighbor-discovery-grouping {
    description
        "neighbor discovery global level information";
    container neighbor-discovery {
        if-feature feature-list:HAVE_L3;
        if-feature feature-list:HAVE_IPV6;
        if-feature feature-list:NOT_HAVE_NDD;
        description
            "neighbor discovery global level information";
        uses global-ipv6-nd;
    } // END of neighbor-discovery-container definition.
    } // END of neighbor-discovery-grouping definition.

    uses neighbor-discovery-grouping;

    rpc clear-ipv6-neighbors {
        if-feature feature-list:HAVE_L3;
        if-feature feature-list:HAVE_IPV6;
        if-feature feature-list:NOT_HAVE_NDD;
        description "clear ipv6 neighbors";
    }

}
