/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-rip-vrf.yang
*
*/

submodule ipi-rip-vrf {

    yang-version 1.1;

    belongs-to  ipi-rip { prefix ipi-rip; }

    import feature-list {
        prefix feature-list;
        revision-date 2026-09-15;
    }

    import ipi-rip-types {
        prefix ipi-rip-types;
        revision-date 2024-09-05;
    }

    import ipi-network-instance {
        prefix ipi-network-instance;
        revision-date 2026-08-12;
    }

    import ipi-vrf {
        prefix ipi-vrf;
        revision-date 2026-08-12;
    }

    include ipi-rip-common { revision-date 2023-01-18;}
    organization
        "IP Infusion Inc.";

    contact
        "Address: 3965 Freedom Circle, Suite 200, Santa Clara, CA 95054
         Phone: +1 408-400-1900
         E-mail: support@ipinfusion.com
         Web: http://www.ipinfusion.com/";

    description
        "Data model for IPI RIP VRF Configuration and Operational state";


    revision "2023-01-18" {
        description "Added cli input for source-prefix";
        reference " 0.1.3.";
    }

    revision "2022-09-29" {
        description "Modified RPC names";
        reference " 0.1.2.";
    }

    revision "2022-08-09" {
        description "Added get_api header file for vrf";
        reference " 0.1.1.";
    }

    revision "2022-07-26" {
        description "Initial Version";
        reference " 0.1.0.";
    }

    grouping rip-vrf-redistribute-policies-config {
        description
            "Grouping for redistribute attributes";
        leaf route-type  {
            type  ipi-rip-types:rip_vrf_redistribute_proto_t;
            description "Use this attribute to redistributes only specified route-type routes
                        matching the specified route type into the RIP routing instance";
        } // END of route-type definition.

        leaf metric  {
            type  uint8 {
                 range "0..16"  {
                    description "0..16: Supported range 0 - 16";
                 }
            }
            description "Use this attribute to set the metric used for the redistributed route";
        } // END of metric definition.

        leaf route-map  {
            type  string {
                length "1..1965";
                pattern "[^?' =,>|]+";
            }
            description "Use this attribute to set the name of the route-map";
        } // END of route-map definition.

    } // END of rip-vrf-redistribute-policies-config definition.
    grouping rip-vrf-redistribute-policies-top {
        description
            "Grouping for RIP VRF redistribute attributes";
        container redistribute-policies {
            description
                "Redistributes routes learned from other routing protocols into the RIP
                        routing instance";

            list redistribute-policy {
                key "route-type";
                description
                    "List of redistributes routes";
                leaf route-type  {
                    type  leafref {
                        path  "../config/route-type";
                    }
                    description "Use this attribute to redistributes only specified route-type routes
                                matching the specified route type into the RIP routing instance";
                } // END of route-type definition.

                container config {
                    description
                        "Configuration data for Redistribute routes";
                    uses rip-vrf-redistribute-policies-config;
                } // END of config-container definition.
                container state {
                    config false;
                    description
                        "Operational data for Redistribute routes";
                    uses rip-vrf-redistribute-policies-config;
                } // END of state-container definition.
            } // End of redistribute-policy-list
        } // END of redistribute-policies-container definition.
    } // END of rip-vrf-redistribute-policies-top definition.
    grouping rip-vrf-config {
        description
            "Grouping for RIP VRF attributes";
        leaf vrf-name  {
            type  leafref {
                path  "/ipi-network-instance:network-instances/ipi-network-instance:network-instance/ipi-vrf:vrf/ipi-vrf:config/ipi-vrf:vrf-name";
            }
            description "VRF name";
        } // END of vrf-name definition.

    } // END of rip-vrf-config definition.
    grouping rip-vrfs-top {
        description
            "Grouping for RIP VRF Configurations";

        list vrf {
            key "vrf-name";
            description
                "List of VRFs";
            leaf vrf-name  {
                type  leafref {
                    path  "../config/vrf-name";
                }
                description "VRF name";
            } // END of vrf-name definition.

            container config {
                description
                    "Configurational data for RIP VRF";
                uses rip-vrf-config;
                uses rip-instance-common-config;
            } // END of config-container definition.
            container state {
                config false;
                description
                    "Operational data for RIP VRF";
                uses rip-vrf-config;
                uses rip-instance-common-config;
            } // END of state-container definition.
            uses rip-distances-top;
            uses rip-vrf-redistribute-policies-top;
            uses rip-default-information-top;
            uses rip-offset-lists-top;
            uses rip-distribute-filter-lists-top;
            uses rip-distribute-prefix-lists-top;
            uses rip-instance-interfaces-top;
            uses rip-routes-top;
        } // End of vrf-list
    } // END of rip-vrfs-top definition.

    grouping  vrfs-grouping {
    description
        "Top level container for VRF Routing Information Protocol (RIP)";
    container vrfs {
        if-feature feature-list:HAVE_VRF_RIP;
        if-feature feature-list:HAVE_RIPD;
        description
            "Top level container for VRF Routing Information Protocol (RIP)";
        uses rip-vrfs-top;
    } // END of vrfs-container definition.
    } // END of vrfs-grouping definition.


}
