/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-rip-types.yang
*
*/

module ipi-rip-types {

    yang-version 1.1;

    namespace   "http://www.ipinfusion.com/yang/ocnos/ipi-rip-types";

    prefix "ipi-rip-types";

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "This module defines data types related to the RIP module";


    revision "2024-09-05" {
        description "Updated if-feature for datatype RIP_ROUTE_TYPE_T";
        reference " 0.2.0.";
    }

    revision "2022-07-26" {
        description "Initial Version";
        reference " 0.1.0.";
    }



    typedef  rip_debug_t {
        type bits {
            bit events {
                position 0;
                description "RIP events";
            }
            bit packet-send {
                position 1;
                description "RIP packets,RIP send packets";
            }
            bit packet-recv {
                position 2;
                description "RIP packets, RIP receive packets";
            }
            bit packet-detail {
                position 3;
                description "RIP packets, Detailed information display";
            }
            bit nsm {
                position 4;
                description "RIP NSM information";
            }
            bit rib {
                position 5;
                if-feature feature-list:HAVE_RIBD;
                description "RIP RIB information";
            }
            bit bfd {
                position 6;
                if-feature feature-list:HAVE_BFD;
                description "RIP BFD information";
            }
        }
        description "type definition for RIP_DEBUG_T";
    }

    typedef  rip_version_t {
        type enumeration {
            enum 1 {
                value 1;
                description "RIP version 1";
            }
            enum 2 {
                value 2;
                description "RIP version 2";
            }
            enum 1-2 {
                value 3;
                description "RIP version 1, RIP version 2";
            }
            enum 1-compatible {
                value 4;
                description "RIPv1-compatible";
            }
        }
        description "type definition for RIP_VERSION_T";
    }

    typedef  rip_auth_mode_t {
        type enumeration {
            enum text {
                value 2;
                description "Clear text authentication";
            }
            enum md5 {
                value 3;
                description "Keyed message digest";
            }
        }
        description "type definition for RIP_AUTH_MODE_T";
    }

    typedef  rip_redistribute_proto_t {
        type enumeration {
            enum kernel {
                value 0;
                if-feature feature-list:HAVE_SWFWDR;
                description "Kernel routes";
            }
            enum connected {
                value 1;
                description "Connected";
            }
            enum static {
                value 2;
                description "Static routes";
            }
            enum ospf {
                value 3;
                description "Open Shortest Path First (OSPF)";
            }
            enum isis {
                value 4;
                description "ISO IS-IS";
            }
            enum bgp {
                value 5;
                description "Border Gateway Protocol (BGP)";
            }
        }
        description "type definition for RIP_REDISTRIBUTE_PROTO_T";
    }

    typedef  rip_redistribute_proto_clear_t {
        type enumeration {
            enum kernel {
                value 0;
                if-feature feature-list:HAVE_SWFWDR;
                description "Kernel routes";
            }
            enum connected {
                value 1;
                description "Connected";
            }
            enum static {
                value 2;
                description "Static routes";
            }
            enum ospf {
                value 3;
                description "Open Shortest Path First (OSPF)";
            }
            enum isis {
                value 4;
                description "ISO IS-IS";
            }
            enum bgp {
                value 5;
                description "Border Gateway Protocol (BGP)";
            }
            enum rip {
                value 6;
                description "Routing Information Protocol (RIP)";
            }
            enum all {
                value 7;
                description "all of the RIP routing table";
            }
        }
        description "type definition for RIP_REDISTRIBUTE_PROTO_CLEAR_T";
    }

    typedef  rip_vrf_redistribute_proto_t {
        type enumeration {
            enum connected {
                value 1;
                description "Connected";
            }
            enum static {
                value 2;
                description "Static routes";
            }
            enum ospf {
                value 3;
                description "Open Shortest Path First (OSPF)";
            }
            enum bgp {
                value 5;
                description "Border Gateway Protocol (BGP)";
            }
        }
        description "type definition for RIP_VRF_REDISTRIBUTE_PROTO_T";
    }

    typedef  rip_direction_t {
        type enumeration {
            enum in {
                value 0;
                description "For incoming updates";
            }
            enum out {
                value 1;
                description "For outgoing updates";
            }
        }
        description "type definition for RIP_DIRECTION_T";
    }

    typedef  rip_route_type_t {
        type enumeration {
            enum default {
                value 0;
                description "Kernel routes";
            }
            enum kernel {
                value 1;
                if-feature feature-list:HAVE_SWFWDR;
                description "Kernel routes";
            }
            enum connected {
                value 2;
                description "Connected";
            }
            enum static {
                value 3;
                description "Static routes";
            }
            enum rip {
                value 4;
                description "Border Gateway Protocol (BGP)";
            }
            enum ripng {
                value 5;
                description "Border Gateway Protocol (BGP)";
            }
            enum ospf {
                value 6;
                description "Open Shortest Path First (OSPF)";
            }
            enum ospf6 {
                value 7;
                description "Open Shortest Path First (OSPF)";
            }
            enum bgp {
                value 8;
                description "Border Gateway Protocol (BGP)";
            }
            enum isis {
                value 9;
                description "ISO IS-IS";
            }
        }
        description "type definition for RIP_ROUTE_TYPE_T";
    }

    typedef  rip_route_subtype_t {
        type enumeration {
            enum rip-other {
                value 0;
                description "Kernel,routes";
            }
            enum rip-entry {
                value 1;
                description "Rip,Connected";
            }
            enum rip-connect {
                value 2;
                description "Rip,Static routes";
            }
            enum rip-static {
                value 3;
                description "Rip,Open Shortest Path First (OSPF)";
            }
        }
        description "type definition for RIP_ROUTE_SUBTYPE_T";
    }

}
