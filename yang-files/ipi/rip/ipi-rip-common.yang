/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-rip-common.yang
*
*/

submodule ipi-rip-common {

    yang-version 1.1;

    belongs-to  ipi-rip { prefix ipi-rip; }

    import cml-data-types {
        prefix cml-data-types;
        revision-date 2026-05-15;
    }

    import ipi-interface {
        prefix ipi-interface;
        revision-date 2026-03-10;
    }

    import ipi-rip-types {
        prefix ipi-rip-types;
        revision-date 2024-09-05;
    }

    import ietf-inet-types {
        prefix inet;
        revision-date 2013-07-15;
    }

    organization
        "IP Infusion Inc.";

    contact
        "Address: 3965 Freedom Circle, Suite 200, Santa Clara, CA 95054
         Phone: +1 408-400-1900
         E-mail: support@ipinfusion.com
         Web: http://www.ipinfusion.com/";

    description
        "Data model for common configuration and and operational state for
                default and VRF RIP instances";


    revision "2023-01-18" {
        description "Added cli input for source-prefix";
        reference " 0.1.1.";
    }

    revision "2022-07-26" {
        description "Initial Version";
        reference " 0.1.0.";
    }

    grouping rip-instance-common-config {
        description
            "Grouping for RIP and RIP Address-family common attributes";
        leaf enable-cisco-metric-behavior  {
            type  cml-data-types:cml_enable_disable_t;
            description "Use this attribute to set metric updation behavior as Cisco";
        } // END of enable-cisco-metric-behavior definition.

        leaf default-metric  {
            type  uint8 {
                 range "1..15"  {
                    description "1..15: Supported range 1 - 15";
                 }
            }
            default "1";
            description "Set the default metric";
        } // END of default-metric definition.

        leaf version  {
            type  uint8 {
                 range "1..2"  {
                    description "1..2: Supported range 1 - 2";
                 }
            }
            default "2";
            description "Use this attribute to set version of routing protocol";
        } // END of version definition.

        leaf distance  {
            type  uint8 {
                 range "1..255"  {
                    description "1..255: Supported range 1 - 255";
                 }
            }
            default "120";
            description "Use this attribute to set administrative distance of the RIP for the
                        current RIP instance";
        } // END of distance definition.

        leaf-list network-interfaces  {
            type  leafref {
                path  "/ipi-interface:interfaces/ipi-interface:interface/ipi-interface:name";
            }
            description "Use this attribute to enable routing on an interface";
        } // END of network-interfaces definition.

        leaf-list network-routes  {
            type  cml-data-types:cml_ipv4_prefix_t;
            description "Use this attribute to enable routing on an IP network";
        } // END of network-routes definition.

    } // END of rip-instance-common-config definition.
    grouping rip-distance-config {
        description
            "Grouping for RIP distance attributes";
        leaf source-prefix  {
            type  cml-data-types:cml_ipv4_prefix_t;
            description "Use this attribute to set the network prefix and length";
        } // END of source-prefix definition.

        leaf distance  {
            type  uint8 {
                 range "1..255"  {
                    description "1..255: Supported range 1 - 255";
                 }
            }
            mandatory true;
            description "Use this attribute to set adminitrative distance";
        } // END of distance definition.

        leaf access-list-name  {
            type  string {
                length "1..1965";
                pattern "[^?' =,>|]+";
            }
            description "Use this attribute to set the access list name";
        } // END of access-list-name definition.

    } // END of rip-distance-config definition.
    grouping rip-distances-top {
        description
            "Grouping for RIP distance attributes";
        container distances {
            description
                "Enclosing container for the list of distances";

            list distance {
                key "source-prefix";
                description
                    "List of distances";
                leaf source-prefix  {
                    type  leafref {
                        path  "../config/source-prefix";
                    }
                    description "Use this attribute to set the network prefix and length";
                } // END of source-prefix definition.

                container config {
                    description
                        "Configuration data for distance";
                    uses rip-distance-config;
                } // END of config-container definition.
                container state {
                    config false;
                    description
                        "Operational data for distance";
                    uses rip-distance-config;
                } // END of state-container definition.
            } // End of distance-list
        } // END of distances-container definition.
    } // END of rip-distances-top definition.
    grouping rip-default-information-config {
        description
            "Grouping for default information attributes";
        leaf originate  {
            type  empty;
            mandatory true;
            description "Use this attribute to add default routes to the RIP updates";
        } // END of originate definition.

        leaf always-advertise  {
            type  empty;
            description "Use this attribute to always advertise default route";
        } // END of always-advertise definition.

        leaf route-map  {
            type  string {
                length "1..1965";
                pattern "[^?' =,>|]+";
            }
            description "Use this attribute to apply conditions of the route policy to the
                        default route";
        } // END of route-map definition.

    } // END of rip-default-information-config definition.
    grouping rip-default-information-top {
        description
            "Grouping for settings on whether to originate the default route in RIP
                        routing instance";
        container default-information {
            description
                "Injects the default route into the RIP";
            container config {
                presence "Originating default route";
                description
                    "Configuration data for default route information";
                uses rip-default-information-config;
            } // END of config-container definition.
            container state {
                config false;
                description
                    "Operational data for default route information";
                uses rip-default-information-config;
            } // END of state-container definition.
        } // END of default-information-container definition.
    } // END of rip-default-information-top definition.
    grouping rip-offset-list-config {
        description
            "Grouping for offset lists";
        leaf direction  {
            type  ipi-rip-types:rip_direction_t;
            description "Use this attribute to set direction of the routing updates";
        } // END of direction definition.

        leaf access-list-name  {
            type  string {
                length "1..1965";
                pattern "[^?' =,>|]+";
            }
            mandatory true;
            description "Use this attribute to set access-list number or names to apply";
        } // END of access-list-name definition.

        leaf metric  {
            type  uint8 {
                 range "0..16"  {
                    description "0..16: Supported range 0 - 16";
                 }
            }
            mandatory true;
            description "Use this attribute to set the metric value of routing protocol";
        } // END of metric definition.

    } // END of rip-offset-list-config definition.
    grouping rip-offset-lists-top {
        description
            "Grouping for offset lists attributes";
        container offset-lists {
            description
                "Enclosing container for the offset lists";

            list offset-list {
                key "direction";
                description
                    "Offset lists";
                leaf direction  {
                    type  leafref {
                        path  "../config/direction";
                    }
                    description "Use this attribute to set direction of the routing updates";
                } // END of direction definition.

                container config {
                    description
                        "Configuration data for offset list";
                    uses rip-offset-list-config;
                } // END of config-container definition.
                container state {
                    config false;
                    description
                        "Operational data for offset list";
                    uses rip-offset-list-config;
                } // END of state-container definition.
            } // End of offset-list-list
        } // END of offset-lists-container definition.
    } // END of rip-offset-lists-top definition.
    grouping rip-distribute-filter-list-config {
        description
            "Grouping for distribute list attributes";
        leaf direction  {
            type  ipi-rip-types:rip_direction_t;
            description "Use this attribute to set direction of the routing updates";
        } // END of direction definition.

        leaf access-list-name  {
            type  string {
                length "1..1965";
                pattern "[^?' =,>|]+";
            }
            mandatory true;
            description "Use this attribute to specify the IPv4 access-list number or name to
                        use";
        } // END of access-list-name definition.

    } // END of rip-distribute-filter-list-config definition.
    grouping rip-distribute-filter-lists-top {
        description
            "Grouping for distribute lists";
        container distribute-filter-lists {
            description
                "Enclosing container for the distribute lists";

            list distribute-filter-list {
                key "direction";
                description
                    "distribute lists";
                leaf direction  {
                    type  leafref {
                        path  "../config/direction";
                    }
                    description "Use this attribute to set direction of the routing updates";
                } // END of direction definition.

                container config {
                    description
                        "Operational data for distribute list";
                    uses rip-distribute-filter-list-config;
                } // END of config-container definition.
                container state {
                    config false;
                    description
                        "Operational data for distribute list";
                    uses rip-distribute-filter-list-config;
                } // END of state-container definition.
            } // End of distribute-filter-list-list
        } // END of distribute-filter-lists-container definition.
    } // END of rip-distribute-filter-lists-top definition.
    grouping rip-distribute-prefix-list-config {
        description
            "Grouping for distribute prffix list";
        leaf direction  {
            type  ipi-rip-types:rip_direction_t;
            description "Use this attribute to set direction of the routing updates";
        } // END of direction definition.

        leaf access-list-name  {
            type  string {
                length "1..1965";
                pattern "[^?' =,>|]+";
            }
            mandatory true;
            description "Use this attribute to specify the name of the IPv4 prefix-list to use";
        } // END of access-list-name definition.

    } // END of rip-distribute-prefix-list-config definition.
    grouping rip-distribute-prefix-lists-top {
        description
            "Grouping for distribute prefix list";
        container distribute-prefix-lists {
            description
                "Enclosing container for the distribute prefix lists";

            list distribute-prefix-list {
                key "direction";
                description
                    "List of distribute prefixes";
                leaf direction  {
                    type  leafref {
                        path  "../config/direction";
                    }
                    description "Use this attribute to set direction of the routing updates";
                } // END of direction definition.

                container config {
                    description
                        "Operational data for distribute prefix list";
                    uses rip-distribute-prefix-list-config;
                } // END of config-container definition.
                container state {
                    config false;
                    description
                        "Operational data for distribute prefix list";
                    uses rip-distribute-prefix-list-config;
                } // END of state-container definition.
            } // End of distribute-prefix-list-list
        } // END of distribute-prefix-lists-container definition.
    } // END of rip-distribute-prefix-lists-top definition.
    grouping rip-instance-interface-config {
        description
            "Grouping for interface related attribute";
        leaf name  {
            type  leafref {
                path  "/ipi-interface:interfaces/ipi-interface:interface/ipi-interface:name";
            }
            description "Reference to an interface to which the prefix list is applied";
        } // END of name definition.

    } // END of rip-instance-interface-config definition.
    grouping rip-instance-interfaces-top {
        description
            "Grouping for interface related instance attribute";
        container interfaces {
            description
                "Enclosing container for the list of interfaces";

            list interface {
                key "name";
                description
                    "List of interface";
                leaf name  {
                    type  leafref {
                        path  "../config/name";
                    }
                    description "Reference to an interface to which configs are applied";
                } // END of name definition.

                container config {
                    description
                        "Configuration data for interface";
                    uses rip-instance-interface-config;
                } // END of config-container definition.
                container state {
                    config false;
                    description
                        "Operational data for interface";
                    uses rip-instance-interface-config;
                } // END of state-container definition.
                uses rip-offset-lists-top;
                uses rip-distribute-filter-lists-top;
                uses rip-distribute-prefix-lists-top;
            } // End of interface-list
        } // END of interfaces-container definition.
    } // END of rip-instance-interfaces-top definition.
    grouping rip-routes-state {
        description
            "Grouping for RIP routes";
        leaf prefix  {
            type  cml-data-types:cml_ipv4_prefix_t;
            description "Prefix address";
        } // END of prefix definition.

        leaf type  {
            type  ipi-rip-types:rip_route_type_t;
            description "Route type";
        } // END of type definition.

        leaf rip-sub-type  {
            type  ipi-rip-types:rip_route_subtype_t;
            description "Route sub-type";
        } // END of rip-sub-type definition.

        leaf tag  {
            type  uint16;
            description "Tag";
        } // END of tag definition.

    } // END of rip-routes-state definition.
    grouping rip-nexthop-state {
        description
            "Grouping for nexthop attributes";
        leaf address  {
            type  inet:ipv4-address;
            description "Address of next hop";
        } // END of address definition.

        leaf if-name  {
            type  string {
                length "1..1965";
                pattern "[^?' =,>|]+";
            }
            description "Interface Name";
        } // END of if-name definition.

        leaf metric  {
            type  uint8;
            description "Metric of nexthop";
        } // END of metric definition.

        leaf up-time  {
            type  string {
                length "1..1965";
                pattern "((([0-1]?[0-9])|(2[0-3])):[0-5][0-9]:[0-5][0-9])|([0-9]+d(([0-1][0-9])|(2[0-3]))h[0-5][0-9]m)|([0-9]+w[0-9]+d[0-9]+h)";
            }
            description "Uptime of the link";
        } // END of up-time definition.

    } // END of rip-nexthop-state definition.
    grouping rip-nexthop-top {
        description
            "Grouping for RIP next hop";
        container nexthops {
            config false;
            description
                "Enclosing container for the list of next hops";

            list nexthop {
                key "address";
                config false;
                description
                    "List of next hops";
                leaf address  {
                    type  leafref {
                        path  "../state/address";
                    }
                    description "Address of nexthop";
                } // END of address definition.

                container state {
                    config false;
                    description
                        "Operational data for next hop";
                    uses rip-nexthop-state;
                } // END of state-container definition.
            } // End of nexthop-list
        } // END of nexthops-container definition.
    } // END of rip-nexthop-top definition.
    grouping rip-routes-top {
        description
            "Grouping for RIP routes";
        container routes {
            config false;
            description
                "Enclosing container for the list of RIP routes";

            list route {
                key "prefix";
                config false;
                description
                    "List of routes";
                leaf prefix  {
                    type  leafref {
                        path  "../state/prefix";
                    }
                    description "Prefix address";
                } // END of prefix definition.

                container state {
                    config false;
                    description
                        "Operational data for routes";
                    uses rip-routes-state;
                } // END of state-container definition.
                uses rip-nexthop-top;
            } // End of route-list
        } // END of routes-container definition.
    } // END of rip-routes-top definition.


}
