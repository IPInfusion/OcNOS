/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-rip.yang
*
*/

module ipi-rip {

    yang-version 1.1;

    namespace   "http://www.ipinfusion.com/yang/ocnos/ipi-rip";

    prefix "ipi-rip";

    import cml-data-types {
        prefix cml-data-types;
        revision-date 2026-05-15;
    }

    import ipi-rip-types {
        prefix ipi-rip-types;
        revision-date 2024-09-05;
    }

    import ipi-interface {
        prefix ipi-interface;
        revision-date 2026-03-10;
    }

    import ietf-inet-types {
        prefix inet;
        revision-date 2013-07-15;
    }

    import ietf-yang-types {
        prefix yang;
        revision-date 2013-07-15;
    }

    import feature-list {
        prefix feature-list;
        revision-date 2026-09-15;
    }

    include ipi-rip-common { revision-date 2023-01-18;}
    include ipi-rip-vrf { revision-date 2023-01-18;}
    organization
        "IP Infusion Inc.";

    contact
        "Address: 3965 Freedom Circle, Suite 200, Santa Clara, CA 95054
         Phone: +1 408-400-1900
         E-mail: support@ipinfusion.com
         Web: http://www.ipinfusion.com/";

    description
        "Data model for IPI RIP Configuration and Operational state";


    revision "2024-09-05" {
        description "Updated if-feature for datatype RIP_ROUTE_TYPE_T";
        reference " 0.4.0.";
    }

    revision "2024-05-07" {
        description "Added dependentObject 'ipi-rip-vrf:vrfs/vrf' with operation 'delete' in 'config' container.";
        reference " 0.3.0.";
    }

    revision "2023-01-18" {
        description "Added cli input for source-prefix";
        reference " 0.1.6.";
    }

    revision "2023-01-05" {
        description "Modified cli-command attr path";
        reference " 0.1.5.";
    }

    revision "2022-09-29" {
        description "Modified RPC names";
        reference " 0.1.4.";
    }

    revision "2022-08-19" {
        description "Added implicit_delete for rip debug";
        reference " 0.1.3.";
    }

    revision "2022-08-09" {
        description "Added get_api header file for vrf";
        reference " 0.1.2.";
    }

    revision "2022-07-30" {
        description "Updated when expression";
        reference " 0.1.1.";
    }

    revision "2022-07-26" {
        description "Initial Version";
        reference " 0.1.0.";
    }

    revision "2022-02-09" {
        description "Added When tag constraints for 'debug' container";
        reference " 0.2.0.";
    }

    grouping rip-terminal-debug-state {
        description
            "Grouping for RIP terminal Debug attributes";
        leaf terminal-debug-status  {
            type  ipi-rip-types:rip_debug_t;
            description "This attribute describes the RIP terminal debug status";
        } // END of terminal-debug-status definition.

    } // END of rip-terminal-debug-state definition.
    grouping rip-debug-config {
        description
            "Grouping for RIP terminal Debug attributes";
        leaf options  {
            type  ipi-rip-types:rip_debug_t;
            description "This attribute enables debugging for RIP";
        } // END of options definition.

    } // END of rip-debug-config definition.
    grouping rip-global-config {
        description
            "Grouping for Global RIP attributes";
        leaf restart-grace-period  {
            if-feature feature-list:HAVE_RIP_GR_SUPPORT;
            if-feature feature-list:HAVE_RESTART;
            type  uint16 {
                 range "1..65535"  {
                    description "1..65535: Supported range 1 - 65535";
                 }
            }
            description "Use this attribute to configure grace period for rip graceful restart";
        } // END of restart-grace-period definition.

    } // END of rip-global-config definition.
    grouping rip-global-top {
        description
            "Grouping for Global RIP attributes";
        container global {
            description
                "Global RIP container";
            container config {
                description
                    "RIP Global Configuration data";
                uses rip-global-config;
            } // END of config-container definition.
            container state {
                config false;
                description
                    "RIP Global Operational data";
                uses rip-global-config;
            } // END of state-container definition.
        } // END of global-container definition.
    } // END of rip-global-top definition.
    grouping rip-debug-top {
        description
            "Grouping for RIP debug attributes";
        container debug {
            description
                "debug container";
            container config {
                description
                    "RIP debug Configuration data";
                uses rip-debug-config;
            } // END of config-container definition.
            container state {
                config false;
                description
                    "RIP debug Operational data";
                uses rip-debug-config;
                uses rip-terminal-debug-state;
            } // END of state-container definition.
        } // END of debug-container definition.
    } // END of rip-debug-top definition.
    grouping rip-statistics-state {
        description
            "Grouping for global statistics counters";
        container statistics {
            config false;
            description
                "RIP statistics container";
            leaf sent-mcast-updates  {
                type  yang:counter32;
                description "Counter for numbers of mcast route updates sent";
            } // END of sent-mcast-updates definition.

            leaf sent-mcast-requests  {
                type  yang:counter32;
                description "The number of mcast requests sent by RIP";
            } // END of sent-mcast-requests definition.

            leaf sent-unicast-updates  {
                type  yang:counter32;
                description "Counter for number of unicast route update sent";
            } // END of sent-unicast-updates definition.

            leaf sent-unicast-requests  {
                type  yang:counter32;
                description "The number of unicast requests sent by RIP";
            } // END of sent-unicast-requests definition.

            leaf received-mcast-updates  {
                type  yang:counter32;
                description "Counter for number mcast route updates received";
            } // END of received-mcast-updates definition.

            leaf received-mcast-requests  {
                type  yang:counter32;
                description "The number of mcast requests received by RIP";
            } // END of received-mcast-requests definition.

            leaf received-unicast-updates  {
                type  yang:counter32;
                description "Counter for number of unicast route updates received";
            } // END of received-unicast-updates definition.

            leaf received-unicast-requests  {
                type  yang:counter32;
                description "The number of unicast requests received by RIP";
            } // END of received-unicast-requests definition.

            leaf received-bad-packets  {
                type  yang:counter32;
                description "The number of RIP invalid packets received from this neighbor that
                            were subsequently discarded for any reason";
            } // END of received-bad-packets definition.

            leaf received-bad-routes  {
                type  yang:counter32;
                description "The number of routes received from this neighbor, in valid RIP packets
                            that were ignored for any reason";
            } // END of received-bad-routes definition.

        } // END of statistics-container definition.
    } // END of rip-statistics-state definition.
    grouping rip-interfaces-config {
        description
            "Grouping for RIP interface attributes";
        leaf name  {
            type  leafref {
                path  "/ipi-interface:interfaces/ipi-interface:interface/ipi-interface:name";
            }
            description "Enable RIP on this interface";
        } // END of name definition.

        leaf disable-receive-packet  {
            type  empty;
            description "Use this attribute to configure the interface to enable/disable the
                        reception of RIP packets";
        } // END of disable-receive-packet definition.

        leaf disable-send-packet  {
            type  empty;
            description "Use this attribute to enable/disable sending RIP packets through
                        current interface";
        } // END of disable-send-packet definition.

        leaf receive-version  {
            type  ipi-rip-types:rip_version_t;
            description "Use this attribute to receive specified version of RIP packets on an
                        interface";
        } // END of receive-version definition.

        leaf send-version  {
            type  ipi-rip-types:rip_version_t;
            description "Use this attribute to set the version of RIP packets which can be sent
                        from an interface";
        } // END of send-version definition.

        leaf auth-mode  {
            type  ipi-rip-types:rip_auth_mode_t;
            description "Use this attrbute to set the type of authentication mode used for RIP
                        packets";
        } // END of auth-mode definition.

        leaf auth-string  {
            // when " !ipi-rip:rip/interfaces/interface/config/auth-keychain + ipi-rip:rip/interfaces/interface/config/auth-mode ";
            type  cml-data-types:cml_line_t {
                length "1..1965";
            }
            description "Use this attribute to set the authentication string or password used
                        by a key";
        } // END of auth-string definition.

        leaf auth-keychain  {
            // when " !ipi-rip:rip/interfaces/interface/config/auth-string + ipi-rip:rip/interfaces/interface/config/auth-mode ";
            type  string {
                length "1..1965";
                pattern "[^?' =,>|]+";
            }
            description "Use this attribute to enable RIP authentication on an interface and
                        specify the name of the key chain to be used";
        } // END of auth-keychain definition.

        leaf split-horizon  {
            type  boolean;
            description "Use this attribute to controls RIP split-horizon processing on the
                        specified interface.";
        } // END of split-horizon definition.

    } // END of rip-interfaces-config definition.
    grouping rip-interfaces-top {
        description
            "Grouping for RIP interface related attributes";
        container interfaces {
            description
                "Container for RIP interface related attributes";

            list interface {
            // when " ipi-interface:interfaces/interface/config/enable-switchport != '1' ";
                key "name";
                description
                    "List of Interfaces";
                leaf name  {
                    type  leafref {
                        path  "../config/name";
                    }
                    description "Enable RIP on this interface";
                } // END of name definition.

                container config {
                    description
                        "Interface Configuration data";
                    uses rip-interfaces-config;
                } // END of config-container definition.
                container state {
                    config false;
                    description
                        "Interface Operational data";
                    uses rip-interfaces-config;
                    uses rip-statistics-state;
                } // END of state-container definition.
            } // End of interface-list
        } // END of interfaces-container definition.
    } // END of rip-interfaces-top definition.
    grouping rip-timers-config {
        description
            "Grouping for basic timers settings";
        leaf route-table-update-interval  {
            type  uint32 {
                 range "5..2147483647"  {
                    description "5..2147483647: Supported range 5 - 2147483647";
                 }
            }
            mandatory true;
            description "Interval at which RIP updates are sent";
        } // END of route-table-update-interval definition.

        leaf route-info-timeout-interval  {
            type  uint32 {
                 range "5..2147483647"  {
                    description "5..2147483647: Supported range 5 - 2147483647";
                 }
            }
            mandatory true;
            description "Interval before a route is declared invalid after no updates are
                        received";
        } // END of route-info-timeout-interval definition.

        leaf garbage-collection-interval  {
            type  uint32 {
                 range "5..2147483647"  {
                    description "5..2147483647: Supported range 5 - 2147483647";
                 }
            }
            mandatory true;
            description "Interval before a route is flushed from the routing table";
        } // END of garbage-collection-interval definition.

    } // END of rip-timers-config definition.
    grouping rip-timers-top {
        description
            "Grouping for RIP timers";
        container timers {
            description
                "Enclosing container for settings of basic timers";
            container config {
                presence "RIP timers";
                description
                    "Configuration data for basic timers";
                uses rip-timers-config;
            } // END of config-container definition.
            container state {
                config false;
                description
                    "Operational data for basic timers";
                uses rip-timers-config;
            } // END of state-container definition.
        } // END of timers-container definition.
    } // END of rip-timers-top definition.
    grouping rip-maximum-prefix-config {
        description
            "Grouping for maximum prefix attribute";
        leaf max-routes  {
            type  uint32 {
                 range "1..65535"  {
                    description "1..65535: Supported range 1 - 65535";
                 }
            }
            mandatory true;
            description "Use this attribute to set the limit of number of RIP routes in routing
                        table";
        } // END of max-routes definition.

        leaf warning-threshold-percentage  {
            type  uint32 {
                 range "1..100"  {
                    description "1..100: Supported range 1 - 100";
                 }
            }
            description "Use this attribute to set the percentage of maximum routes to generate
                        a warning";
        } // END of warning-threshold-percentage definition.

    } // END of rip-maximum-prefix-config definition.
    grouping rip-maximum-prefix-top {
        description
            "Grouping for maximum-prefix attributes";
        container maximum-prefix {
            description
                "Enclosing container for the maximum-prefix container";
            container config {
                presence "Maximum-prefix";
                description
                    "Configurational data for maximum-prefix";
                uses rip-maximum-prefix-config;
            } // END of config-container definition.
            container state {
                config false;
                description
                    "Operational data for maximum-prefix";
                uses rip-maximum-prefix-config;
            } // END of state-container definition.
        } // END of maximum-prefix-container definition.
    } // END of rip-maximum-prefix-top definition.
    grouping rip-redistribute-policies-config {
        description
            "Grouping for redistribute attributes";
        leaf route-type  {
            type  ipi-rip-types:rip_redistribute_proto_t;
            description "Use this attribute to redistributes only specified route-type routes
                        matching the specified route type into the RIP routing instance";
        } // END of route-type definition.

        leaf metric  {
            type  uint8 {
                 range "0..16"  {
                    description "0..16: Supported range 0 - 16";
                 }
            }
            description "Metric used for the redistributed route";
        } // END of metric definition.

        leaf route-map  {
            type  string {
                length "1..1965";
                pattern "[^?' =,>|]+";
            }
            description "Use this attribute to set th route-map";
        } // END of route-map definition.

    } // END of rip-redistribute-policies-config definition.
    grouping rip-redistribute-policies-top {
        description
            "Grouping for RIP terminal Debug attributes";
        container redistribute-policies {
            description
                "Redistributes routes learned from other routing protocols into the RIP
                        routing instance";

            list redistribute-policy {
                key "route-type";
                description
                    "List of redistributes routes";
                leaf route-type  {
                    type  leafref {
                        path  "../config/route-type";
                    }
                    description "Use this attribute to redistributes only specified route-type routes
                                matching the specified route type into the RIP routing instance";
                } // END of route-type definition.

                container config {
                    description
                        "Configuration data for Redistribute routes";
                    uses rip-redistribute-policies-config;
                } // END of config-container definition.
                container state {
                    config false;
                    description
                        "Operational data for Redistribute routes";
                    uses rip-redistribute-policies-config;
                } // END of state-container definition.
            } // End of redistribute-policy-list
        } // END of redistribute-policies-container definition.
    } // END of rip-redistribute-policies-top definition.
    grouping rip-instance-config {
        description
            "Grouping for RIP instance attributes";
        leaf rip-enabled  {
            type  empty;
            mandatory true;
            description "Use this attribute enable a RIP routing process";
        } // END of rip-enabled definition.

        leaf bfd-enable  {
            if-feature feature-list:HAVE_BFD;
            type  empty;
            description "This feature indicates that the RIP implementation on the system
                        supports BFD";
        } // END of bfd-enable definition.

        leaf receive-buffer-size  {
            type  uint32 {
                 range "8192..2147483647"  {
                    description "8192..2147483647: Supported range 8192 - 2147483647";
                 }
            }
            default "32768";
            description "Use this attribute to set the RIP UDP receive-buffer size.";
        } // END of receive-buffer-size definition.

        leaf-list passive-interfaces  {
            type  leafref {
                path  "/ipi-interface:interfaces/ipi-interface:interface/ipi-interface:name";
            }
            description "Disables sending of RIP  packets on the specified interface";
        } // END of passive-interfaces definition.

        leaf-list static-routes  {
            type  cml-data-types:cml_ipv4_prefix_t;
            description "Use this attribute to set static RIP routes";
        } // END of static-routes definition.

        leaf-list neighbors  {
            type  inet:ipv4-address;
            description "Specifies the RIP neighbors";
        } // END of neighbors definition.

        leaf-list neighbor-fall-over-bfd  {
            if-feature feature-list:HAVE_BFD;
            type  inet:ipv4-address;
            description "Specified the BFD neighbors";
        } // END of neighbor-fall-over-bfd definition.

    } // END of rip-instance-config definition.
    grouping rip-instance-top {
        description
            "Grouping for RIP instance attributes";
        container instance {
            description
                "Instance container";
            container config {
                presence "Enable RIP";
                description
                    "Configuration data for RIP instance";
                uses rip-instance-config;
                uses rip-instance-common-config;
            } // END of config-container definition.
            container state {
                config false;
                description
                    "Operational data for RIP instance";
                uses rip-instance-config;
                uses rip-instance-common-config;
            } // END of state-container definition.
            uses rip-distances-top;
            uses rip-timers-top;
            uses rip-maximum-prefix-top;
            uses rip-redistribute-policies-top;
            uses rip-default-information-top;
            uses rip-offset-lists-top;
            uses rip-distribute-filter-lists-top;
            uses rip-distribute-prefix-lists-top;
            uses rip-instance-interfaces-top;
            uses rip-routes-top;
            uses vrfs-grouping;
        } // END of instance-container definition.
    } // END of rip-instance-top definition.

    grouping  rip-grouping {
    description
        "Top level container for Routing Information Protocol (RIP)";
    container rip {
        if-feature feature-list:HAVE_RIPD;
        description
            "Top level container for Routing Information Protocol (RIP)";
        uses rip-global-top;
        uses rip-debug-top;
        uses rip-interfaces-top;
        uses rip-instance-top;
    } // END of rip-container definition.
    } // END of rip-grouping definition.

    uses rip-grouping;

    rpc rip-vrf-clear-route {
        if-feature feature-list:HAVE_VRF_RIP;
        if-feature feature-list:HAVE_RIPD;
        description "Use this RPC to clear learned routes for the specified prefix";
        input  {
            leaf vrf-name  {
                type string;
                mandatory true;
                description "VRF name";
            }
            leaf prefix  {
                type cml-data-types:cml_ipv4_prefix_t;
                mandatory true;
                description "Prefix Address";
            }
        }
    }

    rpc rip-vrf-clear-route-all {
        if-feature feature-list:HAVE_VRF_RIP;
        if-feature feature-list:HAVE_RIPD;
        description "Use this RPC to clear learned routes";
        input  {
            leaf vrf-name  {
                type string;
                mandatory true;
                description "VRF name";
            }
        }
    }

    rpc rip-clear-route {
        if-feature feature-list:HAVE_RIPD;
        description "Use this RPC to clear RIP learned routes";
        input  {
            leaf route-type  {
                type ipi-rip-types:rip_redistribute_proto_clear_t;
                mandatory true;
                description "Route type";
            }
        }
    }

    rpc rip-clear-route-prefix {
        if-feature feature-list:HAVE_RIPD;
        description "Use this RPC to clear the learned routes of RIP based on prefix";
        input  {
            leaf prefix-address  {
                type cml-data-types:cml_ipv4_prefix_t;
                mandatory true;
                description "Route type";
            }
        }
    }

    rpc rip-clear-statistics {
        if-feature feature-list:HAVE_RIPD;
        description "Use this RPC to clear RIP interface statistics";
        input  {
            leaf name  {
                type string;
                mandatory true;
                description "Interface name";
            }
        }
    }

    rpc rip-restart-graceful {
        if-feature feature-list:HAVE_RIP_GR_SUPPORT;
        if-feature feature-list:HAVE_RESTART;
        if-feature feature-list:HAVE_RIPD;
        description "Use this RPC to gracefully restart RIP";
        input  {
            leaf grace-period  {
                type uint32 {
                    range "1..65535";
                }
                mandatory true;
                description "This attribute set grace period restart time";
            }
        }
    }

    rpc rip-snmp-restart {
        if-feature feature-list:HAVE_SNMP;
        if-feature feature-list:HAVE_RIPD;
        description "Use this RPC for SNMP restart";
    }

    rpc rip-terminal-debugging-on {
        if-feature feature-list:HAVE_RIPD;
        description "Use this RPC to set RIP debug options in EXEC mode";
        input  {
            leaf terminal-debug-options  {
                type ipi-rip-types:rip_debug_t;
                mandatory true;
                description "Debug configuration flag";
            }
        }
    }

    rpc rip-terminal-debugging-off {
        if-feature feature-list:HAVE_RIPD;
        description "Use this RPC to unset RIP debug options in EXEC mode";
        input  {
            leaf terminal-debug-options  {
                type ipi-rip-types:rip_debug_t;
                mandatory true;
                description "Debug configuration flag";
            }
        }
    }

}
