/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-sat-types.yang
*
*/

module ipi-sat-types {

    yang-version 1.1;

    namespace   "http://www.ipinfusion.com/yang/ocnos/ipi-sat-types";

    prefix "ipi-sat-types";

    organization
        "IP Infusion Inc.";

    contact
        "Address: 3965 Freedom Circle, Suite 200, Santa Clara, CA 95054
         Phone: +1 408-400-1900
         E-mail: support@ipinfusion.com
         Web: http://www.ipinfusion.com/";

    description
        "Service Authentication Test";


    revision "2025-11-13" {
        description "Added the default values for the attributes";
        reference " 0.2.2.";
    }

    revision "2024-12-13" {
        description "Corrected the helpstring for SAT_DELAY_RATE_T";
        reference " 0.2.1.";
    }

    revision "2024-05-22" {
        description "Removed CRC packet pattens";
        reference " 0.1.2.";
    }

    revision "2024-05-11" {
        description "Added missed element in the datatype";
        reference " 0.2.0.";
    }

    revision "2024-04-17" {
        description "Get api implementation";
        reference " 0.1.1.";
    }

    revision "2023-12-29" {
        description "Initial version";
        reference " 0.1.0.";
    }



    typedef  sat_mode_t {
        type enumeration {
            enum generator {
                value 1;
                description "Configure test mode as generator";
            }
            enum receiver {
                value 2;
                description "Configure test mode as receiver";
            }
            enum generator-receiver {
                value 3;
                description "Configure test mode as generator-receier";
            }
        }
        description "type definition for SAT_MODE_T";
    }

    typedef  sat_rate_unit_t {
        type enumeration {
            enum kbps {
                value 1;
                description "Specifies the unit of kilobits per second";
            }
            enum mbps {
                value 2;
                description "Specifies the unit of megabits per second";
            }
        }
        description "type definition for SAT_RATE_UNIT_T";
    }

    typedef  sat_delay_rate_t {
        type enumeration {
            enum ms {
                value 1;
                description "Specifies the unit of Milli second";
            }
            enum us {
                value 2;
                description "Specifies the unit of Micro second";
            }
            enum ns {
                value 3;
                description "Specifies the unit of Nano second";
            }
        }
        description "type definition for SAT_DELAY_RATE_T";
    }

    typedef  sat_direction_t {
        type enumeration {
            enum upstream {
                value 1;
                description "Configure upstream";
            }
            enum downstream {
                value 2;
                description "Configure downstream";
            }
        }
        description "type definition for SAT_DIRECTION_T";
    }

    typedef  sat_stream_run_t {
        type enumeration {
            enum parallel {
                value 1;
                description "Configure parallel";
            }
            enum one-by-one {
                value 2;
                description "Configure one-by-one";
            }
        }
        description "type definition for SAT_STREAM_RUN_T";
    }

    typedef  sat_service_t {
        type enumeration {
            enum cir {
                value 1;
                description "Configure cir";
            }
            enum cir-eir {
                value 2;
                description "Configure cir-eir";
            }
            enum policing {
                value 3;
                description "Configure policing";
            }
            enum performance {
                value 4;
                description "Configure performance";
            }
            enum all {
                value 255;
                description "Configure all";
            }
        }
        description "type definition for SAT_SERVICE_T";
    }

    typedef  sat_repeat_last_fail_test_t {
        type enumeration {
            enum repeat-last-fail-test {
                value 1;
                description "Repeat from the Last failed test case for SAT.";
            }
            enum new-test {
                value 255;
                description "Start the new test for SAT.";
            }
        }
        description "type definition for SAT_REPEAT_LAST_FAIL_TEST_T";
    }

    typedef  sat_tag_type_t {
        type enumeration {
            enum dot1q {
                value 33024;
                description "IEEE 802.1Q VLAN-tagged packets";
            }
            enum dot1ad {
                value 34984;
                description "IEEE 802.1ad VLAN-tagged packets";
            }
        }
        description "datatype for sub-interface encap type";
    }

    typedef  sat_data_pattern_t {
        type enumeration {
            enum null-sig {
                value 1;
                description "Configure null-sig";
            }
            enum prbs {
                value 3;
                description "Configure prbs";
            }
        }
        description "datatype for frame data pattern";
    }

    typedef  sat_mac_addr_t {
        type string {
            pattern "[0-9a-fA-F]{1,4}.[0-9a-fA-F]{1,4}.[0-9a-fA-F]{1,4}";
        }
        description "type definition for SAT_MAC_ADDR_T";
    }

    typedef  sat_color_aware_type {
        type enumeration {
            enum on {
                value 1;
                description "on";
            }
            enum off {
                value 2;
                description "off";
            }
        }
        description "color aware is on or off";
    }

    typedef  sat_oper_status {
        type enumeration {
            enum Failed {
                value 1;
                description "Failed";
            }
            enum In-progress {
                value 3;
                description "In progress";
            }
            enum Aborted {
                value 4;
                description "Aborted";
            }
            enum Passed {
                value 5;
                description "Passed";
            }
        }
        description "oper status";
    }

    typedef  sat_summary_status {
        type enumeration {
            enum In-progress {
                value 1;
                description "In progress";
            }
            enum Passed {
                value 2;
                description "Passed";
            }
            enum Aborted {
                value 3;
                description "Aborted";
            }
            enum Failed {
                value 4;
                description "Failed";
            }
        }
        description "summary status";
    }

}
