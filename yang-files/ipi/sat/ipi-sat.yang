/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-sat.yang
*
*/

module ipi-sat {

    yang-version 1.1;

    namespace   "http://www.ipinfusion.com/yang/ocnos/ipi-sat";

    prefix "ipi-sat";

    import ipi-sat-types {
        prefix ipi-sat-types;
        revision-date 2025-11-13;
    }

    import cml-data-types {
        prefix cml-data-types;
        revision-date 2026-05-15;
    }

    import ipi-interface {
        prefix ipi-interface;
        revision-date 2026-03-10;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Service Activation Test Linear";


    revision "2025-11-13" {
        description "Added the default values for the attributes";
        reference " 0.4.2.";
    }

    revision "2025-07-03" {
        description "Updated SAT Domain name length support";
        reference " 0.4.1.";
    }

    revision "2025-06-18" {
        description "Corrected md ma name length as supported";
        reference " 0.4.0.";
    }

    revision "2025-05-22" {
        description "Frame size h,u range is updated based on board support";
        reference " 0.3.0.";
    }

    revision "2025-02-28" {
        description "Allowed upto 8 SAT packet lengths to be configured in frame sequence";
        reference " 0.2.7.";
    }

    revision "2025-02-13" {
        description "Added bit map check flag for the optional attribute timing CLI";
        reference " 0.2.6.";
    }

    revision "2025-01-23" {
        description "Updated the help string for test direction configuration";
        reference " 0.2.5.";
    }

    revision "2024-12-13" {
        description "Added presence in config container for mandatory attributes";
        reference " 0.2.4.";
    }

    revision "2024-12-06" {
        description "Added stream description min and max length";
        reference " 0.2.3.";
    }

    revision "2024-11-28" {
        description "Added CML_RESET_INSTANCE for required attributes";
        reference " 0.2.2.";
    }

    revision "2024-11-22" {
        description "Added CML_HITLESS_MERGE for required attributes";
        reference " 0.2.1.";
    }

    revision "2024-05-22" {
        description "Removed CRC packet pattens";
        reference " 0.1.2.";
    }

    revision "2024-05-11" {
        description "Added missed attributes to the getapi";
        reference " 0.2.0.";
    }

    revision "2024-04-17" {
        description "Get api implementation";
        reference " 0.1.1.";
    }

    revision "2023-12-29" {
        description "Initial Version";
        reference " 0.1.0.";
    }

    grouping sat-test-summary-top {
        description
            "Top level grouping fpr SAT state top";
        container summaries {
            config false;
            description
                "container for summaries";
            uses sat-test-summary-run-top;
        } // END of summaries-container definition.
    } // END of sat-test-summary-top definition.
    grouping sat-test-summary-run-top {
        description
            "Top level grouping for SAT test summary";

        list summary {
            key "run";
            config false;
            description
                "List of SAT summary";
            leaf run  {
                type  leafref {
                    path  "../state/run";
                }
                description "This attribute specifies run for summary";
            } // END of run definition.

            container state {
                config false;
                description
                    "Operational data for summary";
                uses sat-run-summary-state;
            } // END of state-container definition.
        } // End of summary-list
    } // END of sat-test-summary-run-top definition.
    grouping sat-run-summary-state {
        description
            "Grouping for SAT run summaries";
        leaf run  {
            type  uint8;
            description "This attribute specifies run id";
        } // END of run definition.

        leaf status  {
            type  ipi-sat-types:sat_summary_status;
            description "This attribute specifies status of run";
        } // END of status definition.

        leaf start-time  {
            type  string {
                length "1..1965";
            }
            description "This attribute specifies start time of run";
        } // END of start-time definition.

        leaf end-time  {
            type  string {
                length "1..1965";
            }
            description "This attribute specifies end time of run";
        } // END of end-time definition.

    } // END of sat-run-summary-state definition.
    grouping sat-stream-state {
        description
            "Grouping for SAT streams";
        leaf stream-name  {
            type  string {
                length "1..1965";
                pattern "[^?' =,>|]+";
            }
            description "This attribute specifies stream name";
        } // END of stream-name definition.

        leaf cir  {
            type  string {
                length "1..1965";
                pattern "[^?' =,>|]+";
            }
            description "This attribute specifies the CIR";
        } // END of cir definition.

        leaf cir-range  {
            type  uint32;
            description "This attribute specifies CIR range";
        } // END of cir-range definition.

        leaf cir-unit  {
            type  ipi-sat-types:sat_rate_unit_t;
            description "This attribute specifies CIR unit";
        } // END of cir-unit definition.

        leaf cir-cos  {
            type  uint8;
            description "This attribute specifies CIR Configure class of service";
        } // END of cir-cos definition.

        leaf cir-dei  {
            type  uint8;
            description "This attribute specifies CIR Drop Eligibility Indicator";
        } // END of cir-dei definition.

        leaf eir  {
            type  string {
                length "1..1965";
                pattern "[^?' =,>|]+";
            }
            description "This attribute specifies EIR";
        } // END of eir definition.

        leaf eir-range  {
            type  uint32;
            description "This attribute specifies EIR range";
        } // END of eir-range definition.

        leaf eir-unit  {
            type  ipi-sat-types:sat_rate_unit_t;
            description "This attribute specifies EIR unit";
        } // END of eir-unit definition.

        leaf eir-cos  {
            type  uint8;
            description "This attribute specifies the EIR cos";
        } // END of eir-cos definition.

        leaf eir-dei  {
            type  uint8;
            description "This attribute specifies EIR Drop Eligibility Indicator";
        } // END of eir-dei definition.

        leaf color-mthod  {
            type  string {
                length "1..1965";
                pattern "[^?' =,>|]+";
            }
            description "This attribute specifies colour method";
        } // END of color-mthod definition.

        leaf color-aware  {
            type  ipi-sat-types:sat_color_aware_type;
            description "This attribute specifies color aware";
        } // END of color-aware definition.

        leaf test-mtu  {
            type  string {
                length "1..1965";
            }
            description "This attribute specifies test MTU";
        } // END of test-mtu definition.

        leaf frame-info  {
            type  string {
                length "1..1965";
            }
            description "This attribute specifies frame information for stream";
        } // END of frame-info definition.

        leaf cir-flr  {
            type  string {
                length "1..1965";
            }
            units "%";
            description "This attribute specifies CIR frame loss ratio";
        } // END of cir-flr definition.

        leaf cir-ftd-delay  {
            type  uint16;
            description "This attribute specifies CIR frame transfer delay";
        } // END of cir-ftd-delay definition.

        leaf cir-ftd-delay-unit  {
            type  ipi-sat-types:sat_delay_rate_t;
            description "This attribute specifies CIR frame transfer delay unit";
        } // END of cir-ftd-delay-unit definition.

        leaf cir-fdv-delay  {
            type  uint16;
            description "This attribute specifies CIR frame delay variation";
        } // END of cir-fdv-delay definition.

        leaf cir-fdv-delay-unit  {
            type  ipi-sat-types:sat_delay_rate_t;
            description "This attribute specifies CIR frame delay variation unit";
        } // END of cir-fdv-delay-unit definition.

        leaf interface-name  {
            type  string {
                length "1..1965";
                pattern "[^?' =,>|]+";
            }
            description "This attribute specifies name of interface";
        } // END of interface-name definition.

        leaf destination-mac  {
            type  string {
                length "1..1965";
                pattern "[^?' =,>|]+";
            }
            description "This attribute specifies destination MAC";
        } // END of destination-mac definition.

        leaf encap-tag  {
            type  ipi-sat-types:sat_tag_type_t;
            description "This attribute specifies encapsulation tag";
        } // END of encap-tag definition.

        leaf outer-vid  {
            type  uint8;
            description "This attribute specifies outer VLAN id";
        } // END of outer-vid definition.

        leaf inner-vlan-id  {
            type  uint8;
            description "This attribute specifies inner VLAN id";
        } // END of inner-vlan-id definition.

        leaf cfm-details  {
            type  string {
                length "1..1965";
            }
            description "This attribute specifies CFM details";
        } // END of cfm-details definition.

    } // END of sat-stream-state definition.
    grouping sat-test-state {
        description
            "Grouping for SAT service tests";
        leaf stest-name  {
            type  string {
                length "1..1965";
                pattern "[^?' =,>|]+";
            }
            description "This attribute specifies service test name";
        } // END of stest-name definition.

        leaf load  {
            type  string {
                length "1..1965";
                pattern "[^?' =,>|]+";
            }
            description "This attribute specifies load";
        } // END of load definition.

        leaf opera-status  {
            type  ipi-sat-types:sat_oper_status;
            description "This attribute specifies status";
        } // END of opera-status definition.

        leaf test-duration  {
            type  string {
                length "1..1965";
            }
            description "This attribute specifies test duration";
        } // END of test-duration definition.

        leaf start-time  {
            type  string {
                length "1..1965";
            }
            description "This attribute specifies start time";
        } // END of start-time definition.

        leaf end-time  {
            type  string {
                length "1..1965";
            }
            description "This attribute specifies end time";
        } // END of end-time definition.

        leaf tx-packets  {
            type  uint64;
            description "This attribute specifies tx packets";
        } // END of tx-packets definition.

        leaf tx-bytes  {
            type  uint64;
            description "This attribute specifies tx bytes";
        } // END of tx-bytes definition.

        leaf rx-packets  {
            type  uint64;
            description "This attribute specifies rx packets";
        } // END of rx-packets definition.

        leaf rx-bytes  {
            type  uint64;
            description "This attribute specifies rx bytes";
        } // END of rx-bytes definition.

        leaf frame-loss  {
            type  uint64;
            units "packets";
            description "This attribute specifies frame loss";
        } // END of frame-loss definition.

        leaf frame-loss-ratio  {
            type  string {
                length "1..1965";
            }
            units "%";
            description "This attribute specifies frame loss ratio";
        } // END of frame-loss-ratio definition.

        leaf frame-delay  {
            type  string {
                length "1..1965";
            }
            description "This attribute specifies frame delay";
        } // END of frame-delay definition.

        leaf frame-delay-variation  {
            type  string {
                length "1..1965";
            }
            description "This attribute specifies frame delay variation";
        } // END of frame-delay-variation definition.

        leaf frame-delay-min  {
            type  string {
                length "1..1965";
            }
            description "This attribute specifies frame delay min";
        } // END of frame-delay-min definition.

        leaf frame-delay-max  {
            type  string {
                length "1..1965";
            }
            description "This attribute specifies frame delay max";
        } // END of frame-delay-max definition.

        leaf frame-delay-exceed  {
            type  string {
                length "1..1965";
            }
            units "%";
            description "This attribute specifies frame delay exceed";
        } // END of frame-delay-exceed definition.

        leaf out-of-order-packets  {
            type  uint64;
            description "This attribute specifies out of order packets";
        } // END of out-of-order-packets definition.

        leaf error-packets  {
            type  uint64;
            description "This attribute specifies error packets";
        } // END of error-packets definition.

    } // END of sat-test-state definition.
    grouping sat-result-state {
        description
            "Grouping for SAT results";
        leaf result-name  {
            type  string {
                length "1..1965";
            }
            description "This attribute specifies result name";
        } // END of result-name definition.

        leaf tx-packets  {
            type  uint64;
            description "This attribute specifies Tx packets";
        } // END of tx-packets definition.

        leaf tx-bytes  {
            type  uint64;
            description "This attribute specifies Tx bytes";
        } // END of tx-bytes definition.

        leaf rx-packets  {
            type  uint64;
            description "This attribute specifies Rx packets";
        } // END of rx-packets definition.

        leaf rx-bytes  {
            type  uint64;
            description "This attribute specifies Rx bytes";
        } // END of rx-bytes definition.

        leaf frame-loss  {
            type  uint64;
            description "This attribute specifies frame loss";
        } // END of frame-loss definition.

        leaf frame-loss-ratio  {
            type  string {
                length "1..1965";
                pattern "[^?' =,>|]+";
            }
            units "%";
            description "This attribute specifies frame loss ratio";
        } // END of frame-loss-ratio definition.

        leaf frame-delay  {
            type  string {
                length "1..1965";
            }
            description "This attribute specifies frame delay";
        } // END of frame-delay definition.

        leaf frame-delay-variation  {
            type  string {
                length "1..1965";
            }
            description "This attribute specifies frame delay variation";
        } // END of frame-delay-variation definition.

        leaf frame-delay-min  {
            type  string {
                length "1..1965";
            }
            description "This attribute specifies frame delay min";
        } // END of frame-delay-min definition.

        leaf frame-delay-max  {
            type  string {
                length "1..1965";
            }
            description "This attribute specifies frame delay max";
        } // END of frame-delay-max definition.

        leaf frame-delay-exceed  {
            type  string {
                length "1..1965";
            }
            units "%";
            description "This attribute specifies frame delay exceed";
        } // END of frame-delay-exceed definition.

        leaf out-of-order-packets  {
            type  uint64;
            description "This attribute specifies out of order packets";
        } // END of out-of-order-packets definition.

        leaf error-packets  {
            type  uint64;
            description "This attribute specifies error packets";
        } // END of error-packets definition.

    } // END of sat-result-state definition.
    grouping sat-results-top {
        description
            "Top level grouping for SAT results";
        container results {
            config false;
            description
                "Container for results";
            uses sat-state-result-top;
        } // END of results-container definition.
    } // END of sat-results-top definition.
    grouping sat-state-result-top {
        description
            "Top level grouping for SAT results";

        list result {
            key "result-name";
            config false;
            description
                "List of SAT results";
            leaf result-name  {
                type  leafref {
                    path  "../state/result-name";
                }
                description "This attribute specifies test result name";
            } // END of result-name definition.

            container state {
                config false;
                description
                    "Operational data for result";
                uses sat-result-state;
            } // END of state-container definition.
        } // End of result-list
    } // END of sat-state-result-top definition.
    grouping sat-state-service-test-top {
        description
            "Top level grouping for SAT service tests";

        list s-test {
            key "stest-name";
            config false;
            description
                "List of SAT tests";
            leaf stest-name  {
                type  leafref {
                    path  "../state/stest-name";
                }
                description "This attribute specifies service test name";
            } // END of stest-name definition.

            container state {
                config false;
                description
                    "Operational data for service test";
                uses sat-test-state;
            } // END of state-container definition.
            uses sat-results-top;
        } // End of s-test-list
    } // END of sat-state-service-test-top definition.
    grouping sat-service-tests-state-top {
        description
            "Top level grouping for SAT tests";
        container s-tests {
            config false;
            description
                "Container for service tests";
            uses sat-state-service-test-top;
        } // END of s-tests-container definition.
    } // END of sat-service-tests-state-top definition.
    grouping sat-stream-state-top {
        description
            "Top level grouping fpr SAT streams";
        container service-streams {
            config false;
            description
                "Container for service streams";
            uses sat-stream-top;
        } // END of service-streams-container definition.
    } // END of sat-stream-state-top definition.
    grouping sat-stream-top {
        description
            "Top level grouping for SAT stream top";

        list service-stream {
            key "stream-name";
            config false;
            description
                "List of SAT service streams";
            leaf stream-name  {
                type  leafref {
                    path  "../state/stream-name";
                }
                description "This attribute specifies SAT stream name";
            } // END of stream-name definition.

            container state {
                config false;
                description
                    "Operational data for service stream";
                uses sat-stream-state;
            } // END of state-container definition.
            uses sat-service-tests-state-top;
        } // End of service-stream-list
    } // END of sat-stream-top definition.
    grouping sat-test-state-top {
        description
            "Top level grouping fpr SAT sate top";
        container runs {
            config false;
            description
                "Container for runs";
            uses sat-test-runs-top;
        } // END of runs-container definition.
    } // END of sat-test-state-top definition.
    grouping sat-test-runs-top {
        description
            "Top level Grouping for SAT tests runs";

        list run {
            key "run-id";
            config false;
            description
                "List of SAT runs";
            leaf run-id  {
                type  leafref {
                    path  "../state/run-id";
                }
                description "This attribute specifies the run id";
            } // END of run-id definition.

            container state {
                config false;
                description
                    "Operational data for run";
                uses sat-test-run;
            } // END of state-container definition.
            uses sat-stream-state-top;
        } // End of run-list
    } // END of sat-test-runs-top definition.
    grouping sat-test-run {
        description
            "Grouping for SAT test run";
        leaf run-id  {
            type  uint8;
            description "This attribute specifies run id";
        } // END of run-id definition.

        leaf description  {
            type  string {
                length "1..1965";
            }
            description "This attribute specifies description for each run";
        } // END of description definition.

        leaf oper-state  {
            type  ipi-sat-types:sat_oper_status;
            description "This attribute specifies the status of the run";
        } // END of oper-state definition.

        leaf start-time  {
            type  string {
                length "1..1965";
            }
            description "This attribute specifies the start-time";
        } // END of start-time definition.

        leaf end-time  {
            type  string {
                length "1..1965";
            }
            description "This attribute specifies the end-time";
        } // END of end-time definition.

        leaf direction  {
            type  ipi-sat-types:sat_direction_t;
            description "This attribute specifies the direction";
        } // END of direction definition.

        leaf stream-run  {
            type  ipi-sat-types:sat_stream_run_t;
            description "This attribute specifies the stream run";
        } // END of stream-run definition.

    } // END of sat-test-run definition.
    grouping sat-excess-information-rate-config {
        description
            "Grouping for SAT EIR config";
        leaf eir  {
            type  uint64 {
                 range "1..400000"  {
                    description "1..400000: Supported range 1 - 400000";
                 }
            }
            mandatory true;
            description "Excess Information Rate";
        } // END of eir definition.

        leaf eir-unit  {
            type  ipi-sat-types:sat_rate_unit_t;
            mandatory true;
            description "Excess Information Rate unit";
        } // END of eir-unit definition.

        leaf eir-cos  {
            type  uint8 {
                 range "0..7"  {
                    description "0..7: Supported range 0 - 7";
                 }
            }
            mandatory true;
            description "Specify the EIR COS";
        } // END of eir-cos definition.

        leaf eir-dei  {
            type  uint8 {
                 range "0..1"  {
                    description "0..1: Supported range 0 - 1";
                 }
            }
            mandatory true;
            description "Specify the EIR DEI";
        } // END of eir-dei definition.

    } // END of sat-excess-information-rate-config definition.
    grouping sat-excess-information-rate-top {
        description
            "Top level grouping for EIR";
        container excess-information-rate {
            description
                "Container for EIR";
            container config {
                presence "yes";
                description
                    "Configuration data for EIR";
                uses sat-excess-information-rate-config;
            } // END of config-container definition.
            container state {
                config false;
                description
                    "Operational data for EIR";
                uses sat-excess-information-rate-config;
            } // END of state-container definition.
        } // END of excess-information-rate-container definition.
    } // END of sat-excess-information-rate-top definition.
    grouping sat-delay-bins-config {
        description
            "sat-delay";
        leaf min-rate  {
            type  ipi-sat-types:sat_delay_rate_t;
            mandatory true;
            description "Configures the unit for maximum delay rate as
                        milli-secs/micro-secs/nano-secs";
        } // END of min-rate definition.

        leaf min-range  {
            type  uint16 {
                 range "1..10000"  {
                    description "1..10000: Supported range 1 - 10000";
                 }
            }
            mandatory true;
            description "Specifies the minimum range";
        } // END of min-range definition.

        leaf max-rate  {
            type  ipi-sat-types:sat_delay_rate_t;
            mandatory true;
            description "Configures the unit for maximum delay rate as
                        milli-secs/micro-secs/nano-secs";
        } // END of max-rate definition.

        leaf max-range  {
            type  uint16 {
                 range "1..10000"  {
                    description "1..10000: Supported range 1 - 10000";
                 }
            }
            mandatory true;
            description "Specifies the maximum range";
        } // END of max-range definition.

    } // END of sat-delay-bins-config definition.
    grouping sat-delay-bins-top {
        description
            "Top level grouping for delay";
        container delay-bins {
            description
                "Container for delay bins";
            container config {
                presence "yes";
                description
                    "Configuration data for delay bins";
                uses sat-delay-bins-config;
            } // END of config-container definition.
            container state {
                config false;
                description
                    "Operational data for delay bins";
                uses sat-delay-bins-config;
            } // END of state-container definition.
        } // END of delay-bins-container definition.
    } // END of sat-delay-bins-top definition.
    grouping sat-committed-information-rate-config {
        description
            "Configuration for CIR configuration data";
        leaf cir  {
            type  uint64 {
                 range "1..400000"  {
                    description "1..400000: Supported range 1 - 400000";
                 }
            }
            mandatory true;
            description "commited information rate";
        } // END of cir definition.

        leaf cir-unit  {
            type  ipi-sat-types:sat_rate_unit_t;
            mandatory true;
            description "commited information rate unit";
        } // END of cir-unit definition.

        leaf cir-cos  {
            type  uint8 {
                 range "0..7"  {
                    description "0..7: Supported range 0 - 7";
                 }
            }
            mandatory true;
            description "commited information rate COS";
        } // END of cir-cos definition.

        leaf cir-dei  {
            type  uint8 {
                 range "0..1"  {
                    description "0..1: Supported range 0 - 1";
                 }
            }
            mandatory true;
            description "commited information DEI";
        } // END of cir-dei definition.

    } // END of sat-committed-information-rate-config definition.
    grouping sat-commited-information-rate-top {
        description
            "Top level grouping for CIR";
        container commited-information-rate {
            description
                "Contaiener for CIR";
            container config {
                presence "yes";
                description
                    "Configuration data for CIR";
                uses sat-committed-information-rate-config;
            } // END of config-container definition.
            container state {
                config false;
                description
                    "Operational data for CIR";
                uses sat-committed-information-rate-config;
            } // END of state-container definition.
        } // END of commited-information-rate-container definition.
    } // END of sat-commited-information-rate-top definition.
    grouping sat-rate-profile-config {
        description
            "Grouping for SAT rate Profile Configuration data";
        leaf rate-pname  {
            type  string {
                length "1..1965";
                pattern "[^?' =,>|]+";
            }
            description "SAT profile name";
        } // END of rate-pname definition.

        leaf two-way  {
            type  empty;
            description "Used to set/unset two-way";
        } // END of two-way definition.

        leaf color-aware  {
            type  empty;
            description "Used to set/unset the color-aware";
        } // END of color-aware definition.

        leaf load-step  {
            type  uint8 {
                 range "1..10"  {
                    description "1..10: Supported range 1 - 10";
                 }
            }
            description "Specify the load-step";
        } // END of load-step definition.

        leaf mode  {
            type  ipi-sat-types:sat_mode_t;
            description "Use this attribute to set/unset the SAT mode";
        } // END of mode definition.

    } // END of sat-rate-profile-config definition.
    grouping sat-rate-profile-top {
        description
            "Grouping for SAT rate profile top grouping";
        container rate-profiles {
            description
                "Container for SAT rate profile";

            list rate-profile {
                key "rate-pname";
                description
                    "Lis of SAT rate profile";
                leaf rate-pname  {
                    type  leafref {
                        path  "../config/rate-pname";
                    }
                    description "SAT profile name";
                } // END of rate-pname definition.

                container config {
                    description
                        "Configuration data for SAT profile";
                    uses sat-rate-profile-config;
                } // END of config-container definition.
                container state {
                    config false;
                    description
                        "Operational data for SAT profile";
                    uses sat-rate-profile-config;
                } // END of state-container definition.
                uses sat-commited-information-rate-top;
                uses sat-excess-information-rate-top;
                uses sat-delay-bins-top;
            } // End of rate-profile-list
        } // END of rate-profiles-container definition.
    } // END of sat-rate-profile-top definition.
    grouping sat-acceptance-profile-config {
        description
            "Grouping for SAT acceptance Profile Configuration data";
        leaf acceptance-pname  {
            type  string {
                length "1..1965";
                pattern "[^?' =,>|]+";
            }
            description "SAT profile name";
        } // END of acceptance-pname definition.

        leaf cir-frame-loss-ratio  {
            type  string {
                length "1..1965";
                pattern "([0-9][.][0-9]{4})|([1-9][0][.][0-9]{4})|([1-9]{2}[.][0-9]{4})|([1][0][0][.][0]{4})";
            }
            description "Specify the cir frame loss ratio";
        } // END of cir-frame-loss-ratio definition.

        leaf cir-frame-loss-ratio-policing  {
            type  string {
                length "1..1965";
                pattern "([0-9][.][0-9]{4})|([1-9][0][.][0-9]{4})|([1-9]{2}[.][0-9]{4})|([1][0][0][.][0]{4})";
            }
            description "Specifiy cir frame loss ratio policing";
        } // END of cir-frame-loss-ratio-policing definition.

        leaf cir-frame-delay-variation  {
            // when " ../cir-frame-delay-variation-range ";
            type  ipi-sat-types:sat_delay_rate_t;
            description "Specify the cir frame delay variation";
        } // END of cir-frame-delay-variation definition.

        leaf cir-frame-delay-variation-range  {
            // when " ../cir-frame-delay-variation ";
            type  uint16 {
                 range "1..10000"  {
                    description "1..10000: Supported range 1 - 10000";
                 }
            }
            description "Specify the cir frame delay variation range";
        } // END of cir-frame-delay-variation-range definition.

        leaf cir-frame-delay  {
            // when " ../cir-frame-delay-range ";
            type  ipi-sat-types:sat_delay_rate_t;
            description "Specify the cir frame delay variation";
        } // END of cir-frame-delay definition.

        leaf cir-frame-delay-range  {
            // when " ../cir-frame-delay ";
            type  uint16 {
                 range "1..10000"  {
                    description "1..10000: Supported range 1 - 10000";
                 }
            }
            description "specify the cir frame delay variation range";
        } // END of cir-frame-delay-range definition.

    } // END of sat-acceptance-profile-config definition.
    grouping sat-acceptance-profile-top {
        description
            "Top level grouping for SAT acceptance profile";
        container acceptance-profiles {
            description
                "Container for SAT acceptance profile";

            list acceptance-profile {
                key "acceptance-pname";
                description
                    "Lis of SAT acceptance profile";
                leaf acceptance-pname  {
                    type  leafref {
                        path  "../config/acceptance-pname";
                    }
                    description "SAT acceptance profile name";
                } // END of acceptance-pname definition.

                container config {
                    description
                        "Configuration data for SAT profile";
                    uses sat-acceptance-profile-config;
                } // END of config-container definition.
                container state {
                    config false;
                    description
                        "Operational data for SAT profile";
                    uses sat-acceptance-profile-config;
                } // END of state-container definition.
            } // End of acceptance-profile-list
        } // END of acceptance-profiles-container definition.
    } // END of sat-acceptance-profile-top definition.
    grouping sat-frame-size-profile-config {
        description
            "Grouping for SAT frame size Profile Configuration data";
        leaf size-pname  {
            type  string {
                length "1..1965";
                pattern "[^?' =,>|]+";
            }
            description "SAT profile name";
        } // END of size-pname definition.

        leaf size-a  {
            type  empty;
            description "Specify the size a frame size as 64";
        } // END of size-a definition.

        leaf size-b  {
            type  empty;
            description "Specify the size b frame size as 128";
        } // END of size-b definition.

        leaf size-c  {
            type  empty;
            description "Specify the size c frame size as 256";
        } // END of size-c definition.

        leaf size-d  {
            type  empty;
            description "Specify the size d frame size as 512";
        } // END of size-d definition.

        leaf size-e  {
            type  empty;
            description "Specify the size e frame size as 1024";
        } // END of size-e definition.

        leaf size-f  {
            type  empty;
            description "Specify the size f frame size as 1280";
        } // END of size-f definition.

        leaf size-g  {
            type  empty;
            description "Specify the size g frame size as 1518";
        } // END of size-g definition.

        leaf size-h  {
            type  uint16 {
                 range "64..9200"  {
                    description "64..9200: Supported range 64 - 9200";
                 }
            }
            description "Specify the size h frame size range between 64 to 9200";
        } // END of size-h definition.

        leaf size-u  {
            type  uint16 {
                 range "64..9200"  {
                    description "64..9200: Supported range 64 - 9200";
                 }
            }
            description "Specify the size u frame size range between 64 to 9200";
        } // END of size-u definition.

    } // END of sat-frame-size-profile-config definition.
    grouping sat-frame-size-profile-top {
        description
            "Top level grouping for SAT frame size profile";
        container frame-size-profiles {
            description
                "Container for SAT frame size profile";

            list frame-size-profile {
                key "size-pname";
                description
                    "Lis of SAT frame size profile";
                leaf size-pname  {
                    type  leafref {
                        path  "../config/size-pname";
                    }
                    description "SAT frame size profile name";
                } // END of size-pname definition.

                container config {
                    description
                        "Configuration data for SAT profile";
                    uses sat-frame-size-profile-config;
                } // END of config-container definition.
                container state {
                    config false;
                    description
                        "Operational data for SAT profile";
                    uses sat-frame-size-profile-config;
                } // END of state-container definition.
            } // End of frame-size-profile-list
        } // END of frame-size-profiles-container definition.
    } // END of sat-frame-size-profile-top definition.
    grouping service-test-config {
        description
            "Grouping or service test config";
        leaf test-type  {
            type  ipi-sat-types:sat_service_t;
            description "test-type";
        } // END of test-type definition.

        leaf duration  {
            type  empty;
            description "Used to set duration";
        } // END of duration definition.

        leaf hours  {
            // when " ../duration ";
            type  uint8 {
                 range "1..60"  {
                    description "1..60: Supported range 1 - 60";
                 }
            }
            description "Set the time in terms of hours";
        } // END of hours definition.

        leaf minutes  {
            // when " ../duration ";
            type  uint8 {
                 range "1..60"  {
                    description "1..60: Supported range 1 - 60";
                 }
            }
            description "Set the time in terms of minutes";
        } // END of minutes definition.

        leaf seconds  {
            // when " ../duration ";
            type  uint8 {
                 range "1..60"  {
                    description "1..60: Supported range 1 - 60";
                 }
            }
            description "Set the time in terms of seconds";
        } // END of seconds definition.

    } // END of service-test-config definition.
    grouping sat-frame-payload-config {
        description
            "Grouping for SAT frame payload configuration data";
        leaf frame-payload  {
            type  empty;
            mandatory true;
            description "Specify frame payload";
        } // END of frame-payload definition.

        leaf dst-mac  {
            type  ipi-sat-types:sat_mac_addr_t {
                length "1..1965";
            }
            description "Specify the destination MAC address";
        } // END of dst-mac definition.

        leaf source-interface  {
            type  leafref {
                path  "/ipi-interface:interfaces/ipi-interface:interface/ipi-interface:name";
            }
            description "Specify the source interface name";
        } // END of source-interface definition.

        leaf tag-type  {
            type  ipi-sat-types:sat_tag_type_t;
            description "This attribute is used to configure the tag type (dot1q|dot1ad).";
        } // END of tag-type definition.

        leaf vlan-id  {
            // when " ../tag-type ";
            type  uint16 {
                 range "1..4095"  {
                    description "1..4095: Supported range 1 - 4095";
                 }
            }
            description "The VID monitored by this MA";
        } // END of vlan-id definition.

        leaf inner-vlan-id  {
            // when " ../tag-type ";
            type  uint16 {
                 range "1..4094"  {
                    description "1..4094: Supported range 1 - 4094";
                 }
            }
            description "The inner VLAN ID monitored by this MA";
        } // END of inner-vlan-id definition.

    } // END of sat-frame-payload-config definition.
    grouping sat-cfm-config {
        description
            "Grouping for SAT CFM configuration";
        leaf domain-name  {
            type  string {
                length "1..43";
                pattern "[^?' =,>|]+";
            }
            mandatory true;
            description "Specify the CFM domain name";
        } // END of domain-name definition.

        leaf ma-name  {
            type  string {
                length "1..6";
                pattern "[^?' =,>|]+";
            }
            mandatory true;
            description "Specify the MA name";
        } // END of ma-name definition.

        leaf mep-id  {
            type  uint16 {
                 range "1..8191"  {
                    description "1..8191: Supported range 1 - 8191";
                 }
            }
            mandatory true;
            description "Use this attribute to set the MEP id";
        } // END of mep-id definition.

    } // END of sat-cfm-config definition.
    grouping sat-cfm-top {
        description
            "Top level grouping for SAT CFM configuration";
        container cfm {
            description
                "Container for SAT CFM configuration";
            container config {
                presence "yes";
                description
                    "Configuration data for SAT CFM";
                uses sat-cfm-config;
            } // END of config-container definition.
            container state {
                config false;
                description
                    "SAT CFM Operational state data";
                uses sat-cfm-config;
            } // END of state-container definition.
        } // END of cfm-container definition.
    } // END of sat-cfm-top definition.
    grouping sat-frame-payload-top {
        description
            "Top level grouping for SAT frame payload";
        container frame-payload {
            description
                "Container for SAT frame payload configuration";
            container config {
                presence "frame payload";
                description
                    "Configuration data for frame-payload";
                uses sat-frame-payload-config;
            } // END of config-container definition.
            container state {
                config false;
                description
                    "SAT frame payload Operational state data";
                uses sat-frame-payload-config;
            } // END of state-container definition.
            uses sat-cfm-top;
        } // END of frame-payload-container definition.
    } // END of sat-frame-payload-top definition.
    grouping sat-stream-config {
        description
            "Grouping for SAT stream Configuration data";
        leaf stream-name  {
            type  string {
                length "1..1965";
                pattern "[^?' =,>|]+";
            }
            description "SAT profile name";
        } // END of stream-name definition.

        leaf description  {
            type  cml-data-types:cml_line_t {
                length "1..255";
            }
            description "Used to set the description";
        } // END of description definition.

        leaf rate-profile  {
            type  leafref {
                path  "/sat/rate-profiles/rate-profile/config/rate-pname";
            }
            description "Specify the rate profile";
        } // END of rate-profile definition.

        leaf acceptance-profile  {
            type  leafref {
                path  "/sat/acceptance-profiles/acceptance-profile/config/acceptance-pname";
            }
            description "Specify the acceptance profile name";
        } // END of acceptance-profile definition.

        leaf frame-size-profile  {
            type  leafref {
                path  "/sat/frame-size-profiles/frame-size-profile/config/size-pname";
            }
            description "Specify the frame size profile name";
        } // END of frame-size-profile definition.

        leaf frame-sequence  {
            type  string {
                length "1..32";
                pattern "[a-hu]{1,8}";
            }
            description "Specify the frame sequence";
        } // END of frame-sequence definition.

        leaf frame-data-pattern  {
            type  ipi-sat-types:sat_data_pattern_t;
            description "Specify the frame data pattern";
        } // END of frame-data-pattern definition.

        leaf frame-delay-disable  {
            type  empty;
            description "Use this attribute to disable frame delay";
        } // END of frame-delay-disable definition.

    } // END of sat-stream-config definition.
    grouping sat-service-stream-top {
        description
            "Top level grouping for SAT service stream";
        container streams {
            description
                "Container for SAT service streams";

            list stream {
                key "stream-name";
                description
                    "Lis of SAT service stream";
                leaf stream-name  {
                    type  leafref {
                        path  "../config/stream-name";
                    }
                    description "SAT test";
                } // END of stream-name definition.

                container config {
                    description
                        "Configuration data for SAT service stream";
                    uses sat-stream-config;
                } // END of config-container definition.
                container state {
                    config false;
                    description
                        "Operational data for SAT service stream";
                    uses sat-stream-config;
                } // END of state-container definition.
                uses sat-frame-payload-top;
            } // End of stream-list
        } // END of streams-container definition.
    } // END of sat-service-stream-top definition.
    grouping sat-service-test-top {
        description
            "Top level grouping for SAT service test";
        container service-tests {
            description
                "Container for SAT service tests";

            list service-test {
                key "test-type";
                description
                    "Lis of SAT service test";
                leaf test-type  {
                    type  leafref {
                        path  "../config/test-type";
                    }
                    description "SAT test";
                } // END of test-type definition.

                container config {
                    description
                        "Configuration data for SAT service test";
                    uses service-test-config;
                } // END of config-container definition.
                container state {
                    config false;
                    description
                        "Operational data for SAT service test";
                    uses service-test-config;
                } // END of state-container definition.
            } // End of service-test-list
        } // END of service-tests-container definition.
    } // END of sat-service-test-top definition.
    grouping sat-test-config {
        description
            "Grouping for SAT test Configuration data";
        leaf test-name  {
            type  string {
                length "1..32";
                pattern "[^?' =,>|]+";
            }
            description "SAT profile name";
        } // END of test-name definition.

        leaf description  {
            type  cml-data-types:cml_line_t {
                length "1..255";
            }
            description "Used to set the description";
        } // END of description definition.

        leaf direction  {
            type  ipi-sat-types:sat_direction_t;
            description "Used to map the direction as upstream/downstream";
        } // END of direction definition.

        leaf stream-run  {
            type  ipi-sat-types:sat_stream_run_t;
            description "Used to set the stream run";
        } // END of stream-run definition.

    } // END of sat-test-config definition.
    grouping sat-test-top {
        description
            "Tpp level grouping for SAT test";
        container tests {
            description
                "Container for SAT test configuration";

            list test {
                key "test-name";
                description
                    "Lis of SAT test configuration";
                leaf test-name  {
                    type  leafref {
                        path  "../config/test-name";
                    }
                    description "SAT test";
                } // END of test-name definition.

                container config {
                    description
                        "Configuration data for SAT test";
                    uses sat-test-config;
                } // END of config-container definition.
                container state {
                    config false;
                    description
                        "Operational data for SAT test";
                    uses sat-test-config;
                } // END of state-container definition.
                uses sat-service-test-top;
                uses sat-service-stream-top;
                uses sat-test-state-top;
                uses sat-test-summary-top;
            } // End of test-list
        } // END of tests-container definition.
    } // END of sat-test-top definition.
    grouping sat-interface-config {
        description
            "Grouping for SAT module config objects";
        leaf interface-name  {
            type  leafref {
                path  "/ipi-interface:interfaces/ipi-interface:interface/ipi-interface:name";
            }
            description "This attribute describes the textual name of the interface";
        } // END of interface-name definition.

        leaf data-loopback  {
            type  ipi-sat-types:sat_direction_t;
            description "Use this attribute to set the ethernet data loopback for
                        upstream/downstream";
        } // END of data-loopback definition.

    } // END of sat-interface-config definition.
    grouping sat-interface-top {
        description
            "Grouping for SAT interface configuration";
        container interfaces {
            description
                "container for interface level configuration for SAT";

            list interface {
                key "interface-name";
                description
                    "List of SAT interface related operations";
                leaf interface-name  {
                    type  leafref {
                        path  "../config/interface-name";
                    }
                    description "Use this attribute to perform platform's interface SAT related
                                configurations";
                } // END of interface-name definition.

                container config {
                    description
                        "configuration container for interface list";
                    uses sat-interface-config;
                } // END of config-container definition.
                container state {
                    config false;
                    description
                        "Operational data for interface";
                    uses sat-interface-config;
                } // END of state-container definition.
            } // End of interface-list
        } // END of interfaces-container definition.
    } // END of sat-interface-top definition.

    grouping  sat-grouping {
    description
        "Container for SAT (Service Activation Test)";
    container sat {
        if-feature feature-list:HAVE_CFM;
        if-feature feature-list:HAVE_ONMD;
        if-feature feature-list:HAVE_ETH_SAT;
        description
            "Container for SAT (Service Activation Test)";
        uses sat-rate-profile-top;
        uses sat-acceptance-profile-top;
        uses sat-frame-size-profile-top;
        uses sat-test-top;
        uses sat-interface-top;
    } // END of sat-container definition.
    } // END of sat-grouping definition.

    uses sat-grouping;

    rpc service-activation-test-start {
        if-feature feature-list:HAVE_CFM;
        if-feature feature-list:HAVE_ONMD;
        if-feature feature-list:HAVE_ETH_SAT;
        description "start a servoce activation test";
        input  {
            leaf test-name  {
                type string {
                    length "1..32";
                }
                mandatory true;
                description "This attribute specify the  SAT test name";
            }
            leaf sat-unit  {
                type ipi-sat-types:sat_service_t;
                default "all";
                description "Specify the SAT unit";
            }
            leaf service-stream  {
                type string {
                    length "1..32";
                }
                default "NULL";
                description "Specify the service stream name";
            }
            leaf repeat-last-fail-test  {
                type ipi-sat-types:sat_repeat_last_fail_test_t;
                default "new-test";
                description "Repeat from the Last failed test case for SAT";
            }
        }
    }

    rpc service-activation-test-abort {
        if-feature feature-list:HAVE_CFM;
        if-feature feature-list:HAVE_ONMD;
        if-feature feature-list:HAVE_ETH_SAT;
        description "start a service activation test";
        input  {
            leaf test-name  {
                type string {
                    length "1..32";
                }
                mandatory true;
                description "This attribute specify the  SAT test name";
            }
            leaf sat-unit  {
                type ipi-sat-types:sat_service_t;
                default "all";
                description "Specify the SAT UNIT";
            }
            leaf service-stream  {
                type string {
                    length "1..32";
                }
                default "NULL";
                description "Specify the service stream name";
            }
        }
    }

    rpc service-activation-test-clear {
        if-feature feature-list:HAVE_CFM;
        if-feature feature-list:HAVE_ONMD;
        if-feature feature-list:HAVE_ETH_SAT;
        description "start a service activation test";
        input  {
            leaf test-name  {
                type string {
                    length "1..32";
                }
                mandatory true;
                description "This attribute specify the  SAT test name";
            }
            leaf sat-unit  {
                type ipi-sat-types:sat_service_t;
                default "all";
                description "This attribute specify sat test unit";
            }
            leaf service-stream  {
                type string {
                    length "1..32";
                }
                default "255";
                description "Specify the service stream name";
            }
        }
    }

    rpc data-loopback-start {
        if-feature feature-list:HAVE_CFM;
        if-feature feature-list:HAVE_ONMD;
        if-feature feature-list:HAVE_ETH_SAT;
        description "start a data loopback";
        input  {
            leaf interface-name  {
                type string {
                    length "1..32";
                }
                mandatory true;
                description "This attribute specify the interface name";
            }
            leaf timeout  {
                type uint16 {
                    range "0..1440";
                }
                mandatory true;
                description "This attribute specify the time out";
            }
        }
    }

    rpc data-loopback-abort {
        if-feature feature-list:HAVE_CFM;
        if-feature feature-list:HAVE_ONMD;
        if-feature feature-list:HAVE_ETH_SAT;
        description "abort a data loopback";
        input  {
            leaf interface-name  {
                type string {
                    length "1..32";
                }
                mandatory true;
                description "This attribute specify the interface name";
            }
            leaf timeout  {
                type uint16 {
                    range "0..1440";
                }
                mandatory true;
                description "This attribute specify the time";
            }
        }
    }

    notification sat-tests-results-completed {
        if-feature feature-list:HAVE_CFM;
        if-feature feature-list:HAVE_ONMD;
        if-feature feature-list:HAVE_ETH_SAT;

        description "Notify that the result is completed.";

        leaf severity {
            type cml-data-types:cml_notif_severity_t;
            description "Notification severity level (value: INFO)";
        }

        leaf eventClass {
            type cml-data-types:cml_notif_class_t;
            description "Notification event class (value: STATE)";
        }

        leaf run {
            type  uint8;
        description
            "This attribute specifies run for summary";
        }

        leaf test-name {
            type  string;
        description
            "SAT test";
        }

        leaf status {
            type ipi-sat-types:sat_summary_status;
        description
            "This attribute specifies status of run";
        }
    }

}
