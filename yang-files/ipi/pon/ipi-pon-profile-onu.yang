/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-pon-profile-onu.yang
*
*/

submodule ipi-pon-profile-onu {

    yang-version 1.1;

    belongs-to  ipi-pon { prefix ipi-pon; }

    import feature-list {
        prefix feature-list;
        revision-date 2026-09-15;
    }

    import ipi-pon-types {
        prefix ipi-pon-types;
        revision-date 2023-02-06;
    }

    organization
        "IP Infusion Inc.";

    contact
        "Address: 3965 Freedom Circle, Suite 200, Santa Clara, CA 95054
         Phone: +1 408-400-1900
         E-mail: support@ipinfusion.com
         Web: http://www.ipinfusion.com/";

    description
        "This module defines a data model for ONU profiles configuration for
                passive optical network";


    revision "2022-06-01" {
        description "Updated the yang file with feature";
        reference " 0.4.0.";
    }

    revision "2021-09-03" {
        description "Update descriptions of attribute";
        reference " 0.3.0.";
    }

    revision "2021-02-15" {
        description "Added support for state container corresponding to config containers";
        reference " 0.2.0.";
    }

    revision "2020-11-13" {
        description "Initial Version";
        reference "Initial Version";
    }

    grouping onu-profile-name-config {
        description
            "Grouping for ONU profile name";
        leaf profile-name  {
            type  string {
                length "1..64";
                pattern "[^?' =,>|]+";
            }
            description "The attribute is to have unique ONU profile name";
        } // END of profile-name definition.

    } // END of onu-profile-name-config definition.
    grouping onu-profile-ready-state {
        description
            "Grouping for ONU profile ready state";
        leaf ready-status  {
            type  ipi-pon-types:pon_ready_status_t;
            description "The attribute is to show profile ready status";
        } // END of ready-status definition.

    } // END of onu-profile-ready-state definition.
    grouping onu-profile-global-config {
        description
            "Grouping for ONU profile global configuration";
        leaf tconts-max  {
            type  uint16 {
                 range "1..15360"  {
                    description "1..15360: Supported range 1 - 15360";
                 }
            }
            default "8";
            description "Use this setting to change T-CONT number per ONU. User should not
                        change this value";
        } // END of tconts-max definition.

    } // END of onu-profile-global-config definition.
    grouping uni-rule-id-config {
        description
            "Grouping for ONU profile UNI rule ID and mode";
        leaf logical-port-id  {
            type  uint16 {
                 range "0..255"  {
                    description "0..255: Supported range 0 - 255";
                 }
            }
            description "This is the UNI logical port ID from 0 to 255";
        } // END of logical-port-id definition.

    } // END of uni-rule-id-config definition.
    grouping uni-rule-gem-port-name-config {
        description
            "Grouping GEM port name for UNI rule of ONU profile";
        leaf gem-port-name  {
            type  string {
                length "1..64";
                pattern "[^?' =,>|]+";
            }
            description "This is the unique GEM port name for the UNI rule";
        } // END of gem-port-name definition.

    } // END of uni-rule-gem-port-name-config definition.
    grouping uni-rule-gem-port-config {
        description
            "Grouping GEM port configuration for UNI rule of ONU profile";
        leaf p-bits  {
            type  uint8 {
                 range "0..7"  {
                    description "0..7: Supported range 0 - 7";
                 }
            }
            mandatory true;
            description "3-bit IEEE 802.1p class of service";
        } // END of p-bits definition.

        leaf upstream-priority-queue  {
            type  uint16 {
                 range "0..65535"  {
                    description "0..65535: Supported range 0 - 65535";
                 }
            }
            mandatory true;
            description "This is the UNI upstream priority queue number";
        } // END of upstream-priority-queue definition.

        leaf downstream-priority-queue  {
            type  uint16 {
                 range "0..65535"  {
                    description "0..65535: Supported range 0 - 65535";
                 }
            }
            mandatory true;
            description "This is the UNI downstream priority queue number";
        } // END of downstream-priority-queue definition.

    } // END of uni-rule-gem-port-config definition.
    grouping tcont-rule-config {
        description
            "Grouping T-CONT rule configuration for ONU profile";
        leaf tcont-name  {
            type  string {
                length "1..64";
                pattern "[^?' =,>|]+";
            }
            description "This is the unique T-CONT name for the T-CONT rule";
        } // END of tcont-name definition.

        leaf-list gem-port-name  {
            type  string {
                length "1..64";
                pattern "[^?' =,>|]+";
            }
            description "This is the unique GEM port name for the T-CONT rule";
        } // END of gem-port-name definition.

    } // END of tcont-rule-config definition.
    grouping uni-rule-gem-port-lists {
        description
            "Grouping UNI rule GEM port list for ONU profile";
        container uni-gem-ports {
            description
                "UNI GEM port list";

            list uni-gem-port {
                key "gem-port-name";
                description
                    "UNI GEM port";
                leaf gem-port-name  {
                    type  leafref {
                        path  "../config/gem-port-name";
                    }
                    description "This is the unique GEM port name for the UNI rule";
                } // END of gem-port-name definition.

                container config {
                    presence "UNI GEM";
                    description
                        "UNI GEM port configuration";
                    uses uni-rule-gem-port-name-config;
                    uses uni-rule-gem-port-config;
                } // END of config-container definition.
                container state {
                    config false;
                    description
                        "UNI GEM port state for ONU profile";
                    uses uni-rule-gem-port-name-config;
                    uses uni-rule-gem-port-config;
                } // END of state-container definition.
            } // End of uni-gem-port-list
        } // END of uni-gem-ports-container definition.
    } // END of uni-rule-gem-port-lists definition.
    grouping uni-rule-lists {
        description
            "Grouping UNI rule list configuration for ONU profile";
        container uni-rules {
            description
                "UNI rule list";

            list uni-rule {
                key "logical-port-id";
                description
                    "UNI rule";
                leaf logical-port-id  {
                    type  leafref {
                        path  "../config/logical-port-id";
                    }
                    description "This is the UNI logical port ID from 0 to 255";
                } // END of logical-port-id definition.

                container config {
                    description
                        "UNI Rule ID configuration";
                    uses uni-rule-id-config;
                } // END of config-container definition.
                container state {
                    config false;
                    description
                        "UNI Rule state for ONU profile";
                    uses uni-rule-id-config;
                } // END of state-container definition.
                uses uni-rule-gem-port-lists;
            } // End of uni-rule-list
        } // END of uni-rules-container definition.
    } // END of uni-rule-lists definition.
    grouping tcont-rule-lists {
        description
            "Grouping T-CONT rule list configuration for ONU profile";
        container tcont-rules {
            description
                "T-CONT rules";

            list tcont-rule {
                key "tcont-name";
                description
                    "T-CONT rule";
                leaf tcont-name  {
                    type  leafref {
                        path  "../config/tcont-name";
                    }
                    description "This is the unique T-CONT name for the T-CONT rule";
                } // END of tcont-name definition.

                container config {
                    description
                        "T-CONT rule name configuration";
                    uses tcont-rule-config;
                } // END of config-container definition.
                container state {
                    config false;
                    description
                        "T-CONT rule state for ONU profile";
                    uses tcont-rule-config;
                } // END of state-container definition.
            } // End of tcont-rule-list
        } // END of tcont-rules-container definition.
    } // END of tcont-rule-lists definition.
    grouping onu-default-profile-state {
        description
            "Grouping for ONU default profile state";
        container default-profile {
            config false;
            description
                "ONU default profile";
            container state {
                config false;
                description
                    "ONU default profile state";
                uses onu-profile-name-config;
                uses onu-profile-global-config;
                uses onu-profile-ready-state;
            } // END of state-container definition.
            container uni-rules {
                config false;
                description
                    "UNI rule list";

                list uni-rule {
                    key "logical-port-id";
                    config false;
                    description
                        "UNI rule";
                    leaf logical-port-id  {
                        type  leafref {
                            path  "../state/logical-port-id";
                        }
                        description "This is the UNI logical port ID from 0 to 255";
                    } // END of logical-port-id definition.

                    container state {
                        config false;
                        description
                            "UNI Rule state for ONU profile";
                        uses uni-rule-id-config;
                    } // END of state-container definition.
                    container uni-gem-ports {
                        config false;
                        description
                            "UNI GEM port list";

                        list uni-gem-port {
                            key "gem-port-name";
                            config false;
                            description
                                "UNI GEM port";
                            leaf gem-port-name  {
                                type  leafref {
                                    path  "../state/gem-port-name";
                                }
                                description "This is the unique GEM port name for the UNI rule";
                            } // END of gem-port-name definition.

                            container state {
                                config false;
                                description
                                    "UNI GEM port state for ONU profile";
                                uses uni-rule-gem-port-name-config;
                                uses uni-rule-gem-port-config;
                            } // END of state-container definition.
                        } // End of uni-gem-port-list
                    } // END of uni-gem-ports-container definition.
                } // End of uni-rule-list
            } // END of uni-rules-container definition.
            container tcont-rules {
                config false;
                description
                    "T-CONT rules";

                list tcont-rule {
                    key "tcont-name";
                    config false;
                    description
                        "T-CONT rule";
                    leaf tcont-name  {
                        type  leafref {
                            path  "../state/tcont-name";
                        }
                        description "This is the unique T-CONT name for the T-CONT rule";
                    } // END of tcont-name definition.

                    container state {
                        config false;
                        description
                            "T-CONT rule state for ONU profile";
                        uses tcont-rule-config;
                    } // END of state-container definition.
                } // End of tcont-rule-list
            } // END of tcont-rules-container definition.
        } // END of default-profile-container definition.
    } // END of onu-default-profile-state definition.

    grouping  onu-profiles-grouping {
    description
        "ONU profiles";
    container onu-profiles {
        if-feature feature-list:HAVE_POND;
        description
            "ONU profiles";

        list onu-profile {
            key "profile-name";
            description
                "ONU profile";
            leaf profile-name  {
                type  leafref {
                    path  "../config/profile-name";
                }
                description "The attribute is to have unique ONU profile name";
            } // END of profile-name definition.

            container config {
                description
                    "Basic configuration data for ONU profile configuration";
                uses onu-profile-name-config;
                uses onu-profile-global-config;
            } // END of config-container definition.
            container state {
                config false;
                description
                    "ONU profile state";
                uses onu-profile-name-config;
                uses onu-profile-global-config;
                uses onu-profile-ready-state;
            } // END of state-container definition.
            uses uni-rule-lists;
            uses tcont-rule-lists;
        } // End of onu-profile-list
        uses onu-default-profile-state;
    } // END of onu-profiles-container definition.
    } // END of onu-profiles-grouping definition.


}
