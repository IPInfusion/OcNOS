/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-pon-onu-software-upgrade.yang
*
*/

submodule ipi-pon-onu-software-upgrade {

    yang-version 1.1;

    belongs-to  ipi-pon { prefix ipi-pon; }

    import feature-list {
        prefix feature-list;
        revision-date 2026-09-15;
    }

    import ipi-pon-types {
        prefix ipi-pon-types;
        revision-date 2023-02-06;
    }

    organization
        "IP Infusion Inc.";

    contact
        "Address: 3965 Freedom Circle, Suite 200, Santa Clara, CA 95054
         Phone: +1 408-400-1900
         E-mail: support@ipinfusion.com
         Web: http://www.ipinfusion.com/";

    description
        "This module defines a data model for ONU software upgrade";


    revision "2022-12-29" {
        description "Added support to software-upgrade error reason and new runtime attributes for upgrade process general-info";
        reference " 0.2.4.";
    }

    revision "2022-12-20" {
        description "Added support to software-upgrade group auto activate and commit";
        reference " 0.2.3.";
    }

    revision "2022-12-12" {
        description "Added support to software-upgrade group activate and commit command";
        reference " 0.2.2.";
    }

    revision "2022-12-07" {
        description "Added support to software-upgrade group configuration and command";
        reference " 0.2.1.";
    }

    revision "2022-11-16" {
        description "Added support to software-image-activate command";
        reference " 0.2.0.";
    }

    revision "2022-10-28" {
        description "Added support to software upgrade progress statistics";
        reference " 0.1.2.";
    }

    revision "2022-10-18" {
        description "Added support to software-image-commit command";
        reference " 0.1.1.";
    }

    revision "2022-08-09" {
        description "Initial Version";
        reference " 0.1.0.";
    }

    grouping onu-software-upgrade-group-vendor-config {
        description
            "Grouping for software upgrade ONU group vendor configuration";
        leaf vendor-id  {
            type  string {
                length "1..4";
                pattern "[^?' =,>|]+";
            }
            mandatory true;
            description "Use this attribute to configure the ONU vendor-id. e.g ALPH";
        } // END of vendor-id definition.

        leaf active-firmware-version  {
            type  string {
                length "1..32";
                pattern "[^?' =,>|]+";
            }
            mandatory true;
            description "Use this attribute to configure the ONU active-firmware version";
        } // END of active-firmware-version definition.

    } // END of onu-software-upgrade-group-vendor-config definition.
    grouping onu-software-upgrade-group-vendor-top {
        description
            "Grouping for software upgrade ONU group vendor configuration";
        container vendor {
            description
                "ONU group vendor configuration data";
            container config {
                presence "yes";
                description
                    "Configuration data for onu group vendor";
                uses onu-software-upgrade-group-vendor-config;
            } // END of config-container definition.
            container state {
                config false;
                description
                    "Operational state data for onu group vendor";
                uses onu-software-upgrade-group-vendor-config;
            } // END of state-container definition.
        } // END of vendor-container definition.
    } // END of onu-software-upgrade-group-vendor-top definition.
    grouping onu-software-upgrade-group-config {
        description
            "Grouping for software upgrade ONU group configuration";
        leaf group-name  {
            type  string {
                length "1..64";
                pattern "[^?' =,>|]+";
            }
            description "Use this attribute to configure a group of ONUs for software upgrade";
        } // END of group-name definition.

        leaf-list olt-id  {
            type  uint16 {
                 range "0..65535"  {
                    description "0..65535:Feature : HAVE_TIBIT Supported range 0 - 63Not Feature :
                            HAVE_TIBIT  Supported range 0 - 65535";
                 }
            }
            description "This is the logical OLT identity in the system. The OLT identity in
                        Tibit is 0 to 63 while the identity in other system is between 0 and
                        65535";
        } // END of olt-id definition.

        leaf-list pon-port  {
            type  string {
                length "4..64";
                pattern "[^?' =,>|]+";
            }
            description "PON port name starting with 'pon' on which ONU will be presented";
        } // END of pon-port definition.

    } // END of onu-software-upgrade-group-config definition.
    grouping onu-software-upgrade-group-top {
        description
            "Grouping for software upgrade ONU groups";
        container onu-groups {
            description
                "ONU groups configuration data";

            list onu-group {
                key "group-name";
                description
                    "ONU group list configuration";
                leaf group-name  {
                    type  leafref {
                        path  "../config/group-name";
                    }
                    description "Use this attribute to configure a group of ONUs for software upgrade";
                } // END of group-name definition.

                container config {
                    description
                        "Configuration data for ONU group";
                    uses onu-software-upgrade-group-config;
                } // END of config-container definition.
                container state {
                    config false;
                    description
                        "Operational state data for ONU group";
                    uses onu-software-upgrade-group-config;
                } // END of state-container definition.
                uses onu-software-upgrade-group-vendor-top;
            } // End of onu-group-list
        } // END of onu-groups-container definition.
    } // END of onu-software-upgrade-group-top definition.
    grouping onu-software-upgrade-progress-general-info-state {
        description
            "Grouping for software upgrade general-indo";
        leaf group-name  {
            type  string {
                length "1..1965";
                pattern "[^?' =,>|]+";
            }
            description "The software upgrade group used to upgrade the current ONU upgrades in
                        progress";
        } // END of group-name definition.

        leaf auto-commit  {
            type  ipi-pon-types:pon_onu_software_upgrade_auto_t;
            description "The software upgrade auto-commit status, if it is ON or OFF.";
        } // END of auto-commit definition.

        leaf auto-activate  {
            type  ipi-pon-types:pon_onu_software_upgrade_auto_t;
            description "The software upgrade auto-activate status, if it is ON or OFF.";
        } // END of auto-activate definition.

    } // END of onu-software-upgrade-progress-general-info-state definition.
    grouping onu-software-upgrade-progress-general-info-top {
        description
            "Grouping for software upgrade progress general information";
        container general-info {
            config false;
            description
                "general info of software upgrade";
            container state {
                config false;
                description
                    "Operational state data for software upgrade general-info";
                uses onu-software-upgrade-progress-general-info-state;
            } // END of state-container definition.
        } // END of general-info-container definition.
    } // END of onu-software-upgrade-progress-general-info-top definition.
    grouping onu-software-upgrade-progress-statistics-time {
        description
            "Grouping for software upgrade time statistics";
        leaf average  {
            type  decimal64 {
                 fraction-digits 2;            }
            units "minutes";
            description "The software-upgrade average time in minutes";
        } // END of average definition.

        leaf minimum  {
            type  decimal64 {
                 fraction-digits 2;            }
            units "minutes";
            description "The software-upgrade minimum time in minutes";
        } // END of minimum definition.

        leaf maximum  {
            type  decimal64 {
                 fraction-digits 2;            }
            units "minutes";
            description "The software-upgrade maximum time in minutes";
        } // END of maximum definition.

    } // END of onu-software-upgrade-progress-statistics-time definition.
    grouping onu-software-upgrade-progress-statistics-percentage {
        description
            "Grouping for software upgrade percentage rate statistics";
        leaf in-progress  {
            type  uint8;
            units "percentage";
            description "The current in-progress upgrade percentage from the total number of
                        ONUs upgrading";
        } // END of in-progress definition.

        leaf success  {
            type  uint8;
            units "percentage";
            description "The current success rate of upgrades from the total number of ONUs
                        upgrading";
        } // END of success definition.

        leaf failure  {
            type  uint8;
            units "percentage";
            description "The current failure rate of upgrades from the total number of ONUs
                        upgrading";
        } // END of failure definition.

    } // END of onu-software-upgrade-progress-statistics-percentage definition.
    grouping onu-software-upgrade-progress-statistics-top {
        description
            "Grouping for software upgrade statistics";
        container overall-statistics {
            config false;
            description
                "overall statistics of software upgrade";
            container upgrade-time {
                config false;
                description
                    "Time statistics of software upgrade";
                container state {
                    config false;
                    description
                        "Operational state data for software upgrade time statistics";
                    uses onu-software-upgrade-progress-statistics-time;
                } // END of state-container definition.
            } // END of upgrade-time-container definition.
            container upgrade-percentage {
                config false;
                description
                    "The rate of in-progress, successful,failed onu upgrades";
                container state {
                    config false;
                    description
                        "Operational state data for software upgrade percentage statistics";
                    uses onu-software-upgrade-progress-statistics-percentage;
                } // END of state-container definition.
            } // END of upgrade-percentage-container definition.
        } // END of overall-statistics-container definition.
    } // END of onu-software-upgrade-progress-statistics-top definition.
    grouping onu-software-upgrade-progress-onus-state {
        description
            "onu-software-upgrade-progress-onus-state";
        leaf onu-id  {
            type  uint32;
            description "This is the logical ONU identity in the system. The ONU identity is
                        from 0 to 4095";
        } // END of onu-id definition.

        leaf olt-id  {
            type  uint16;
            description "Indicate the OLT ID on which the ONU is presented";
        } // END of olt-id definition.

        leaf progress  {
            type  uint8;
            description "The percentage of ONU software upgrade completion";
        } // END of progress definition.

        leaf status  {
            type  ipi-pon-types:pon_onu_software_upgrade_status_t;
            description "The current status of ONU software upgrade";
        } // END of status definition.

        leaf error-reason  {
            type  ipi-pon-types:pon_onu_software_upgrade_error_reason_t;
            description "The error reason when the software upgrade failed. If no error, it
                        will display NA.";
        } // END of error-reason definition.

    } // END of onu-software-upgrade-progress-onus-state definition.
    grouping onu-software-upgrade-progress-onus-top {
        description
            "Grouping for software upgrade progress in each OLT and ONU";
        container onus {
            config false;
            description
                "The list of ONUs upgrading";

            list onu {
                key "onu-id";
                config false;
                description
                    "TThe list of ONUs upgrading";
                leaf onu-id  {
                    type  leafref {
                        path  "../state/onu-id";
                    }
                    description "This is the logical ONU identity in the system. The ONU identity is
                                from 0 to 4095";
                } // END of onu-id definition.

                container state {
                    config false;
                    description
                        "Operational state data for onu";
                    uses onu-software-upgrade-progress-onus-state;
                } // END of state-container definition.
            } // End of onu-list
        } // END of onus-container definition.
    } // END of onu-software-upgrade-progress-onus-top definition.
    grouping onu-software-upgrade-progress-top {
        description
            "Grouping for software-images info of the ONU";
        container upgrade-progress {
            config false;
            description
                "Software-images info of the ONU";
            uses onu-software-upgrade-progress-general-info-top;
            uses onu-software-upgrade-progress-statistics-top;
            uses onu-software-upgrade-progress-onus-top;
        } // END of upgrade-progress-container definition.
    } // END of onu-software-upgrade-progress-top definition.

    grouping  onu-software-upgrade-grouping {
    description
        "ONU Software Upgrade";
    container onu-software-upgrade {
        if-feature feature-list:HAVE_POND;
        description
            "ONU Software Upgrade";
        uses onu-software-upgrade-group-top;
        uses onu-software-upgrade-progress-top;
    } // END of onu-software-upgrade-container definition.
    } // END of onu-software-upgrade-grouping definition.


}
