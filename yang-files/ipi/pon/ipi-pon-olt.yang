/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-pon-olt.yang
*
*/

submodule ipi-pon-olt {

    yang-version 1.1;

    belongs-to  ipi-pon { prefix ipi-pon; }

    import feature-list {
        prefix feature-list;
        revision-date 2026-09-15;
    }

    import ipi-pon-types {
        prefix ipi-pon-types;
        revision-date 2023-02-06;
    }

    import ietf-yang-types {
        prefix yang;
        revision-date 2013-07-15;
    }

    organization
        "IP Infusion Inc.";

    contact
        "Address: 3965 Freedom Circle, Suite 200, Santa Clara, CA 95054
         Phone: +1 408-400-1900
         E-mail: support@ipinfusion.com
         Web: http://www.ipinfusion.com/";

    description
        "This module defines a data model for optical line terminal(OLT)
                configuration for passive optical network";


    revision "2023-07-07" {
        description "Removing the misplaced initialized from  details";
        reference " 0.1.0.";
    }

    revision "2023-02-07" {
        description "Updated some list structures by adding a container above";
        reference " 0.10.1.";
    }

    revision "2023-02-06" {
        description "Change type for OLT serial number";
        reference " 0.10.0.";
    }

    revision "2022-06-01" {
        description "Updated the yang file with feature";
        reference " 0.9.0.";
    }

    revision "2022-03-08" {
        description "Disable PPPoE in Tibit";
        reference " 0.8.0.";
    }

    revision "2021-11-18" {
        description "Update pon-type description for Alpha Networks SPX70D0-168F OLT";
        reference " 0.7.0.";
    }

    revision "2021-10-17" {
        description "Added management tpid configuration for Tibit";
        reference " 0.6.0.";
    }

    revision "2021-09-03" {
        description "Update descriptions of attribute";
        reference " 0.3.0.";
    }

    revision "2021-02-15" {
        description "Added support for state container corresponding to config containers";
        reference " 0.2.0.";
    }

    revision "2020-11-13" {
        description "Initial Version";
        reference "Initial Version";
    }

    grouping olt-id-config {
        description
            "Grouping for OLT identity configuration";
        leaf olt-id  {
            type  uint32 {
                 range "0..65535"  {
                    description "0..65535:Feature : HAVE_TIBIT Supported range 0 - 63Not Feature :
                            HAVE_TIBIT  Supported range 0 - 65535";
                 }
            }
            description "This is the logical OLT identity in the system. The OLT identity in
                        Tibit is 0 to 63 while the identity in other system is from 0 to 65535";
        } // END of olt-id definition.

    } // END of olt-id-config definition.
    grouping olt-serial-number-value {
        description
            "Grouping for OLT serial number value";
        leaf serial-number  {
            type  ipi-pon-types:pon_olt_serial_t {
                length "1..18";
            }
            description "The serial number i.e. MAC address for Tibit OLT";
        } // END of serial-number definition.

    } // END of olt-serial-number-value definition.
    grouping olt-extent-config {
        description
            "Grouping for OLT extent configuration";
        leaf pon-type  {
            if-feature feature-list:NOT_HAVE_TIBIT;
            type  ipi-pon-types:pon_olt_pon_type_t;
            default "combo-xgspon";
            description "The setting is supported by Zyxel SDA3016SS and Alpha Networks
                        SPX70D0-168F OLTs only. The PON type setting is either combo-xgspon or
                        single-gpon. The default is combo-xgspon. SDA3016SS OLT supports combo
                        and xgspon in combo-xgspon type. SPX70D0-168F OLT only supports xgspon
                        in combo-xgspon type";
        } // END of pon-type definition.

        leaf dhcp-one2one  {
            type  ipi-pon-types:pon_dhcp_on_off_t;
            default "off";
            description "The on or off state for DHCP relay function on the OLT. By default the
                        relay is off for 1:1 flow mode";
        } // END of dhcp-one2one definition.

        leaf dhcp-n2one  {
            type  ipi-pon-types:pon_dhcp_on_off_t;
            default "on";
            description "The on or off state for DHCP relay function on the OLT. By default the
                        relay is on for N:1 flow mode";
        } // END of dhcp-n2one definition.

        leaf pppoe  {
            if-feature feature-list:NOT_HAVE_TIBIT;
            type  ipi-pon-types:pon_pppoe_on_off_t;
            default "off";
            description "The on or off state for PPPoE relay function on the OLT. By default
                        the relay is off";
        } // END of pppoe definition.

        leaf encryption  {
            if-feature feature-list:HAVE_TIBIT;
            type  ipi-pon-types:pon_gem_encryption_t;
            default "off";
            description "The on or off state of PON communication encryption for Tibit OLT.
                        Default is off state";
        } // END of encryption definition.

        leaf key-time  {
            type  uint32 {
                 range "10..3600"  {
                    description "10..3600:Feature : HAVE_TIBIT Supported range 60 - 3600Not Feature :
                            HAVE_TIBIT  Supported range 10 - 3600";
                 }
            }
            units "seconds";
            default "60";
            description "The encryption key exchange time in seconds for the PON communication.
                        Default value is 60 seconds.";
        } // END of key-time definition.

        leaf management-tpid  {
            if-feature feature-list:HAVE_TIBIT;
            type  ipi-pon-types:pon_olt_mgmt_tpid_t;
            description "Either 802.1q TPID 0x8100 or 802.1ad TPID 0x88a8 to be used for OLT
                        management.";
        } // END of management-tpid definition.

    } // END of olt-extent-config definition.
    grouping olt-enable-config {
        description
            "Grouping for OLT administration state and ONU provision mode
                        configuration";
        leaf provisioning-type  {
            type  ipi-pon-types:pon_olt_onu_enabling_t;
            description "This is the ONU provisioning control on the OLT. OLT can configure and
                        enable the discovered ONUs automatically or manually. The type can be
                        manual or automatic";
        } // END of provisioning-type definition.

        leaf administrative-state  {
            type  ipi-pon-types:pon_olt_up_down_t;
            description "The enable or disable control for OLT. The value can either up or down";
        } // END of administrative-state definition.

    } // END of olt-enable-config definition.
    grouping olt-enable-state {
        description
            "Grouping for OLT enabling state";
        leaf operational-status  {
            type  ipi-pon-types:pon_up_down_status_t;
            description "This is to indicate the operational status of the OLT";
        } // END of operational-status definition.

    } // END of olt-enable-state definition.
    grouping olt-mapping-config {
        description
            "Grouping for OLT serial number mapping configuration";
        container mapping {
            if-feature feature-list:HAVE_TIBIT;
            description
                "serial number mapping for the OLT";
            container config {
                description
                    "OLT serial number configuration";
                uses olt-serial-number-value;
            } // END of config-container definition.
            container state {
                config false;
                description
                    "OLT serial number state";
                uses olt-serial-number-value;
            } // END of state-container definition.
        } // END of mapping-container definition.
    } // END of olt-mapping-config definition.
    grouping olt-enable-operation-top {
        description
            "Grouping for OLT enable configuration";
        container enable-operations {
            description
                "The configuration to enable or disable OLT in auto or manual mode";

            list enable-operation {
                key "provisioning-type administrative-state";
                max-elements 1;
                description
                    "The configuration to enable or disable OLT in auto or manual mode";
                leaf provisioning-type  {
                    type  leafref {
                        path  "../config/provisioning-type";
                    }
                    description "This is the ONU provisioning control on the OLT. OLT can configure and
                                enable the discovered ONUs automatically or manually. The type can be
                                manual or automatic";
                } // END of provisioning-type definition.

                leaf administrative-state  {
                    type  leafref {
                        path  "../config/administrative-state";
                    }
                    description "The enable or disable control for OLT. The value can either up or down";
                } // END of administrative-state definition.

                container config {
                    description
                        "Basic OLT operation configuration";
                    uses olt-enable-config;
                } // END of config-container definition.
                container state {
                    config false;
                    description
                        "OLT Basic operation state";
                    uses olt-enable-config;
                    uses olt-enable-state;
                } // END of state-container definition.
            } // End of enable-operation-list
        } // END of enable-operations-container definition.
    } // END of olt-enable-operation-top definition.
    grouping olt-component-chip-info {
        description
            "Grouping for the OLT chip info";
        leaf product-name  {
            type  ipi-pon-types:pon_info_string_t {
                length "1..1965";
            }
            description "Indicate the chip production name for the OLT";
        } // END of product-name definition.

        leaf part-number  {
            type  ipi-pon-types:pon_info_string_t {
                length "1..1965";
            }
            description "Indicate the chip part number for the OLT";
        } // END of part-number definition.

        leaf serial-number  {
            type  ipi-pon-types:pon_info_string_t {
                length "1..1965";
            }
            description "Indicate the chip serial number for the OLT";
        } // END of serial-number definition.

        leaf vendor  {
            type  ipi-pon-types:pon_info_string_t {
                length "1..1965";
            }
            description "Indicate the chip verdor for the OLT";
        } // END of vendor definition.

        leaf firmware-version  {
            type  ipi-pon-types:pon_info_string_t {
                length "1..1965";
            }
            description "Indicate the chip firmware version for the OLT";
        } // END of firmware-version definition.

        leaf revision  {
            type  ipi-pon-types:pon_info_string_t {
                length "1..1965";
            }
            description "Indicate the chip revision for the OLT";
        } // END of revision definition.

        leaf temperature  {
            type  decimal64 {
                 fraction-digits 2;            }
            units "Celsius";
            description "Indicate the chip temperature in Celsius if multiple sensors
                        unavailable";
        } // END of temperature definition.

    } // END of olt-component-chip-info definition.
    grouping olt-component-sensor-info {
        description
            "Grouping for the OLT sensor info";
        leaf name  {
            type  ipi-pon-types:pon_info_string_t {
                length "1..1965";
            }
            description "Indicate the sensor name";
        } // END of name definition.

        leaf temperature  {
            type  decimal64 {
                 fraction-digits 2;            }
            units "Celsius";
            description "Indicate the chip sensor temperature in Celsius";
        } // END of temperature definition.

    } // END of olt-component-sensor-info definition.
    grouping olt-component-firmware-info {
        description
            "Grouping for the OLT firmware info";
        leaf id  {
            type  uint32;
            description "Indicate the firmware memory bank id for the OLT";
        } // END of id definition.

        leaf version  {
            type  ipi-pon-types:pon_info_string_t {
                length "1..1965";
            }
            description "Indicate the firmware version for the OLT";
        } // END of version definition.

        leaf sha  {
            type  ipi-pon-types:pon_info_string_t {
                length "1..1965";
            }
            description "Indicate the firmware SHA signature for the OLT";
        } // END of sha definition.

        leaf date  {
            type  ipi-pon-types:pon_info_string_t {
                length "1..1965";
            }
            description "Indicate the firmware date string";
        } // END of date definition.

        leaf active  {
            type  ipi-pon-types:pon_yes_no_status_t;
            description "Indicate whether the bank is active";
        } // END of active definition.

        leaf next-activated  {
            type  ipi-pon-types:pon_yes_no_status_t;
            description "Indicate whether the bank will be activated for next reboot";
        } // END of next-activated definition.

    } // END of olt-component-firmware-info definition.
    grouping olt-component-detail {
        description
            "Grouping for the OLT component info";
        container component-info {
            if-feature feature-list:HAVE_TIBIT;
            config false;
            description
                "The OLT component info";
            container chip {
                config false;
                description
                    "The OLT chip info";
                container state {
                    config false;
                    description
                        "The chip info";
                    uses olt-component-chip-info;
                } // END of state-container definition.
                container sensor-temperature {
                    config false;
                    description
                        "The OLT chip temperatures when multi-sensors available";

                    list sensor {
                        key "name";
                        config false;
                        description
                            "The chip temperature sensor";
                        leaf name  {
                            type  leafref {
                                path  "../state/name";
                            }
                            description "Indicate the sensor name";
                        } // END of name definition.

                        container state {
                            config false;
                            description
                                "The sensor temperature";
                            uses olt-component-sensor-info;
                        } // END of state-container definition.
                    } // End of sensor-list
                } // END of sensor-temperature-container definition.
            } // END of chip-container definition.
            container firmware {
                config false;
                description
                    "The OLT firmware info";

                list bank {
                    key "id";
                    config false;
                    description
                        "The memory bank list";
                    leaf id  {
                        type  leafref {
                            path  "../state/id";
                        }
                        description "Indicate the firmware memory bank id for the OLT";
                    } // END of id definition.

                    container state {
                        config false;
                        description
                            "The firmware info";
                        uses olt-component-firmware-info;
                    } // END of state-container definition.
                } // End of bank-list
            } // END of firmware-container definition.
        } // END of component-info-container definition.
    } // END of olt-component-detail definition.
    grouping olt-interface-info {
        description
            "Grouping for the OLT interface info";
        leaf name  {
            type  string {
                length "1..1965";
                pattern "[^?' =,>|]+";
            }
            description "Indicate OLT interface name";
        } // END of name definition.

        leaf administrative-state  {
            type  ipi-pon-types:pon_up_down_status_t;
            description "Indicate OLT interface administrative state";
        } // END of administrative-state definition.

        leaf operational-status  {
            type  ipi-pon-types:pon_up_down_status_t;
            description "Indicate OLT interface operational status";
        } // END of operational-status definition.

        leaf operational-down-reason  {
            type  ipi-pon-types:pon_info_string_t {
                length "1..1965";
            }
            description "Indicate OLT interface operational down reason";
        } // END of operational-down-reason definition.

        leaf speed  {
            type  string {
                length "1..1965";
                pattern "[^?' =,>|]+";
            }
            description "Indicate OLT interface speed";
        } // END of speed definition.

    } // END of olt-interface-info definition.
    grouping olt-nni-fec-state {
        description
            "Grouping FEC state for the OLT NNI interface";
        leaf fec  {
            if-feature feature-list:NOT_HAVE_TIBIT;
            type  ipi-pon-types:pon_on_off_auto_status_t;
            description "Indicate FEC status for the OLT NNI interface. Tibit has no such
                        status";
        } // END of fec definition.

    } // END of olt-nni-fec-state definition.
    grouping olt-pon-rogue-detect-info {
        description
            "Grouping ONU rogue detection info for the OLT PON interface";
        leaf rogue-detect  {
            type  ipi-pon-types:pon_on_off_status_t;
            description "Indicate ONU rogue detection status for the OLT PON interface";
        } // END of rogue-detect definition.

    } // END of olt-pon-rogue-detect-info definition.
    grouping olt-pon-bandwidth-info {
        description
            "Grouping for PON bandwith info";
        leaf total  {
            type  uint32;
            units "Kbps";
            description "Indicate total PON bandwidth in Kbps for guaranteed traffic";
        } // END of total definition.

        leaf cbr  {
            type  uint32;
            units "Kbps";
            description "Indicate total PON bandwidth in Kbps available for CBR real-time
                        traffic";
        } // END of cbr definition.

        leaf available  {
            type  uint32;
            units "Kbps";
            description "Indicate total PON bandwidth in Kbps available for guaranteed traffic
                        after new ONU is added";
        } // END of available definition.

    } // END of olt-pon-bandwidth-info definition.
    grouping olt-interface-counters {
        description
            "Grouping for the OLT interface counters";
        leaf rx-packets  {
            type  yang:counter64;
            description "Indicate the interface receive packets";
        } // END of rx-packets definition.

        leaf rx-bytes  {
            type  yang:counter64;
            description "Indicate the interface receive bytes";
        } // END of rx-bytes definition.

        leaf tx-packets  {
            type  yang:counter64;
            description "Indicate the interface transmission packets";
        } // END of tx-packets definition.

        leaf tx-bytes  {
            type  yang:counter64;
            description "Indicate the interface transmission bytes";
        } // END of tx-bytes definition.

        leaf rx-drop-packets  {
            type  yang:counter64;
            description "Indicate the interface ingress dropped packets";
        } // END of rx-drop-packets definition.

        leaf tx-drop-packets  {
            type  yang:counter64;
            description "Indicate the interface egress dropped packets";
        } // END of tx-drop-packets definition.

    } // END of olt-interface-counters definition.
    grouping olt-interfaces-state {
        description
            "Grouping for the state of OLT intefaces";
        container interfaces {
            config false;
            description
                "OLT intefaces state";
            container nni {
                config false;
                description
                    "OLT NNI intefaces state";

                list interface {
                    key "name";
                    config false;
                    description
                        "OLT NNI interface list";
                    leaf name  {
                        type  leafref {
                            path  "../state/name";
                        }
                        description "Indicate OLT NNI interface name";
                    } // END of name definition.

                    container state {
                        config false;
                        description
                            "OLT NNI interface state";
                        container counters {
                            config false;
                            description
                                "OLT NNI interface statistics counters";
                            uses olt-interface-counters;
                        } // END of counters-container definition.
                        uses olt-interface-info;
                        uses olt-nni-fec-state;
                    } // END of state-container definition.
                } // End of interface-list
            } // END of nni-container definition.
            container pon {
                config false;
                description
                    "OLT PON intefaces state";

                list interface {
                    key "name";
                    config false;
                    description
                        "OLT PON interface list";
                    leaf name  {
                        type  leafref {
                            path  "../state/name";
                        }
                        description "Indicate OLT PON interface name";
                    } // END of name definition.

                    container state {
                        config false;
                        description
                            "OLT PON interface state";
                        container counters {
                            config false;
                            description
                                "OLT PON interface statistics counters";
                            uses olt-interface-counters;
                        } // END of counters-container definition.
                        uses olt-interface-info;
                        uses olt-pon-rogue-detect-info;
                    } // END of state-container definition.
                    container bandwidth {
                        if-feature feature-list:NOT_HAVE_TIBIT;
                        config false;
                        description
                            "PON bandwidth";
                        container state {
                            config false;
                            description
                                "state";
                            uses olt-pon-bandwidth-info;
                        } // END of state-container definition.
                    } // END of bandwidth-container definition.
                } // End of interface-list
            } // END of pon-container definition.
        } // END of interfaces-container definition.
    } // END of olt-interfaces-state definition.
    grouping olt-config {
        description
            "Grouping for OLT configuration";

        list olt {
            key "olt-id";
            description
                "OLT list";
            leaf olt-id  {
                type  leafref {
                    path  "../config/olt-id";
                }
                description "This is the logical OLT identity in the system. The OLT identity in
                            Tibit is 0 to 63 while the identity in other systems is from 0 to
                            65535";
            } // END of olt-id definition.

            container config {
                description
                    "Extent configuration data for OLT";
                uses olt-id-config;
                uses olt-extent-config;
            } // END of config-container definition.
            container state {
                config false;
                description
                    "Extent OLT config state";
                uses olt-id-config;
                uses olt-extent-config;
            } // END of state-container definition.
            uses olt-mapping-config;
            uses olt-enable-operation-top;
            uses olt-component-detail;
            uses olt-interfaces-state;
        } // End of olt-list
    } // END of olt-config definition.
    grouping olt-mapped-data {
        description
            "Grouping for OLT mapped data";
        leaf id  {
            type  uint32;
            description "Indicate mapped OLT id";
        } // END of id definition.

        leaf serial-number  {
            type  string {
                length "1..1965";
                pattern "[^?' =,>|]+";
            }
            description "Indicate mapped OLT serial number";
        } // END of serial-number definition.

    } // END of olt-mapped-data definition.
    grouping olt-unmapped-data {
        description
            "Grouping for OLT unmapped data";
        leaf-list serial-number  {
            type  string {
                length "1..1965";
                pattern "[^?' =,>|]+";
            }
            description "Indicate mapped OLT serial number";
        } // END of serial-number definition.

    } // END of olt-unmapped-data definition.
    grouping olts-mapping-state {
        description
            "Grouping for mapping state for OLTs";
        container mapping-info {
            config false;
            description
                "The mapping info for OLTs";
            container mapped {
                config false;
                description
                    "mapped OLTs";

                list olt {
                    key "id serial-number";
                    config false;
                    description
                        "mapped OLT";
                    leaf id  {
                        type  uint32;
                        description "Indicate mapped OLT id";
                    } // END of id definition.

                    leaf serial-number  {
                        type  string {
                            length "1..1965";
                            pattern "[^?' =,>|]+";
                        }
                        description "Indicate mapped OLT serial number";
                    } // END of serial-number definition.

                    container state {
                        config false;
                        description
                            "OLT mapped info";
                        uses olt-mapped-data;
                    } // END of state-container definition.
                } // End of olt-list
            } // END of mapped-container definition.
            container unmapped {
                config false;
                description
                    "unmapped OLTs";
                container state {
                    config false;
                    description
                        "OLT unmapped serial number";
                    uses olt-unmapped-data;
                } // END of state-container definition.
            } // END of unmapped-container definition.
        } // END of mapping-info-container definition.
    } // END of olts-mapping-state definition.

    grouping  olt-management-grouping {
    description
        "OLT management";
    container olt-management {
        if-feature feature-list:HAVE_POND;
        description
            "OLT management";
        container olts {
            description
                "All OLT configuration";
            uses olt-config;
        } // END of olts-container definition.
        uses olts-mapping-state;
    } // END of olt-management-container definition.
    } // END of olt-management-grouping definition.


}
