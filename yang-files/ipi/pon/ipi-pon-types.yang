/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-pon-types.yang
*
*/

module ipi-pon-types {

    yang-version 1.1;

    namespace   "http://www.ipinfusion.com/yang/ocnos/ipi-pon-types";

    prefix "ipi-pon-types";

    organization
        "IP Infusion Inc.";

    contact
        "Address: 3965 Freedom Circle, Suite 200, Santa Clara, CA 95054
         Phone: +1 408-400-1900
         E-mail: support@ipinfusion.com
         Web: http://www.ipinfusion.com/";

    description
        "This module defines all types for PON module and submodules";


    revision "2023-02-06" {
        description "Add new type for OLT serial number";
        reference " 0.9.2.";
    }

    revision "2023-01-13" {
        description "Add new value to upgrade status enum";
        reference " 0.9.1.";
    }

    revision "2022-12-29" {
        description "New datatype added for ONU software upgrade error reason and auto-activate/auto-commit";
        reference " 0.9.0.";
    }

    revision "2022-10-28" {
        description "New datatype added for ONU software upgrade";
        reference " 0.8.0.";
    }

    revision "2022-06-01" {
        description "Updated the yang file with feature";
        reference " 0.7.0.";
    }

    revision "2021-10-17" {
        description "Added management tpid configuration for Tibit";
        reference " 0.6.0.";
    }

    revision "2021-09-03" {
        description "Update descriptions of attribute";
        reference " 0.3.0.";
    }

    revision "2021-02-15" {
        description "Added support for state container corresponding to config containers";
        reference " 0.2.0.";
    }

    revision "2020-11-13" {
        description "Initial Version";
        reference "Initial Version";
    }



    typedef  pon_acl_action_t {
        type enumeration {
            enum allow {
                value 0;
                description "Allow matching traffic";
            }
            enum drop {
                value 1;
                description "Drop matching traffic";
            }
            enum trap-to-cpu {
                value 2;
                description "Trap matching traffic to cpu";
            }
        }
        description "This is the type for the access control list action";
    }

    typedef  pon_lock_unlock_t {
        type enumeration {
            enum unlock {
                value 0;
                description "Unlock";
            }
            enum lock {
                value 1;
                description "Lock";
            }
        }
        description "This is the type for lock state";
    }

    typedef  pon_olt_onu_enabling_t {
        type enumeration {
            enum manual {
                value 1;
                description "Manual ONU configuration";
            }
            enum automatic {
                value 2;
                description "Automatic ONU configuration";
            }
        }
        description "This is the ONU working mode type for OLT";
    }

    typedef  pon_input_vlan_untagged_t {
        type enumeration {
            enum untagged {
                value 0;
                description "untagged VLAN";
            }
        }
        description "This is the untagged input VLAN type";
    }

    typedef  pon_input_vlan_tagged_t {
        type enumeration {
            enum tagged {
                value 1;
                description "Tagged VLAN";
            }
        }
        description "This is the tagged input VLAN type";
    }

    typedef  pon_input_vlan_ptagged_t {
        type enumeration {
            enum prioritytagged {
                value 2;
                description "Priority Tagged VLAN";
            }
        }
        description "This is the priority tagged input VLAN type";
    }

    typedef  pon_service_operation_t {
        type enumeration {
            enum none {
                value 0;
                description "none";
            }
            enum remove-vlan {
                value 1;
                description "Remove VLAN";
            }
        }
        description "This is the VLAN operation type for translation";
    }

    typedef  pon_instance_t {
        type enumeration {
            enum pon-configuration {
                value 1;
                description "Configure PON parameters";
            }
        }
        description "This is the terminal PON configuration command mode type";
    }

    typedef  pon_tp_input_instance_t {
        type enumeration {
            enum classification {
                value 1;
                description "input match rule";
            }
        }
        description "This is the terminal classification command mode type for translation
                    profile";
    }

    typedef  pon_tp_output_instance_t {
        type enumeration {
            enum treatment {
                value 1;
                description "action to apply";
            }
        }
        description "This is the terminal treatment command mode type for translation
                    profile";
    }

    typedef  pon_downstream_instance_t {
        type enumeration {
            enum downstream {
                value 1;
                description "Enter QOS downstream config mode";
            }
        }
        description "This is the terminal downstream QOS command mode type for QOS profile";
    }

    typedef  pon_upstream_instance_t {
        type enumeration {
            enum upstream {
                value 1;
                description "Enter QOS upstream config mode";
            }
        }
        description "This is the terminal upstream QOS command mode type for QOS profile";
    }

    typedef  pon_flow_uni_instance_t {
        type enumeration {
            enum uni {
                value 1;
                description "Enter UNI config for flow mode";
            }
        }
        description "This is the terminal UNI command mode type for flow configuration";
    }

    typedef  pon_flow_nni_instance_t {
        type enumeration {
            enum nni {
                value 1;
                description "Enter NNI config for flow mode";
            }
        }
        description "This is the terminal NNI command mode type for flow configuration";
    }

    typedef  pon_flow_qos_instance_t {
        type enumeration {
            enum qos {
                value 1;
                description "Enter QOS config for flow mode";
            }
        }
        description "This is the terminal QOS command mode type for flow configuration";
    }

    typedef  pon_flow_stats_instance_t {
        type enumeration {
            enum statistics {
                value 1;
                description "Enter FLOW statistics config for flow mode";
            }
        }
        description "This is the terminal statistics command mode type for flow
                    configuration";
    }

    typedef  pon_acl_instance_t {
        type enumeration {
            enum acl {
                value 1;
                description "Enter Acl config for flow mode";
            }
        }
        description "This is the terminal ACL command mode type for flow configuration";
    }

    typedef  pon_gem_encryption_t {
        type enumeration {
            enum off {
                value 0;
                description "GEM encryption OFF";
            }
            enum on {
                value 1;
                description "GEM encryption ON";
            }
        }
        description "This is the GEM encryption enabling type";
    }

    typedef  pon_flow_stats_t {
        type enumeration {
            enum off {
                value 0;
                description "Flow statistics OFF";
            }
            enum on {
                value 1;
                description "Flow statistics ON";
            }
        }
        description "This is the flow statistics enabling type";
    }

    typedef  pon_qos_rate_t {
        type enumeration {
            enum kbps {
                value 1;
                description "Specifies the units of kilobits per second";
            }
            enum mbps {
                value 2;
                description "Specifies the units of megabits per second";
            }
            enum gbps {
                value 3;
                description "Specifies the units of gigabits per second";
            }
        }
        description "This is the QOS data rate unit type";
    }

    typedef  pon_qos_burst_t {
        type enumeration {
            enum kbytes {
                value 1;
                description "Specifies the units of kilobytes per second";
            }
            enum mbytes {
                value 2;
                description "Specifies the units of megabytes per second";
            }
            enum gbytes {
                value 3;
                description "Specifies the units of gigabytes per second";
            }
        }
        description "This is the QOS data burst unit type";
    }

    typedef  pon_ip_protocol_t {
        type enumeration {
            enum any {
                value 0;
                description "Specify ANY protocol for IP";
            }
            enum tcp {
                value 1;
                description "Specify TCP protocol for IP";
            }
            enum udp {
                value 2;
                description "Specify UDP protocol for IP";
            }
        }
        description "This is the IP protocol type";
    }

    typedef  pon_acl_direction_t {
        type enumeration {
            enum upstream {
                value 0;
                description "upstream";
            }
            enum downstream {
                value 1;
                description "downstream";
            }
        }
        description "This is the ACL direction type";
    }

    typedef  pon_acl_port_any_t {
        type enumeration {
            enum any {
                value 0;
                description "any port";
            }
        }
        description "This is the ACL any port type";
    }

    typedef  pon_acl_addr_w_any_t {
        type string {
            length 0..15;
            pattern "(any)|(([0-9]|[1-9][0-9]|1[0-9][0-9]|2[0-4][0-9]|25[0-5])\\.([0-9]|[1-9][0-9]|1[0-9][0-9]|2[0-4][0-9]|25[0-5])\\.([0-9]|[1-9][0-9]|1[0-9][0-9]|2[0-4][0-9]|25[0-5])\\.([0-9]|[1-9][0-9]|1[0-9][0-9]|2[0-4][0-9]|25[0-5]))";
        }
        description "This is the ACL IP address type";
    }

    typedef  pon_acl_port_t {
        type union {
            type pon_acl_port_any_t {

            }
            type uint16 {
                range "1..65535";

            }
        }
        description "This is the ACL port any and range type";
    }

    typedef  pon_olt_up_down_t {
        type enumeration {
            enum down {
                value 0;
                description "Disable OLT";
            }
            enum up {
                value 1;
                description "Enable OLT";
            }
        }
        description "This is the OLT enabling type";
    }

    typedef  pon_dhcp_on_off_t {
        type enumeration {
            enum off {
                value 0;
                description "DHCP processing OFF";
            }
            enum on {
                value 1;
                description "DHCP processing ON";
            }
        }
        description "This is the DHCP enabling type";
    }

    typedef  pon_pppoe_on_off_t {
        type enumeration {
            enum off {
                value 0;
                description "PPPoE processing OFF";
            }
            enum on {
                value 1;
                description "PPPoE processing ON";
            }
        }
        description "This is the PPPoE enabling type";
    }

    typedef  pon_fec_t {
        type enumeration {
            enum off {
                value 0;
                description "FEC processing OFF";
            }
            enum on {
                value 1;
                description "FEC processing ON";
            }
        }
        description "This is the FEC enabling type";
    }

    typedef  pon_acl_trap_dump_enable_t {
        type enumeration {
            enum enable {
                value 1;
                description "Enable ACL trap dump globally";
            }
        }
        description "This is the ACL dump enabling type";
    }

    typedef  pon_flow_mode_t {
        type enumeration {
            enum one2one {
                value 0;
                description "one2one Flow mode";
            }
            enum n2one {
                value 1;
                description "n2one Flow mode";
            }
        }
        description "This is the flow-type definition";
    }

    typedef  pon_uni_flow_ethertype_t {
        type enumeration {
            enum 0x8100 {
                value 0;
                description "Default 802.1Q VLAN TPID for flow";
            }
            enum 0x88a8 {
                value 1;
                description "Replace ETHERTYPE to 0x88a8 for flow";
            }
        }
        description "This is the UNI ether-type for flow";
    }

    typedef  pon_olt_ports_type_t {
        type enumeration {
            enum nni {
                value 0;
                description "nni ports";
            }
            enum pon {
                value 1;
                description "pon ports";
            }
            enum nni-pon-ports {
                value 2;
                description "both nni and pon ports";
            }
        }
        description "This is the OLT ports type";
    }

    typedef  pon_flow_cleared_target_type_t {
        type enumeration {
            enum nni-port {
                value 0;
                description "nni port associated with the flow";
            }
            enum uni-port {
                value 1;
                description "uni port associated with the flow";
            }
            enum flow {
                value 2;
                description "flow";
            }
        }
        description "This is the flow ports type";
    }

    typedef  pon_acl_trap_dump_any_t {
        type enumeration {
            enum any {
                value 65536;
                description "any dump";
            }
        }
        description "This is the ACL trap any dump type";
    }

    typedef  pon_acl_trap_dump_flow_id_t {
        type union {
            type uint32 {
                range "0..65535";

            }
            type pon_acl_trap_dump_any_t {

            }
        }
        description "This is the dump ACL trap flow ID any and range type";
    }

    typedef  pon_acl_trap_dump_acl_id_t {
        type union {
            type uint32 {
                range "0..65535";

            }
            type pon_acl_trap_dump_any_t {

            }
        }
        description "This is the dump trap ACL ID any and range type";
    }

    typedef  pon_acl_trap_dump_direction_t {
        type enumeration {
            enum both {
                value 0;
                description "both upstream and downstream";
            }
            enum upstream {
                value 1;
                description "upstream";
            }
            enum downstream {
                value 2;
                description "downstream";
            }
        }
        description "This is the ACL direction type";
    }

    typedef  pon_vlan_tag_value_t {
        type string {
            length 1..4;
            pattern "([2-9])|([1-9][0-9])|([1-9][0-9][0-9])|([1-3][0-9][0-9][0-9])|(40[0-9][0-4])";
        }
        description "This is the VLAN tag value string type";
    }

    typedef  pon_vlan_tag_format_t {
        type string {
            length 4..6;
            pattern "(0x8100)|(0x88a8)";
        }
        description "This is the VLAN TPID string type";
    }

    typedef  pon_debug_type_t {
        type bits {
            bit pond {
                position 0;
                description "pond general debug";
            }
            bit state-machine {
                position 1;
                description "pond state machine debug";
            }
            bit nsm {
                position 2;
                description "pond nsm debug";
            }
            bit omci-flow {
                position 3;
                description "pond omci flow debug";
            }
            bit omci-onu {
                position 4;
                description "pond omci onu debug";
            }
            bit omci-packet {
                position 5;
                description "pond omci packet debug";
            }
            bit omci-packet-detail {
                position 6;
                description "pond omci details debug";
            }
        }
        description "This is the PON DEBUG type";
    }

    typedef  pon_ready_status_t {
        type enumeration {
            enum not-ready {
                value 0;
                description "the setting is not ready";
            }
            enum ready {
                value 1;
                description "the setting is ready";
            }
        }
        description "This is the setting ready status type";
    }

    typedef  pon_up_down_status_t {
        type enumeration {
            enum down {
                value 0;
                description "the down status";
            }
            enum down-rebooting {
                value 2;
                description "the rebooting down status";
            }
            enum up {
                value 100;
                description "the up status";
            }
        }
        description "This is the operational up-down type";
    }

    typedef  pon_info_string_t {
        type string;
        description "type definition for PON_INFO_STRING_T";
    }

    typedef  pon_byte_size_base_2_unit_t {
        type enumeration {
            enum B {
                value 0;
                description "the byte unit";
            }
            enum KB {
                value 1;
                description "the base 2 kilobyte unit or 1024 bytes per unit";
            }
            enum MB {
                value 2;
                description "the base 2 megabyte unit or 1024 KB per unit";
            }
            enum GB {
                value 3;
                description "the base 2 gigabyte unit or 1024 MB per unit";
            }
        }
        description "This is the byte unit type";
    }

    typedef  pon_on_off_status_t {
        type enumeration {
            enum off {
                value 0;
                description "the off status";
            }
            enum on {
                value 1;
                description "the on status";
            }
        }
        description "This is the operational on/off type";
    }

    typedef  pon_on_off_auto_status_t {
        type enumeration {
            enum off {
                value 0;
                description "the off status";
            }
            enum on {
                value 1;
                description "the on status";
            }
            enum auto {
                value 2;
                description "the auto status";
            }
        }
        description "This is the operational auto/on/off type";
    }

    typedef  pon_yes_no_status_t {
        type enumeration {
            enum no {
                value 0;
                description "the no status";
            }
            enum yes {
                value 1;
                description "the yes status";
            }
        }
        description "This is the operational yes/no type";
    }

    typedef  pon_dhcpr_custom_format_t {
        type string {
            length 1..255;
            pattern "[^?'=,>|]*";
        }
        description "This is DHCP Relay Option 82 custom string format type";
    }

    typedef  pon_trust_on_off_t {
        type enumeration {
            enum off {
                value 0;
                description "UNI port trust OFF";
            }
            enum on {
                value 1;
                description "UNI port trust ON";
            }
        }
        description "This is uni port trust type";
    }

    typedef  pon_onu_mib_audit_on_off_t {
        type enumeration {
            enum off {
                value 0;
                description "Disable ONU MIB Audit mechanism";
            }
            enum on {
                value 1;
                description "Enable ONU MIB Audit mechanism";
            }
        }
        description "This is ONU MIB audit type";
    }

    typedef  pon_olt_pon_type_t {
        type enumeration {
            enum combo-xgspon {
                value 0;
                description "Combo XGS/G-PON or XGS-PON ports";
            }
            enum single-gpon {
                value 1;
                description "Only GPON ports";
            }
        }
        description "This is the type of OLT PON type";
    }

    typedef  pon_olt_mgmt_tpid_t {
        type enumeration {
            enum 0x8100 {
                value 33024;
                description "Replace 802.1Q VLAN TPID";
            }
            enum 0x88a8 {
                value 34984;
                description "Default TPID to 0x88a8";
            }
        }
        description "This is the tpid for OLTs' management channel";
    }

    typedef  pon_onu_software_upgrade_status_t {
        type enumeration {
            enum none {
                value 0;
                description "Default upgrade state";
            }
            enum upgrading {
                value 1;
                description "Upgrading state";
            }
            enum upgraded {
                value 2;
                description "Upgraded state";
            }
            enum upgrade-failed {
                value 3;
                description "Upgrade failed state";
            }
            enum waiting-upgrade {
                value 4;
                description "Waiting upgrade state";
            }
            enum committing {
                value 5;
                description "Committing state";
            }
            enum committed {
                value 6;
                description "Committed state";
            }
            enum commit-failed {
                value 7;
                description "Commit failed state";
            }
            enum activating {
                value 8;
                description "Activating state";
            }
            enum activated {
                value 9;
                description "Activated state";
            }
            enum activate-failed {
                value 10;
                description "Activate failed state";
            }
        }
        description "This is ONU software upgrade status";
    }

    typedef  pon_onu_software_upgrade_error_reason_t {
        type enumeration {
            enum NA {
                value 0;
                description "Default error reason";
            }
            enum START-UPGRADE-FAILED {
                value 1;
                description "The start of ONU upgrade failed";
            }
            enum ONU-IMAGE-TRANSFER-FAILED {
                value 2;
                description "The image transfer to ONU failed";
            }
            enum WINDOW-ACK-TIMEOUT {
                value 3;
                description "OLT did not receive ACK from ONU after send a complete window";
            }
            enum END-SW-UPGRADE-FAILED {
                value 4;
                description "The last phase of upgrade (End Sw Dl) after send the whole image to ONU failed";
            }
            enum END-SW-UPGRADE-ACK-TIMEOUT {
                value 5;
                description "The End Sw dl did not receive the ACK from ONU that determines that upgrade completed.";
            }
            enum SW-ACTIVATION-ABORTED {
                value 6;
                description "The ONU image activation aborted during the process";
            }
            enum SW-ACTIVATION-ACK-TIMEOUT {
                value 7;
                description "The ONU image activation did not received ACK from ONU that determined the activation was received";
            }
            enum SW-COMMIT-ABORTED {
                value 8;
                description "The ONU image commit aborted during the process";
            }
            enum SW-COMMIT-ACK-TIMEOUT {
                value 9;
                description "The ONU image activation did not received ACK from ONU that determined the commit was received";
            }
            enum UNKNOWN {
                value 10;
                description "Unknown error";
            }
        }
        description "This is ONU software upgrade error reason";
    }

    typedef  pon_onu_software_upgrade_auto_t {
        type enumeration {
            enum OFF {
                value 0;
                description "Auto-commit/Auto-Activate is OFF";
            }
            enum ON {
                value 1;
                description "Auto-commit/Auto-Activate is ON";
            }
        }
        description "This is ONU software upgrade status for automatic commit and automatic
                    activate features";
    }

    typedef  pon_olt_serial_t {
        type string {
            length 0..18;
            pattern "([0-9a-f]{2}[:]){5}[0-9a-f]{2}";
        }
        description "This is the OLT serial number type";
    }

}
