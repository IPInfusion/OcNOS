/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-pon.yang
*
*/

module ipi-pon {

    yang-version 1.1;

    namespace   "http://www.ipinfusion.com/yang/ocnos/ipi-pon";

    prefix "ipi-pon";

    import cml-data-types {
        prefix cml-data-types;
        revision-date 2026-05-15;
    }

    import ipi-pon-types {
        prefix ipi-pon-types;
        revision-date 2023-02-06;
    }

    import ietf-yang-types {
        prefix yang;
        revision-date 2013-07-15;
    }

    import ipi-interface {
        prefix ipi-interface;
        revision-date 2026-03-10;
    }

    import feature-list {
        prefix feature-list;
        revision-date 2026-09-15;
    }

    include ipi-pon-profile { revision-date 2023-02-07;}
    include ipi-pon-olt { revision-date 2023-07-07;}
    include ipi-pon-onu { revision-date 2023-07-07;}
    include ipi-pon-flow { revision-date 2023-07-31;}
    include ipi-pon-onu-software-upgrade { revision-date 2022-12-29;}
    include ipi-pon-profile-translation { revision-date 2023-02-07;}
    include ipi-pon-profile-onu { revision-date 2022-06-01;}
    organization
        "IP Infusion Inc.";

    contact
        "Address: 3965 Freedom Circle, Suite 200, Santa Clara, CA 95054
         Phone: +1 408-400-1900
         E-mail: support@ipinfusion.com
         Web: http://www.ipinfusion.com/";

    description
        "This module defines a data model for passive optical network(PON)
                configuration which can include profiles, optical line terminal(OLT),
                optical network unit(ONU) and flow";


    revision "2023-07-31" {
        description "Removing the misplaced initialized or added presence container";
        reference " 0.2.0.";
    }

    revision "2023-07-07" {
        description "Removing the misplaced initialized or added presence container";
        reference " 0.1.0.";
    }

    revision "2023-02-07" {
        description "Updated some list structures by adding a container above for this module and submodules.";
        reference " 0.11.10.";
    }

    revision "2023-02-06" {
        description "Add new function for debug in exec mode and change type for OLT serial number";
        reference " 0.11.9.";
    }

    revision "2023-01-31" {
        description "Fixed the pon initial attributes at startup";
        reference " 0.11.8.";
    }

    revision "2023-01-30" {
        description "Fix flow nni string length";
        reference " 0.11.7.";
    }

    revision "2023-01-23" {
        description "Removed unwanted implicit delete tag for interfaces";
        reference " 0.11.6.";
    }

    revision "2023-01-16" {
        description "Leafref correction for config container";
        reference " 0.11.5.";
    }

    revision "2022-12-29" {
        description "Added support to software-upgrade error reason and new runtime attributes for upgrade process general-info";
        reference " 0.11.4.";
    }

    revision "2022-12-20" {
        description "Added support to software-upgrade group auto activate and commit";
        reference " 0.11.3.";
    }

    revision "2022-12-12" {
        description "Added support to software-upgrade group activate and commit command";
        reference " 0.11.2.";
    }

    revision "2022-12-07" {
        description "Added support to software-upgrade group configuration and command";
        reference " 0.11.1.";
    }

    revision "2022-11-16" {
        description "Added support to software-image-activate command";
        reference " 0.11.0.";
    }

    revision "2022-10-28" {
        description "Added support to software upgrade progress statistics and to ONU software-images runtime info";
        reference " 0.10.3.";
    }

    revision "2022-10-18" {
        description "Added support to software-image-commit command in ipi-pon-onu-software";
        reference " 0.10.2.";
    }

    revision "2022-09-30" {
        description "Import cml-data-types used by notifications";
        reference " 0.10.1.";
    }

    revision "2022-08-09" {
        description "Initial Version of submodule ipi-pon-onu-software upgrade";
        reference " 0.10.0.";
    }

    revision "2022-06-01" {
        description "Updated the yang file with feature";
        reference " 0.9.0.";
    }

    revision "2022-03-08" {
        description "Disable PPPoE in Tibit";
        reference " 0.8.0.";
    }

    revision "2021-11-18" {
        description "Update pon-type description for Alpha Networks SPX70D0-168F OLT";
        reference " 0.7.0.";
    }

    revision "2021-10-17" {
        description "Added management tpid configuration for Tibit";
        reference " 0.6.0.";
    }

    revision "2021-10-14" {
        description "Update isolate ONU port description";
        reference " 0.5.0.";
    }

    revision "2021-09-03" {
        description "Update descriptions of attribute";
        reference " 0.4.0.";
    }

    revision "2021-08-13" {
        description "Added support for inband management container";
        reference " 0.3.0.";
    }

    revision "2021-02-15" {
        description "Added support for state container corresponding to config containers";
        reference " 0.2.0.";
    }

    revision "2020-11-13" {
        description "Initial Version";
        reference "Initial Version";
    }

    grouping pon-debug-config {
        description
            "Grouping for PON debugging configuration";
        leaf debug-options  {
            type  ipi-pon-types:pon_debug_type_t;
            description "Debugging enable configuration for PON functionalities";
        } // END of debug-options definition.

    } // END of pon-debug-config definition.
    grouping pon-terminal-debug {
        description
            "Grouping for PON terminal debug info";
        leaf terminal-debug-options  {
            type  ipi-pon-types:pon_debug_type_t;
            description "Indicate current terminal debugging state for the PON module";
        } // END of terminal-debug-options definition.

    } // END of pon-terminal-debug definition.
    grouping pon-license-info {
        description
            "Grouping for PON license info";
        leaf maximum-licenses  {
            type  int32;
            description "This is to show maximum license number";
        } // END of maximum-licenses definition.

        leaf used-licenses  {
            type  int32;
            description "This is to show used license number";
        } // END of used-licenses definition.

        leaf available-licenses  {
            type  int32;
            description "This is to show available license number";
        } // END of available-licenses definition.

    } // END of pon-license-info definition.
    grouping pon-debug {
        description
            "The global PON debug configuration group";
        container debug {
            description
                "The debug configuration data";
            container config {
                description
                    "configuration data for PON debug configuration";
                uses pon-debug-config;
            } // END of config-container definition.
            container state {
                config false;
                description
                    "PON debug states";
                uses pon-debug-config;
                uses pon-terminal-debug;
            } // END of state-container definition.
        } // END of debug-container definition.
    } // END of pon-debug definition.
    grouping pon-license-state {
        description
            "The PON license state group";
        container license {
            config false;
            description
                "The license state";
            container pon-license {
                if-feature feature-list:HAVE_FLEXLM;
                if-feature feature-list:HAVE_TIBIT;
                config false;
                description
                    "The PON license state";
                container state {
                    config false;
                    description
                        "License states";
                    uses pon-license-info;
                } // END of state-container definition.
            } // END of pon-license-container definition.
            container onu-license {
                config false;
                description
                    "The ONU license state";
                container state {
                    config false;
                    description
                        "License states";
                    uses pon-license-info;
                } // END of state-container definition.
            } // END of onu-license-container definition.
        } // END of license-container definition.
    } // END of pon-license-state definition.
    grouping pon-mode-config {
        description
            "Grouping for PON mode configuration";
        leaf instance-id  {
            type  ipi-pon-types:pon_instance_t;
            mandatory true;
            description "Start to configure PON related parameters. PON configuration mode will
                        be switched for command terminal. Netconf should set the value as
                        pon-configuration before doing any PON related configuration";
        } // END of instance-id definition.

    } // END of pon-mode-config definition.
    grouping pon-relay-counter {
        description
            "Grouping for relay counter";
        leaf name  {
            type  ipi-pon-types:pon_info_string_t {
                length "1..1965";
            }
            description "Indicate the relay counter name";
        } // END of name definition.

        leaf value  {
            type  yang:counter64;
            description "Indicate the relay counter value";
        } // END of value definition.

    } // END of pon-relay-counter definition.
    grouping pon-dhcpr-stats {
        description
            "Grouping for DHCP relay statistics";
        container counters {
            config false;
            description
                "DHCP relay statistics";

            list counter {
                key "name";
                config false;
                description
                    "DHCP relay statistics counter";
                leaf name  {
                    type  leafref {
                        path  "../state/name";
                    }
                    description "Indicate the DHCP relay counter name";
                } // END of name definition.

                container state {
                    config false;
                    description
                        "DHCP relay counter state";
                    uses pon-relay-counter;
                } // END of state-container definition.
            } // End of counter-list
        } // END of counters-container definition.
    } // END of pon-dhcpr-stats definition.
    grouping dhcpr-option82-config {
        description
            "Grouping for dhcp relay option82 configuration";
        leaf circuit-id  {
            type  ipi-pon-types:pon_dhcpr_custom_format_t;
            default "none";
            description "This is the custom circuit-id format for dhcp relay option82";
        } // END of circuit-id definition.

        leaf remote-id  {
            type  ipi-pon-types:pon_dhcpr_custom_format_t;
            default "none";
            description "This is the custom remote-id format for dhcp relay option82";
        } // END of remote-id definition.

    } // END of dhcpr-option82-config definition.
    grouping pon-dhcpr-config {
        description
            "Grouping for DHCP relay configuration";
        container dhcp-relay-agent {
            description
                "DHCP relay agent";
            container config {
                description
                    "DHCP relay agent configuration";
                uses dhcpr-option82-config;
            } // END of config-container definition.
            container state {
                config false;
                description
                    "DHCP relay agent state";
                uses dhcpr-option82-config;
            } // END of state-container definition.
            uses pon-dhcpr-stats;
        } // END of dhcp-relay-agent-container definition.
    } // END of pon-dhcpr-config definition.
    grouping pon-pppoe-stats {
        description
            "Grouping for PPPoE relay statistics";
        container counters {
            config false;
            description
                "PPPoE relay statistics";

            list counter {
                key "name";
                config false;
                description
                    "PPPoE relay statistics counter";
                leaf name  {
                    type  leafref {
                        path  "../state/name";
                    }
                    description "Indicate the PPPoE relay counter name";
                } // END of name definition.

                container state {
                    config false;
                    description
                        "PPPoE relay counter state";
                    uses pon-relay-counter;
                } // END of state-container definition.
            } // End of counter-list
        } // END of counters-container definition.
    } // END of pon-pppoe-stats definition.
    grouping pon-pppoe-config {
        description
            "Grouping for PPPoE relay configuration";
        container pppoe-relay-agent {
            if-feature feature-list:NOT_HAVE_TIBIT;
            description
                "PPPoE relay agent";
            uses pon-pppoe-stats;
        } // END of pppoe-relay-agent-container definition.
    } // END of pon-pppoe-config definition.
    grouping pon-interface-config {
        description
            "Pon interface Grouping";
        leaf interface-name  {
            if-feature feature-list:NOT_HAVE_TIBIT;
            type  leafref {
                path  "/ipi-interface:interfaces/ipi-interface:interface/ipi-interface:name";
            }
            description "PON inband management interface name";
        } // END of interface-name definition.

    } // END of pon-interface-config definition.
    grouping pon-inband-mgmt-config {
        description
            "Grouping for inband management configuration data";
        leaf vlan-id  {
            type  uint32 {
                 range "2..4094"  {
                    description "2..4094: Supported range 2 - 4094";
                 }
            }
            description "This is the inband management VLAN ID. Inband management will use this
                        VLAN ID on NNI side";
        } // END of vlan-id definition.

        leaf nni-port-name  {
            type  string {
                length "3..64";
                pattern "[^?' =,>|]+";
            }
            description "The NNI port name for the inband management";
        } // END of nni-port-name definition.

    } // END of pon-inband-mgmt-config definition.
    grouping pon-inband-mgmt {
        description
            "Global PON inband management group";
        container inband-management {
            if-feature feature-list:NOT_HAVE_TIBIT;
            description
                "inband management properties";
            container interfaces {
                description
                    "inband management interface";

                list interface {
                    key "interface-name";
                    max-elements 1;
                    description
                        "inband management interface";
                    leaf interface-name  {
                        type  leafref {
                            path  "../config/interface-name";
                        }
                        description "PON inband management interface name";
                    } // END of interface-name definition.

                    container config {
                        description
                            "PON interface related configurations";
                        uses pon-interface-config;
                    } // END of config-container definition.
                    container state {
                        config false;
                        description
                            "Operational data for PON interface";
                        uses pon-interface-config;
                    } // END of state-container definition.
                    container vlan-nnis {
                        description
                            "VLAN and NNI properties for inband management";

                        list vlan-nni {
                            key "vlan-id nni-port-name";
                            max-elements 1;
                            description
                                "VLAN and NNI for inband management";
                            leaf vlan-id  {
                                type  leafref {
                                    path  "../config/vlan-id";
                                }
                                description "This is the inband management VLAN ID. Inband management will use this
                                            VLAN ID on NNI side";
                            } // END of vlan-id definition.

                            leaf nni-port-name  {
                                type  leafref {
                                    path  "../config/nni-port-name";
                                }
                                description "The NNI port name for the inband management";
                            } // END of nni-port-name definition.

                            container config {
                                description
                                    "PON inband management interface related configurations";
                                uses pon-inband-mgmt-config;
                            } // END of config-container definition.
                            container state {
                                config false;
                                description
                                    "Operational data for PON inband management interface";
                                uses pon-inband-mgmt-config;
                            } // END of state-container definition.
                        } // End of vlan-nni-list
                    } // END of vlan-nnis-container definition.
                } // End of interface-list
            } // END of interfaces-container definition.
        } // END of inband-management-container definition.
    } // END of pon-inband-mgmt definition.
    grouping pon-global {
        description
            "Grouping for PON configuration and state";
        container pon-instance {
            description
                "PON related configurations and states";
            container config {
                presence "PON mode config";
                description
                    "PON related configurations";
                uses pon-mode-config;
            } // END of config-container definition.
            container state {
                config false;
                description
                    "PON mode state";
                uses pon-mode-config;
            } // END of state-container definition.
            uses pon-dhcpr-config;
            uses pon-pppoe-config;
            uses profiles-grouping;
            uses olt-management-grouping;
            uses onu-management-grouping;
            uses flow-management-grouping;
            uses onu-software-upgrade-grouping;
        } // END of pon-instance-container definition.
    } // END of pon-global definition.

    grouping  pon-grouping {
    description
        "Top PON container for all PON controls and states.";
    container pon {
        if-feature feature-list:HAVE_POND;
        description
            "Top PON container for all PON controls and states.";
        uses pon-debug;
        uses pon-license-state;
        uses pon-inband-mgmt;
        uses pon-global;
    } // END of pon-container definition.
    } // END of pon-grouping definition.

    uses pon-grouping;

    rpc pon-clear-olt-ports-statistics {
        if-feature feature-list:HAVE_POND;
        description "clear the ports statistics of NNI or PON or all-NNI-PON ports on an
                    OLT";
        input  {
            leaf olt-id  {
                type uint32 {
                    range "0..65535";
                }
                mandatory true;
                description "This is the logical OLT identity in the system. The OLT identity in
                            Tibit is 0 to 63 while the identity in other system is from 0 to 65535";
            }
            leaf olt-ports-type  {
                type ipi-pon-types:pon_olt_ports_type_t;
                mandatory true;
                description "The port-type of nni or pon as parameter to clear OLT port statistics.
                            By default the statistics of both NNI and PON ports will be clear";
            }
        }
    }

    rpc pon-clear-nni-port-statistics {
        if-feature feature-list:HAVE_POND;
        description "Clear one or all OLT NNI port statistics";
        input  {
            leaf port-name  {
                type string {
                    length "3..64";
                }
                mandatory true;
                description "The NNI port name starting with 'nni' for the specific port or 'all'
                            for all NNI ports to have statistics cleared";
            }
        }
    }

    rpc pon-clear-sa-port-statistics {
        if-feature feature-list:HAVE_POND;
        description "Clear one or all OLT static aggregator port statistics";
        input  {
            leaf port-name  {
                type string {
                    length "3..64";
                }
                mandatory true;
                description "The SA port name starting with 'sa' for the specific port or 'all' for
                            all SA ports to have statistics cleared";
            }
        }
    }

    rpc pon-clear-pon-port-statistics {
        if-feature feature-list:HAVE_POND;
        description "Clear one or all OLT PON ports statistics";
        input  {
            leaf port-name  {
                type string {
                    length "3..64";
                }
                mandatory true;
                description "The PON port name starting with 'pon' for the specific port or 'all'
                            for all PON ports to have statistics cleared";
            }
        }
    }

    rpc pon-olt-reboot {
        if-feature feature-list:HAVE_TIBIT;
        if-feature feature-list:HAVE_POND;
        description "Reboot OLT for Tibit system";
        input  {
            leaf olt-id  {
                type uint32 {
                    range "0..63";
                }
                mandatory true;
                description "The OLT identity as parameter to reboot Tibit OLT. The ID range is
                            from 0 to 63";
            }
            leaf next-active-bank  {
                type uint32 {
                    range "0..3";
                }
                mandatory true;
                description "Select the memory bank from which the Tibit OLT firmware will be
                            loaded after Tibit OLT rebooted. The bank is from 0 to 3";
            }
        }
    }

    rpc pon-olt-firmware-install {
        if-feature feature-list:HAVE_TIBIT;
        if-feature feature-list:HAVE_POND;
        description "Upgrade OLT firmware for Tibit system";
        input  {
            leaf olt-id  {
                type uint32 {
                    range "0..63";
                }
                mandatory true;
                description "The OLT identity as parameter to install Tibit OLT firmware. The ID
                            range is from 0 to 63";
            }
            leaf bank  {
                type uint32 {
                    range "0..3";
                }
                mandatory true;
                description "Select the memory bank where the Tibit OLT firmware will be installed.
                            The bank is from 0 to 3";
            }
            leaf url  {
                type string;
                mandatory true;
                description "The URL to Tibit OLT firmware image to be installed. It can be
                            http://your-server-ip/path-to-install-file or
                            ftp://your-server-ip/path-to-install-file or
                            tftp://your-server-ip/path-to-install-file or
                            file:///local-path-to-install-file";
            }
        }
    }

    rpc pon-onu-reboot {
        if-feature feature-list:HAVE_POND;
        description "Reboot the provisioned ONU";
        input  {
            leaf onu-id  {
                type uint16 {
                    range "0..4095";
                }
                mandatory true;
                description "This is the logical ONU identity in the system. The ONU identity is
                            from 0 to 4095";
            }
        }
    }

    rpc pon-onu-mib-reset {
        if-feature feature-list:HAVE_POND;
        description "Reset the MIB of the provisioned ONU to its default";
        input  {
            leaf onu-id  {
                type uint16 {
                    range "0..4095";
                }
                mandatory true;
                description "This is the logical ONU identity in the system. The ONU identity is
                            from 0 to 4095";
            }
        }
    }

    rpc pon-clear-uni-statistics {
        if-feature feature-list:HAVE_POND;
        description "Clear the UNI port statistics in the provisioned ONU";
        input  {
            leaf onu-id  {
                type uint16 {
                    range "0..4095";
                }
                mandatory true;
                description "This is the logical ONU identity in the system. The ONU identity is
                            from 0 to 4095";
            }
            leaf uni-port  {
                type uint16 {
                    range "0..255";
                }
                mandatory true;
                description "This is the UNI port ID in the ONU. The ID can be between 0 and 255
                            depending on the ONU UNI capability";
            }
        }
    }

    rpc pon-clear-onu-rogue-onu-data {
        if-feature feature-list:HAVE_POND;
        description "Clear the rogue ONU data by the ONU serial number";
        input  {
            leaf serial-number  {
                type string {
                    length "1..64";
                }
                mandatory true;
                description "ONU serial number which can be full hexadecimal string or staring with
                            manufacturer alphabet ID";
            }
        }
    }

    rpc pon-clear-onu-rogue-port-data {
        if-feature feature-list:HAVE_POND;
        description "Clear all rogue ONU data for the PON port";
        input  {
            leaf pon-port-name  {
                type string {
                    length "4..64";
                }
                mandatory true;
                description "PON port name starting with 'pon'";
            }
        }
    }

    rpc pon-onu-isolate {
        if-feature feature-list:HAVE_POND;
        description "Isolate the ONU by using ONU serial number";
        input  {
            leaf serial-number  {
                type string {
                    length "1..64";
                }
                mandatory true;
                description "ONU serial number which can be full hexadecimal string or staring with
                            manufacturer alphabet ID";
            }
            leaf pon-port-name  {
                type string {
                    length "4..64";
                }
                description "The pon port name is not use anymore. This is for backward command
                            compatibility";
            }
        }
    }

    rpc pon-onu-deisolate {
        if-feature feature-list:HAVE_POND;
        description "Discharge the isolated the ONU by using ONU serial number";
        input  {
            leaf serial-number  {
                type string {
                    length "1..64";
                }
                mandatory true;
                description "ONU serial number which can be full hexadecimal string or staring with
                            manufacturer alphabet ID";
            }
            leaf pon-port-name  {
                type string {
                    length "4..64";
                }
                description "The pon port name is not use anymore. This is for backward command
                            compatibility";
            }
        }
    }

    rpc pon-clear-flow-statistics {
        if-feature feature-list:HAVE_POND;
        description "clear flow-aggregate port statistics for a flow";
        input  {
            leaf flow-id  {
                type uint16 {
                    range "0..65535";
                }
                mandatory true;
                description "The subscriber flow identity in the system. The ID range is between 0
                            and 65535";
            }
            leaf cleared-target  {
                type ipi-pon-types:pon_flow_cleared_target_type_t;
                mandatory true;
                description "The statistics cleared target can be nni-port, uni-port or flow. The
                            statistics of NNI or UNI port associated with the flow will be cleared
                            if target is nni-port or uni-port, although the port may accommodate
                            different flows. The statistics of the flow will be cleared if target
                            is flow";
            }
        }
    }

    rpc pon-onu-software-upgrade {
        if-feature feature-list:HAVE_POND;
        description "Upgrade a single ONU";
        input  {
            leaf onu-id  {
                type uint32 {
                    range "0..4095";
                }
                mandatory true;
                description "This is the logical ONU identity in the system. The ONU identity is
                            from 0 to 4095";
            }
            leaf url  {
                type string;
                mandatory true;
                description "The URL to ONU image to be installed on ONUs. It can be
                            http://your-server-ip/path-to-install-file or
                            ftp://your-server-ip/path-to-install-file or
                            tftp://your-server-ip/path-to-install-file or
                            file://path-to-install-file";
            }
            leaf auto-activate  {
                type boolean;
                default false;
                description "Use this to auto-activate the new ONU image after the upgrade process
                            on ONU";
            }
            leaf auto-commit  {
                type boolean;
                default false;
                description "Use this to auto-commit the new ONU image after the upgrade process on
                            ONU";
            }
        }
    }

    rpc pon-onu-group-software-upgrade {
        if-feature feature-list:HAVE_POND;
        description "Upgrade a group of ONUs";
        input  {
            leaf group-name  {
                type string {
                    length "1..64";
                }
                mandatory true;
                description "Use this attribute to upgrade a group of ONUs";
            }
            leaf url  {
                type string;
                mandatory true;
                description "The URL to ONU image to be installed on ONUs. It can be
                            http://your-server-ip/path-to-install-file or
                            ftp://your-server-ip/path-to-install-file or
                            tftp://your-server-ip/path-to-install-file or
                            file://path-to-install-file";
            }
            leaf auto-activate  {
                type boolean;
                default false;
                description "Use this to auto-activate the new ONU image after the upgrade process
                            on ONU";
            }
            leaf auto-commit  {
                type boolean;
                default false;
                description "Use this to auto-commit the new ONU image after the upgrade process on
                            ONU";
            }
        }
    }

    rpc pon-onu-software-image-activate {
        if-feature feature-list:HAVE_POND;
        description "Activate the image of a single ONU";
        input  {
            leaf onu-id  {
                type uint32 {
                    range "0..4095";
                }
                mandatory true;
                description "This is the logical ONU identity in the system. The ONU identity is
                            from 0 to 4095";
            }
            leaf version-name  {
                type string {
                    length "1..32";
                }
                mandatory true;
                description "ONU firmware version name to be activated";
            }
        }
    }

    rpc pon-onu-group-software-image-activate {
        if-feature feature-list:HAVE_POND;
        description "Activate the image of a group of ONUs";
        input  {
            leaf group-name  {
                type string {
                    length "1..64";
                }
                mandatory true;
                description "This is the group of ONUs identification";
            }
            leaf version-name  {
                type string {
                    length "1..32";
                }
                mandatory true;
                description "ONU firmware version name to be activated";
            }
        }
    }

    rpc pon-onu-software-image-commit {
        if-feature feature-list:HAVE_POND;
        description "Commit the image of a single ONU";
        input  {
            leaf onu-id  {
                type uint32 {
                    range "0..4095";
                }
                mandatory true;
                description "This is the logical ONU identity in the system. The ONU identity is
                            from 0 to 4095";
            }
            leaf version-name  {
                type string {
                    length "1..32";
                }
                mandatory true;
                description "ONU firmware version name to be committed";
            }
        }
    }

    rpc pon-onu-group-software-image-commit {
        if-feature feature-list:HAVE_POND;
        description "Commit the image of a group of ONUs";
        input  {
            leaf group-name  {
                type string {
                    length "1..64";
                }
                mandatory true;
                description "This is the group of ONUs identification";
            }
            leaf version-name  {
                type string {
                    length "1..32";
                }
                mandatory true;
                description "ONU firmware version name to be committed";
            }
        }
    }

    rpc pon-terminal-debug-on {
        if-feature feature-list:HAVE_POND;
        description "Enable terminal debug for PON functionalities";
        input  {
            leaf debug-options  {
                type ipi-pon-types:pon_debug_type_t;
                mandatory true;
                description "Debugging state for PON functionalities";
            }
        }
    }

    rpc pon-terminal-debug-off {
        if-feature feature-list:HAVE_POND;
        description "Disable terminal debug for  PON functionalities";
        input  {
            leaf debug-options  {
                type ipi-pon-types:pon_debug_type_t;
                mandatory true;
                description "Debugging state for PON functionalities";
            }
        }
    }

    rpc pon-clear-dhcp-statistics {
        if-feature feature-list:HAVE_POND;
        description "Clear the DHCP relay statistics on the system";
    }

    rpc pon-clear-pppoe-statistics {
        if-feature feature-list:NOT_HAVE_TIBIT;
        if-feature feature-list:HAVE_POND;
        description "Clear the PPPoE relay statistics on the system";
    }

    notification pon-olt-firmware-install-status {
        if-feature feature-list:HAVE_POND;

        description "Notification to indicate Tibit OLT firmware download operation completion. On success with INFO severity or on failure with MAJOR severity.";

        leaf severity {
            type cml-data-types:cml_notif_severity_t;
            description "Notification severity level (value: CRITICAL)";
        }

        leaf eventClass {
            type cml-data-types:cml_notif_class_t;
            description "Notification event class (value: MESSAGE)";
        }

        leaf message {
            type string;
            description " alarm message notification";
        }
    }

    notification onu-software-image-download-status {
        if-feature feature-list:HAVE_POND;

        description "Notification to indicate ONU software image download operation completed. On success with INFO severity or on failure with MAJOR severity.";

        leaf severity {
            type cml-data-types:cml_notif_severity_t;
            description "Notification severity level (value: CRITICAL)";
        }

        leaf eventClass {
            type cml-data-types:cml_notif_class_t;
            description "Notification event class (value: MESSAGE)";
        }

        leaf message {
            type string;
            description " alarm message notification";
        }
    }

    notification onu-software-upgrade-status {
        if-feature feature-list:HAVE_POND;

        description "Notification sent on successful ONU upgrade operation with INFO severity or on failed ONU upgrade operation with MAJOR severity..";

        leaf severity {
            type cml-data-types:cml_notif_severity_t;
            description "Notification severity level (value: INFO)";
        }

        leaf eventClass {
            type cml-data-types:cml_notif_class_t;
            description "Notification event class (value: MESSAGE)";
        }

        leaf message {
            type string;
            description " alarm message notification";
        }
    }

    notification onu-software-activation-status {
        if-feature feature-list:HAVE_POND;

        description "Notification sent on successful ONU software image activation operation with INFO severity or on failed ONU upgrade operation with MAJOR severity..";

        leaf severity {
            type cml-data-types:cml_notif_severity_t;
            description "Notification severity level (value: INFO)";
        }

        leaf eventClass {
            type cml-data-types:cml_notif_class_t;
            description "Notification event class (value: MESSAGE)";
        }

        leaf message {
            type string;
            description " alarm message notification";
        }
    }

    notification onu-software-commit-status {
        if-feature feature-list:HAVE_POND;

        description "Notification sent on successful ONU software image commit operation with INFO severity or on failed ONU upgrade operation with MAJOR severity..";

        leaf severity {
            type cml-data-types:cml_notif_severity_t;
            description "Notification severity level (value: INFO)";
        }

        leaf eventClass {
            type cml-data-types:cml_notif_class_t;
            description "Notification event class (value: MESSAGE)";
        }

        leaf message {
            type string;
            description " alarm message notification";
        }
    }

}
