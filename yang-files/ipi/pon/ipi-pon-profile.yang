/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-pon-profile.yang
*
*/

submodule ipi-pon-profile {

    yang-version 1.1;

    belongs-to  ipi-pon { prefix ipi-pon; }

    import feature-list {
        prefix feature-list;
        revision-date 2026-09-15;
    }

    import ipi-pon-types {
        prefix ipi-pon-types;
        revision-date 2023-02-06;
    }

    include ipi-pon-profile-translation { revision-date 2023-02-07;}
    include ipi-pon-profile-onu { revision-date 2022-06-01;}
    organization
        "IP Infusion Inc.";

    contact
        "Address: 3965 Freedom Circle, Suite 200, Santa Clara, CA 95054
         Phone: +1 408-400-1900
         E-mail: support@ipinfusion.com
         Web: http://www.ipinfusion.com/";

    description
        "This module defines a data model for QOS profile configuration for
                passive optical network, including the translation and ONU profile
                modules";


    revision "2023-02-07" {
        description "Updated some list structures by adding a container above";
        reference " 0.5.0.";
    }

    revision "2022-06-01" {
        description "Updated the yang file with feature";
        reference " 0.4.0.";
    }

    revision "2021-09-03" {
        description "Update descriptions of attribute";
        reference " 0.3.0.";
    }

    revision "2021-02-15" {
        description "Added support for state container corresponding to config containers";
        reference " 0.2.0.";
    }

    revision "2020-11-13" {
        description "Initial Version";
        reference "Initial Version";
    }

    grouping qos-profile-name-config {
        description
            "Grouping for QOS profile name";
        leaf profile-name  {
            type  string {
                length "1..64";
                pattern "[^?' =,>|]+";
            }
            description "The attribute is to have unique QOS profile name";
        } // END of profile-name definition.

    } // END of qos-profile-name-config definition.
    grouping qos-profile-ready-state {
        description
            "Grouping for QOS profile ready state";
        leaf ready-status  {
            type  ipi-pon-types:pon_ready_status_t;
            description "The attribute is to show profile ready status";
        } // END of ready-status definition.

    } // END of qos-profile-ready-state definition.
    grouping qos-upstream-mode-config {
        description
            "Grouping for QOS profile upstream mode";
        leaf instance-id  {
            type  ipi-pon-types:pon_upstream_instance_t;
            mandatory true;
            description "It's to have QOS upstream mode switch command for command terminal.
                        Netconf will simply set the value as upstream";
        } // END of instance-id definition.

    } // END of qos-upstream-mode-config definition.
    grouping qos-upstream-config {
        description
            "Grouping for QOS profile upstream configuration";
        leaf cir  {
            type  uint32 {
                 range "1..10000000"  {
                    description "1..10000000:Feature : HAVE_TIBIT Supported range 1 - 10000000Not
                            Feature : HAVE_TIBIT  Supported range 1 - 10000000";
                 }
            }
            description "The committed information rate setting for the upstream traffic";
        } // END of cir definition.

        leaf cir-type  {
            type  ipi-pon-types:pon_qos_rate_t;
            description "The unit of committed information rate for the upstream traffic";
        } // END of cir-type definition.

        leaf pir  {
            type  uint32 {
                 range "1..10000000"  {
                    description "1..10000000:Feature : HAVE_TIBIT Supported range 1 - 10000000Not
                            Feature : HAVE_TIBIT  Supported range 1 - 10000000";
                 }
            }
            description "The peak information rate setting for the upstream traffic";
        } // END of pir definition.

        leaf pir-type  {
            type  ipi-pon-types:pon_qos_rate_t;
            description "The unit of peak information rate for the upstream traffic";
        } // END of pir-type definition.

    } // END of qos-upstream-config definition.
    grouping qos-downstream-mode-config {
        description
            "Grouping for QOS profile downstream mode";
        leaf instance-id  {
            type  ipi-pon-types:pon_downstream_instance_t;
            mandatory true;
            description "It's to have QOS downstream mode switch command for command terminal.
                        Netconf will simply set the value as downstream";
        } // END of instance-id definition.

    } // END of qos-downstream-mode-config definition.
    grouping qos-downstream-config {
        description
            "Grouping for QOS profile downstream configuration";
        leaf cir  {
            type  uint32 {
                 range "1..10000000"  {
                    description "1..10000000:Feature : HAVE_TIBIT Supported range 1 - 10000000Not
                            Feature : HAVE_TIBIT  Supported range 1 - 10000000";
                 }
            }
            description "The committed information rate setting for the downstream traffic";
        } // END of cir definition.

        leaf cir-type  {
            type  ipi-pon-types:pon_qos_rate_t;
            description "The unit of committed information rate for the downstream traffic";
        } // END of cir-type definition.

        leaf pir  {
            type  uint32 {
                 range "1..10000000"  {
                    description "1..10000000:Feature : HAVE_TIBIT Supported range 1 - 10000000Not
                            Feature : HAVE_TIBIT  Supported range 1 - 10000000";
                 }
            }
            description "The peak information rate setting for the downstream traffic";
        } // END of pir definition.

        leaf pir-type  {
            type  ipi-pon-types:pon_qos_rate_t;
            description "The unit of peak information rate for the downstream traffic";
        } // END of pir-type definition.

        leaf pbs  {
            type  uint32 {
                 range "1..10000000"  {
                    description "1..10000000:Feature : HAVE_TIBIT Supported range 1 - 10000000Not
                            Feature : HAVE_TIBIT  Supported range 1 - 10000000";
                 }
            }
            description "The unit of peak information rate for the downstream traffic";
        } // END of pbs definition.

        leaf pbs-type  {
            type  ipi-pon-types:pon_qos_burst_t;
            description "The unit of peak burst size for the downstream traffic";
        } // END of pbs-type definition.

    } // END of qos-downstream-config definition.
    grouping qos-upstream-config-instance {
        description
            "Grouping instance configuration for upstream QOS profile";
        container instance {
            presence "Instance";
            description
                "Upstream QOS instance";
            container config {
                presence "Instance";
                description
                    "Upstream QOS instance configuration";
                uses qos-upstream-mode-config;
            } // END of config-container definition.
            container state {
                config false;
                description
                    "Upstream QOS instance state";
                uses qos-upstream-mode-config;
            } // END of state-container definition.
        } // END of instance-container definition.
    } // END of qos-upstream-config-instance definition.
    grouping qos-upstream-config-all {
        description
            "Grouping for upstream QOS profile configuration";
        container rates {
            description
                "Rate for upstream QOS profile";

            list rate {
                key "cir cir-type pir pir-type";
                max-elements 1;
                description
                    "Rate for upstream QOS profile";
                leaf cir  {
                    type  leafref {
                        path  "../config/cir";
                    }
                    description "The committed information rate setting for the upstream traffic";
                } // END of cir definition.

                leaf cir-type  {
                    type  leafref {
                        path  "../config/cir-type";
                    }
                    description "The unit of committed information rate for the upstream traffic";
                } // END of cir-type definition.

                leaf pir  {
                    type  leafref {
                        path  "../config/pir";
                    }
                    description "The peak information rate setting for the upstream traffic";
                } // END of pir definition.

                leaf pir-type  {
                    type  leafref {
                        path  "../config/pir-type";
                    }
                    description "The unit of peak information rate for the upstream traffic";
                } // END of pir-type definition.

                container config {
                    description
                        "Rate configuration for upstream QOS profile";
                    uses qos-upstream-config;
                } // END of config-container definition.
                container state {
                    config false;
                    description
                        "Upstream QOS profile Rate state";
                    uses qos-upstream-config;
                } // END of state-container definition.
            } // End of rate-list
        } // END of rates-container definition.
    } // END of qos-upstream-config-all definition.
    grouping qos-downstream-config-instance {
        description
            "Grouping instance configuration for downstream QOS profile";
        container instance {
            presence "Instance";
            description
                "Downstream QOS instance";
            container config {
                presence "Instance";
                description
                    "Downstream QOS instance configuration";
                uses qos-downstream-mode-config;
            } // END of config-container definition.
            container state {
                config false;
                description
                    "Downstream QOS instance state";
                uses qos-downstream-mode-config;
            } // END of state-container definition.
        } // END of instance-container definition.
    } // END of qos-downstream-config-instance definition.
    grouping qos-downstream-config-all {
        description
            "Grouping for downstream QOS profile configuration";
        container rates {
            description
                "Rate for downstream QOS profile";

            list rate {
                key "cir cir-type pir pir-type pbs pbs-type";
                max-elements 1;
                description
                    "Rate for downstream QOS profile";
                leaf cir  {
                    type  leafref {
                        path  "../config/cir";
                    }
                    description "The committed information rate setting for the downstream traffic";
                } // END of cir definition.

                leaf cir-type  {
                    type  leafref {
                        path  "../config/cir-type";
                    }
                    description "The unit of committed information rate for the downstream traffic";
                } // END of cir-type definition.

                leaf pir  {
                    type  leafref {
                        path  "../config/pir";
                    }
                    description "The peak information rate setting for the downstream traffic";
                } // END of pir definition.

                leaf pir-type  {
                    type  leafref {
                        path  "../config/pir-type";
                    }
                    description "The unit of peak information rate for the downstream traffic";
                } // END of pir-type definition.

                leaf pbs  {
                    type  leafref {
                        path  "../config/pbs";
                    }
                    description "The unit of peak information rate for the downstream traffic";
                } // END of pbs definition.

                leaf pbs-type  {
                    type  leafref {
                        path  "../config/pbs-type";
                    }
                    description "The unit of peak burst size for the downstream traffic";
                } // END of pbs-type definition.

                container config {
                    description
                        "Rate configuration for downstream QOS profile";
                    uses qos-downstream-config;
                } // END of config-container definition.
                container state {
                    config false;
                    description
                        "Downstream QOS profile Rate state";
                    uses qos-downstream-config;
                } // END of state-container definition.
            } // End of rate-list
        } // END of rates-container definition.
    } // END of qos-downstream-config-all definition.
    grouping qos-default-profile-state {
        description
            "Grouping for QOS default profile state";
        container default-profile {
            config false;
            description
                "QOS default profile";
            container state {
                config false;
                description
                    "QOS default profile state";
                uses qos-profile-name-config;
                uses qos-profile-ready-state;
            } // END of state-container definition.
            container upstream {
                config false;
                description
                    "Upstream QOS profile";
                container detail {
                    config false;
                    description
                        "Upstream QOS profile detail";
                    container rate {
                        config false;
                        description
                            "Rate for upstream QOS profile";
                        container state {
                            config false;
                            description
                                "Upstream rate state";
                            uses qos-upstream-config;
                        } // END of state-container definition.
                    } // END of rate-container definition.
                } // END of detail-container definition.
            } // END of upstream-container definition.
            container downstream {
                config false;
                description
                    "Downstream QOS profile";
                container detail {
                    config false;
                    description
                        "Downstream QOS profile detail";
                    container rate {
                        config false;
                        description
                            "Rate for downstream QOS profile";
                        container state {
                            config false;
                            description
                                "Downstream rate state";
                            uses qos-downstream-config;
                        } // END of state-container definition.
                    } // END of rate-container definition.
                } // END of detail-container definition.
            } // END of downstream-container definition.
        } // END of default-profile-container definition.
    } // END of qos-default-profile-state definition.
    grouping qos-profiles-config {
        description
            "Grouping configuration for QOS profiles";
        container qos-profiles {
            description
                "QOS profiles";

            list qos-profile {
                key "profile-name";
                description
                    "QOS profile";
                leaf profile-name  {
                    type  leafref {
                        path  "../config/profile-name";
                    }
                    description "The attribute is to have unique QOS profile name";
                } // END of profile-name definition.

                container config {
                    description
                        "QOS profile name configuration";
                    uses qos-profile-name-config;
                } // END of config-container definition.
                container state {
                    config false;
                    description
                        "QOS profile name state";
                    uses qos-profile-name-config;
                    uses qos-profile-ready-state;
                } // END of state-container definition.
                container upstream {
                    description
                        "Upstream QOS profile";
                    container detail {
                        description
                            "Upstream QOS profile detail";
                        uses qos-upstream-config-all;
                    } // END of detail-container definition.
                    uses qos-upstream-config-instance;
                } // END of upstream-container definition.
                container downstream {
                    description
                        "Downstream QOS profile";
                    container detail {
                        description
                            "Downstream QOS profile detail";
                        uses qos-downstream-config-all;
                    } // END of detail-container definition.
                    uses qos-downstream-config-instance;
                } // END of downstream-container definition.
            } // End of qos-profile-list
            uses qos-default-profile-state;
        } // END of qos-profiles-container definition.
    } // END of qos-profiles-config definition.

    grouping  profiles-grouping {
    description
        "PON profiles";
    container profiles {
        if-feature feature-list:HAVE_POND;
        description
            "PON profiles";
        uses qos-profiles-config;
        uses translation-profiles-grouping;
        uses onu-profiles-grouping;
    } // END of profiles-container definition.
    } // END of profiles-grouping definition.


}
