/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-pon-flow.yang
*
*/

submodule ipi-pon-flow {

    yang-version 1.1;

    belongs-to  ipi-pon { prefix ipi-pon; }

    import feature-list {
        prefix feature-list;
        revision-date 2026-09-15;
    }

    import ipi-pon-types {
        prefix ipi-pon-types;
        revision-date 2023-02-06;
    }

    import ietf-yang-types {
        prefix yang;
        revision-date 2013-07-15;
    }

    organization
        "IP Infusion Inc.";

    contact
        "Address: 3965 Freedom Circle, Suite 200, Santa Clara, CA 95054
         Phone: +1 408-400-1900
         E-mail: support@ipinfusion.com
         Web: http://www.ipinfusion.com/";

    description
        "This module defines a data model for flow configuration for passive
                optical network";


    revision "2023-07-31" {
        description "Removing the misplaced initialized from  qos-profile-name";
        reference " 0.2.0.";
    }

    revision "2023-07-07" {
        description "Removing the misplaced initialized from  details";
        reference " 0.1.0.";
    }

    revision "2023-02-07" {
        description "Updated some list structures by adding a container above";
        reference " 0.4.2.";
    }

    revision "2023-01-30" {
        description "Fix flow nni string length";
        reference " 0.4.1.";
    }

    revision "2022-06-01" {
        description "Updated the yang file with feature";
        reference " 0.4.0.";
    }

    revision "2021-09-03" {
        description "Update descriptions of attribute";
        reference " 0.3.0.";
    }

    revision "2021-02-15" {
        description "Added support for state container corresponding to config containers";
        reference " 0.2.0.";
    }

    revision "2020-11-13" {
        description "Initial Version";
        reference "Initial Version";
    }

    grouping flow-id-config {
        description
            "Grouping for flow identity configuration";
        leaf flow-id  {
            type  uint16;
            description "This is the subscriber flow identity in the system. The ID range is
                        between 0 and 65535";
        } // END of flow-id definition.

    } // END of flow-id-config definition.
    grouping flow-global-config {
        description
            "Grouping for flow global configuration";
        leaf mode  {
            type  ipi-pon-types:pon_flow_mode_t;
            default "one2one";
            description "This is the flow mode which can be 1:1 or N:1 VLAN model. It's 1:1
                        VLAN by default. The value can be either one2one or n2one";
        } // END of mode definition.

    } // END of flow-global-config definition.
    grouping flow-global-state {
        description
            "Grouping for flow global state";
        leaf operational-status  {
            type  ipi-pon-types:pon_up_down_status_t;
            description "Indicate the operational status of the flow";
        } // END of operational-status definition.

        leaf operational-down-reason  {
            type  ipi-pon-types:pon_info_string_t {
                length "1..1965";
            }
            description "Indicate the reason when flow is down";
        } // END of operational-down-reason definition.

        leaf ready-status  {
            type  ipi-pon-types:pon_ready_status_t;
            description "The attribute is to show flow setting ready status";
        } // END of ready-status definition.

    } // END of flow-global-state definition.
    grouping flow-qos-mode-config {
        description
            "Grouping for flow QOS mode configuration";
        leaf instance-id  {
            type  ipi-pon-types:pon_flow_qos_instance_t;
            mandatory true;
            description "It's to have flow QOS mode switch command for command terminal.
                        Netconf will simply set the value as qos";
        } // END of instance-id definition.

    } // END of flow-qos-mode-config definition.
    grouping flow-qos-config-detail {
        description
            "Grouping for flow QOS configuration";
        leaf qos-profile-name  {
            type  string {
                length "1..64";
                pattern "[^?' =,>|]+";
            }
            description "QOS profile applied to the flow in the OLT. The predefined
                        default_qos_profile is provided as a choice";
        } // END of qos-profile-name definition.

    } // END of flow-qos-config-detail definition.
    grouping flow-qos-queue-info {
        description
            "Grouping for flow QOS queue info";
        leaf upstream-queue  {
            if-feature feature-list:NOT_HAVE_TIBIT;
            type  uint16;
            description "Indicate upstream QOS queue ID for the flow";
        } // END of upstream-queue definition.

        leaf upstream-scheduler  {
            if-feature feature-list:NOT_HAVE_TIBIT;
            type  uint16;
            description "Indicate upstream QOS scheduler ID for the flow";
        } // END of upstream-scheduler definition.

        leaf downstream-queue  {
            if-feature feature-list:NOT_HAVE_TIBIT;
            type  uint16;
            description "Indicate downstream QOS queue ID for the flow";
        } // END of downstream-queue definition.

        leaf downstream-scheduler  {
            if-feature feature-list:NOT_HAVE_TIBIT;
            type  uint16;
            description "Indicate downstream QOS scheduler ID for the flow";
        } // END of downstream-scheduler definition.

    } // END of flow-qos-queue-info definition.
    grouping flow-qos-config {
        description
            "Grouping for flow QOS configuration";
        container flow-qos {
            description
                "Flow QOS";
            container instance {
                presence "Instance";
                description
                    "Flow QOS Instance";
                container config {
                    presence "Instance";
                    description
                        "Flow QOS instance configuration";
                    uses flow-qos-mode-config;
                } // END of config-container definition.
                container state {
                    config false;
                    description
                        "Flow QOS instance state";
                    uses flow-qos-mode-config;
                } // END of state-container definition.
            } // END of instance-container definition.
            container detail {
                description
                    "Flow QOS detail";
                container config {
                    description
                        "Flow QOS detail configuration";
                    uses flow-qos-config-detail;
                } // END of config-container definition.
                container state {
                    config false;
                    description
                        "Flow QOS detail state";
                    uses flow-qos-config-detail;
                } // END of state-container definition.
            } // END of detail-container definition.
            container operational-detail {
                config false;
                description
                    "Current operational flow QOS states";
                container state {
                    config false;
                    description
                        "Flow QOS detail state";
                    uses flow-qos-config-detail;
                    uses flow-qos-queue-info;
                } // END of state-container definition.
            } // END of operational-detail-container definition.
        } // END of flow-qos-container definition.
    } // END of flow-qos-config definition.
    grouping flow-uni-mode-config {
        description
            "Grouping for flow UNI mode configuration";
        leaf instance-id  {
            type  ipi-pon-types:pon_flow_uni_instance_t;
            mandatory true;
            description "It's to have flow UNI mode switch command for command terminal.
                        Netconf will simply set the value as uni";
        } // END of instance-id definition.

    } // END of flow-uni-mode-config definition.
    grouping flow-uni-config-detail {
        description
            "Grouping for flow UNI configuration";
        leaf onu-id  {
            type  uint32 {
                 range "0..4095"  {
                    description "0..4095: Supported range 0 - 4095";
                 }
            }
            description "This is the logical ONU identity in the system. The ONU identity is
                        between 0 and 4095";
        } // END of onu-id definition.

        leaf uni-port-id  {
            type  uint32 {
                 range "0..255"  {
                    description "0..255: Supported range 0 - 255";
                 }
            }
            description "This is the UNI port ID in the ONU. The ID can be between 0 and 255
                        depending on the ONU UNI capability";
        } // END of uni-port-id definition.

        leaf vlan-tag  {
            type  uint32 {
                 range "2..4094"  {
                    description "2..4094: Supported range 2 - 4094";
                 }
            }
            description "The VLAN ID presented on PON port, the ID ranges between 2 and 4094";
        } // END of vlan-tag definition.

        leaf translation-profile-name  {
            type  string {
                length "1..64";
                pattern "[^?' =,>|]+";
            }
            description "The translation profile applied to the ONU UNI. The predefined
                        default_translation_profile is provided as a choice";
        } // END of translation-profile-name definition.

        leaf ether-type  {
            type  ipi-pon-types:pon_uni_flow_ethertype_t;
            mandatory true;
            description "Either 802.1q TPID 0x8100 or 802.1ad TPID 0x88a8 be used for the flow.
                        The choice can be 0x8100 or 0x88a8";
        } // END of ether-type definition.

    } // END of flow-uni-config-detail definition.
    grouping flow-pon-transport-info-detail {
        description
            "Grouping for flow PON transport info";
        leaf tcont-name  {
            type  ipi-pon-types:pon_info_string_t {
                length "1..1965";
            }
            description "Indicate the T-CONT name for the flow";
        } // END of tcont-name definition.

        leaf gem-port-name  {
            type  ipi-pon-types:pon_info_string_t {
                length "1..1965";
            }
            description "Indicate the GEM port name for the flow";
        } // END of gem-port-name definition.

        leaf p-bits  {
            type  uint8;
            description "Indicate IEEE 802.1p class of service associated to the GEM port";
        } // END of p-bits definition.

        leaf upstream-priority-queue  {
            type  uint16;
            description "Indicate the UNI upstream priority queue number";
        } // END of upstream-priority-queue definition.

        leaf downstream-priority-queue  {
            type  uint16;
            description "Indicate the UNI downstream priority queue number";
        } // END of downstream-priority-queue definition.

    } // END of flow-pon-transport-info-detail definition.
    grouping flow-onu-me-class-info {
        description
            "Grouping for flow ONU OMCI ME info";
        leaf name  {
            type  ipi-pon-types:pon_info_string_t {
                length "1..1965";
            }
            description "Indicate G.988 ONU managed entity class name";
        } // END of name definition.

        leaf entity-number  {
            type  uint32;
            description "Indicate ONU management entity number";
        } // END of entity-number definition.

    } // END of flow-onu-me-class-info definition.
    grouping flow-uni-config {
        description
            "Grouping for flow UNI configuration";
        container flow-uni {
            description
                "Flow UNI";
            container instance {
                presence "Instance";
                description
                    "Flow UNI Instance";
                container config {
                    presence "Instance";
                    description
                        "Flow UNI instance configuration";
                    uses flow-uni-mode-config;
                } // END of config-container definition.
                container state {
                    config false;
                    description
                        "Flow UNI instance state";
                    uses flow-uni-mode-config;
                } // END of state-container definition.
            } // END of instance-container definition.
            container details {
                description
                    "Flow UNI details";

                list detail {
                    key "onu-id uni-port-id vlan-tag translation-profile-name";
                    max-elements 1;
                    description
                        "Flow UNI detail";
                    leaf onu-id  {
                        type  leafref {
                            path  "../config/onu-id";
                        }
                        description "This is the logical ONU identity in the system. The ONU identity is
                                    between 0 and 4095";
                    } // END of onu-id definition.

                    leaf uni-port-id  {
                        type  leafref {
                            path  "../config/uni-port-id";
                        }
                        description "This is the UNI port ID in the ONU. The ID can be between 0 and 255
                                    depending on the ONU UNI capability";
                    } // END of uni-port-id definition.

                    leaf vlan-tag  {
                        type  leafref {
                            path  "../config/vlan-tag";
                        }
                        description "The VLAN ID presented on PON port, the ID ranges between 2 and 4094";
                    } // END of vlan-tag definition.

                    leaf translation-profile-name  {
                        type  leafref {
                            path  "../config/translation-profile-name";
                        }
                        description "The translation profile applied to the ONU UNI. The predefined
                                    default_translation_profile is provided as a choice";
                    } // END of translation-profile-name definition.

                    container config {
                        description
                            "Flow UNI detail configuration";
                        uses flow-uni-config-detail;
                    } // END of config-container definition.
                    container state {
                        config false;
                        description
                            "Flow UNI detail state";
                        uses flow-uni-config-detail;
                    } // END of state-container definition.
                } // End of detail-list
            } // END of details-container definition.
            container operational-detail {
                config false;
                description
                    "Current operational flow UNI states";
                container state {
                    config false;
                    description
                        "Flow UNI detail state";
                    uses flow-uni-config-detail;
                } // END of state-container definition.
                container pon-transport-info {
                    config false;
                    description
                        "PON transport info for the flow";
                    container state {
                        config false;
                        description
                            "Flow pon transport state";
                        uses flow-pon-transport-info-detail;
                    } // END of state-container definition.
                } // END of pon-transport-info-container definition.
                container onu-me-info {
                    if-feature feature-list:NOT_HAVE_TIBIT;
                    config false;
                    description
                        "ONU ME info for the flow";

                    list class {
                        key "name entity-number";
                        config false;
                        description
                            "ONU flow ME classes";
                        leaf name  {
                            type  leafref {
                                path  "../state/name";
                            }
                            description "Indicate G.988 ONU managed entity class name";
                        } // END of name definition.

                        leaf entity-number  {
                            type  leafref {
                                path  "../state/entity-number";
                            }
                            description "Indicate ONU management entity number";
                        } // END of entity-number definition.

                        container state {
                            config false;
                            description
                                "ONU flow ME info";
                            uses flow-onu-me-class-info;
                        } // END of state-container definition.
                    } // End of class-list
                } // END of onu-me-info-container definition.
            } // END of operational-detail-container definition.
        } // END of flow-uni-container definition.
    } // END of flow-uni-config definition.
    grouping flow-nni-mode-config {
        description
            "Grouping for flow NNI mode configuration";
        leaf instance-id  {
            type  ipi-pon-types:pon_flow_nni_instance_t;
            mandatory true;
            description "It's to have flow NNI mode switch command for command terminal.
                        Netconf will simply set the value as nni";
        } // END of instance-id definition.

    } // END of flow-nni-mode-config definition.
    grouping flow-nni-config-common {
        description
            "Grouping for flow NNI configuration";
        leaf olt-id  {
            type  uint32 {
                 range "0..65535"  {
                    description "0..65535:Feature : HAVE_TIBIT Supported range 0 - 63Not Feature :
                            HAVE_TIBIT  Supported range 0 - 65535";
                 }
            }
            description "This is the logical OLT identity in the system. The OLT identity in
                        Tibit is 0 to 63 while the identity in other system is between 0 and
                        65535";
        } // END of olt-id definition.

        leaf nni-port-name  {
            type  string {
                length "3..64";
                pattern "[^?' =,>|]+";
            }
            description "The NNI port name starting with 'nni' for the flow";
        } // END of nni-port-name definition.

    } // END of flow-nni-config-common definition.
    grouping flow-nni-config-tagged {
        description
            "Grouping for flow NNI tagged configuration";
        leaf vlan-tag-value  {
            type  ipi-pon-types:pon_vlan_tag_value_t;
            description "The VLAN ID presented on NNI port, the ID string has 1 to 4 numeric
                        digits. The ID string can be none or 2 to 4094";
        } // END of vlan-tag-value definition.

        leaf vlan-tag-format  {
            type  ipi-pon-types:pon_vlan_tag_format_t;
            mandatory true;
            description "The 802.1q TPID 0x8100 or 802.1ad TPID 0x88a8 presented in the NNI
                        packet. The format may be set when vlan-tag-value is not 'none'. The
                        input value can be either 0x8100 or 0x88a8";
        } // END of vlan-tag-format definition.

    } // END of flow-nni-config-tagged definition.
    grouping flow-nni-config {
        description
            "Grouping for flow NNI configuration";
        container flow-nni {
            description
                "Flow NNI";
            container instance {
                presence "Instance";
                description
                    "Flow NNI Instance";
                container config {
                    presence "Instance";
                    description
                        "Flow NNI Instance configuration";
                    uses flow-nni-mode-config;
                } // END of config-container definition.
                container state {
                    config false;
                    description
                        "Flow NNI instance state";
                    uses flow-nni-mode-config;
                } // END of state-container definition.
            } // END of instance-container definition.
            container operational-detail {
                config false;
                description
                    "Current operational flow NNI states";
                container state {
                    config false;
                    description
                        "Flow NNI detail state";
                    uses flow-nni-config-common;
                    uses flow-nni-config-tagged;
                } // END of state-container definition.
            } // END of operational-detail-container definition.
            choice nni-detail {
                description
                    "The choice of flow NNI detail";
                case tagged {

                    description
                        "Tagged NNI";

                    container tagged-details {
                        description
                            "Tagged flow NNI details";

                        list tagged-detail {
                            key "olt-id nni-port-name vlan-tag-value";
                            max-elements 1;
                            description
                                "Tagged flow NNI detail";
                            leaf olt-id  {
                                type  leafref {
                                    path  "../config/olt-id";
                                }
                                description "This is the logical OLT identity in the system. The OLT identity in
                                            Tibit is 0 to 63 while the identity in other system is between 0 and
                                            65535";
                            } // END of olt-id definition.

                            leaf nni-port-name  {
                                type  leafref {
                                    path  "../config/nni-port-name";
                                }
                                description "The NNI port name starting with 'nni' for the flow";
                            } // END of nni-port-name definition.

                            leaf vlan-tag-value  {
                                type  leafref {
                                    path  "../config/vlan-tag-value";
                                }
                                description "The VLAN ID presented on NNI port, the ID string has 1 to 4 numeric
                                            digits. The ID string can be none or 2 to 4094";
                            } // END of vlan-tag-value definition.

                            container config {
                                description
                                    "Flow NNI detail configuration";
                                uses flow-nni-config-common;
                                uses flow-nni-config-tagged;
                            } // END of config-container definition.
                            container state {
                                config false;
                                description
                                    "Flow NNI detail state";
                                uses flow-nni-config-common;
                                uses flow-nni-config-tagged;
                            } // END of state-container definition.
                        } // End of tagged-detail-list
                    } // END of tagged-details-container definition.
                }
                case untagged {

                    description
                        "Untagged NNI";

                    container untagged-details {
                        description
                            "Untagged flow NNI details";

                        list untagged-detail {
                            key "olt-id nni-port-name";
                            max-elements 1;
                            description
                                "Untagged flow NNI detail";
                            leaf olt-id  {
                                type  leafref {
                                    path  "../config/olt-id";
                                }
                                description "This is the logical OLT identity in the system. The OLT identity in
                                            Tibit is 0 to 63 while the identity in other system is between 0 and
                                            65535";
                            } // END of olt-id definition.

                            leaf nni-port-name  {
                                type  leafref {
                                    path  "../config/nni-port-name";
                                }
                                description "The NNI port name starting with 'nni' for the flow";
                            } // END of nni-port-name definition.

                            container config {
                                description
                                    "Flow NNI detail configuration";
                                uses flow-nni-config-common;
                            } // END of config-container definition.
                            container state {
                                config false;
                                description
                                    "Flow NNI detail state";
                                uses flow-nni-config-common;
                            } // END of state-container definition.
                        } // End of untagged-detail-list
                    } // END of untagged-details-container definition.
                }
            } // END of nni-detail-choice definition.
        } // END of flow-nni-container definition.
    } // END of flow-nni-config definition.
    grouping flow-statistics-mode-config {
        description
            "Grouping for flow statistics mode configuration";
        leaf instance-id  {
            type  ipi-pon-types:pon_flow_stats_instance_t;
            mandatory true;
            description "It's to have flow statistics mode switch command for command terminal.
                        Netconf will simply set the value as statistics";
        } // END of instance-id definition.

    } // END of flow-statistics-mode-config definition.
    grouping flow-statistics-config-detail {
        description
            "Grouping for flow statistics enabling detail configuration";
        leaf statistics  {
            type  ipi-pon-types:pon_flow_stats_t;
            description "Statistics per flow setting which can be on or off";
        } // END of statistics definition.

    } // END of flow-statistics-config-detail definition.
    grouping flow-statistics-operational-detail {
        description
            "Grouping for flow statistics enabling perational detail";
        leaf operational-statistics  {
            type  ipi-pon-types:pon_flow_stats_t;
            description "Indicate current flow statistics status";
        } // END of operational-statistics definition.

    } // END of flow-statistics-operational-detail definition.
    grouping flow-statistics-counters {
        description
            "Grouping for one2one flow statistics counters";
        leaf rx-packets  {
            type  yang:counter64;
            description "Indicate the flow receive packets";
        } // END of rx-packets definition.

        leaf rx-bytes  {
            type  yang:counter64;
            description "Indicate the flow receive bytes";
        } // END of rx-bytes definition.

        leaf tx-packets  {
            type  yang:counter64;
            description "Indicate the flow transmission packets";
        } // END of tx-packets definition.

        leaf tx-bytes  {
            type  yang:counter64;
            description "Indicate the flow transmission bytes";
        } // END of tx-bytes definition.

        leaf drop-packets  {
            type  yang:counter64;
            description "Indicate the flow dropped packets";
        } // END of drop-packets definition.

        leaf drop-bytes  {
            type  yang:counter64;
            description "Indicate the flow dropped bytes";
        } // END of drop-bytes definition.

    } // END of flow-statistics-counters definition.
    grouping flow-statistics-config {
        description
            "Grouping for Flow statistics enabling configuration";
        container flow-statistics {
            if-feature feature-list:NOT_HAVE_TIBIT;
            description
                "Flow statistics enabling";
            container config {
                presence "Stats Mode";
                description
                    "Flow statistics enabling configuration";
                uses flow-statistics-mode-config;
                uses flow-statistics-config-detail;
            } // END of config-container definition.
            container state {
                config false;
                description
                    "Flow statistics state";
                container counters {
                    config false;
                    description
                        "Flow statistics counters";
                    container upstream {
                        config false;
                        description
                            "Flow upstream statistics counters(rx on PON side, tx on NNI side)";
                        uses flow-statistics-counters;
                    } // END of upstream-container definition.
                    container downstream {
                        config false;
                        description
                            "Flow downstream statistics counters(rx on NNI side, tx on PON side)";
                        uses flow-statistics-counters;
                    } // END of downstream-container definition.
                } // END of counters-container definition.
                uses flow-statistics-mode-config;
                uses flow-statistics-config-detail;
                uses flow-statistics-operational-detail;
            } // END of state-container definition.
        } // END of flow-statistics-container definition.
    } // END of flow-statistics-config definition.
    grouping flow-acl-mode-config {
        description
            "Grouping for flow ACL mode configuration";
        leaf instance-id  {
            type  ipi-pon-types:pon_acl_instance_t;
            mandatory true;
            description "It's to have flow ACL mode switch command for command terminal.
                        Netconf will simply set the value as acl";
        } // END of instance-id definition.

    } // END of flow-acl-mode-config definition.
    grouping flow-acl-id-config {
        description
            "Grouping for flow ACL identity configuration";
        leaf flow-acl-id  {
            type  uint16;
            description "ACL identity number between 0 and 65535";
        } // END of flow-acl-id definition.

    } // END of flow-acl-id-config definition.
    grouping flow-acl-config-detail {
        description
            "Grouping for flow ACL configuration";
        leaf priority  {
            type  uint16;
            mandatory true;
            description "ACL priority between 0 and 65535, the lower value the higher priority";
        } // END of priority definition.

        leaf action  {
            type  ipi-pon-types:pon_acl_action_t;
            mandatory true;
            description "ACL action which can be allow, drop or trap-to-cpu";
        } // END of action definition.

        leaf direction  {
            type  ipi-pon-types:pon_acl_direction_t;
            mandatory true;
            description "Subscriber traffic direction which can be either upstream or
                        downstream";
        } // END of direction definition.

        leaf remote-ip-address  {
            type  ipi-pon-types:pon_acl_addr_w_any_t;
            mandatory true;
            description "Subscriber remote IP address. It can be a four dotted decimal number
                        (n.n.n.n) or any";
        } // END of remote-ip-address definition.

        leaf protocol  {
            type  ipi-pon-types:pon_ip_protocol_t;
            mandatory true;
            description "Layer 4 protocol which can be tcp, udp or any(0)";
        } // END of protocol definition.

        leaf remote-port  {
            type  ipi-pon-types:pon_acl_port_t;
            mandatory true;
            description "Subscriber remote port number in the layer 4 protocol, the port range
                        is between 1 to 65535 or any";
        } // END of remote-port definition.

    } // END of flow-acl-config-detail definition.
    grouping flow-acl-dump-config-detail {
        description
            "Grouping for flow ACL dump configuration detail";
        leaf dump-trap  {
            type  ipi-pon-types:pon_acl_trap_dump_enable_t;
            description "Enable ACL trap dump globally";
        } // END of dump-trap definition.

        leaf trap-flow-id  {
            type  ipi-pon-types:pon_acl_trap_dump_flow_id_t;
            mandatory true;
            description "Dump the traffic from the trapped flow ID. The ID range is between 0
                        and 65535";
        } // END of trap-flow-id definition.

        leaf trap-acl-id  {
            type  ipi-pon-types:pon_acl_trap_dump_acl_id_t;
            mandatory true;
            description "Dump the traffic that matched the trapped ACL ID";
        } // END of trap-acl-id definition.

        leaf trap-acl-direction  {
            type  ipi-pon-types:pon_acl_trap_dump_direction_t;
            mandatory true;
            description "Dump the traffic that matched the trapped traffic direction which can
                        be upstream, downstream or both directions";
        } // END of trap-acl-direction definition.

        leaf trap-dump-limit  {
            type  uint16 {
                 range "1..4000"  {
                    description "1..4000: Supported range 1 - 4000";
                 }
            }
            units "MB";
            mandatory true;
            description "The approximate maximum dump size between 1MB and 4000MB for the
                        trapped traffic, by default it limits to 10MB. The dump file path is
                        /tmp/pon_acl_trap_dump.pcap on the OLT file system";
        } // END of trap-dump-limit definition.

    } // END of flow-acl-dump-config-detail definition.
    grouping flow-acl-dump-status {
        description
            "Grouping for flow acl dump status";
        leaf completion-status  {
            type  ipi-pon-types:pon_info_string_t {
                length "1..1965";
            }
            description "Indicate flow ACL dump completion status";
        } // END of completion-status definition.

    } // END of flow-acl-dump-status definition.
    grouping flow-acl-dump-written-counters {
        description
            "Grouping for flow acl dump written counter";
        leaf wr-size  {
            type  yang:counter64;
            description "Indicate the bytes of traffic packet data in written-size-unit written
                        into the dump file. The size doesn't include PCAP file and packet
                        headers";
        } // END of wr-size definition.

        leaf wr-size-unit  {
            type  ipi-pon-types:pon_byte_size_base_2_unit_t;
            description "Indicate the byte unit (base 2) for the written-size";
        } // END of wr-size-unit definition.

        leaf wr-packets  {
            type  yang:counter64;
            description "Indicate the traffic packets written into the dump file";
        } // END of wr-packets definition.

        leaf wr-drop-packets  {
            type  yang:counter64;
            description "Indicate the packets unable to be written into the dump file";
        } // END of wr-drop-packets definition.

    } // END of flow-acl-dump-written-counters definition.
    grouping flow-acl-rule-config {
        description
            "Grouping for flow ACL rule configuration";
        container acl-rules {
            description
                "Flow ACL rule lists";

            list acl-rule {
                key "flow-acl-id";
                description
                    "ACL rule";
                leaf flow-acl-id  {
                    type  leafref {
                        path  "../config/flow-acl-id";
                    }
                    description "ACL identity number between 0 and 65535";
                } // END of flow-acl-id definition.

                container config {
                    presence "ACL Rule";
                    description
                        "Flow ACL rule configuration";
                    uses flow-acl-id-config;
                    uses flow-acl-config-detail;
                } // END of config-container definition.
                container state {
                    config false;
                    description
                        "Flow ACL rule state";
                    uses flow-acl-id-config;
                    uses flow-acl-config-detail;
                } // END of state-container definition.
            } // End of acl-rule-list
        } // END of acl-rules-container definition.
    } // END of flow-acl-rule-config definition.
    grouping flow-acl-config {
        description
            "Grouping for flow ACL configuration";
        container flow-acl {
            if-feature feature-list:NOT_HAVE_TIBIT;
            description
                "Flow ACL";
            container instance {
                presence "Instance";
                description
                    "Flow ACL Instance";
                container config {
                    presence "Instance";
                    description
                        "Flow ACL instance configuration";
                    uses flow-acl-mode-config;
                } // END of config-container definition.
                container state {
                    config false;
                    description
                        "Flow ACL instance state";
                    uses flow-acl-mode-config;
                } // END of state-container definition.
            } // END of instance-container definition.
            uses flow-acl-rule-config;
        } // END of flow-acl-container definition.
    } // END of flow-acl-config definition.
    grouping flow-config {
        description
            "Grouping for subscriber flow configuration";

        list flow {
            key "flow-id";
            description
                "Subscriber flows";
            leaf flow-id  {
                type  leafref {
                    path  "../config/flow-id";
                }
                description "This is the subscriber flow identity in the system. The ID range is
                            between 0 and 65535";
            } // END of flow-id definition.

            container config {
                description
                    "Subscriber flow  configuration";
                uses flow-id-config;
                uses flow-global-config;
            } // END of config-container definition.
            container state {
                config false;
                description
                    "Flow state";
                uses flow-id-config;
                uses flow-global-config;
                uses flow-global-state;
            } // END of state-container definition.
            uses flow-qos-config;
            uses flow-uni-config;
            uses flow-nni-config;
            uses flow-statistics-config;
            uses flow-acl-config;
        } // End of flow-list
    } // END of flow-config definition.
    grouping flow-acl-dump-config {
        description
            "Grouping for flow ACL dump configuration";

        list acl-trap-dump {
            if-feature feature-list:NOT_HAVE_TIBIT;
            key "dump-trap";
            description
                "ACL dump";
            leaf dump-trap  {
                type  leafref {
                    path  "../config/dump-trap";
                }
                description "Enable ACL trap dump globally";
            } // END of dump-trap definition.

            container config {
                description
                    "ACL dump configuration";
                uses flow-acl-dump-config-detail;
            } // END of config-container definition.
            container state {
                config false;
                description
                    "ACL dump state";
                container dump-written-counters {
                    config false;
                    description
                        "ACL dump written counters";
                    uses flow-acl-dump-written-counters;
                } // END of dump-written-counters-container definition.
                uses flow-acl-dump-config-detail;
                uses flow-acl-dump-status;
            } // END of state-container definition.
        } // End of acl-trap-dump-list
    } // END of flow-acl-dump-config definition.

    grouping  flow-management-grouping {
    description
        "Flow management";
    container flow-management {
        if-feature feature-list:HAVE_POND;
        description
            "Flow management";
        container flows {
            description
                "All flow configuration";
            uses flow-config;
        } // END of flows-container definition.
        container acl-trap-dumps {
            description
                "All flow ACL dump configuration";
            uses flow-acl-dump-config;
        } // END of acl-trap-dumps-container definition.
    } // END of flow-management-container definition.
    } // END of flow-management-grouping definition.


}
