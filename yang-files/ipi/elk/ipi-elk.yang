/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-elk.yang
*
*/

module ipi-elk {

    yang-version 1.1;

    namespace   "http://www.ipinfusion.com/yang/ocnos/ipi-elk";

    prefix "ipi-elk";

    import ietf-inet-types {
        prefix inet;
        revision-date 2013-07-15;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "ELK Beats in OcNOS configurations";


    revision "2023-07-03" {
        description "Added reset instance flag for metricbeat and filebeat single instance object lists";
        reference " 0.2.2.";
    }

    revision "2023-02-03" {
        description "Enclosed the microbeat and filebeat objectlist with container";
        reference " 0.2.1.";
    }

    revision "2022-06-01" {
        description "Updated the yang file with feature";
        reference " 0.1.2.";
    }

    revision "2022-04-22" {
        description "Addressing Review Comments";
        reference " 0.1.1.";
    }

    revision "2022-02-01" {
        description "Initial Version";
        reference " 0.1.0.";
    }

    grouping elk-beats-metricbeat-config {
        description
            "ELK metricbeat configurations";
        leaf ip  {
            type  inet:ipv4-address;
            description "Use this to configure ELK Server IP Address.";
        } // END of ip definition.

        leaf username  {
            type  string {
                length "1..1965";
                pattern "[^?' =,>|]+";
            }
            mandatory true;
            description "Use this to configure ELK server user name";
        } // END of username definition.

        leaf password  {
            type  string {
                length "1..1965";
                pattern "[^?' =,>|]+";
            }
            mandatory true;
            description "Use this to configure ELK server password";
        } // END of password definition.

    } // END of elk-beats-metricbeat-config definition.
    grouping elk-beats-filebeat-config {
        description
            "ELK filebeat configurations";
        leaf ip  {
            type  inet:ipv4-address;
            description "Use this to configure ELK Server IP Address.";
        } // END of ip definition.

        leaf certificate-path  {
            type  string {
                length "1..1965";
                pattern "[^?' =,>|]+";
            }
            description "Used to configure Filebeat server path to certificate file";
        } // END of certificate-path definition.

    } // END of elk-beats-filebeat-config definition.

    grouping  elk-grouping {
    description
        "ELK Beats related operation";
    container elk {
        if-feature feature-list:HAVE_HOSTPD;
        description
            "ELK Beats related operation";
        container metricbeats {
            description
                "Enclosing container for ELK Metricbeat servers";

            list metricbeat {
                key "ip";
                max-elements 1;
                description
                    "ELK Metricbeat Server";
                leaf ip  {
                    type  leafref {
                        path  "../config/ip";
                    }
                    description "Use this to configure ELK Server IP Address.";
                } // END of ip definition.

                container config {
                    description
                        "ELK beats related operation";
                    uses elk-beats-metricbeat-config;
                } // END of config-container definition.
                container state {
                    config false;
                    description
                        "This container defines the ELK server status";
                    uses elk-beats-metricbeat-config;
                } // END of state-container definition.
            } // End of metricbeat-list
        } // END of metricbeats-container definition.
        container filebeats {
            description
                "Enclosing container for ELK Filebeat servers";

            list filebeat {
                key "ip";
                max-elements 1;
                description
                    "ELK Filebeat Server";
                leaf ip  {
                    type  leafref {
                        path  "../config/ip";
                    }
                    description "Use this to configure ELK Server IP Address.";
                } // END of ip definition.

                container config {
                    description
                        "ELK beats related operation";
                    uses elk-beats-filebeat-config;
                } // END of config-container definition.
                container state {
                    config false;
                    description
                        "This container defines the ELK server status";
                    uses elk-beats-filebeat-config;
                } // END of state-container definition.
            } // End of filebeat-list
        } // END of filebeats-container definition.
    } // END of elk-container definition.
    } // END of elk-grouping definition.

    uses elk-grouping;

    rpc elk-metricbeat-service-enable {
        if-feature feature-list:HAVE_HOSTPD;
        description "Use this RPC to enable the metricbeat service";
        input  {
            leaf vrf-name  {
                type string;
                mandatory true;
                description "VRF name associated with this instance.";
            }
        }
    }

    rpc elk-filebeat-service-enable {
        if-feature feature-list:HAVE_HOSTPD;
        description "Use this RPC to enable the filebeat service";
        input  {
            leaf vrf-name  {
                type string;
                mandatory true;
                description "VRF name associated with this instance.";
            }
        }
    }

    rpc elk-metricbeat-service-disable {
        if-feature feature-list:HAVE_HOSTPD;
        description "Use this RPC to disable the metricbeat service";
        input  {
            leaf vrf-name  {
                type string;
                mandatory true;
                description "VRF name associated with this instance.";
            }
        }
    }

    rpc elk-filebeat-service-disable {
        if-feature feature-list:HAVE_HOSTPD;
        description "Use this RPC to disable the filebeat service";
        input  {
            leaf vrf-name  {
                type string;
                mandatory true;
                description "VRF name associated with this instance.";
            }
        }
    }

}
