/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-ospfv3-global.yang
*
*/

submodule ipi-ospfv3-global {

    yang-version 1.1;

    belongs-to  ipi-ospfv3 { prefix ipi-ospfv3; }

    import feature-list {
        prefix feature-list;
        revision-date 2026-09-15;
    }

    import ietf-inet-types {
        prefix inet;
        revision-date 2013-07-15;
    }

    organization
        "IP Infusion Inc.";

    contact
        "Address: 3965 Freedom Circle, Suite 200, Santa Clara, CA 95054
         Phone: +1 408-400-1900
         E-mail: support@ipinfusion.com
         Web: http://www.ipinfusion.com/";

    description
        "Layer-3 OSPFv3 configurations";


    revision "2023-07-25" {
        description "Updated confirmation string for ospfv3-restart-graceful";
        reference " 0.4.0.";
    }

    revision "2023-02-02" {
        description "Updated missing Description";
        reference " 0.3.0.";
    }

    revision "2022-06-01" {
        description "Updated the yang file with feature";
        reference " 0.2.4.";
    }

    revision "2021-10-19" {
        description "Added RPC ospfv3-clear-process-all";
        reference " 0.2.3.";
    }

    revision "2021-09-03" {
        description "Update descriptions of attribute";
        reference " 0.2.2.";
    }

    revision "2021-08-16" {
        description "Added display route on single-line to yang";
        reference " 0.2.1.";
    }

    revision "2021-08-05" {
        description "Graceful restart disable-all-neighbors triggers deletion of disable-all-neighbor when set";
        reference " 0.2.0.";
    }

    revision "2021-06-17" {
        description "Restructured module in accordance with OpenConfig style";
        reference " 0.1.0.";
    }

    grouping ospfv3-graceful-restart-helper-config {
        description
            "Grouping for OSPFv3 graceful restart helper configuration data";
        leaf max-grace-period  {
            // when " !ipi-ospfv3:ospfv3/global/graceful-restart/helper/config/disable-all-neighbors ";
            type  uint16 {
                 range "2..1800"  {
                    description "2..1800: Supported range 2 - 1800";
                 }
            }
            units "seconds";
            description "Use this attribute to set the maximum grace period to act as helper.
                        i.e Help only if received grace-period is less than set value.";
        } // END of max-grace-period definition.

        leaf disable-all-neighbors  {
            // when " !ipi-ospfv3:ospfv3/global/graceful-restart/helper/config/max-grace-period ";
            type  empty;
            description "Use this attribute to set disable acting as helper for all neighbors.";
        } // END of disable-all-neighbors definition.

        leaf-list disable-neighbor  {
            // when " !ipi-ospfv3:ospfv3/global/graceful-restart/helper/config/disable-all-neighbors ";
            type  inet:ipv4-address;
            description "Use this attribute to set disable acting as helper for specified
                        neighbor.";
        } // END of disable-neighbor definition.

    } // END of ospfv3-graceful-restart-helper-config definition.
    grouping ospfv3-graceful-restart-helper-top {
        description
            "Grouping for OSPFv3 graceful restart helper";
        container helper {
            description
                "Configuration data for OSPFv3 graceful restart helper";
            container config {
                description
                    "Configuration data for OSPFv3 graceful restart helper";
                uses ospfv3-graceful-restart-helper-config;
            } // END of config-container definition.
            container state {
                config false;
                description
                    "Operational state data for OSPFv3 graceful restart helper";
                uses ospfv3-graceful-restart-helper-config;
            } // END of state-container definition.
        } // END of helper-container definition.
    } // END of ospfv3-graceful-restart-helper-top definition.
    grouping ospfv3-graceful-restart-config {
        description
            "Grouping for OSPFv3 graceful restart configuration data";
        leaf grace-period  {
            type  uint16 {
                 range "2..1800"  {
                    description "2..1800: Supported range 2 - 1800";
                 }
            }
            units "seconds";
            default "120";
            description "Use this attribute to enable the graceful restart feature and set the
                        grace period for restarting the router";
        } // END of grace-period definition.

        leaf controlled-restarts-only  {
            type  empty;
            description "Use this attribute to enable the graceful restart controlled restarts
                        only for the router";
        } // END of controlled-restarts-only definition.

    } // END of ospfv3-graceful-restart-config definition.
    grouping ospfv3-graceful-restart-top {
        description
            "Grouping for OSPFv3 graceful restart";
        container graceful-restart {
            if-feature feature-list:HAVE_RESTART;
            description
                "Configuration data for OSPFv3 graceful restart";
            container config {
                description
                    "Configuration data for OSPFv3 graceful restart";
                uses ospfv3-graceful-restart-config;
            } // END of config-container definition.
            container state {
                config false;
                description
                    "Operational state data for OSPFv3 graceful restart";
                uses ospfv3-graceful-restart-config;
            } // END of state-container definition.
            uses ospfv3-graceful-restart-helper-top;
        } // END of graceful-restart-container definition.
    } // END of ospfv3-graceful-restart-top definition.
    grouping ospfv3-global-config {
        description
            "Grouping for OSPFv3 global configuration data";
        leaf display-route-on-single-line  {
            type  empty;
            description "Use this attribute to display the output of the show ipv6 ospf route
                        command with each route entry in a singleline.";
        } // END of display-route-on-single-line definition.

    } // END of ospfv3-global-config definition.
    grouping ospfv3-global-top {
        description
            "Grouping for OSPFv3 global";
        container global {
            description
                "Configuration data for OSPFv3 global";
            container config {
                description
                    "Configuration data for OSPFv3 global";
                uses ospfv3-global-config;
            } // END of config-container definition.
            container state {
                config false;
                description
                    "Operational state data for OSPFv3 global";
                uses ospfv3-global-config;
            } // END of state-container definition.
            uses ospfv3-graceful-restart-top;
        } // END of global-container definition.
    } // END of ospfv3-global-top definition.


}
