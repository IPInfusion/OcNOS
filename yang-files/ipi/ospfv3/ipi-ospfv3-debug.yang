/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-ospfv3-debug.yang
*
*/

submodule ipi-ospfv3-debug {

    yang-version 1.1;

    belongs-to  ipi-ospfv3 { prefix ipi-ospfv3; }

    import feature-list {
        prefix feature-list;
        revision-date 2026-09-15;
    }

    import ipi-ospfv3-types {
        prefix ipi-ospfv3-types;
        revision-date 2024-09-05;
    }

    import cml-data-types {
        prefix cml-data-types;
        revision-date 2026-05-15;
    }

    organization
        "IP Infusion Inc.";

    contact
        "Address: 3965 Freedom Circle, Suite 200, Santa Clara, CA 95054
         Phone: +1 408-400-1900
         E-mail: support@ipinfusion.com
         Web: http://www.ipinfusion.com/";

    description
        "Layer-3 OSPFv3 debug configurations";


    revision "2023-02-02" {
        description "Updated missing Description";
        reference " 0.3.0.";
    }

    revision "2022-09-09" {
        description "Fixed db-sync debug ospf all bug";
        reference " 0.2.3.";
    }

    revision "2022-08-10" {
        description "Debug hierarchy change";
        reference " 0.2.2.";
    }

    revision "2022-08-05" {
        description "BGP-LS Support for OSPFv3-Bug fix";
        reference " 0.2.1.";
    }

    revision "2022-07-30" {
        description "BGP-LS Support for OSPFv3";
        reference " 0.2.0.";
    }

    revision "2022-06-01" {
        description "Updated the yang file with feature";
        reference " 0.1.3.";
    }

    revision "2022-02-09" {
        description "Added When tag constraints for 'debug' container";
        reference " 0.3.1.";
    }

    revision "2021-09-01" {
        description "Fixed command to enable all debugging after partial configuration";
        reference " 0.1.2.";
    }

    revision "2021-08-13" {
        description "Added container to debug packet";
        reference " 0.1.1.";
    }

    revision "2021-06-17" {
        description "Restructured module in accordance with OpenConfig style";
        reference " 0.1.0.";
    }

    grouping ospfv3-debug-config {
        description
            "Grouping for OSPFv3 debug configuration data";
        leaf bfd  {
            if-feature feature-list:HAVE_BFD;
            type  empty;
            description "Bidirectional Forwarding Detection (BFD)";
        } // END of bfd definition.

        leaf retransmission  {
            type  empty;
            description "OSPFv3 retransmission information";
        } // END of retransmission definition.

        leaf dist-ls  {
            if-feature feature-list:HAVE_BGP_LS;
            type  empty;
            description "Use this attribute to enable OSPF distribute linkstate details debug.";
        } // END of dist-ls definition.

        leaf events  {
            type  ipi-ospfv3-types:ospfv3_debug_event_t;
            description "OSPFv3 events information";
        } // END of events definition.

        leaf ifsm  {
            type  ipi-ospfv3-types:ospfv3_debug_ifsm_t;
            description "Use this attribute to enable OSPFv3 Interface State Machine debug";
        } // END of ifsm definition.

        leaf lfa  {
            if-feature feature-list:HAVE_OSPF6_LFA;
            type  empty;
            description "Use this attribute to enable OSPFv3 LFA route install details debug";
        } // END of lfa definition.

        leaf lsa  {
            type  ipi-ospfv3-types:ospfv3_debug_lsa_t;
            description "Use this attribute to enable OSPFv3 Link State Advertisement debug";
        } // END of lsa definition.

        leaf nfsm  {
            type  ipi-ospfv3-types:ospfv3_debug_nfsm_t;
            description "Use this attribute to enable OSPFv3 Neighbor State Machine debug";
        } // END of nfsm definition.

        leaf nsm  {
            type  ipi-ospfv3-types:ospfv3_debug_nsm_t;
            description "Use this attribute to enable OSPFv3 NSM information debug";
        } // END of nsm definition.

        leaf rib  {
            if-feature feature-list:HAVE_RIBD;
            type  ipi-ospfv3-types:ospfv3_debug_rib_t;
            description "Use this attribute to enable OSPFv3 RIB information debug";
        } // END of rib definition.

        leaf route  {
            type  ipi-ospfv3-types:ospfv3_debug_route_t;
            description "Use this attribute to enable OSPFv3 route information debug";
        } // END of route definition.

        leaf packet-hello  {
            type  ipi-ospfv3-types:ospfv3_debug_packet_options_t;
            description "OSPFv3 Hello";
        } // END of packet-hello definition.

        leaf packet-dd  {
            type  ipi-ospfv3-types:ospfv3_debug_packet_options_t;
            description "OSPFv3 Database Description";
        } // END of packet-dd definition.

        leaf packet-ls-request  {
            type  ipi-ospfv3-types:ospfv3_debug_packet_options_t;
            description "OSPFv3 Link State Request";
        } // END of packet-ls-request definition.

        leaf packet-ls-update  {
            type  ipi-ospfv3-types:ospfv3_debug_packet_options_t;
            description "OSPFv3 Link State Update";
        } // END of packet-ls-update definition.

        leaf packet-ls-ack  {
            type  ipi-ospfv3-types:ospfv3_debug_packet_options_t;
            description "OSPFv3 Link State Acknowledgment";
        } // END of packet-ls-ack definition.

    } // END of ospfv3-debug-config definition.
    grouping ospfv3-debug-terminal-state {
        description
            "Grouping for OSPFv3 debug state for exec mode";
        container terminal-debug-status {
            config false;
            description
                "Runtime attributes for terminal debug";
            leaf bfd  {
                if-feature feature-list:HAVE_BFD;
                type  cml-data-types:cml_on_off_t;
                description "Bidirectional Forwarding Detection (BFD)";
            } // END of bfd definition.

            leaf retransmission  {
                type  cml-data-types:cml_on_off_t;
                description "OSPFv3 Debug retransmission information";
            } // END of retransmission definition.

            leaf dist-ls  {
                if-feature feature-list:HAVE_BGP_LS;
                type  empty;
                description "Use this attribute to enable OSPFv3 distribute linkstate details
                            debug.";
            } // END of dist-ls definition.

            leaf events  {
                type  ipi-ospfv3-types:ospfv3_debug_event_t;
                description "OSPFv3 events information";
            } // END of events definition.

            leaf ifsm  {
                type  ipi-ospfv3-types:ospfv3_debug_ifsm_t;
                description "Use this attribute to enable OSPFv3 Interface State Machine debug";
            } // END of ifsm definition.

            leaf lfa  {
                if-feature feature-list:HAVE_OSPF6_LFA;
                type  cml-data-types:cml_on_off_t;
                description "Use this attribute to enable OSPFv3 LFA route install details debug";
            } // END of lfa definition.

            leaf lsa  {
                type  ipi-ospfv3-types:ospfv3_debug_lsa_t;
                description "Use this attribute to enable OSPFv3 Link State Advertisement debug";
            } // END of lsa definition.

            leaf nfsm  {
                type  ipi-ospfv3-types:ospfv3_debug_nfsm_t;
                description "Use this attribute to enable OSPFv3 Neighbor State Machine debug";
            } // END of nfsm definition.

            leaf nsm  {
                type  ipi-ospfv3-types:ospfv3_debug_nsm_t;
                description "Use this attribute to enable OSPFv3 NSM information debug";
            } // END of nsm definition.

            leaf rib  {
                if-feature feature-list:HAVE_RIBD;
                type  ipi-ospfv3-types:ospfv3_debug_rib_t;
                description "Use this attribute to enable OSPFv3 RIB information debug";
            } // END of rib definition.

            leaf route  {
                type  ipi-ospfv3-types:ospfv3_debug_route_t;
                description "Use this attribute to enable OSPFv3 route information debug";
            } // END of route definition.

            leaf packet-hello  {
                type  ipi-ospfv3-types:ospfv3_debug_packet_options_t;
                description "OSPFv3 Hello";
            } // END of packet-hello definition.

            leaf packet-dd  {
                type  ipi-ospfv3-types:ospfv3_debug_packet_options_t;
                description "OSPFv3 Database Description";
            } // END of packet-dd definition.

            leaf packet-ls-request  {
                type  ipi-ospfv3-types:ospfv3_debug_packet_options_t;
                description "OSPFv3 Link State Request";
            } // END of packet-ls-request definition.

            leaf packet-ls-update  {
                type  ipi-ospfv3-types:ospfv3_debug_packet_options_t;
                description "OSPFv3 Link State Update";
            } // END of packet-ls-update definition.

            leaf packet-ls-ack  {
                type  ipi-ospfv3-types:ospfv3_debug_packet_options_t;
                description "OSPFv3 Link State Acknowledgment";
            } // END of packet-ls-ack definition.

        } // END of terminal-debug-status-container definition.
    } // END of ospfv3-debug-terminal-state definition.
    grouping ospfv3-debug-top {
        description
            "Grouping for OSPFv3 debug";
        container debug {
            description
                "Configuration data for OSPFv3 debug";
            container config {
                description
                    "Configuration data for OSPFv3 debug";
                uses ospfv3-debug-config;
            } // END of config-container definition.
            container state {
                config false;
                description
                    "Operational state data for OSPFv3 debug";
                uses ospfv3-debug-config;
                uses ospfv3-debug-terminal-state;
            } // END of state-container definition.
        } // END of debug-container definition.
    } // END of ospfv3-debug-top definition.


}
