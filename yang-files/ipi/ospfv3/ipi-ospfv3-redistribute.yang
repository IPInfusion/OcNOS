/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-ospfv3-redistribute.yang
*
*/

submodule ipi-ospfv3-redistribute {

    yang-version 1.1;

    belongs-to  ipi-ospfv3 { prefix ipi-ospfv3; }

    import ipi-ospfv3-types {
        prefix ipi-ospfv3-types;
        revision-date 2024-09-05;
    }

    include ipi-ospfv3-distribute-list { revision-date 2022-06-01;}
    organization
        "IP Infusion Inc.";

    contact
        "Address: 3965 Freedom Circle, Suite 200, Santa Clara, CA 95054
         Phone: +1 408-400-1900
         E-mail: support@ipinfusion.com
         Web: http://www.ipinfusion.com/";

    description
        "Layer-3 OSPFv3 configurations";


    revision "2022-06-01" {
        description "Updated the yang file with feature";
        reference " 0.1.3.";
    }

    revision "2021-09-03" {
        description "Update descriptions of attribute";
        reference " 0.1.2.";
    }

    revision "2021-06-17" {
        description "Restructured module in accordance with OpenConfig style";
        reference " 0.1.0.";
    }

    grouping ospfv3-redistribute-common-config {
        description
            "Grouping for OSPFv3 redistribute common configuration data";
        leaf metric  {
            type  uint32 {
                 range "0..16777214"  {
                    description "0..16777214: Supported range 0 - 16777214";
                 }
            }
            default "1";
            description "Use this attribute to inform the value of the metric for OSPFv3
                        default route.";
        } // END of metric definition.

        leaf metric-type  {
            type  ipi-ospfv3-types:ospfv3_metric_type_t;
            default "2";
            description "Use this attribute to inform the type of the metric for OSPFv3 default
                        route.";
        } // END of metric-type definition.

        leaf route-map  {
            type  string {
                length "1..1965";
                pattern "[^?' =,>|]+";
            }
            description "Use this attributes to import routes from other routing protocols, or
                        from another OSPF instance, into OSPFv3 AS-external-LSAs.";
        } // END of route-map definition.

        leaf route-tag  {
            type  uint32 {
                 range "0..4294967295"  {
                    description "0..4294967295: Supported range 0 - 4294967295";
                 }
            }
            default "0";
            description "Use this attribute to specify the route tag.";
        } // END of route-tag definition.

    } // END of ospfv3-redistribute-common-config definition.
    grouping ospfv3-address-family-redistribute-ospf-process-config {
        description
            "Grouping for OSPFv3 redistribute for address family OSPF process
                        configuration data";
        leaf ospfv2-process-id  {
            type  uint16 {
                 range "0..65535"  {
                    description "0..65535: Supported range 0 - 65535";
                 }
            }
            description "Use this attribute to filter networks in routing updates.";
        } // END of ospfv2-process-id definition.

    } // END of ospfv3-address-family-redistribute-ospf-process-config definition.
    grouping ospfv3-address-family-redistribute-ospf-process-top {
        description
            "Grouping for OSPFv3 redistribute for address family OSPF process";
        container ospf-processes {
            description
                "Configuration data for OSPFv3 redistribute OSPF process";

            list ospf-process {
                key "ospfv2-process-id";
                description
                    "List of OSPFv3 redistribute OSPF process";
                leaf ospfv2-process-id  {
                    type  leafref {
                        path  "../config/ospfv2-process-id";
                    }
                    description "Use this attribute to specify OSPF routes.";
                } // END of ospfv2-process-id definition.

                container config {
                    description
                        "Configuration data for OSPFv3 redistribute  for address familyOSPF
                                process";
                    uses ospfv3-address-family-redistribute-ospf-process-config;
                    uses ospfv3-redistribute-common-config;
                } // END of config-container definition.
                container state {
                    config false;
                    description
                        "Operational state data for OSPFv3 redistribute for address family OSPF
                                process";
                    uses ospfv3-address-family-redistribute-ospf-process-config;
                    uses ospfv3-redistribute-common-config;
                } // END of state-container definition.
            } // End of ospf-process-list
        } // END of ospf-processes-container definition.
    } // END of ospfv3-address-family-redistribute-ospf-process-top definition.
    grouping ospfv3-address-family-redistribute-routing-protocol-config {
        description
            "Grouping for OSPFv3 redistribute protocol for address family
                        configuration data";
        leaf protocol-af  {
            type  ipi-ospfv3-types:ospfv3_af_route_source_type_t;
            description "Use this attribute to import routes from other routing protocols, or
                        from another OSPF instance, into OSPFv3 ASexternal-LSAs.";
        } // END of protocol-af definition.

    } // END of ospfv3-address-family-redistribute-routing-protocol-config definition.
    grouping ospfv3-address-family-redistribute-routing-protocol-top {
        description
            "Grouping for OSPFv3 redistribute routing protocols for address family";
        container routing-protocols {
            description
                "Configuration data for OSPFv3 redistribute routing protocols";

            list routing-protocol {
                key "protocol-af";
                description
                    "List of OSPFv3 redistribute routing protocols";
                leaf protocol-af  {
                    type  leafref {
                        path  "../config/protocol-af";
                    }
                    description "Use this attribute to import routes from other routing protocols, or
                                from another OSPF instance, into OSPFv3 ASexternal-LSAs.";
                } // END of protocol-af definition.

                container config {
                    description
                        "Configuration data for OSPFv3 redistribute routing protocols";
                    uses ospfv3-address-family-redistribute-routing-protocol-config;
                    uses ospfv3-redistribute-common-config;
                } // END of config-container definition.
                container state {
                    config false;
                    description
                        "Operational state data for OSPFv3 redistribute routing protocols";
                    uses ospfv3-address-family-redistribute-routing-protocol-config;
                    uses ospfv3-redistribute-common-config;
                } // END of state-container definition.
            } // End of routing-protocol-list
        } // END of routing-protocols-container definition.
    } // END of ospfv3-address-family-redistribute-routing-protocol-top definition.
    grouping ospfv3-address-family-redistribute-top {
        description
            "Grouping for OSPFv3 redistribute for address family";
        container redistribute {
            description
                "Container for OSPFv3 redistribute";
            uses ospfv3-address-family-redistribute-routing-protocol-top;
            uses ospfv3-address-family-redistribute-ospf-process-top;
        } // END of redistribute-container definition.
    } // END of ospfv3-address-family-redistribute-top definition.
    grouping ospfv3-redistribute-ospf-process-config {
        description
            "Grouping for OSPFv3 redistribute OSPF process configuration data";
        leaf ospf-process-id  {
            type  ipi-ospfv3-types:ospfv3_string_t;
            description "Use this attribute to filter networks in routing updates.";
        } // END of ospf-process-id definition.

    } // END of ospfv3-redistribute-ospf-process-config definition.
    grouping ospfv3-redistribute-ospf-process-top {
        description
            "Grouping for OSPFv3 redistribute OSPF process";
        container ospf-processes {
            description
                "Configuration data for OSPFv3 redistribute OSPF process";

            list ospf-process {
                key "ospf-process-id";
                description
                    "List of OSPFv3 redistribute OSPF process";
                leaf ospf-process-id  {
                    type  leafref {
                        path  "../config/ospf-process-id";
                    }
                    description "Use this attribute to specify OSPF routes.";
                } // END of ospf-process-id definition.

                container config {
                    description
                        "Configuration data for OSPFv3 redistribute OSPF process";
                    uses ospfv3-redistribute-ospf-process-config;
                    uses ospfv3-redistribute-common-config;
                } // END of config-container definition.
                container state {
                    config false;
                    description
                        "Operational state data for OSPFv3 redistribute OSPF process";
                    uses ospfv3-redistribute-ospf-process-config;
                    uses ospfv3-redistribute-common-config;
                } // END of state-container definition.
            } // End of ospf-process-list
        } // END of ospf-processes-container definition.
    } // END of ospfv3-redistribute-ospf-process-top definition.
    grouping ospfv3-redistribute-protocol-config {
        description
            "Grouping for OSPFv3 redistribute protocol configuration data";
        leaf protocol  {
            type  ipi-ospfv3-types:ospfv3_route_source_type_t;
            description "Use this attribute to import routes from other routing protocols, or
                        from another OSPF instance, into OSPFv3 ASexternal-LSAs.";
        } // END of protocol definition.

    } // END of ospfv3-redistribute-protocol-config definition.
    grouping ospfv3-redistribute-routing-protocol-top {
        description
            "Grouping for OSPFv3 redistribute routing protocols";
        container routing-protocols {
            description
                "Configuration data for OSPFv3 redistribute routing protocols";

            list routing-protocol {
                key "protocol";
                description
                    "List of OSPFv3 redistribute routing protocols";
                leaf protocol  {
                    type  leafref {
                        path  "../config/protocol";
                    }
                    description "Use this attribute to import routes from other routing protocols, or
                                from another OSPF instance, into OSPFv3 ASexternal-LSAs.";
                } // END of protocol definition.

                container config {
                    description
                        "Configuration data for OSPFv3 redistribute routing protocols";
                    uses ospfv3-redistribute-protocol-config;
                    uses ospfv3-redistribute-common-config;
                } // END of config-container definition.
                container state {
                    config false;
                    description
                        "Operational state data for OSPFv3 redistribute routing protocols";
                    uses ospfv3-redistribute-protocol-config;
                    uses ospfv3-redistribute-common-config;
                } // END of state-container definition.
            } // End of routing-protocol-list
        } // END of routing-protocols-container definition.
    } // END of ospfv3-redistribute-routing-protocol-top definition.
    grouping ospfv3-redistribute-top {
        description
            "Grouping for OSPFv3 redistribute";
        container redistribute {
            description
                "Container for OSPFv3 redistribute";
            uses ospfv3-redistribute-routing-protocol-top;
            uses ospfv3-redistribute-ospf-process-top;
        } // END of redistribute-container definition.
    } // END of ospfv3-redistribute-top definition.


}
