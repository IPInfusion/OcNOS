/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-ospfv3-distribute-list.yang
*
*/

submodule ipi-ospfv3-distribute-list {

    yang-version 1.1;

    belongs-to  ipi-ospfv3 { prefix ipi-ospfv3; }

    import feature-list {
        prefix feature-list;
        revision-date 2026-09-15;
    }

    import ipi-ospfv3-types {
        prefix ipi-ospfv3-types;
        revision-date 2024-09-05;
    }

    organization
        "IP Infusion Inc.";

    contact
        "Address: 3965 Freedom Circle, Suite 200, Santa Clara, CA 95054
         Phone: +1 408-400-1900
         E-mail: support@ipinfusion.com
         Web: http://www.ipinfusion.com/";

    description
        "Layer-3 OSPFv3 configurations";


    revision "2022-06-01" {
        description "Updated the yang file with feature";
        reference " 0.1.2.";
    }

    revision "2021-09-03" {
        description "Update descriptions of attribute";
        reference " 0.1.1.";
    }

    revision "2021-06-17" {
        description "Restructured module in accordance with OpenConfig style";
        reference " 0.1.0.";
    }

    grouping ospfv3-filter-out-process-config {
        description
            "Grouping for OSPFv3 distribute list filter-out OSPF proccess
                        configuration data";
        leaf ospf-process-id  {
            type  ipi-ospfv3-types:ospfv3_string_t;
            description "Use this attribute to filter networks in routing updates.";
        } // END of ospf-process-id definition.

        leaf access-control-list  {
            type  string {
                length "1..64";
                pattern "[^?' =,>|]+";
            }
            mandatory true;
            description "Use this attribute to set the access control list name in distribution
                        list.";
        } // END of access-control-list definition.

    } // END of ospfv3-filter-out-process-config definition.
    grouping ospfv3-filter-out-process-top {
        description
            "Grouping for OSPFv3 distribute list filter-out OSPF proccess";
        container ospf-processes {
            description
                "Configuration data for OSPFv3 process references";

            list ospf-process {
            // when " ipi-ospfv3:ospfv3/processes/process/distribute-list/filter-out/ospf-processes/ospf-process/config/access-control-list ";
                key "ospf-process-id";
                description
                    "List of OSPFv3 processes reference";
                leaf ospf-process-id  {
                    type  leafref {
                        path  "../config/ospf-process-id";
                    }
                    description "Use this attribute to filter networks in routing updates.";
                } // END of ospf-process-id definition.

                container config {
                    description
                        "Configuration data for OSPFv3 process reference";
                    uses ospfv3-filter-out-process-config;
                } // END of config-container definition.
                container state {
                    config false;
                    description
                        "Operational state data for OSPFv3 process reference";
                    uses ospfv3-filter-out-process-config;
                } // END of state-container definition.
            } // End of ospf-process-list
        } // END of ospf-processes-container definition.
    } // END of ospfv3-filter-out-process-top definition.
    grouping ospfv3-filter-out-routing-protocols-config {
        description
            "Grouping for OSPFv3 distribute list filter-out routing protocols
                        configuration data";
        leaf protocol  {
            type  ipi-ospfv3-types:ospfv3_route_source_type_t;
            description "Use this attribute to import routes from other routing protocols, or
                        from another OSPF instance, into OSPFv3 ASexternal-LSAs.";
        } // END of protocol definition.

        leaf access-control-list  {
            type  string {
                length "1..64";
                pattern "[^?' =,>|]+";
            }
            mandatory true;
            description "Use this attribute to set the access control list name in distribution
                        list.";
        } // END of access-control-list definition.

    } // END of ospfv3-filter-out-routing-protocols-config definition.
    grouping ospfv3-filter-out-routing-protocols-top {
        description
            "Grouping for OSPFv3 distribute list filter-out routing protocols";
        container routing-protocols {
            description
                "Configuration data for OSPFv3 distribute list filter-out routing
                        protocols";

            list routing-protocol {
            // when " ipi-ospfv3:ospfv3/processes/process/distribute-list/filter-out/routing-protocols/routing-protocol/config/access-control-list ";
                key "protocol";
                description
                    "List of OSPFv3 distribute list filter-out routing protocols";
                leaf protocol  {
                    type  leafref {
                        path  "../config/protocol";
                    }
                    description "Use this attribute to import routes from other routing protocols, or
                                from another OSPF instance, into OSPFv3 ASexternal-LSAs.";
                } // END of protocol definition.

                container config {
                    description
                        "Configuration data for OSPFv3 distribute list filter-out outing
                                protocols";
                    uses ospfv3-filter-out-routing-protocols-config;
                } // END of config-container definition.
                container state {
                    config false;
                    description
                        "Operational state data for OSPFv3 distribute list filter-out outing
                                protocols";
                    uses ospfv3-filter-out-routing-protocols-config;
                } // END of state-container definition.
            } // End of routing-protocol-list
        } // END of routing-protocols-container definition.
    } // END of ospfv3-filter-out-routing-protocols-top definition.
    grouping ospfv3-distribute-list-filter-out-top {
        description
            "Grouping for OSPFv3 distribute list filter-out";
        container filter-out {
            description
                "Configuration data for OSPFv3 distribute list filter-out";
            uses ospfv3-filter-out-routing-protocols-top;
            uses ospfv3-filter-out-process-top;
        } // END of filter-out-container definition.
    } // END of ospfv3-distribute-list-filter-out-top definition.
    grouping ospfv3-distribute-list-filter-in-config {
        description
            "Grouping for OSPFv3 distribute list filter-in configuration data";
        leaf access-control-list  {
            type  string {
                length "1..64";
                pattern "[^?' =,>|]+";
            }
            description "Use this attribute to set the access control list name in distribution
                        list.";
        } // END of access-control-list definition.

    } // END of ospfv3-distribute-list-filter-in-config definition.
    grouping ospfv3-distribute-list-filter-in-top {
        description
            "Grouping for OSPFv3 distribute list filter-in";
        container filter-in {
            description
                "Container for OSPFv3 distribute list filter-in";
            container config {
                description
                    "Configuration data for OSPFv3 distribute list filter-in";
                uses ospfv3-distribute-list-filter-in-config;
            } // END of config-container definition.
            container state {
                config false;
                description
                    "Operational state data for OSPFv3 distribute list filter-in";
                uses ospfv3-distribute-list-filter-in-config;
            } // END of state-container definition.
        } // END of filter-in-container definition.
    } // END of ospfv3-distribute-list-filter-in-top definition.
    grouping ospfv3-distribute-list-top {
        description
            "Grouping for OSPFv3 distribute list";
        container distribute-list {
            if-feature feature-list:HAVE_ACL;
            description
                "Configuration data for OSPFv3 distribute lists";
            uses ospfv3-distribute-list-filter-in-top;
            uses ospfv3-distribute-list-filter-out-top;
        } // END of distribute-list-container definition.
    } // END of ospfv3-distribute-list-top definition.


}
