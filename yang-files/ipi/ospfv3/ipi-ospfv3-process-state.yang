/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-ospfv3-process-state.yang
*
*/

submodule ipi-ospfv3-process-state {

    yang-version 1.1;

    belongs-to  ipi-ospfv3 { prefix ipi-ospfv3; }

    import feature-list {
        prefix feature-list;
        revision-date 2026-09-15;
    }

    import cml-data-types {
        prefix cml-data-types;
        revision-date 2026-05-15;
    }

    import ietf-yang-types {
        prefix yang;
        revision-date 2013-07-15;
    }

    import ietf-inet-types {
        prefix inet;
        revision-date 2013-07-15;
    }

    import ipi-ospfv3-types {
        prefix ipi-ospfv3-types;
        revision-date 2024-09-05;
    }

    organization
        "IP Infusion Inc.";

    contact
        "Address: 3965 Freedom Circle, Suite 200, Santa Clara, CA 95054
         Phone: +1 408-400-1900
         E-mail: support@ipinfusion.com
         Web: http://www.ipinfusion.com/";

    description
        "Layer-3 OSPFv3 process state";


    revision "2022-07-31" {
        description "Stop using inet:ipv4-prefix and inet:ipv6-prefix due to Cisco NSO iterop";
        reference " 0.2.0.";
    }

    revision "2022-06-01" {
        description "Updated the yang file with feature";
        reference " 0.1.4.";
    }

    revision "2021-09-29" {
        description "Changed discard-connection to empty";
        reference " 0.1.3.";
    }

    revision "2021-09-03" {
        description "Update descriptions of attribute";
        reference " 0.1.2.";
    }

    revision "2021-07-05" {
        description "Changed inter-router, external and not-so-stubby-area structure";
        reference " 0.1.1.";
    }

    revision "2021-06-17" {
        description "Restructured module in accordance with OpenConfig style";
        reference " 0.1.0.";
    }

    grouping ospfv3-next-hop-state {
        description
            "Grouping for OSPFv3 process next hop state";
        leaf address  {
            type  inet:ip-address;
            description "This attribute returns the address value.";
        } // END of address definition.

        leaf interface-name  {
            type  string {
                length "1..1965";
                pattern "[^?' =,>|]+";
            }
            description "This attribute returns the interface name value.";
        } // END of interface-name definition.

        leaf transit-area  {
            type  empty;
            description "This attribute returns the transit area value.";
        } // END of transit-area definition.

        leaf area-id  {
            type  inet:ipv4-address;
            description "This attribute returns the area id value.";
        } // END of area-id definition.

        leaf connected  {
            type  empty;
            description "This attribute returns the connected value.";
        } // END of connected definition.

        leaf invalid  {
            type  empty;
            description "This attribute returns the invalid value.";
        } // END of invalid definition.

        leaf code  {
            type  string {
                length "1..1965";
                pattern "[^?' =,>|]+";
            }
            description "This attribute returns the code value.";
        } // END of code definition.

    } // END of ospfv3-next-hop-state definition.
    grouping ospfv3-route-path-state {
        description
            "Grouping for OSPFv3 process route path state";
        leaf type  {
            type  ipi-ospfv3-types:ospfv3_path_type_t;
            description "This attribute returns the type value.";
        } // END of type definition.

        leaf code  {
            type  string {
                length "1..1965";
                pattern "[^?' =,>|]+";
            }
            description "This attribute returns the code value.";
        } // END of code definition.

        leaf discard-connection  {
            type  empty;
            description "This attribute returns the discard connection value.";
        } // END of discard-connection definition.

        leaf cost  {
            type  uint32;
            description "This attribute returns the cost value.";
        } // END of cost definition.

        leaf type-2-cost  {
            type  uint32;
            description "This attribute returns the type 2 cost value.";
        } // END of type-2-cost definition.

        leaf path-flags  {
            type  ipi-ospfv3-types:ospfv3_path_flags_t;
            description "This attribute returns the path flags value.";
        } // END of path-flags definition.

    } // END of ospfv3-route-path-state definition.
    grouping ospfv3-route-state-attr {
        description
            "Grouping for OSPFv3 process route state attr";
        leaf prefix  {
            type  cml-data-types:cml_ip_prefix_t;
            description "This attribute returns the prefix value.";
        } // END of prefix definition.

        leaf distance  {
            type  uint8;
            description "This attribute returns the distance value.";
        } // END of distance definition.

    } // END of ospfv3-route-state-attr definition.
    grouping ospfv3-lsa-nssa-state {
        description
            "Grouping for OSPFv3 process lsa nssa state";
        leaf nssa-index  {
            type  uint32;
            description "This attribute returns the nssa index value.";
        } // END of nssa-index definition.

        leaf referenced-ls-id  {
            type  string {
                length "1..1965";
                pattern "[^?' =,>|]+";
            }
            description "This attribute returns the referenced ls id value.";
        } // END of referenced-ls-id definition.

        leaf referenced-ls-type  {
            type  uint32;
            description "This attribute returns the referenced ls type value.";
        } // END of referenced-ls-type definition.

        leaf route-tag  {
            type  uint32;
            description "This attribute returns the route tag value.";
        } // END of route-tag definition.

        leaf forwarding-address  {
            type  inet:ip-address;
            description "This attribute returns the forwarding address value.";
        } // END of forwarding-address definition.

        leaf metric  {
            type  uint16;
            description "This attribute returns the metric value.";
        } // END of metric definition.

        leaf metric-type  {
            type  ipi-ospfv3-types:ospfv3_ls_metric_type_t;
            description "This attribute returns the metric type value.";
        } // END of metric-type definition.

    } // END of ospfv3-lsa-nssa-state definition.
    grouping ospfv3-lsa-external-state {
        description
            "Grouping for OSPFv3 process lsa external state";
        leaf external-index  {
            type  uint32;
            description "This attribute returns the external index value.";
        } // END of external-index definition.

        leaf referenced-ls-id  {
            type  string {
                length "1..1965";
                pattern "[^?' =,>|]+";
            }
            description "This attribute returns the referenced ls id value.";
        } // END of referenced-ls-id definition.

        leaf referenced-ls-type  {
            type  uint32;
            description "This attribute returns the referenced ls type value.";
        } // END of referenced-ls-type definition.

        leaf route-tag  {
            type  uint32;
            description "This attribute returns the route tag value.";
        } // END of route-tag definition.

        leaf forwarding-address  {
            type  inet:ip-address;
            description "This attribute returns the forwarding address value.";
        } // END of forwarding-address definition.

        leaf metric  {
            type  uint16;
            description "This attribute returns the metric value.";
        } // END of metric definition.

        leaf metric-type  {
            type  ipi-ospfv3-types:ospfv3_ls_metric_type_t;
            description "This attribute returns the metric type value.";
        } // END of metric-type definition.

    } // END of ospfv3-lsa-external-state definition.
    grouping ospfv3-lsa-inter-prefix-state {
        description
            "Grouping for OSPFv3 process lsa inter prefix state";
        leaf inter-prefix-index  {
            type  uint32;
            description "This attribute returns the inter prefix index value.";
        } // END of inter-prefix-index definition.

        leaf area-id  {
            type  inet:ipv4-address;
            description "This attribute returns the area id value.";
        } // END of area-id definition.

    } // END of ospfv3-lsa-inter-prefix-state definition.
    grouping ospfv3-lsa-inter-router-state {
        description
            "Grouping for OSPFv3 process lsa inter router state";
        leaf inter-router-index  {
            type  uint32;
            description "This attribute returns the inter prefix index value.";
        } // END of inter-router-index definition.

        leaf area-id  {
            type  inet:ipv4-address;
            description "This attribute returns the area id value.";
        } // END of area-id definition.

        leaf router-id  {
            type  inet:ipv4-address;
            description "This attribute returns the router id value.";
        } // END of router-id definition.

    } // END of ospfv3-lsa-inter-router-state definition.
    grouping ospfv3-lsa-prefix-metric-state {
        description
            "Grouping for OSPFv3 process lsa prefix metric state";
        leaf metric  {
            type  uint16;
            description "This attribute returns the metric value.";
        } // END of metric definition.

    } // END of ospfv3-lsa-prefix-metric-state definition.
    grouping ospfv3-lsa-intra-prefix-state {
        description
            "Grouping for OSPFv3 process lsa intra prefix state";
        leaf intra-prefix-index  {
            type  uint32;
            description "This attribute returns the intra prefix index value.";
        } // END of intra-prefix-index definition.

        leaf area-id  {
            type  inet:ipv4-address;
            description "This attribute returns the area id value.";
        } // END of area-id definition.

        leaf referenced-ls-advertising-router  {
            type  inet:ipv4-address;
            description "This attribute returns the referenced ls advertising router value.";
        } // END of referenced-ls-advertising-router definition.

        leaf referenced-ls-id  {
            type  string {
                length "1..1965";
                pattern "[^?' =,>|]+";
            }
            description "This attribute returns the referenced ls id value.";
        } // END of referenced-ls-id definition.

        leaf referenced-ls-type  {
            type  string {
                length "1..1965";
                pattern "[^?' =,>|]+";
            }
            description "This attribute returns the referenced ls type value.";
        } // END of referenced-ls-type definition.

        leaf prefix-count  {
            type  uint32;
            description "This attribute returns the prefix count value.";
        } // END of prefix-count definition.

    } // END of ospfv3-lsa-intra-prefix-state definition.
    grouping ospfv3-lsa-network-state {
        description
            "Grouping for OSPFv3 process lsa network state";
        leaf-list attached-router  {
            type  inet:ipv4-address;
            description "This attribute returns the attached router value.";
        } // END of attached-router definition.

    } // END of ospfv3-lsa-network-state definition.
    grouping ospfv3-lsa-router-link-state {
        description
            "Grouping for OSPFv3 process lsa router link state";
        leaf link-index  {
            type  uint32;
            description "This attribute returns the link index value.";
        } // END of link-index definition.

        leaf neighbor-router-id  {
            type  inet:ipv4-address;
            description "This attribute returns the neighbor router id value.";
        } // END of neighbor-router-id definition.

        leaf neighbor-interface-id  {
            type  uint32;
            description "This attribute returns the neighbor interface id value.";
        } // END of neighbor-interface-id definition.

        leaf interface-id  {
            type  uint32;
            description "This attribute returns the interface id value.";
        } // END of interface-id definition.

        leaf metric  {
            type  uint16;
            description "This attribute returns the metric value.";
        } // END of metric definition.

        leaf metric-type  {
            type  ipi-ospfv3-types:ospfv3_link_metric_type_t;
            description "This attribute returns the metric type value.";
        } // END of metric-type definition.

    } // END of ospfv3-lsa-router-link-state definition.
    grouping ospfv3-lsa-router-state {
        description
            "Grouping for OSPFv3 process lsa router state";
        leaf router-index  {
            type  uint32;
            description "This attribute returns the router index value.";
        } // END of router-index definition.

        leaf area-id  {
            type  inet:ipv4-address;
            description "This attribute returns the area id value.";
        } // END of area-id definition.

        leaf ls-router-properties  {
            type  ipi-ospfv3-types:ospfv3_router_properties_t;
            description "This attribute returns the ls router properties value.";
        } // END of ls-router-properties definition.

    } // END of ospfv3-lsa-router-state definition.
    grouping ospfv3-lsa-prefix-state {
        description
            "Grouping for OSPFv3 process lsa prefix state";
        leaf prefix  {
            type  cml-data-types:cml_ipv6_prefix_t;
            description "This attribute returns the prefix value.";
        } // END of prefix definition.

        leaf no-unicast-bit  {
            type  empty;
            description "This attribute returns the no unicast bit value.";
        } // END of no-unicast-bit definition.

        leaf prefix-options  {
            type  ipi-ospfv3-types:ospfv3_prefix_options_t;
            description "This attribute returns the prefix options value.";
        } // END of prefix-options definition.

    } // END of ospfv3-lsa-prefix-state definition.
    grouping ospfv3-lsa-header-options-state {
        description
            "Grouping for OSPFv3 process lsa header options state";
        leaf ls-options  {
            type  ipi-ospfv3-types:ospfv3_ls_options_t;
            description "This attribute returns the ls options value.";
        } // END of ls-options definition.

    } // END of ospfv3-lsa-header-options-state definition.
    grouping ospfv3-lsa-link-state {
        description
            "Grouping for OSPFv3 process lsa link state";
        leaf link-index  {
            type  uint32;
            description "This attribute returns the link index value.";
        } // END of link-index definition.

        leaf link-local-address  {
            type  inet:ipv6-address;
            description "This attribute returns the link local address value.";
        } // END of link-local-address definition.

        leaf priority  {
            type  uint8;
            description "This attribute returns the priority value.";
        } // END of priority definition.

        leaf interface-name  {
            type  string {
                length "1..1965";
                pattern "[^?' =,>|]+";
            }
            description "This attribute returns the interface name value.";
        } // END of interface-name definition.

        leaf prefix-count  {
            type  uint32;
            description "This attribute returns the prefix count value.";
        } // END of prefix-count definition.

    } // END of ospfv3-lsa-link-state definition.
    grouping ospfv3-lsa-extra-info-state {
        description
            "Grouping for OSPFv3 process lsa extra info state";
        leaf inter-router  {
            type  empty;
            description "This attribute returns the inter router value.";
        } // END of inter-router definition.

        leaf link-count  {
            type  uint32;
            description "This attribute returns the link count value.";
        } // END of link-count definition.

        leaf referenced-type  {
            type  uint32;
            description "This attribute returns the referenced type value.";
        } // END of referenced-type definition.

    } // END of ospfv3-lsa-extra-info-state definition.
    grouping ospfv3-lsa-header-state {
        description
            "Grouping for OSPFv3 process lsa header state";
        leaf advertising-router  {
            type  inet:ipv4-address;
            description "This attribute returns the advertising router value.";
        } // END of advertising-router definition.

        leaf ls-age  {
            type  uint16;
            description "This attribute returns the ls age value.";
        } // END of ls-age definition.

        leaf ls-type  {
            type  ipi-ospfv3-types:ospfv3_ls_type_t;
            description "This attribute returns the ls type value.";
        } // END of ls-type definition.

        leaf ls-id  {
            type  string {
                length "1..1965";
                pattern "[^?' =,>|]+";
            }
            description "This attribute returns the ls id value.";
        } // END of ls-id definition.

        leaf ls-sequence-number  {
            type  string {
                length "1..1965";
                pattern "[^?' =,>|]+";
            }
            description "This attribute returns the ls sequence number value.";
        } // END of ls-sequence-number definition.

        leaf ls-checksum  {
            type  string {
                length "1..1965";
                pattern "[^?' =,>|]+";
            }
            description "This attribute returns the ls checksum value.";
        } // END of ls-checksum definition.

        leaf ls-length  {
            type  uint16;
            description "This attribute returns the ls length value.";
        } // END of ls-length definition.

    } // END of ospfv3-lsa-header-state definition.
    grouping ospfv3-route-state {
        description
            "Grouping for OSPFv3 process route state database data";

        list route {
            key "prefix";
            config false;
            description
                "List of routes";
            leaf prefix  {
                type  leafref {
                    path  "../state/prefix";
                }
                description "This attribute returns the prefix value.";
            } // END of prefix definition.


            list next-hop {
                key "address";
                config false;
                description
                    "List of next hops for route";
                leaf address  {
                    type  leafref {
                        path  "../state/address";
                    }
                    description "This attribute returns the address value.";
                } // END of address definition.

                container state {
                    config false;
                    description
                        "Operational state data for address of route";
                    uses ospfv3-next-hop-state;
                } // END of state-container definition.
            } // End of next-hop-list
            container state {
                config false;
                description
                    "Operational state data for route";
                uses ospfv3-route-state-attr;
            } // END of state-container definition.
            container route-path {
                config false;
                description
                    "Path of route";
                container state {
                    config false;
                    description
                        "Operational state data for path of route";
                    uses ospfv3-route-path-state;
                } // END of state-container definition.
            } // END of route-path-container definition.
        } // End of route-list
    } // END of ospfv3-route-state definition.
    grouping ospfv3-lsdb-process-state {
        description
            "Grouping for OSPFv3 process link state database data";
        container link-state-database {
            config false;
            description
                "OSPFv3 process link state database data";

            list link {
                key "link-index";
                config false;
                description
                    "List of links for link state database";
                leaf link-index  {
                    type  leafref {
                        path  "../state/link-index";
                    }
                    description "This attribute returns the link value.";
                } // END of link-index definition.


                list lsa-prefix {
                    key "prefix";
                    config false;
                    description
                        "List of lsas for link";
                    leaf prefix  {
                        type  leafref {
                            path  "../state/prefix";
                        }
                        description "This attribute returns the lsa prefix value.";
                    } // END of prefix definition.

                    container state {
                        config false;
                        description
                            "Operational state data for lsa prefix of link";
                        uses ospfv3-lsa-prefix-state;
                    } // END of state-container definition.
                } // End of lsa-prefix-list
                container state {
                    config false;
                    description
                        "Operational state data for links of link state database";
                    uses ospfv3-lsa-link-state;
                    uses ospfv3-lsa-header-state;
                    uses ospfv3-lsa-header-options-state;
                } // END of state-container definition.
            } // End of link-list

            list router {
                key "router-index";
                config false;
                description
                    "List of routers for link state database";
                leaf router-index  {
                    type  leafref {
                        path  "../state/router-index";
                    }
                    description "This attribute returns the router value.";
                } // END of router-index definition.


                list link {
                    key "link-index";
                    config false;
                    description
                        "List of links for router";
                    leaf link-index  {
                        type  leafref {
                            path  "../state/link-index";
                        }
                        description "This attribute returns the link value.";
                    } // END of link-index definition.

                    container state {
                        config false;
                        description
                            "Operational state data for link index of router";
                        uses ospfv3-lsa-router-link-state;
                    } // END of state-container definition.
                } // End of link-list
                container state {
                    config false;
                    description
                        "Operational state data for routers of link state database";
                    uses ospfv3-lsa-router-state;
                    uses ospfv3-lsa-header-state;
                    uses ospfv3-lsa-header-options-state;
                } // END of state-container definition.
            } // End of router-list

            list network {
                key "advertising-router";
                config false;
                description
                    "List of networks for link state database";
                leaf advertising-router  {
                    type  leafref {
                        path  "../state/advertising-router";
                    }
                    description "This attribute returns the advertising router value.";
                } // END of advertising-router definition.

                container state {
                    config false;
                    description
                        "Operational state data for advertising routers of link state database";
                    uses ospfv3-lsa-header-state;
                    uses ospfv3-lsa-header-options-state;
                    uses ospfv3-lsa-network-state;
                } // END of state-container definition.
            } // End of network-list

            list intra-prefix {
                key "intra-prefix-index";
                config false;
                description
                    "List of intra prefixes for link state database";
                leaf intra-prefix-index  {
                    type  leafref {
                        path  "../state/intra-prefix-index";
                    }
                    description "This attribute returns the intra prefix value.";
                } // END of intra-prefix-index definition.


                list lsa-prefix {
                    key "prefix";
                    config false;
                    description
                        "List of lsas for intra prefix";
                    leaf prefix  {
                        type  leafref {
                            path  "../state/prefix";
                        }
                        description "This attribute returns the prefix value.";
                    } // END of prefix definition.

                    container state {
                        config false;
                        description
                            "Operational state data for lsa prefix of intra prefix";
                        uses ospfv3-lsa-prefix-state;
                        uses ospfv3-lsa-prefix-metric-state;
                    } // END of state-container definition.
                } // End of lsa-prefix-list
                container state {
                    config false;
                    description
                        "Operational state data for routers of link state database";
                    uses ospfv3-lsa-intra-prefix-state;
                    uses ospfv3-lsa-header-state;
                } // END of state-container definition.
            } // End of intra-prefix-list

            list inter-prefix {
                key "inter-prefix-index";
                config false;
                description
                    "List of inter prefixes for link state database";
                leaf inter-prefix-index  {
                    type  leafref {
                        path  "../state/inter-prefix-index";
                    }
                    description "This attribute returns the inter prefix index value.";
                } // END of inter-prefix-index definition.


                list lsa-prefix {
                    key "prefix";
                    config false;
                    description
                        "List of lsas for inter prefix";
                    leaf prefix  {
                        type  leafref {
                            path  "../state/prefix";
                        }
                        description "This attribute returns the prefix value.";
                    } // END of prefix definition.

                    container state {
                        config false;
                        description
                            "Operational state data for lsa prefix of inter prefix";
                        uses ospfv3-lsa-prefix-state;
                        uses ospfv3-lsa-prefix-metric-state;
                    } // END of state-container definition.
                } // End of lsa-prefix-list
                container state {
                    config false;
                    description
                        "Operational state data for routers of link state database";
                    uses ospfv3-lsa-inter-prefix-state;
                    uses ospfv3-lsa-header-state;
                } // END of state-container definition.
            } // End of inter-prefix-list

            list inter-router {
                key "inter-router-index";
                config false;
                description
                    "List of inter router for link state database";
                leaf inter-router-index  {
                    type  leafref {
                        path  "../state/inter-router-index";
                    }
                    description "This attribute returns the inter router index value.";
                } // END of inter-router-index definition.

                container state {
                    config false;
                    description
                        "Operational state data for routers of link state database";
                    uses ospfv3-lsa-inter-router-state;
                    uses ospfv3-lsa-header-state;
                    uses ospfv3-lsa-prefix-metric-state;
                    uses ospfv3-lsa-header-options-state;
                } // END of state-container definition.
            } // End of inter-router-list

            list external {
                key "external-index";
                config false;
                description
                    "List of externals for link state database";
                leaf external-index  {
                    type  leafref {
                        path  "../state/external-index";
                    }
                    description "This attribute returns the external value.";
                } // END of external-index definition.


                list lsa-prefix {
                    key "prefix";
                    config false;
                    description
                        "List of lsas for external";
                    leaf prefix  {
                        type  leafref {
                            path  "../state/prefix";
                        }
                        description "This attribute returns the prefix value.";
                    } // END of prefix definition.

                    container state {
                        config false;
                        description
                            "Operational state data for lsa prefix of external";
                        uses ospfv3-lsa-prefix-state;
                    } // END of state-container definition.
                } // End of lsa-prefix-list
                container state {
                    config false;
                    description
                        "Operational state data for routers of link state database";
                    uses ospfv3-lsa-external-state;
                    uses ospfv3-lsa-header-state;
                } // END of state-container definition.
            } // End of external-list

            list not-so-stubby-area {
                key "nssa-index";
                config false;
                description
                    "List of not so stubby areas for link state database";
                leaf nssa-index  {
                    type  leafref {
                        path  "../state/nssa-index";
                    }
                    description "This attribute returns the nssa value.";
                } // END of nssa-index definition.


                list lsa-prefix {
                    key "prefix";
                    config false;
                    description
                        "List of lsas for nssa";
                    leaf prefix  {
                        type  leafref {
                            path  "../state/prefix";
                        }
                        description "This attribute returns the prefix value.";
                    } // END of prefix definition.

                    container state {
                        config false;
                        description
                            "Operational state data for lsa prefix of nssa";
                        uses ospfv3-lsa-prefix-state;
                    } // END of state-container definition.
                } // End of lsa-prefix-list
                container state {
                    config false;
                    description
                        "Operational state data for nssas of link state database";
                    uses ospfv3-lsa-nssa-state;
                    uses ospfv3-lsa-header-state;
                } // END of state-container definition.
            } // End of not-so-stubby-area-list
        } // END of link-state-database-container definition.
    } // END of ospfv3-lsdb-process-state definition.
    grouping ospfv3-process-statistics-state {
        description
            "Grouping for OSPFv3 process statistics state data";
        leaf up-time  {
            type  string {
                length "1..1965";
                pattern "((([0-1]?[0-9])|(2[0-3])):[0-5][0-9]:[0-5][0-9])|([0-9]+d(([0-1][0-9])|(2[0-3]))h[0-5][0-9]m)|([0-9]+w[0-9]+d[0-9]+h)";
            }
            description "This attribute returns the up-time value.";
        } // END of up-time definition.

        leaf database-description-in  {
            type  yang:counter64;
            description "This attribute returns the database-description-in value.";
        } // END of database-description-in definition.

        leaf database-description-out  {
            type  yang:counter64;
            description "This attribute returns the database-description-out value.";
        } // END of database-description-out definition.

        leaf external-lsa-count  {
            type  yang:counter64;
            description "This attribute returns the external-lsa-count value.";
        } // END of external-lsa-count definition.

        leaf external-lsa-checksum  {
            type  string {
                length "1..1965";
                pattern "[^?' =,>|]+";
            }
            description "This attribute returns the external-lsa-checksum value.";
        } // END of external-lsa-checksum definition.

        leaf unknown-lsa-count  {
            type  yang:counter64;
            description "This attribute returns the unknown-lsa-count value.";
        } // END of unknown-lsa-count definition.

        leaf lsa-out  {
            type  yang:counter64;
            description "This attribute returns the lsa-out value.";
        } // END of lsa-out definition.

        leaf lsa-in  {
            type  yang:counter64;
            description "This attribute returns the lsa-in value.";
        } // END of lsa-in definition.

        leaf area-count  {
            type  yang:counter64;
            description "This attribute returns the area-count value.";
        } // END of area-count definition.

    } // END of ospfv3-process-statistics-state definition.
    grouping ospfv3-process-state {
        description
            "Grouping for OSPFv3 process state data";
        leaf dste-enable  {
            if-feature feature-list:HAVE_DSTE;
            type  empty;
            description "This attribute returns the dste-status value.";
        } // END of dste-enable definition.

    } // END of ospfv3-process-state definition.


}
