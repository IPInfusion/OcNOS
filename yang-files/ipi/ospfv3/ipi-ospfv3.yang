/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-ospfv3.yang
*
*/

module ipi-ospfv3 {

    yang-version 1.1;

    namespace   "http://www.ipinfusion.com/yang/ocnos/ipi-ospfv3";

    prefix "ipi-ospfv3";

    import cml-data-types {
        prefix cml-data-types;
        revision-date 2026-05-15;
    }

    import ietf-inet-types {
        prefix inet;
        revision-date 2013-07-15;
    }

    import ipi-network-instance {
        prefix ipi-network-instance;
        revision-date 2026-08-12;
    }

    import ipi-vrf {
        prefix ipi-vrf;
        revision-date 2026-08-12;
    }

    import ipi-ospfv3-types {
        prefix ipi-ospfv3-types;
        revision-date 2024-09-05;
    }

    import feature-list {
        prefix feature-list;
        revision-date 2026-09-15;
    }

    include ipi-ospfv3-address-family { revision-date 2023-01-03;}
    include ipi-ospfv3-area { revision-date 2024-02-05;}
    include ipi-ospfv3-area-state { revision-date 2022-06-01;}
    include ipi-ospfv3-debug { revision-date 2023-02-02;}
    include ipi-ospfv3-distribute-list { revision-date 2022-06-01;}
    include ipi-ospfv3-global { revision-date 2023-07-25;}
    include ipi-ospfv3-process-state { revision-date 2022-07-31;}
    include ipi-ospfv3-redistribute { revision-date 2022-06-01;}
    include ipi-ospfv3-interface { revision-date 2025-09-04;}
    include ipi-ospfv3-interface-state { revision-date 2026-01-20;}
    organization
        "IP Infusion Inc.";

    contact
        "Address: 3965 Freedom Circle, Suite 200, Santa Clara, CA 95054
         Phone: +1 408-400-1900
         E-mail: support@ipinfusion.com
         Web: http://www.ipinfusion.com/";

    description
        "Layer-3 OSPFv3 configurations";


    revision "2026-01-20" {
        description "Updated datatype for state-message as CML_LINE_T";
        reference " 0.7.2.";
    }

    revision "2025-11-07" {
        description "Added include-input-for-unset-as-optional flag in router-id attribute";
        reference " 0.7.1.";
    }

    revision "2025-09-04" {
        description "Removed EVPN_IRB_IF_MODE while configuring IRB interface";
        reference " 0.7.0.";
    }

    revision "2024-10-23" {
        description "Added if-feature for enable-bfd attribute in cli-command";
        reference " 0.6.2.";
    }

    revision "2024-09-05" {
        description "Updated if-feature for datatype OSPFV3_ROUTE_SOURCE_TYPE_T";
        reference " 0.6.1.";
    }

    revision "2024-07-03" {
        description "Removed skip-dependency-validation from when tag for not-advertise,all-tag and translate-tag";
        reference " 0.6.0.";
    }

    revision "2024-06-04" {
        description "Updated when tag all-interfaces to passive-interface object-list";
        reference " 0.5.2.";
    }

    revision "2024-03-30" {
        description "Updated implicit delete tag for processes/process/passive-interfaces/config ";
        reference " 0.5.1.";
    }

    revision "2024-02-05" {
        description "Updated cli-commmand for area/nssa/config ";
        reference " 0.5.0.";
    }

    revision "2023-09-29" {
        description "Modified the validate function for ipv6 router ospf cli-command for irb interface";
        reference " 0.7.0.";
    }

    revision "2023-08-30" {
        description "Added OSPFv3 Domain ID support";
        reference " 0.6.3.";
    }

    revision "2023-08-23" {
        description "CLI Commands for EVPN IRB Interface";
        reference " 0.6.2.";
    }

    revision "2023-02-02" {
        description "Updated missing Description";
        reference " 0.6.0.";
    }

    revision "2023-01-03" {
        description "Removing implicit_delete from ospfv3 address-family area/config and address-range/config";
        reference " 0.5.0.";
    }

    revision "2022-09-09" {
        description "Fixed db-sync debug ospf all bug";
        reference " 0.4.7.";
    }

    revision "2022-08-23" {
        description "Updated helpstring for interface cost";
        reference " 0.4.6.";
    }

    revision "2022-08-22" {
        description "UT bug fixes in BGP-LS";
        reference " 0.4.5.";
    }

    revision "2022-08-17" {
        description "UT bug fixes in BGP-LS";
        reference " 0.4.4.";
    }

    revision "2022-08-11" {
        description "Added 'if-feature' tag for autoPopulate of attribute 'traffic-engineering'";
        reference " 0.4.1.";
    }

    revision "2022-08-10" {
        description "Debug hierarchy change";
        reference " 0.4.3.";
    }

    revision "2022-08-05" {
        description "BGP-LS Support for OSPFv3-Debug bug fix";
        reference " 0.4.2.";
    }

    revision "2022-08-01" {
        description "BGP-LS Support for OSPFv3";
        reference " 0.4.1.";
    }

    revision "2022-07-31" {
        description "Stop using inet:ipv4-prefix and inet:ipv6-prefix due to Cisco NSO iterop";
        reference " 0.4.0.";
    }

    revision "2022-07-30" {
        description "Updated when expressions in yang";
        reference " 0.4.0.";
    }

    revision "2022-07-12" {
        description "Fixed revision history refs.";
        reference " 0.3.12.";
    }

    revision "2022-06-27" {
        description "Updated SPI range in ipsec module";
        reference " 0.3.11.";
    }

    revision "2022-06-24" {
        description "Internal fixes handling transform-set from ip-sec module";
        reference " 0.3.10.";
    }

    revision "2022-06-13" {
        description "Removed sa-lifetime attribute from ip-sec module";
        reference " 0.3.9.";
    }

    revision "2022-06-07" {
        description "Changed the dependent module config IPsec Transform-set ESP Configuration data container to a presence container";
        reference " 0.3.8.";
    }

    revision "2022-06-01" {
        description "Updated the yang file with feature";
        reference " 0.3.7.";
    }

    revision "2022-05-04" {
        description "Added authentication-cryptomap attribute for IPSec authentication support of OSPFv3";
        reference " 0.3.6.";
    }

    revision "2022-02-09" {
        description "Added When tag constraints for 'debug' container";
        reference " 0.6.1.";
    }

    revision "2021-11-17" {
        description "Added interface passive mode support";
        reference " 0.3.5.";
    }

    revision "2021-10-27" {
        description "Stub and nsssa config container presence, and enable leaf mandatory";
        reference " 0.3.4.";
    }

    revision "2021-10-19" {
        description "Added RPC ospfv3-clear-process-all";
        reference " 0.3.3.";
    }

    revision "2021-10-12" {
        description "Changed discard-connection to empty";
        reference " 0.3.2.";
    }

    revision "2021-10-06" {
        description "Removed area route-map leafref";
        reference " 0.3.1.";
    }

    revision "2021-09-17" {
        description "Added interface-name leaf inside interface/config";
        reference " 0.3.0.";
    }

    revision "2021-09-07" {
        description "Set route-map max length to 63 chars";
        reference " 0.2.9.";
    }

    revision "2021-09-01" {
        description "Fixed command to enable all debugging after partial configuration";
        reference " 0.2.8.";
    }

    revision "2021-08-19" {
        description "ospfv3-id leaf max length updated to 254";
        reference " 0.2.7.";
    }

    revision "2021-08-16" {
        description "Added display route on single-line to yang";
        reference " 0.2.6.";
    }

    revision "2021-08-13" {
        description "Added possibility to select send, receive or detail for debug packet";
        reference " 0.2.5.";
    }

    revision "2021-08-05" {
        description "Graceful restart disable-all-neighbors triggers deletion of disable-all-neighbor when set";
        reference " 0.2.4.";
    }

    revision "2021-07-26" {
        description "Notification support";
        reference " 0.2.3.";
    }

    revision "2021-07-11" {
        description "Hide cspf config since it is not available in OcNOS 5.0";
        reference " 0.2.2.";
    }

    revision "2021-07-05" {
        description "Changed inter-router, external and not-so-stubby-area structure";
        reference " 0.2.1.";
    }

    revision "2021-06-17" {
        description "Restructured module in accordance with OpenConfig style";
        reference " 0.2.0.";
    }

    revision "2018-06-21" {
        description "Initial Version";
        reference " 0.1.0.";
    }

    grouping ospfv3-default-information-config {
        description
            "Grouping for OSPF default information configuration data";
        leaf originate  {
            type  empty;
            description "Use this attribute to create a default external route into an OSPF
                        routing domain. The system acts like an
                        Autonomous System Boundary Router (ASBR) when you use the
                        default-information originate command
                        to redistribute routes into an OSPF routing domain. An ASBR does not
                        by default generate a default
                        route into the OSPF routing domain";
        } // END of originate definition.

        leaf always-advertise-default-route  {
            // when " ipi-ospfv3:ospfv3/processes/process/default-information/config/originate ";
            type  empty;
            description "Use this attribute to dvertise the default route regardless of whether
                        there is a default route.";
        } // END of always-advertise-default-route definition.

        leaf metric  {
            // when " ipi-ospfv3:ospfv3/processes/process/default-information/config/originate ";
            type  uint32 {
                 range "0..16777214"  {
                    description "0..16777214: Supported range 0 - 16777214";
                 }
            }
            default "20";
            description "Use this attribute to set the OSPF area with default metric.";
        } // END of metric definition.

        leaf metric-type  {
            // when " ipi-ospfv3:ospfv3/processes/process/default-information/config/originate ";
            type  ipi-ospfv3-types:ospfv3_metric_type_t;
            default "2";
            description "Use this attribute to set the OSPF area default metric type.";
        } // END of metric-type definition.

        leaf route-map  {
            // when " ipi-ospfv3:ospfv3/processes/process/default-information/config/originate ";
            type  string {
                length "1..63";
                pattern "[^?' =,>|]+";
            }
            description "Use this attribute to set route-map instance.";
        } // END of route-map definition.

    } // END of ospfv3-default-information-config definition.
    grouping ospfv3-default-information-top {
        description
            "Grouping for OSPF default information";
        container default-information {
            description
                "Container for OSPF default information";
            container config {
                description
                    "Configuration data for default information";
                uses ospfv3-default-information-config;
            } // END of config-container definition.
            container state {
                config false;
                description
                    "Operational state data for default information";
                uses ospfv3-default-information-config;
            } // END of state-container definition.
        } // END of default-information-container definition.
    } // END of ospfv3-default-information-top definition.
    grouping ospfv3-summary-address-config {
        description
            "Grouping for OSPFv3 summary address configuration data";
        leaf address  {
            type  cml-data-types:cml_ipv6_prefix_t;
            description "Use this attribute to summarize or suppress external routes with the
                        specified address range.";
        } // END of address definition.

        leaf not-advertise  {
            type  empty;
            description "Use this attribute to set or unset not advertise to summarize or
                        suppress external routes with the specified address range.";
        } // END of not-advertise definition.

        leaf translate-tag  {
            type  uint32 {
                 range "0..4294967295"  {
                    description "0..4294967295: Supported range 0 - 4294967295";
                 }
            }
            default "0";
            description "Use this attribute to set or unset translate tag to external routes
                        with the specified address range.";
        } // END of translate-tag definition.

        leaf all-tag  {
            type  uint32 {
                 range "0..4294967295"  {
                    description "0..4294967295: Supported range 0 - 4294967295";
                 }
            }
            default "0";
            description "Use this attribute to set or unset all tag to summarize or suppress
                        external routes with the specified address range.";
        } // END of all-tag definition.

    } // END of ospfv3-summary-address-config definition.
    grouping ospfv3-summary-address-top {
        description
            "Grouping for OSPFv3 summary address";
        container summary-addresses {
            description
                "Configuration data for OSPFv3 summary addresses";

            list summary-address {
                key "address";
                description
                    "List of OSPFv3 summary addresses";
                leaf address  {
                    type  leafref {
                        path  "../config/address";
                    }
                    description "Use this attribute to summarize or suppress external routes with the
                                specified address range.";
                } // END of address definition.

                container config {
                    description
                        "Configuration data for OSPFv3 summary address";
                    uses ospfv3-summary-address-config;
                } // END of config-container definition.
                container state {
                    config false;
                    description
                        "Operational state data for OSPFv3 summary address";
                    uses ospfv3-summary-address-config;
                } // END of state-container definition.
            } // End of summary-address-list
        } // END of summary-addresses-container definition.
    } // END of ospfv3-summary-address-top definition.
    grouping ospfv3-passive-interface-name-config {
        description
            "Grouping for OSPFv3 passive interface configuration data";
        leaf name  {
            type  string {
                length "1..33";
                pattern "[^?' =,>|]+";
            }
            description "Use this attribute to set interface as passive or not.";
        } // END of name definition.

        leaf passive-mode  {
            type  ipi-ospfv3-types:ospfv3_passive_mode_t;
            mandatory true;
            description "Use this attribute to define the passive mode.";
        } // END of passive-mode definition.

    } // END of ospfv3-passive-interface-name-config definition.
    grouping ospfv3-passive-interface-name-top {
        description
            "Grouping for OSPFv3 passive interface name";

        list passive-interface {
            key "name";
            description
                "List of OSPFv3 passive interfaces";
            leaf name  {
                type  leafref {
                    path  "../config/name";
                }
                description "Use this attribute to set interface as passive or not.";
            } // END of name definition.

            container config {
                description
                    "Configuration data for OSPFv3 passive interface";
                uses ospfv3-passive-interface-name-config;
            } // END of config-container definition.
            container state {
                config false;
                description
                    "Operational data for OSPFv3 passive interface";
                uses ospfv3-passive-interface-name-config;
            } // END of state-container definition.
        } // End of passive-interface-list
    } // END of ospfv3-passive-interface-name-top definition.
    grouping ospfv3-passive-interfaces-config {
        description
            "Grouping for OSPFv3 passive interface configuration data";
        leaf all-interfaces  {
            type  empty;
            description "Use this attribute to set all interfaces as passive";
        } // END of all-interfaces definition.

    } // END of ospfv3-passive-interfaces-config definition.
    grouping ospfv3-passive-interface-top {
        description
            "Grouping for OSPFv3 passive interface";
        container passive-interfaces {
            description
                "Configuration data for OSPFv3 passive interface";
            container config {
                description
                    "Configuration data for OSPFv3 passive interface";
                uses ospfv3-passive-interfaces-config;
            } // END of config-container definition.
            container state {
                config false;
                description
                    "Operational state data for OSPFv3 passive interface";
                uses ospfv3-passive-interfaces-config;
            } // END of state-container definition.
            uses ospfv3-passive-interface-name-top;
        } // END of passive-interfaces-container definition.
    } // END of ospfv3-passive-interface-top definition.
    grouping ospfv3-timers-spf-config {
        description
            "Grouping for OSPFv3 timers Shortest Path First (SPF) configuration
                        data";
        leaf exponential-min-delay  {
            type  uint32 {
                 range "0..2147483647"  {
                    description "0..2147483647: Supported range 0 - 2147483647";
                 }
            }
            units "milliseconds";
            mandatory true;
            description "Use this attribute to set the minimum SPF hold delay time in
                        milliseconds";
        } // END of exponential-min-delay definition.

        leaf exponential-max-delay  {
            type  uint32 {
                 range "0..2147483647"  {
                    description "0..2147483647: Supported range 0 - 2147483647";
                 }
            }
            units "milliseconds";
            mandatory true;
            description "Use this attribute to set the maximum SPF hold delay time in
                        milliseconds";
        } // END of exponential-max-delay definition.

    } // END of ospfv3-timers-spf-config definition.
    grouping ospfv3-timers-spf-top {
        description
            "Grouping for OSPFv3 timers Shortest Path First (SPF)";
        container spf {
            description
                "Configuration data for OSPFv3 timers Shortest Path First (SPF)";
            container config {
                presence "yes";
                description
                    "Configuration data for OSPFv3 timers Shortest Path First (SPF)";
                uses ospfv3-timers-spf-config;
            } // END of config-container definition.
            container state {
                config false;
                description
                    "Operational state data for OSPFv3 timers Shortest Path First (SPF)";
                uses ospfv3-timers-spf-config;
            } // END of state-container definition.
        } // END of spf-container definition.
    } // END of ospfv3-timers-spf-top definition.
    grouping ospfv3-timers-top {
        description
            "Grouping for OSPFv3 timers";
        container timers {
            description
                "Configuration data for OSPFv3 timers";
            uses ospfv3-timers-spf-top;
        } // END of timers-container definition.
    } // END of ospfv3-timers-top definition.
    grouping ospfv3-segment-routing-srv6-top {
        description
            "Grouping for OSPFv3 SRv6 Segment routing";
        container ospfv3-srv6 {
            when " /ipi-ospfv3:ospfv3/ipi-ospfv3:processes/ipi-ospfv3:process/ipi-ospfv3:ospfv3-id ";
            if-feature feature-list:HAVE_SRV6;
            description
                "SRv6 container for segment routing";
            container config {
                presence "yes";
                description
                    "Segment routing SRv6 configuration and other CLIs inside srv6";
                uses ospfv3-srv6-config;
            } // END of config-container definition.
            container state {
                config false;
                description
                    "Segment routing V6 runtime parameters";
                uses ospfv3-srv6-config;
            } // END of state-container definition.
            uses ospfv3-srv6-locator-lists-config;
        } // END of ospfv3-srv6-container definition.
    } // END of ospfv3-segment-routing-srv6-top definition.
    grouping ospfv3-srv6-locator-lists-config {
        description
            "Locator";
        container locator-lists {
            when " /ipi-ospfv3:ospfv3/ipi-ospfv3:processes/ipi-ospfv3:process/ipi-ospfv3:ospfv3-srv6/ipi-ospfv3:config/ipi-ospfv3:ospf6SRv6enable ";
            description
                "List for locator-lists";

            list locator-list {
                key "ospf6SRv6LocatorName";
                description
                    "Properties of a locator list";
                leaf ospf6SRv6LocatorName  {
                    type  leafref {
                        path  "../config/ospf6SRv6LocatorName";
                    }
                    description "Locator name";
                } // END of ospf6SRv6LocatorName definition.

                container config {
                    description
                        "Config parameters for locator-list configuration";
                    uses ospfv3-locator-name-config;
                } // END of config-container definition.
                container state {
                    config false;
                    description
                        "Operational state for locator-list configuration";
                    uses ospfv3-locator-name-config;
                } // END of state-container definition.
            } // End of locator-list-list
        } // END of locator-lists-container definition.
    } // END of ospfv3-srv6-locator-lists-config definition.
    grouping ospfv3-srv6-config {
        description
            "config attribute for SRv6 for SR Policies";
        leaf ospf6SRv6enable  {
            type  empty;
            mandatory true;
            description "Enable segment routing v6";
        } // END of ospf6SRv6enable definition.

    } // END of ospfv3-srv6-config definition.
    grouping ospfv3-locator-name-config {
        description
            "config attribute for SRv6 for SR Policies";
        leaf ospf6SRv6LocatorName  {
            type  string {
                length "1..1965";
                pattern "[^?' =,>|]+";
            }
            description "Locator name";
        } // END of ospf6SRv6LocatorName definition.

    } // END of ospfv3-locator-name-config definition.
    grouping ospfv3-lfa-fast-reroute-tie-break-config {
        description
            "Grouping for OSPFv3 Loop Free Alternate (LFA) fast reroute tie-break
                        configuration data";
        leaf method  {
            type  ipi-ospfv3-types:ospfv3_frr_tie_break_method_t;
            description "Use this attribute to set the tie-breaking policy for selecting a fast
                        reroute repair path. A priority is assigned to each typeof repair
                        path.";
        } // END of method definition.

        leaf priority  {
            type  uint8 {
                 range "1..4"  {
                    description "1..4: Supported range 1 - 4";
                 }
            }
            mandatory true;
            description "Use this attribute to set the priority to the tie-breaking policy.";
        } // END of priority definition.

    } // END of ospfv3-lfa-fast-reroute-tie-break-config definition.
    grouping ospfv3-lfa-fast-reroute-tie-break-top {
        description
            "Grouping for OSPFv3 Loop Free Alternate (LFA) fast reroute tie-break";
        container tie-breakes {
            description
                "Configuration data for OSPFv3 tie-breaks";

            list tie-break {
                key "method";
                max-elements 4;
                description
                    "List of OSPFv3 tie-breaks";
                leaf method  {
                    type  leafref {
                        path  "../config/method";
                    }
                    description "Use this attribute to set the tie-breaking policy for selecting a fast
                                reroute repair path. A priority is assigned to each typeof repair
                                path.";
                } // END of method definition.

                container config {
                    description
                        "Configuration data for OSPFv3 Loop Free Alternate (LFA) fast reroute
                                tie-break";
                    uses ospfv3-lfa-fast-reroute-tie-break-config;
                } // END of config-container definition.
                container state {
                    config false;
                    description
                        "Operational state data for OSPFv3 Loop Free Alternate (LFA) fast
                                reroute tie-break";
                    uses ospfv3-lfa-fast-reroute-tie-break-config;
                } // END of state-container definition.
            } // End of tie-break-list
        } // END of tie-breakes-container definition.
    } // END of ospfv3-lfa-fast-reroute-tie-break-top definition.
    grouping ospfv3-lfa-fast-reroute-config {
        description
            "Grouping for OSPFv3  Loop Free Alternate (LFA) fast reroute
                        configuration data";
        leaf keep-all-paths  {
            type  empty;
            description "Use this attribute to enable fast rerouting on all OSPFv3 interfaces.";
        } // END of keep-all-paths definition.

    } // END of ospfv3-lfa-fast-reroute-config definition.
    grouping ospfv3-lfa-fast-reroute-top {
        description
            "Grouping for OSPFv3 Loop Free Alternate (LFA) fast reroute";
        container fast-reroute {
            description
                "Configuration data for OSPFv3 Loop Free Alternate (LFA) fast reroute";
            container config {
                description
                    "Configuration data for OSPFv3 Loop Free Alternate (LFA) fast reroute";
                uses ospfv3-lfa-fast-reroute-config;
            } // END of config-container definition.
            container state {
                config false;
                description
                    "Operational state data for OSPFv3 Loop Free Alternate (LFA) fast
                            reroute";
                uses ospfv3-lfa-fast-reroute-config;
            } // END of state-container definition.
            uses ospfv3-lfa-fast-reroute-tie-break-top;
        } // END of fast-reroute-container definition.
    } // END of ospfv3-lfa-fast-reroute-top definition.
    grouping ospfv3-lfa-top {
        description
            "Grouping for OSPFv3 Loop Free Alternate (LFA)";
        container lfa {
            if-feature feature-list:HAVE_OSPF6_LFA;
            description
                "Configuration data for OSPFv3 Loop Free Alternate (LFA)";
            uses ospfv3-lfa-fast-reroute-top;
        } // END of lfa-container definition.
    } // END of ospfv3-lfa-top definition.
    grouping ospfv3-cspf-config {
        description
            "Grouping for OSPFv3 Constrained Shortest Path First (CSPF)
                        configuration data";
    } // END of ospfv3-cspf-config definition.
    grouping ospfv3-cspf-top {
        description
            "Grouping for OSPFv3 Constrained Shortest Path First (CSPF)";
    } // END of ospfv3-cspf-top definition.
    grouping ospfv3-capability-config {
        description
            "Grouping for OSPFv3 capability configuration data";
        leaf traffic-engineering  {
            if-feature feature-list:HAVE_OSPF6_TE;
            type  empty;
            description "OSPFv3 Traffic Engineering extension";
        } // END of traffic-engineering definition.

        leaf disable-graceful-restart  {
            if-feature feature-list:HAVE_RESTART;
            type  empty;
            description "Graceful OSPFv3 Restart";
        } // END of disable-graceful-restart definition.

    } // END of ospfv3-capability-config definition.
    grouping ospfv3-capability-top {
        description
            "Grouping for OSPFv3 capability";
        container capability {
            description
                "OSPFv3 capability";
            container config {
                description
                    "Configuration data for OSPFv3 capability";
                uses ospfv3-capability-config;
            } // END of config-container definition.
            container state {
                config false;
                description
                    "Operational state data for OSPFv3 capability";
                uses ospfv3-capability-config;
            } // END of state-container definition.
        } // END of capability-container definition.
    } // END of ospfv3-capability-top definition.
    grouping ospfv3-administrative-distance-config {
        description
            "Grouping for OSPFv3 administrative distance configuration data";
        leaf default-distance  {
            type  uint8 {
                 range "1..254"  {
                    description "1..254: Supported range 1 - 254";
                 }
            }
            default "110";
            description "Default administrative distance value";
        } // END of default-distance definition.

    } // END of ospfv3-administrative-distance-config definition.
    grouping ospfv3-administrative-distance-ospf-config {
        description
            "Grouping for OSPFv3 administrative distance configuration data";
        leaf intra-area-distance  {
            type  uint8 {
                 range "1..254"  {
                    description "1..254: Supported range 1 - 254";
                 }
            }
            default "110";
            description "Administrative distance for intra-area routes";
        } // END of intra-area-distance definition.

        leaf inter-area-distance  {
            type  uint8 {
                 range "1..254"  {
                    description "1..254: Supported range 1 - 254";
                 }
            }
            default "110";
            description "Administrative distance for inter-area routes";
        } // END of inter-area-distance definition.

        leaf external-routes-distance  {
            type  uint8 {
                 range "1..254"  {
                    description "1..254: Supported range 1 - 254";
                 }
            }
            default "110";
            description "Administrative distance for external routes";
        } // END of external-routes-distance definition.

    } // END of ospfv3-administrative-distance-ospf-config definition.
    grouping ospfv3-administrative-distance-ospf-top {
        description
            "Grouping for OSPFv3 administrative distance";
        container ospf {
            description
                "Configuration data for OSPFv3 administrative distance";
            container config {
                description
                    "Configuration data for OSPFv3 administrative distance";
                uses ospfv3-administrative-distance-ospf-config;
            } // END of config-container definition.
            container state {
                config false;
                description
                    "Operational data for OSPFv3 administrative distance";
                uses ospfv3-administrative-distance-ospf-config;
            } // END of state-container definition.
        } // END of ospf-container definition.
    } // END of ospfv3-administrative-distance-ospf-top definition.
    grouping ospfv3-administrative-distance-top {
        description
            "Grouping for OSPFv3 administrative distance";
        container administrative-distance {
            description
                "Configuration data for OSPFv3 administrative distance";
            container config {
                description
                    "Configuration data for OSPFv3 administrative distance";
                uses ospfv3-administrative-distance-config;
            } // END of config-container definition.
            container state {
                config false;
                description
                    "Operational state data for OSPFv3 administrative distance";
                uses ospfv3-administrative-distance-config;
            } // END of state-container definition.
            uses ospfv3-administrative-distance-ospf-top;
        } // END of administrative-distance-container definition.
    } // END of ospfv3-administrative-distance-top definition.
    grouping ospfv3-process-config {
        description
            "Grouping for OSPFv3 process configuration data";
        leaf ospfv3-id  {
            type  ipi-ospfv3-types:ospfv3_string_t {
                length "0..254";
            }
            description "Use this attribute to set the OSPFv3 process ID";
        } // END of ospfv3-id definition.

        leaf vrf-name  {
            type  leafref {
                path  "/ipi-network-instance:network-instances/ipi-network-instance:network-instance/ipi-vrf:vrf/ipi-vrf:config/ipi-vrf:vrf-name";
            }
            mandatory true;
            description "VRF Name to associate with this instance";
        } // END of vrf-name definition.

        leaf router-id  {
            type  inet:ipv4-address;
            description "Use this attribute to set a router ID for the OSPFv3 process.
                        Configure each router OSPFv3 with an unique router ID";
        } // END of router-id definition.

        leaf flood-reduction  {
            if-feature feature-list:HAVE_OSPF6_OD;
            type  empty;
            description "Use this attribute is used to enable DoNotAge option in LSA sent on
                        all OSPFv3 interfaces.";
        } // END of flood-reduction definition.

        leaf bfd-enable-all-interfaces  {
            if-feature feature-list:HAVE_BFD;
            type  empty;
            description "Use this attribute to enable Bidirectional Forwarding Detection (BFD)
                        on all interfaces.";
        } // END of bfd-enable-all-interfaces definition.

        leaf database-summary  {
            type  empty;
            description "Use this attribute to enable the database summary list optimization
                        for OSPFv3.";
        } // END of database-summary definition.

        leaf area-border-type  {
            type  ipi-ospfv3-types:ospfv3_abr_type_t;
            default "cisco";
            description "Use this attribute to set an OSPFv3 Area Border Router (ABR) type.";
        } // END of area-border-type definition.

        leaf default-metric  {
            type  uint32 {
                 range "1..16777214"  {
                    description "1..16777214: Supported range 1 - 16777214";
                 }
            }
            default "20";
            description "Use this attribute to set a default metric for OSPFv3.";
        } // END of default-metric definition.

        leaf shutdown  {
            type  empty;
            description "Use this attribute to specify an OSPFv3 shutdown";
        } // END of shutdown definition.

        leaf log-adjacency-changes  {
            type  ipi-ospfv3-types:ospfv3_log_adj_opt_t;
            default "brief";
            description "Use this attribute for the the router to send a SYSLOG message when an
                        OSPFv3 neighbor goes up or down.";
        } // END of log-adjacency-changes definition.

        leaf reference-bandwidth  {
            type  uint32 {
                 range "1..4294967"  {
                    description "1..4294967: Supported range 1 - 4294967";
                 }
            }
            units "mbps";
            default "100";
            description "Use this attribute to control how OSPFv3 calculates the default metric
                        for the interface.";
        } // END of reference-bandwidth definition.

        leaf max-database-descriptors  {
            type  uint16 {
                 range "1..65535"  {
                    description "1..65535: Supported range 1 - 65535";
                 }
            }
            default "5";
            description "Use this attribute to limit the number of Database Descriptors (DD)
                        that can be processed concurrently.";
        } // END of max-database-descriptors definition.

    } // END of ospfv3-process-config definition.
    grouping ospfv3-process-top {
        description
            "Grouping for OSPFv3 process";
        container processes {
            description
                "Configuration data for OSPFv3 processes";

            list process {
                key "ospfv3-id";
                description
                    "List of OSPFv3 processes";
                leaf ospfv3-id  {
                    type  leafref {
                        path  "../config/ospfv3-id";
                    }
                    description "Use this attribute to set the OSPFv3 process ID";
                } // END of ospfv3-id definition.

                container config {
                    description
                        "Configuration data for OSPFv3 process";
                    uses ospfv3-process-config;
                } // END of config-container definition.
                container state {
                    config false;
                    description
                        "Operational state data for OSPFv3 process";
                    container statistics {
                        config false;
                        description
                            "OSPFv3 statistics status";
                        uses ospfv3-process-statistics-state;
                    } // END of statistics-container definition.
                    uses ospfv3-process-config;
                    uses ospfv3-process-state;
                } // END of state-container definition.
                uses ospfv3-lsdb-process-state;
                uses ospfv3-route-state;
                uses ospfv3-administrative-distance-top;
                uses ospfv3-capability-top;
                uses ospfv3-cspf-top;
                uses ospfv3-lfa-top;
                uses ospfv3-timers-top;
                uses ospfv3-segment-routing-srv6-top;
                uses ospfv3-passive-interface-top;
                uses ospfv3-summary-address-top;
                uses ospfv3-default-information-top;
                uses ospfv3-distribute-list-top;
                uses ospfv3-redistribute-top;
                uses ospfv3-area-top;
                uses ospfv3-area-info-state;
                uses ospfv3-address-family-top;
                uses ospfv3-originate-lsa;
                uses ospfv3-tx-retransmit;
                uses ospfv3-neighbor-state-change;
                uses ospfv3-distribute-top;
            } // End of process-list
        } // END of processes-container definition.
    } // END of ospfv3-process-top definition.
    grouping ospfv3-originate-lsa {
        description
            "Notification for OSPFv3 originate LSA";
        container originate-lsa {
            config false;
            description
                "OSPFv3 originate LSA";
            leaf router-id  {
                type  leafref {
                    path  "/ospfv3/processes/process/state/router-id";
                }
                config false;
                description "The originator router ID.";
            } // END of router-id definition.

            leaf lsdb-area-id  {
                type  inet:ipv4-address;
                config false;
                description "Link State Database (LSDB) area ID.";
            } // END of lsdb-area-id definition.

            leaf lsdb-type  {
                type  uint32;
                config false;
                description "Link State Database (LSDB) Type.";
            } // END of lsdb-type definition.

            leaf lsdb-id  {
                type  uint32;
                config false;
                description "Link State Database (LSDB) ID.";
            } // END of lsdb-id definition.

            leaf lsdb-router-id  {
                type  inet:ipv4-address;
                config false;
                description "Link State Database (LSDB) router ID.";
            } // END of lsdb-router-id definition.

        } // END of originate-lsa-container definition.
    } // END of ospfv3-originate-lsa definition.
    grouping ospfv3-tx-retransmit {
        description
            "ospfv3-tx-retransmit";
        container tx-retransmit {
            config false;
            description
                "OSPFv3 TX retransmit";
            leaf router-id  {
                type  inet:ipv4-address;
                description "Originating router ID.";
            } // END of router-id definition.

            leaf if-index  {
                type  int32;
                description "The interface index of this OSPFv3 interface.";
            } // END of if-index definition.

            leaf instance-id  {
                type  uint8;
                description "Instance ID.";
            } // END of instance-id definition.

            leaf neighbor-router-id  {
                type  inet:ipv4-address;
                description "Neighbor router ID.";
            } // END of neighbor-router-id definition.

            leaf packet-type  {
                type  ipi-ospfv3-types:ospfv3_packet_type_t;
                description "OSPF patcket type.";
            } // END of packet-type definition.

            leaf lsdb-type  {
                type  uint32;
                description "Link State Database (LSDB) Type.";
            } // END of lsdb-type definition.

            leaf lsdb-lsid  {
                type  uint32;
                description "Link State Database (LSDB) ID.";
            } // END of lsdb-lsid definition.

            leaf lsdb-router-id  {
                type  inet:ipv4-address;
                description "Link State Database (LSDB) router ID.";
            } // END of lsdb-router-id definition.

        } // END of tx-retransmit-container definition.
    } // END of ospfv3-tx-retransmit definition.
    grouping ospfv3-distribute-bgp-ls-config {
        description
            "Grouping for OSPFv3 distribute BGP linkstate configuration data";
        leaf enabled  {
            type  empty;
            description "Use this attribute to distribute linkstate and TE Database to BGP.";
        } // END of enabled definition.

        leaf throttle-timer  {
            // when " ipi-ospfv3:ospfv3/processes/process/bgp-link-state/distribute/config/enabled ";
            type  uint8 {
                 range "5..20"  {
                    description "5..20: Supported range 5 - 20";
                 }
            }
            units "seconds";
            default "5";
            description "Use this attribute to set interval between processing LS DB.";
        } // END of throttle-timer definition.

    } // END of ospfv3-distribute-bgp-ls-config definition.
    grouping ospfv3-distribute-bgp-ls-top {
        description
            "Grouping for OSPFv3 distribute BGP linkstate";
        container distribute {
            description
                "OSPFv3 distribute BGP linkstate";
            container config {
                description
                    "Configuration data for OSPFv3 distribute BGP linkstate";
                uses ospfv3-distribute-bgp-ls-config;
            } // END of config-container definition.
            container state {
                config false;
                description
                    "Operational state data for OSPFv3 distribute BGP linkstate";
                uses ospfv3-distribute-bgp-ls-config;
            } // END of state-container definition.
        } // END of distribute-container definition.
    } // END of ospfv3-distribute-bgp-ls-top definition.
    grouping ospfv3-distribute-top {
        description
            "Grouping for OSPFv3 distribute";
        container bgp-link-state {
            if-feature feature-list:HAVE_BGP_LS;
            description
                "OSPF distribute";
            uses ospfv3-distribute-bgp-ls-top;
        } // END of bgp-link-state-container definition.
    } // END of ospfv3-distribute-top definition.
    grouping ospfv3-neighbor-state-change {
        description
            "Grouping for OSPFv3 neighbor state change";
        container neighbor-state-change {
            config false;
            description
                "Neighbor state change";
            leaf router-id  {
                type  inet:ipv4-address;
                description "Router ID for the OSPF process.";
            } // END of router-id definition.

            leaf if-index  {
                type  int32;
                description "The interface index of this OSPFv3 interface.";
            } // END of if-index definition.

            leaf instance-id  {
                type  uint8;
                description "Instance ID.";
            } // END of instance-id definition.

            leaf neighbor-router-id  {
                type  inet:ipv4-address;
                description "Neighbor router ID.";
            } // END of neighbor-router-id definition.

            leaf neighbor-state  {
                type  ipi-ospfv3-types:ospfv3_neighbor_state_change_t;
                description "Neighbor state.";
            } // END of neighbor-state definition.

        } // END of neighbor-state-change-container definition.
    } // END of ospfv3-neighbor-state-change definition.

    grouping  ospfv3-grouping {
    description
        "Open Shortest Path First version 3 (OSPFv3)";
    container ospfv3 {
        if-feature feature-list:HAVE_OSPF6D;
        if-feature feature-list:HAVE_IPV6;
        description
            "Open Shortest Path First version 3 (OSPFv3)";
        uses ospfv3-global-top;
        uses ospfv3-process-top;
        uses ospfv3-debug-top;
        uses interfaces-grouping;
    } // END of ospfv3-container definition.
    } // END of ospfv3-grouping definition.

    uses ospfv3-grouping;

    rpc ospfv3-terminal-debug-ospf-all-on {
        if-feature feature-list:HAVE_OSPF6D;
        if-feature feature-list:HAVE_IPV6;
        description "Enable all OSPFv3 debug categories";
    }

    rpc ospfv3-terminal-debug-ospf-all-off {
        if-feature feature-list:HAVE_OSPF6D;
        if-feature feature-list:HAVE_IPV6;
        description "Disable all OSPFv3 debug categories";
    }

    rpc ospfv3-terminal-debug-bfd-on {
        if-feature feature-list:HAVE_BFD;
        if-feature feature-list:HAVE_OSPF6D;
        if-feature feature-list:HAVE_IPV6;
        description "Bidirectional Forwarding Detection (BFD)";
    }

    rpc ospfv3-terminal-debug-bfd-off {
        if-feature feature-list:HAVE_BFD;
        if-feature feature-list:HAVE_OSPF6D;
        if-feature feature-list:HAVE_IPV6;
        description "Bidirectional Forwarding Detection (BFD)";
    }

    rpc ospfv3-terminal-debug-retransmission-on {
        if-feature feature-list:HAVE_OSPF6D;
        if-feature feature-list:HAVE_IPV6;
        description "OSPF Debug retransmission information";
    }

    rpc ospfv3-terminal-debug-retransmission-off {
        if-feature feature-list:HAVE_OSPF6D;
        if-feature feature-list:HAVE_IPV6;
        description "OSPF Debug retransmission information";
    }

    rpc ospfv3-terminal-debug-dist-ls-on {
        if-feature feature-list:HAVE_BGP_LS;
        if-feature feature-list:HAVE_OSPF6D;
        if-feature feature-list:HAVE_IPV6;
        description "OSPFv3 distribute linkstate details";
    }

    rpc ospfv3-terminal-debug-dist-ls-off {
        if-feature feature-list:HAVE_BGP_LS;
        if-feature feature-list:HAVE_OSPF6D;
        if-feature feature-list:HAVE_IPV6;
        description "OSPFv3 distribute linkstate details";
    }

    rpc ospfv3-terminal-debug-events-on {
        if-feature feature-list:HAVE_OSPF6D;
        if-feature feature-list:HAVE_IPV6;
        description "OSPFv3 events information";
        input  {
            leaf events  {
                type ipi-ospfv3-types:ospfv3_debug_event_t;
                mandatory true;
                description "OSPF events information";
            }
        }
    }

    rpc ospfv3-terminal-debug-events-off {
        if-feature feature-list:HAVE_OSPF6D;
        if-feature feature-list:HAVE_IPV6;
        description "OSPF events information";
        input  {
            leaf events  {
                type ipi-ospfv3-types:ospfv3_debug_event_t;
                mandatory true;
                description "OSPFv3 events information";
            }
        }
    }

    rpc ospfv3-terminal-debug-ifsm-on {
        if-feature feature-list:HAVE_OSPF6D;
        if-feature feature-list:HAVE_IPV6;
        description "OSPFv3 Interface State Machine";
        input  {
            leaf ifsm  {
                type ipi-ospfv3-types:ospfv3_debug_ifsm_t;
                mandatory true;
                description "OSPFv3 Interface State Machine";
            }
        }
    }

    rpc ospfv3-terminal-debug-ifsm-off {
        if-feature feature-list:HAVE_OSPF6D;
        if-feature feature-list:HAVE_IPV6;
        description "OSPFv3 Interface State Machine";
        input  {
            leaf ifsm  {
                type ipi-ospfv3-types:ospfv3_debug_ifsm_t;
                mandatory true;
                description "OSPFv3 Interface State Machine";
            }
        }
    }

    rpc ospfv3-terminal-debug-lfa-on {
        if-feature feature-list:HAVE_OSPF6_LFA;
        if-feature feature-list:HAVE_OSPF6D;
        if-feature feature-list:HAVE_IPV6;
        description "OSPFv3 LFA route install details";
    }

    rpc ospfv3-terminal-debug-lfa-off {
        if-feature feature-list:HAVE_OSPF6_LFA;
        if-feature feature-list:HAVE_OSPF6D;
        if-feature feature-list:HAVE_IPV6;
        description "OSPFv3 LFA route install details";
    }

    rpc ospfv3-terminal-debug-lsa-on {
        if-feature feature-list:HAVE_OSPF6D;
        if-feature feature-list:HAVE_IPV6;
        description "OSPFv3 Link State Advertisement";
        input  {
            leaf lsa  {
                type ipi-ospfv3-types:ospfv3_debug_lsa_t;
                mandatory true;
                description "OSPFv3 Link State Advertisement";
            }
        }
    }

    rpc ospfv3-terminal-debug-lsa-off {
        if-feature feature-list:HAVE_OSPF6D;
        if-feature feature-list:HAVE_IPV6;
        description "OSPFv3 Link State Advertisement";
        input  {
            leaf lsa  {
                type ipi-ospfv3-types:ospfv3_debug_lsa_t;
                mandatory true;
                description "OSPFv3 Link State Advertisement";
            }
        }
    }

    rpc ospfv3-terminal-debug-nfsm-on {
        if-feature feature-list:HAVE_OSPF6D;
        if-feature feature-list:HAVE_IPV6;
        description "OSPFv3 Neighbor State Machine";
        input  {
            leaf nfsm  {
                type ipi-ospfv3-types:ospfv3_debug_nfsm_t;
                mandatory true;
                description "OSPFv3 Neighbor State Machine";
            }
        }
    }

    rpc ospfv3-terminal-debug-nfsm-off {
        if-feature feature-list:HAVE_OSPF6D;
        if-feature feature-list:HAVE_IPV6;
        description "OSPFv3 Neighbor State Machine";
        input  {
            leaf nfsm  {
                type ipi-ospfv3-types:ospfv3_debug_nfsm_t;
                mandatory true;
                description "OSPFv3 Neighbor State Machine";
            }
        }
    }

    rpc ospfv3-terminal-debug-nsm-on {
        if-feature feature-list:HAVE_OSPF6D;
        if-feature feature-list:HAVE_IPV6;
        description "OSPFv3 NSM information";
        input  {
            leaf nsm  {
                type ipi-ospfv3-types:ospfv3_debug_nsm_t;
                mandatory true;
                description "OSPFv3 NSM information";
            }
        }
    }

    rpc ospfv3-terminal-debug-nsm-off {
        if-feature feature-list:HAVE_OSPF6D;
        if-feature feature-list:HAVE_IPV6;
        description "OSPFv3 NSM information";
        input  {
            leaf nsm  {
                type ipi-ospfv3-types:ospfv3_debug_nsm_t;
                mandatory true;
                description "OSPFv3 NSM information";
            }
        }
    }

    rpc ospfv3-terminal-debug-packet-all-on {
        if-feature feature-list:HAVE_OSPF6D;
        if-feature feature-list:HAVE_IPV6;
        description "OSPFv3 packets";
        input  {
            leaf all  {
                type ipi-ospfv3-types:ospfv3_debug_packet_options_t;
                mandatory true;
                description "OSPFv3 Packets";
            }
        }
    }

    rpc ospfv3-terminal-debug-packet-all-off {
        if-feature feature-list:HAVE_OSPF6D;
        if-feature feature-list:HAVE_IPV6;
        description "OSPFv3 packets";
        input  {
            leaf all  {
                type ipi-ospfv3-types:ospfv3_debug_packet_options_t;
                mandatory true;
                description "OSPFv3 Packets";
            }
        }
    }

    rpc ospfv3-terminal-debug-packet-hello-on {
        if-feature feature-list:HAVE_OSPF6D;
        if-feature feature-list:HAVE_IPV6;
        description "OSPFv3 packet hello";
        input  {
            leaf hello  {
                type ipi-ospfv3-types:ospfv3_debug_packet_options_t;
                mandatory true;
                description "OSPFv3 Hello";
            }
        }
    }

    rpc ospfv3-terminal-debug-packet-hello-off {
        if-feature feature-list:HAVE_OSPF6D;
        if-feature feature-list:HAVE_IPV6;
        description "OSPFv3 packet hello";
        input  {
            leaf hello  {
                type ipi-ospfv3-types:ospfv3_debug_packet_options_t;
                mandatory true;
                description "OSPFv3 Hello";
            }
        }
    }

    rpc ospfv3-terminal-debug-packet-dd-on {
        if-feature feature-list:HAVE_OSPF6D;
        if-feature feature-list:HAVE_IPV6;
        description "OSPFv3 packet database description";
        input  {
            leaf dd  {
                type ipi-ospfv3-types:ospfv3_debug_packet_options_t;
                mandatory true;
                description "OSPFv3 Database Description";
            }
        }
    }

    rpc ospfv3-terminal-debug-packet-dd-off {
        if-feature feature-list:HAVE_OSPF6D;
        if-feature feature-list:HAVE_IPV6;
        description "OSPFv3 packet database description";
        input  {
            leaf dd  {
                type ipi-ospfv3-types:ospfv3_debug_packet_options_t;
                mandatory true;
                description "OSPFv3 Database Description";
            }
        }
    }

    rpc ospfv3-terminal-debug-packet-ls-request-on {
        if-feature feature-list:HAVE_OSPF6D;
        if-feature feature-list:HAVE_IPV6;
        description "OSPFv3 packet link state request";
        input  {
            leaf ls-request  {
                type ipi-ospfv3-types:ospfv3_debug_packet_options_t;
                mandatory true;
                description "OSPFv3 Link State Request";
            }
        }
    }

    rpc ospfv3-terminal-debug-packet-ls-request-off {
        if-feature feature-list:HAVE_OSPF6D;
        if-feature feature-list:HAVE_IPV6;
        description "OSPFv3 packet link state request";
        input  {
            leaf ls-request  {
                type ipi-ospfv3-types:ospfv3_debug_packet_options_t;
                mandatory true;
                description "OSPFv3 Link State Request";
            }
        }
    }

    rpc ospfv3-terminal-debug-packet-ls-update-on {
        if-feature feature-list:HAVE_OSPF6D;
        if-feature feature-list:HAVE_IPV6;
        description "OSPFv3 packet link state update";
        input  {
            leaf ls-update  {
                type ipi-ospfv3-types:ospfv3_debug_packet_options_t;
                mandatory true;
                description "OSPFv3 Link State Update";
            }
        }
    }

    rpc ospfv3-terminal-debug-packet-ls-update-off {
        if-feature feature-list:HAVE_OSPF6D;
        if-feature feature-list:HAVE_IPV6;
        description "OSPFv3 packet link state update";
        input  {
            leaf ls-update  {
                type ipi-ospfv3-types:ospfv3_debug_packet_options_t;
                mandatory true;
                description "OSPFv3 Link State Update";
            }
        }
    }

    rpc ospfv3-terminal-debug-packet-ls-ack-on {
        if-feature feature-list:HAVE_OSPF6D;
        if-feature feature-list:HAVE_IPV6;
        description "OSPFv3 packet link state acknowledgment";
        input  {
            leaf ls-ack  {
                type ipi-ospfv3-types:ospfv3_debug_packet_options_t;
                mandatory true;
                description "OSPFv3 Link State Acknowledgment";
            }
        }
    }

    rpc ospfv3-terminal-debug-packet-ls-ack-off {
        if-feature feature-list:HAVE_OSPF6D;
        if-feature feature-list:HAVE_IPV6;
        description "OSPFv3 packet link state acknowledgment";
        input  {
            leaf ls-ack  {
                type ipi-ospfv3-types:ospfv3_debug_packet_options_t;
                mandatory true;
                description "OSPFv3 Link State Acknowledgment";
            }
        }
    }

    rpc ospfv3-terminal-debug-rib-on {
        if-feature feature-list:HAVE_OSPF6D;
        if-feature feature-list:HAVE_IPV6;
        description "OSPFv3 RIB information";
        input  {
            leaf rib  {
                type ipi-ospfv3-types:ospfv3_debug_rib_t;
                mandatory true;
                description "OSPFv3 RIB information";
            }
        }
    }

    rpc ospfv3-terminal-debug-rib-off {
        if-feature feature-list:HAVE_OSPF6D;
        if-feature feature-list:HAVE_IPV6;
        description "OSPFv3 RIB information";
        input  {
            leaf rib  {
                type ipi-ospfv3-types:ospfv3_debug_rib_t;
                mandatory true;
                description "OSPFv3 RIB information";
            }
        }
    }

    rpc ospfv3-terminal-debug-route-on {
        if-feature feature-list:HAVE_OSPF6D;
        if-feature feature-list:HAVE_IPV6;
        description "OSPFv3 route information";
        input  {
            leaf route  {
                type ipi-ospfv3-types:ospfv3_debug_route_t;
                mandatory true;
                description "OSPFv3 route information";
            }
        }
    }

    rpc ospfv3-terminal-debug-route-off {
        if-feature feature-list:HAVE_OSPF6D;
        if-feature feature-list:HAVE_IPV6;
        description "OSPFv3 route information";
        input  {
            leaf route  {
                type ipi-ospfv3-types:ospfv3_debug_route_t;
                mandatory true;
                description "OSPFv3 route information";
            }
        }
    }

    rpc ospfv3-clear-process {
        if-feature feature-list:HAVE_OSPF6D;
        if-feature feature-list:HAVE_IPV6;
        description "Clear and restart given OSPFv3 processes";
        input  {
            leaf process-id  {
                type string;
                mandatory true;
                description "Use this attribute to specify OSPFv3 processes to clear.";
            }
        }
    }

    rpc ospfv3-clear-process-all {
        if-feature feature-list:HAVE_OSPF6D;
        if-feature feature-list:HAVE_IPV6;
        description "Clear and restart all OSPFv3 processes";
    }

    rpc ospfv3-graceful-restart {
        if-feature feature-list:HAVE_OSPF6D;
        if-feature feature-list:HAVE_IPV6;
        description "Restart gracefully restart OSPFv3. After this command is executed, the
                    router immediately shuts down. NSM is notified that OSPF has shut down
                    gracefully. NSM preserves routes installed by OSPF until the grace
                    period expires.";
        input  {
            leaf grace-period  {
                type uint16 {
                    range "2..1800";
                }
                mandatory true;
                description "Use this attribute to set the grace period for restarting the router.";
            }
        }
    }

    rpc ospfv3-snmp-restart {
        if-feature feature-list:HAVE_SNMP;
        if-feature feature-list:HAVE_OSPF6D;
        if-feature feature-list:HAVE_IPV6;
        description "Restart SNMP in OSPFv3";
    }

    notification ospfv3-originate-lsa {
        if-feature feature-list:HAVE_OSPF6D;
        if-feature feature-list:HAVE_IPV6;

        description "Notification for OSPFv3 originate LSA.";

        leaf severity {
            type cml-data-types:cml_notif_severity_t;
            description "Notification severity level (value: WARNING)";
        }

        leaf eventClass {
            type cml-data-types:cml_notif_class_t;
            description "Notification event class (value: STATE)";
        }

        leaf ospfv3-id {
            type ipi-ospfv3-types:ospfv3_string_t;
        description
            "Use this attribute to set the OSPFv3 process ID";
        }

        leaf router-id {
            type  inet:ipv4-address;
        description
            "The originator router ID.";
        }

        leaf lsdb-area-id {
            type  inet:ipv4-address;
        description
            "Link State Database (LSDB) area ID.";
        }

        leaf lsdb-type {
            type  uint32;
        description
            "Link State Database (LSDB) Type.";
        }

        leaf lsdb-id {
            type  uint32;
        description
            "Link State Database (LSDB) ID.";
        }

        leaf lsdb-router-id {
            type  inet:ipv4-address;
        description
            "Link State Database (LSDB) router ID.";
        }
    }

    notification ospfv3-tx-retransmit {
        if-feature feature-list:HAVE_OSPF6D;
        if-feature feature-list:HAVE_IPV6;

        description "Notification for OSPFv3 re-transmission.";

        leaf severity {
            type cml-data-types:cml_notif_severity_t;
            description "Notification severity level (value: INFO)";
        }

        leaf eventClass {
            type cml-data-types:cml_notif_class_t;
            description "Notification event class (value: STATE)";
        }

        leaf ospfv3-id {
            type ipi-ospfv3-types:ospfv3_string_t;
        description
            "Use this attribute to set the OSPFv3 process ID";
        }

        leaf router-id {
            type  inet:ipv4-address;
        description
            "Originating router ID.";
        }

        leaf if-index {
            type  int32;
        description
            "The interface index of this OSPFv3 interface.";
        }

        leaf instance-id {
            type  uint8;
        description
            "Instance ID.";
        }

        leaf neighbor-router-id {
            type  inet:ipv4-address;
        description
            "Neighbor router ID.";
        }

        leaf packet-type {
            type ipi-ospfv3-types:ospfv3_packet_type_t;
        description
            "OSPF patcket type.";
        }

        leaf lsdb-type {
            type  uint32;
        description
            "Link State Database (LSDB) Type.";
        }

        leaf lsdb-lsid {
            type  uint32;
        description
            "Link State Database (LSDB) ID.";
        }

        leaf lsdb-router-id {
            type  inet:ipv4-address;
        description
            "Link State Database (LSDB) router ID.";
        }
    }

    notification ospfv3-neighbor-state-change {
        if-feature feature-list:HAVE_OSPF6D;
        if-feature feature-list:HAVE_IPV6;

        description "Notification for OSPFv3 interface link state change.";

        leaf severity {
            type cml-data-types:cml_notif_severity_t;
            description "Notification severity level (value: CRITICAL)";
        }

        leaf eventClass {
            type cml-data-types:cml_notif_class_t;
            description "Notification event class (value: STATE)";
        }

        leaf ospfv3-id {
            type ipi-ospfv3-types:ospfv3_string_t;
        description
            "Use this attribute to set the OSPFv3 process ID";
        }

        leaf router-id {
            type  inet:ipv4-address;
        description
            "Router ID for the OSPF process.";
        }

        leaf if-index {
            type  int32;
        description
            "The interface index of this OSPFv3 interface.";
        }

        leaf instance-id {
            type  uint8;
        description
            "Instance ID.";
        }

        leaf neighbor-router-id {
            type  inet:ipv4-address;
        description
            "Neighbor router ID.";
        }

        leaf neighbor-state {
            type ipi-ospfv3-types:ospfv3_neighbor_state_change_t;
        description
            "Neighbor state.";
        }
    }

    notification ospfv3-virtual-link-config-error {
        if-feature feature-list:HAVE_OSPF6D;
        if-feature feature-list:HAVE_IPV6;

        description "Notification for OSPFv3 virtual link configuration error.";

        leaf severity {
            type cml-data-types:cml_notif_severity_t;
            description "Notification severity level (value: WARNING)";
        }

        leaf eventClass {
            type cml-data-types:cml_notif_class_t;
            description "Notification event class (value: STATE)";
        }

        leaf remote-router-id {
            type  inet:ipv4-address;
        description
            "Use this attribute to set the interface IP address of the neighbor.";
        }

        leaf area-id {
            type ipi-ospfv3-types:ospfv3_area_t;
        description
            "Use this attribute to set the OSPFv3 area ID.";
        }

        leaf ospfv3-id {
            type ipi-ospfv3-types:ospfv3_string_t;
        description
            "Use this attribute to set the OSPFv3 process ID";
        }

        leaf router-id {
            type  inet:ipv4-address;
        description
            "The originator Router ID.";
        }

        leaf instance-id {
            type  uint8;
        description
            "Instance ID.";
        }

        leaf error-type {
            type ipi-ospfv3-types:ospfv3_config_error_type_t;
        description
            "Error type.";
        }

        leaf packet-type {
            type ipi-ospfv3-types:ospfv3_packet_type_t;
        description
            "Packet type.";
        }
    }

    notification ospfv3-virtual-link-state-change {
        if-feature feature-list:HAVE_OSPF6D;
        if-feature feature-list:HAVE_IPV6;

        description "Notification for OSPFv3 virtual link state change.";

        leaf severity {
            type cml-data-types:cml_notif_severity_t;
            description "Notification severity level (value: WARNING)";
        }

        leaf eventClass {
            type cml-data-types:cml_notif_class_t;
            description "Notification event class (value: STATE)";
        }

        leaf remote-router-id {
            type  inet:ipv4-address;
        description
            "Use this attribute to set the interface IP address of the neighbor.";
        }

        leaf area-id {
            type ipi-ospfv3-types:ospfv3_area_t;
        description
            "Use this attribute to set the OSPFv3 area ID.";
        }

        leaf ospfv3-id {
            type ipi-ospfv3-types:ospfv3_string_t;
        description
            "Use this attribute to set the OSPFv3 process ID";
        }

        leaf router-id {
            type  inet:ipv4-address;
        description
            "The originator Router ID.";
        }

        leaf instance-id {
            type  uint8;
        description
            "Instance ID.";
        }

        leaf virtual-link-state {
            type ipi-ospfv3-types:ospfv3_interface_state_t;
        description
            "Virtual link state.";
        }
    }

    notification ospfv3-virtual-link-neighbor-state-change {
        if-feature feature-list:HAVE_OSPF6D;
        if-feature feature-list:HAVE_IPV6;

        description "Notification for OSPFv3 virtual neighbor state change.";

        leaf severity {
            type cml-data-types:cml_notif_severity_t;
            description "Notification severity level (value: WARNING)";
        }

        leaf eventClass {
            type cml-data-types:cml_notif_class_t;
            description "Notification event class (value: STATE)";
        }

        leaf remote-router-id {
            type  inet:ipv4-address;
        description
            "Use this attribute to set the interface IP address of the neighbor.";
        }

        leaf area-id {
            type ipi-ospfv3-types:ospfv3_area_t;
        description
            "Use this attribute to set the OSPFv3 area ID.";
        }

        leaf ospfv3-id {
            type ipi-ospfv3-types:ospfv3_string_t;
        description
            "Use this attribute to set the OSPFv3 process ID";
        }

        leaf router-id {
            type  inet:ipv4-address;
        description
            "The originator Router ID.";
        }

        leaf instance-id {
            type  uint8;
        description
            "Instance ID.";
        }

        leaf neighbor-state {
            type ipi-ospfv3-types:ospfv3_interface_state_t;
        description
            "Neighbor state.";
        }
    }

    notification ospfv3-virtual-link-rx-bad-packet {
        if-feature feature-list:HAVE_OSPF6D;
        if-feature feature-list:HAVE_IPV6;

        description "Notification for OSPFv3 virtual link rx bad packet.";

        leaf severity {
            type cml-data-types:cml_notif_severity_t;
            description "Notification severity level (value: WARNING)";
        }

        leaf eventClass {
            type cml-data-types:cml_notif_class_t;
            description "Notification event class (value: STATE)";
        }

        leaf remote-router-id {
            type  inet:ipv4-address;
        description
            "Use this attribute to set the interface IP address of the neighbor.";
        }

        leaf area-id {
            type ipi-ospfv3-types:ospfv3_area_t;
        description
            "Use this attribute to set the OSPFv3 area ID.";
        }

        leaf ospfv3-id {
            type ipi-ospfv3-types:ospfv3_string_t;
        description
            "Use this attribute to set the OSPFv3 process ID";
        }

        leaf router-id {
            type  inet:ipv4-address;
        description
            "The originator Router ID.";
        }

        leaf instance-id {
            type  uint8;
        description
            "Instance ID.";
        }

        leaf packet-type {
            type ipi-ospfv3-types:ospfv3_packet_type_t;
        description
            "Packet type.";
        }
    }

    notification ospfv3-virtual-link-tx-retransmit {
        if-feature feature-list:HAVE_OSPF6D;
        if-feature feature-list:HAVE_IPV6;

        description "Notification for OSPFv3 Virtual Interface re-transmission.";

        leaf severity {
            type cml-data-types:cml_notif_severity_t;
            description "Notification severity level (value: WARNING)";
        }

        leaf eventClass {
            type cml-data-types:cml_notif_class_t;
            description "Notification event class (value: STATE)";
        }

        leaf remote-router-id {
            type  inet:ipv4-address;
        description
            "Use this attribute to set the interface IP address of the neighbor.";
        }

        leaf area-id {
            type ipi-ospfv3-types:ospfv3_area_t;
        description
            "Use this attribute to set the OSPFv3 area ID.";
        }

        leaf ospfv3-id {
            type ipi-ospfv3-types:ospfv3_string_t;
        description
            "Use this attribute to set the OSPFv3 process ID";
        }

        leaf router-id {
            type  inet:ipv4-address;
        description
            "The originator Router ID.";
        }

        leaf instance-id {
            type  uint8;
        description
            "Instance ID.";
        }

        leaf packet-type {
            type ipi-ospfv3-types:ospfv3_packet_type_t;
        description
            "Packet type.";
        }

        leaf lsdb-type {
            type  uint32;
        description
            "Link state advertisement type.";
        }

        leaf lsdb-lsid {
            type  uint32;
        description
            "The Link State ID.";
        }

        leaf lsdb-router-id {
            type  inet:ipv4-address;
        description
            "LSDB router ID.";
        }
    }

    notification ospfv3-interface-config-error {
        if-feature feature-list:HAVE_OSPF6D;
        if-feature feature-list:HAVE_IPV6;

        description "Notification for OSPFv3 interface configuration error.";

        leaf severity {
            type cml-data-types:cml_notif_severity_t;
            description "Notification severity level (value: WARNING)";
        }

        leaf eventClass {
            type cml-data-types:cml_notif_class_t;
            description "Notification event class (value: STATE)";
        }

        leaf interface-name {
            type  string;
        description
            "Interface name for which OSPFv3 is being configured.";
        }

        leaf router-id {
            type  inet:ipv4-address;
        description
            "OSPFv3 router ID.";
        }

        leaf interface-index {
            type  uint32;
        description
            "Interface index.";
        }

        leaf interface-instance-id {
            type  uint8;
        description
            "Interface instance ID.";
        }

        leaf error-type {
            type ipi-ospfv3-types:ospfv3_config_error_type_t;
        description
            "Error type.";
        }

        leaf packet-type {
            type ipi-ospfv3-types:ospfv3_packet_type_t;
        description
            "Packet type.";
        }
    }

    notification ospfv3-interface-state-change {
        if-feature feature-list:HAVE_OSPF6D;
        if-feature feature-list:HAVE_IPV6;

        description "Notification for OSPFv3 interface state change.";

        leaf severity {
            type cml-data-types:cml_notif_severity_t;
            description "Notification severity level (value: WARNING)";
        }

        leaf eventClass {
            type cml-data-types:cml_notif_class_t;
            description "Notification event class (value: STATE)";
        }

        leaf interface-name {
            type  string;
        description
            "Interface name for which OSPFv3 is being configured.";
        }

        leaf router-id {
            type  inet:ipv4-address;
        description
            "OSPFv3 router ID.";
        }

        leaf interface-index {
            type  uint32;
        description
            "Interface index.";
        }

        leaf interface-instance-id {
            type  uint8;
        description
            "Interface instance ID.";
        }

        leaf interface-state {
            type ipi-ospfv3-types:ospfv3_interface_state_t;
        description
            "Interface state.";
        }
    }

    notification ospfv3-interface-rx-bad-packet {
        if-feature feature-list:HAVE_OSPF6D;
        if-feature feature-list:HAVE_IPV6;

        description "Notification for OSPFv3 interface rx bad packet.";

        leaf severity {
            type cml-data-types:cml_notif_severity_t;
            description "Notification severity level (value: WARNING)";
        }

        leaf eventClass {
            type cml-data-types:cml_notif_class_t;
            description "Notification event class (value: STATE)";
        }

        leaf interface-name {
            type  string;
        description
            "Interface name for which OSPFv3 is being configured.";
        }

        leaf router-id {
            type  inet:ipv4-address;
        description
            "OSPFv3 router ID.";
        }

        leaf interface-index {
            type  uint32;
        description
            "Interface index.";
        }

        leaf interface-instance-id {
            type  uint8;
        description
            "Interface instance ID.";
        }

        leaf packet-src {
            type  inet:ipv6-address;
        description
            "The source IPv6 address";
        }

        leaf packet-type {
            type ipi-ospfv3-types:ospfv3_packet_type_t;
        description
            "Packet type.";
        }
    }

}
