/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-bgp-address-family.yang
*
*/

submodule ipi-bgp-address-family {

    yang-version 1.1;

    belongs-to  ipi-bgp { prefix ipi-bgp; }

    import feature-list {
        prefix feature-list;
        revision-date 2026-09-15;
    }

    import ipi-bgp-types {
        prefix ipi-bgp-types;
        revision-date 2025-12-22;
    }

    import cml-data-types {
        prefix cml-data-types;
        revision-date 2026-05-15;
    }

    include ipi-bgp-common { revision-date 2025-12-22;}
    organization
        "IP Infusion Inc.";

    contact
        "Address: 3965 Freedom Circle, Suite 200, Santa Clara, CA 95054
         Phone: +1 408-400-1900
         E-mail: support@ipinfusion.com
         Web: http://www.ipinfusion.com/";

    description
        "Datamodel for bgp network list";


    revision "2026-09-04" {
        description "Removed add-path commands for Ipv4 LU Address-family";
        reference " 0.17.0.";
    }

    revision "2026-01-06" {
        description "Enable multi-path CLI for x86 builds";
        reference " 0.16.17.";
    }

    revision "2025-12-18" {
        description "Added CML_SKIP_HITLESS_MERGE for the attribute 'additional-paths-mode'";
        reference " 0.16.16.";
    }

    revision "2025-12-15" {
        description "Hide multi-path CLI only for Data Centers (DC) builds";
        reference " 0.16.15.";
    }

    revision "2025-09-10" {
        description "Added code to make Add-path commands hidden in LU AF";
        reference " 0.16.14.";
    }

    revision "2025-08-22" {
        description "Deprecated 'max-paths ibgp' CLI and added 'multi-path' CLI for L2VPN EVPN Address-family";
        reference " 0.16.14.";
    }

    revision "2025-06-26" {
        description "initial revion for BGP RPKI Origin Validation";
        reference " 0.16.13.";
    }

    revision "2025-06-02" {
        description "Enabled Additional-paths for IPv4 LU Address-family";
        reference " 0.16.12.";
    }

    revision "2025-04-29" {
        description "Made attr redist-route-map-name mandatory for redistribute configuration";
        reference " 0.16.11.";
    }

    revision "2025-04-08" {
        description "Removed table-map-filter cli-command from BGP_6PE_MODE";
        reference " 0.16.10.";
    }

    revision "2025-03-05" {
        description "Added new CLI for multi-path under address-families";
        reference " 0.16.9.";
    }

    revision "2025-02-17" {
        description "Removed table-map option under IPv6-LU AF";
        reference " 0.14.1.";
    }

    revision "2025-02-13" {
        description "Added utils api for attribute 'aggregate-address'";
        reference " 0.14.0.";
    }

    revision "2024-10-15" {
        description "Updated create and delete operation of table-map";
        reference " 0.13.2.";
    }

    revision "2024-09-11" {
        description "Fix BGP address-family CLI helpstrings";
        reference " 0.13.1.";
    }

    revision "2024-08-29" {
        description "Updated if-feature 'HAVE_MPLS' for VPN address-family";
        reference " 0.13.0.";
    }

    revision "2024-08-02" {
        description "Removed autopopulate for bgp implicit null command'";
        reference " 0.12.1.";
    }

    revision "2024-05-16" {
        description "Added When tag constraints for attribute 'additional-path-select-all' and 'additional-paths-best-select-count'";
        reference " 0.12.0.";
    }

    revision "2024-03-20" {
        description "Added state attribute for dampening";
        reference " 0.11.4.";
    }

    revision "2024-02-28" {
        description "Removed installtion mode not suppported for attribute 'additional-paths-mode', 'additional-path-select-all' and 'additional-paths-best-select-count'";
        reference " 0.11.3.";
    }

    revision "2024-02-08" {
        description "Added enclosing container for missing objectlists";
        reference " 0.11.2.";
    }

    revision "2024-01-05" {
        description "Removed 'ebgp-max-path' cli for address-family l2vpn evpn";
        reference " 0.11.1.";
    }

    revision "2024-01-02" {
        description "Added new attribute 'enable-bgp-implicit-null'for BGP-LU Implicit Null support";
        reference " 0.11.0.";
    }

    revision "2023-11-02" {
        description "Updated cliFlag for attribute 'ibgp-max-path' and 'ebgp-max-path'";
        reference " 0.10.0.";
    }

    revision "2023-09-12" {
        description "Added enclosing container for all objectlists";
        reference " 0.9.4.";
    }

    revision "2023-02-23" {
        description "Removed installtion mode not suppported for attribute 'enable-additional-path-pic'";
        reference " 0.9.3.";
    }

    revision "2023-02-22" {
        description "Corrected the revision";
        reference " 0.9.2.";
    }

    revision "2023-02-21" {
        description "BGP flowspec support";
        reference " 0.9.1.";
    }

    revision "2023-02-02" {
        description "Updated missing Description";
        reference " 0.9.0.";
    }

    revision "2023-01-03" {
        description "Updated bgp debug options";
        reference " 0.8.1.";
    }

    revision "2022-12-22" {
        description "Added if-feature 'HAVE_MPLS' for VPN address-family";
        reference " 0.8.0.";
    }

    revision "2022-07-31" {
        description "Stop using inet:ipv4-prefix and inet:ipv6-prefix due to Cisco NSO iterop";
        reference " 0.7.0.";
    }

    revision "2022-07-16" {
        description "Issues in SRv6 containter deletion with address-family ipv4";
        reference " 0.6.5.";
    }

    revision "2022-07-06" {
        description "Skipped dependency validation for a composite constraint of peer-as and peer-group-tag for BGP peer";
        reference " 0.6.4.";
    }

    revision "2022-06-20" {
        description "Added new attribute 'de-activate' for BGP Peer-group feature.";
        reference " 0.6.3.";
    }

    revision "2022-06-01" {
        description "Updated the yang file with feature";
        reference " 0.6.2.";
    }

    revision "2022-04-28" {
        description "Updated BGP clear RPCs to remove unwanted attributes.";
        reference " 0.6.1.";
    }

    revision "2022-04-19" {
        description "Added new attribute 'peer-shutdown-description' for support of BGP Administrative Shutdown Communication feature.";
        reference " 0.6.0.";
    }

    revision "2022-01-17" {
        description "Modified data type";
        reference " 0.5.0.";
    }

    revision "2021-09-15" {
        description "removed the yang drop element for the additional-path attributes for the bgp-add-path feature.";
        reference " 0.4.3.";
    }

    revision "2021-09-03" {
        description "Update descriptions of attribute";
        reference " 0.4.2.";
    }

    revision "2021-06-09" {
        description "Removal of default ipv4 unicast activate";
        reference " 0.4.1.";
    }

    revision "2021-05-31" {
        description "Added length for route map name";
        reference " 0.4.0.";
    }

    revision "2021-03-05" {
        description "Excluded yang generation for BGP Add path attributes, Added support for address-family ipv6 labeled-unicast deletion.";
        reference " 0.3.0.";
    }

    revision "2020-12-15" {
        description "Change to have data-types in lower case instead of camel case";
        reference " 0.2.0.";
    }

    revision "2020-09-10" {
        description "Initial Version";
        reference " 0.1.0.";
    }

    grouping address-family-config {
        description
            "Configuration data for bgp address family";
        leaf afi  {
            type  ipi-bgp-types:bgp_afi_type_t;
            description "BGP address family identifier";
        } // END of afi definition.

        leaf safi  {
            type  ipi-bgp-types:bgp_safi_type_t;
            description "BGP sub address family identifier";
        } // END of safi definition.

        leaf additional-path-fast-reroute  {
            if-feature feature-list:HAVE_BGP_PIC_CORE_EDGE;
            type  empty;
            description "Use this attribute to specify fast-reroute tie-break secondary-path";
        } // END of additional-path-fast-reroute definition.

        leaf mvpn-abr-enable  {
            if-feature feature-list:HAVE_BGP_MVPN;
            type  empty;
            description "Use this attribute to enable RFC7524 ABR for MVPN";
        } // END of mvpn-abr-enable definition.

        leaf additional-paths-mode  {
            if-feature feature-list:HAVE_BGP_ADD_PATH;
            type  ipi-bgp-types:bgp_additional_path_type_t;
            description ">Use this attribute to add additional paths in the BGP table";
        } // END of additional-paths-mode definition.

        leaf additional-path-select-all  {
            // when " ipi-bgp-address-family:address-families/address-family/config/additional-paths-mode ";
            if-feature feature-list:HAVE_BGP_ADD_PATH;
            type  empty;
            description "Use this attribute to select criteria to pick the paths";
        } // END of additional-path-select-all definition.

        leaf additional-paths-best-select-count  {
            // when " ipi-bgp-address-family:address-families/address-family/config/additional-paths-mode ";
            if-feature feature-list:HAVE_BGP_ADD_PATH;
            type  uint8 {
                 range "2..3"  {
                    description "2..3: Supported range 2 - 3";
                 }
            }
            description "Use this attribute to select best N paths";
        } // END of additional-paths-best-select-count definition.

        leaf no-client-route-reflection  {
            type  empty;
            description "Use this attribute to configure routers as route reflectors. Route
                        reflectors are used when all Interior Border Gateway Protocol (iBGP)
                        speakers are not fully meshed. If the clients are fully meshed the
                        route reflector is not required.";
        } // END of no-client-route-reflection definition.

        leaf multi-path  {
            type  empty;
            description "Use this attribute to enable L3VPN multipath for ECMP";
        } // END of multi-path definition.

    } // END of address-family-config definition.
    grouping bgp-aggregate-address-config {
        description
            "Configuration data for Aggregate Address List";
        leaf aggregate-address  {
            type  cml-data-types:cml_ip_prefix_t;
            description "Aggregates are used to minimize the size of routing tables.
                        Aggregation combines the characteristics of several different routes
                        and advertises a single route.The aggregateAddr attribute creates an
                        aggregate entry in the BGP routing table if any more-specific BGP
                        routes are available in the specified range.";
        } // END of aggregate-address definition.

        leaf aggregate-type  {
            type  ipi-bgp-types:bgp_aggregate_type_t;
            description "The aggregate-type attribute creates an aggregate entry advertising
                        the path for this route, consisting of all elements contained in all
                        paths being summarized. Use this parameter to reduce the size of path
                        information by listing the AS number only once, even if it was
                        included in multiple paths that were aggregated.";
        } // END of aggregate-type definition.

    } // END of bgp-aggregate-address-config definition.
    grouping aggregate-address-top {
        description
            "Grouping for Aggregate Address List";
        container aggregate-address-lists {
            description
                "This container defines Aggregate address lists";

            list aggregate-address-list {
                key "aggregate-address";
                description
                    "Aggregate address list";
                leaf aggregate-address  {
                    type  leafref {
                        path  "../config/aggregate-address";
                    }
                    description "Aggregates are used to minimize the size of routing tables.
                                Aggregation combines the characteristics of several different routes
                                and advertises a single route.The aggregate-address attribute creates
                                an aggregate entry in the BGP routing table if any more-specific BGP
                                routes are available in the specified range.";
                } // END of aggregate-address definition.

                container config {
                    description
                        "Configuration data for Aggregate Address List";
                    uses bgp-aggregate-address-config;
                } // END of config-container definition.
                container state {
                    config false;
                    description
                        "Operational state data for bgp aggregate address list";
                    uses bgp-aggregate-address-config;
                } // END of state-container definition.
            } // End of aggregate-address-list-list
        } // END of aggregate-address-lists-container definition.
    } // END of aggregate-address-top definition.
    grouping address-family-common-config {
        description
            "Common configuration data for BGP Address Family";
        leaf enable-auto-summary  {
            type  empty;
            description "Use this attribute to enable sending summarized routes by a BGP
                        speaker to its peers. Auto-summary is used by a BGP router to
                        advertise summarized routes to its peers. Auto-summary can be enabled
                        if certain routes have already been advertised: in this case,
                        configuring auto-summary advertises the summarized routes first, then
                        corresponding non-summarized routes are withdrawn. If certain routes
                        have already been advertised, and auto-summary is disabled,
                        non-summarized routes are first advertised, then the corresponding
                        summarized routes are withdrawn from all the connected peers.";
        } // END of enable-auto-summary definition.

        leaf enable-additional-path-pic  {
            if-feature feature-list:HAVE_BGP_PIC_CORE_EDGE;
            type  empty;
            description "Use this attribute to enable the additional paths in the BGP
                        table,install the indirect nexthop in RIB";
        } // END of enable-additional-path-pic definition.

        leaf enable-network-igp-sync  {
            type  empty;
            description "Use this attribute to enable IGP synchronization for BGP static
                        network routes";
        } // END of enable-network-igp-sync definition.

        leaf enable-igp-sync  {
            type  empty;
            description "Use this attribute to enable IGP synchronization of Internal BGP
                        (iBGP) learned routes with the Internal Gateway Protocol (IGP) system.
                        Synchronization is used when a BGP router should not advertise routes
                        learned from iBGP neighbors, unless those routes are also present in
                        an IGP (for example, OSPF). Synchronization may be enabled when all
                        the routers in an autonomous system do not speak BGP, and the
                        autonomous system is a transit for other autonomous systems.";
        } // END of enable-igp-sync definition.

        leaf enable-bgp-implicit-null  {
            type  empty;
            description "Use this attribute to enable BGP LU implicit null.";
        } // END of enable-bgp-implicit-null definition.

    } // END of address-family-common-config definition.
    grouping bgp-af-distance-config {
        description
            "Configuration attributes related to Distance for routes";
        leaf ebgp  {
            type  uint8 {
                 range "1..255"  {
                    description "1..255: Supported range 1 - 255";
                 }
            }
            description "Use this attribute to define an administrative distance for external
                        routes. External paths are routes learned from a neighbor outside of
                        the AS. A distance is a rating of trustworthiness of a router. The
                        higher the distance the lower the trust rating.
                        If the administrative distance is changed, it could create
                        inconsistency in the routing table and obstruct routing.";
        } // END of ebgp definition.

        leaf ibgp  {
            type  uint8 {
                 range "1..255"  {
                    description "1..255: Supported range 1 - 255";
                 }
            }
            description "Use this attribute to define an administrative distance for internal
                        routes. Internal routes are routes learned from another router within
                        the same AS. A distance is a rating of trustworthiness of a router.
                        The higher the distance the lower the trust rating.
                        If the administrative distance is changed, it could create
                        inconsistency in the routing table and obstruct routing.";
        } // END of ibgp definition.

        leaf local  {
            type  uint8 {
                 range "1..255"  {
                    description "1..255: Supported range 1 - 255";
                 }
            }
            description "Use this attribute to define an administrative distance for local
                        routes. Local routes are routes that is redistributed from another
                        process.A distance is a rating of trustworthiness of a router. The
                        higher the distance the lower the trust rating.
                        If the administrative distance is changed, it could create
                        inconsistency in the routing table and obstruct routing.";
        } // END of local definition.

    } // END of bgp-af-distance-config definition.
    grouping administrative-disatance-top {
        description
            "Grouping for attributes related to Distance for routes";
        container distances {
            description
                "Container for Attributes related to Distance for routes";

            list distance {
                key "ebgp ibgp local";
                max-elements 1;
                description
                    "Obeject-list for Attributes related to Distance for routes";
                leaf ebgp  {
                    type  leafref {
                        path  "../config/ebgp";
                    }
                    description "Use this attribute to define an administrative distance for external
                                routes. External paths are routes learned from a neighbor outside of
                                the AS. A distance is a rating of trustworthiness of a router. The
                                higher the distance the lower the trust rating.
                                If the administrative distance is changed, it could create
                                inconsistency in the routing table and obstruct routing.";
                } // END of ebgp definition.

                leaf ibgp  {
                    type  leafref {
                        path  "../config/ibgp";
                    }
                    description "Use this attribute to define an administrative distance for internal
                                routes. Internal routes are routes learned from another router within
                                the same AS. A distance is a rating of trustworthiness of a router.
                                The higher the distance the lower the trust rating.
                                If the administrative distance is changed, it could create
                                inconsistency in the routing table and obstruct routing.";
                } // END of ibgp definition.

                leaf local  {
                    type  leafref {
                        path  "../config/local";
                    }
                    description "Use this attribute to define an administrative distance for local
                                routes. Local routes are routes that is redistributed from another
                                process.A distance is a rating of trustworthiness of a router. The
                                higher the distance the lower the trust rating.
                                If the administrative distance is changed, it could create
                                inconsistency in the routing table and obstruct routing.";
                } // END of local definition.

                container config {
                    description
                        "Configuration attributes related to Distance for routes";
                    uses bgp-af-distance-config;
                } // END of config-container definition.
                container state {
                    config false;
                    description
                        "Operational state data related to Distance for routes";
                    uses bgp-af-distance-config;
                } // END of state-container definition.
            } // End of distance-list
        } // END of distances-container definition.
    } // END of administrative-disatance-top definition.
    grouping maximum-paths-top {
        description
            "Grouping for attributes related to multipath ECMP numbers";
        container maximum-paths {
            description
                "Container for attributes related to multipath ECMP numbers";
            container config {
                description
                    "Configuration attributes related to multipath ECMP numbers";
                uses bgp-af-maximum-paths-config;
            } // END of config-container definition.
            container state {
                config false;
                description
                    "Operational state data related to multipath ECMP numbers";
                uses bgp-af-maximum-paths-config;
            } // END of state-container definition.
        } // END of maximum-paths-container definition.
    } // END of maximum-paths-top definition.
    grouping address-family-redist-list-top {
        description
            "Grouping for redistribute for address-family";
        container route-redistribute-lists {
            description
                "redistribute for address-family";

            list route-redistribute-list {
                key "protocol-type";
                description
                    "redistribute for address-family";
                leaf protocol-type  {
                    type  leafref {
                        path  "../config/protocol-type";
                    }
                    description "Use this attribute to inject routes from one routing process into
                                another. Redistribution is used by routing protocols to advertise
                                routes that are learned by some other means, such as by another
                                routing protocol or by static routes. Since all internal routes are
                                dumped into BGP, careful filtering is applied to make sure that only
                                routes to be advertised reach the internet, not everything. This
                                attribute allows redistribution by injecting prefixes from one routing
                                protocol into another routing protocol.";
                } // END of protocol-type definition.

                container config {
                    description
                        "Configuration data for redistribute for address-family";
                    uses address-family-redist-list-config;
                } // END of config-container definition.
                container state {
                    config false;
                    description
                        "Operational state data for redistribute for address-family";
                    uses address-family-redist-list-config;
                } // END of state-container definition.
            } // End of route-redistribute-list-list
        } // END of route-redistribute-lists-container definition.
    } // END of address-family-redist-list-top definition.
    grouping bgp-redistribute-ospf-config {
        description
            "Configuration attributes related to redistribute with ospf proc Id for
                        address family";
        leaf ospf-instance-number  {
            type  ipi-bgp-types:cml_ospf_area_id_t;
            description "Use this attribute to inject routes from OSPF with specified OSPF
                        instance number to BGP.";
        } // END of ospf-instance-number definition.

        leaf redistribute-ospf-route-map  {
            type  string {
                length "1..63";
                pattern "[^?' =,>|]+";
            }
            description "Use this attribute to specify route map to redistribute routes from
                        OSPF into BGP.";
        } // END of redistribute-ospf-route-map definition.

    } // END of bgp-redistribute-ospf-config definition.
    grouping bgp-redistribute-ospf-top {
        description
            "Grouping for redistribute with ospf proc Id for address family";
        container bgp-redistributes-ospf {
            description
                "Container for redistribute with ospf proc Id for address family";

            list bgp-redistribute-ospf {
                key "ospf-instance-number";
                description
                    "Object-list for redistribute with ospf proc Id for address family";
                leaf ospf-instance-number  {
                    type  leafref {
                        path  "../config/ospf-instance-number";
                    }
                    description "Use this attribute to inject routes from one routing process into
                                another. Redistribution is used by routing protocols to advertise
                                routes that are learned by some other means, such as by another
                                routing protocol or by static routes. Since all internal routes are
                                dumped into BGP, careful filtering is applied to make sure that only
                                routes to be advertised reach the internet, not everything. This
                                attribute allows redistribution by injecting prefixes from one routing
                                protocol into another routing protocol.";
                } // END of ospf-instance-number definition.

                container config {
                    description
                        "Configuration data for redistribute with ospf proc Id for address
                                family";
                    uses bgp-redistribute-ospf-config;
                } // END of config-container definition.
                container state {
                    config false;
                    description
                        "Operational state data related to redistribute with ospf proc Id for
                                address family";
                    uses bgp-redistribute-ospf-config;
                } // END of state-container definition.
            } // End of bgp-redistribute-ospf-list
        } // END of bgp-redistributes-ospf-container definition.
    } // END of bgp-redistribute-ospf-top definition.
    grouping route-flap-dampening-state {
        description
            "attributes having bgp route flap dampening state";
        leaf maximum-penalty-ceil  {
            type  int32;
            default "0";
            config false;
            description "dampening penalty ceil";
        } // END of maximum-penalty-ceil definition.

        leaf minimum-penalty-ceil  {
            type  int32;
            default "0";
            config false;
            description "dampening penalty floor";
        } // END of minimum-penalty-ceil definition.

    } // END of route-flap-dampening-state definition.
    grouping route-flap-dampening-param-config {
        description
            "BGP Route Flap Dampening User Configurable Parameters";
        leaf enable-dampening  {
            type  ipi-bgp-types:bgp_dampening_t;
            description "This attribute enable BGP route dampening and set various parameters
                        to default values.";
        } // END of enable-dampening definition.

        leaf reach-half-life  {
            // when " !ipi-bgp-address-family:address-families/address-family/route-flap-dampenings/route-flap-dampening/config/dampening-rmap-name ";
            type  uint32 {
                 range "1..45"  {
                    description "1..45: Supported range 1 - 45";
                 }
            }
            default "15";
            description "Use this attribute to configure reachability half-life time for the
                        penalty in minutes for the bgp route dampening. The time for the
                        penalty to decrease to one-half of its current value.";
        } // END of reach-half-life definition.

        leaf reuse-penalty  {
            // when " ipi-bgp-address-family:address-families/address-family/route-flap-dampenings/route-flap-dampening/config/reach-half-life ";
            type  uint32 {
                 range "1..20000"  {
                    description "1..20000: Supported range 1 - 20000";
                 }
            }
            description "reuse Penalty <1-20000>";
        } // END of reuse-penalty definition.

        leaf suppress-penalty  {
            // when " ipi-bgp-address-family:address-families/address-family/route-flap-dampenings/route-flap-dampening/config/reach-half-life ";
            type  uint32 {
                 range "1..20000"  {
                    description "1..20000: Supported range 1 - 20000";
                 }
            }
            description "Use this attribute to specify suppress-penalty value";
        } // END of suppress-penalty definition.

        leaf max-suppress-time  {
            // when " ipi-bgp-address-family:address-families/address-family/route-flap-dampenings/route-flap-dampening/config/reach-half-life ";
            type  uint32 {
                 range "1..255"  {
                    description "1..255: Supported range 1 - 255";
                 }
            }
            description "Use this attribute to configure the value to start suppressing a route
                        for BGP route dampening. When the penalty for a route exceeds the
                        suppress value, the route is suppressed";
        } // END of max-suppress-time definition.

        leaf unreach-half-life  {
            // when " ipi-bgp-address-family:address-families/address-family/route-flap-dampenings/route-flap-dampening/config/reach-half-life ";
            type  uint32 {
                 range "1..45"  {
                    description "1..45: Supported range 1 - 45";
                 }
            }
            description "Use this attribute to configure un-reachability half-life time for the
                        penalty in minutes for bgp route dampening. The dampening information
                        is purged from the router once the penalty becomes less than half of
                        the reuse limit.";
        } // END of unreach-half-life definition.

        leaf dampening-rmap-name  {
            // when " !ipi-bgp-address-family:address-families/address-family/route-flap-dampenings/route-flap-dampening/config/reach-half-life ";
            type  string {
                length "1..63";
                pattern "[^?' =,>|]+";
            }
            description "Use this attribute to configure route map to specify criteria for
                        dampening.";
        } // END of dampening-rmap-name definition.

    } // END of route-flap-dampening-param-config definition.
    grouping bgp-address-family-network-list-config {
        description
            "grouping for BGP address-family network-list config";
        leaf local-network-prefix  {
            type  ipi-bgp-types:bgp_ip_network_t;
            description "Use this attribute to specify the networks to be advertised by the BGP
                        routing process. A unicast network address without a mask is accepted
                        if it falls into the natural boundary of its class. A class-boundary
                        mask is derived if the address matches its natural class-boundary.";
        } // END of local-network-prefix definition.

        leaf network-rmap-name  {
            type  string {
                length "1..63";
                pattern "[^?' =,>|]+";
            }
            default "NULL";
            description "Use this attribute to configure route map for the network specified in
                        local-network-prefix";
        } // END of network-rmap-name definition.

        leaf backdoor  {
            type  empty;
            description "network address with backdoor for address family";
        } // END of backdoor definition.

    } // END of bgp-address-family-network-list-config definition.
    grouping bgp-srv6-vpnv4-config {
        description
            "BGP SRV6";
        container bgp-srv6 {
            if-feature feature-list:HAVE_SRV6;
            description
                "SRv6 container for BGP segment routing";
            container config {
                presence "yes";
                description
                    "Segment routing SRv6 configuration and other CLIs inside srv6";
                uses bgp-srv6-config;
            } // END of config-container definition.
            container state {
                config false;
                description
                    "Segment routing V6 runtime parameters";
                uses bgp-srv6-config;
            } // END of state-container definition.
            uses bgp-srv6-locator-lists-config;
        } // END of bgp-srv6-container definition.
    } // END of bgp-srv6-vpnv4-config definition.
    grouping bgp-srv6-locator-lists-config {
        description
            "Locator";
        container locators {
            description
                "Container for locator list";

            list locator {
            // when " ipi-bgp-address-family:address-families/address-family/bgp-srv6/config/bgpSRv6enable ";
                key "bgpSRv6LocatorName";
                description
                    "Properties of a locator list";
                leaf bgpSRv6LocatorName  {
                    type  leafref {
                        path  "../config/bgpSRv6LocatorName";
                    }
                    description "Locator name";
                } // END of bgpSRv6LocatorName definition.

                container config {
                    description
                        "Config parameters for locator-list configuration";
                    uses bgp-locator-name-config;
                } // END of config-container definition.
                container state {
                    config false;
                    description
                        "State parameters for locator-list configuration";
                    uses bgp-locator-name-config;
                } // END of state-container definition.
            } // End of locator-list
        } // END of locators-container definition.
    } // END of bgp-srv6-locator-lists-config definition.
    grouping bgp-srv6-config {
        description
            "config attribute for SRv6 for SR Policies";
        leaf bgpSRv6enable  {
            type  empty;
            mandatory true;
            description "This attribute enable Segment Routing V6";
        } // END of bgpSRv6enable definition.

    } // END of bgp-srv6-config definition.
    grouping bgp-locator-name-config {
        description
            "config attribute for SRv6 for SR Policies";
        leaf bgpSRv6LocatorName  {
            type  string {
                length "1..1965";
                pattern "[^?' =,>|]+";
            }
            description "Locator name";
        } // END of bgpSRv6LocatorName definition.

    } // END of bgp-locator-name-config definition.
    grouping route-flap-dampening-config-param {
        description
            "Grouping for BGP Route Flap Dampening User Configurable Parameters";
        container route-flap-dampenings {
            description
                "Container for BGP Route Flap Dampening User Configurable Parameters";

            list route-flap-dampening {
                key "enable-dampening";
                max-elements 1;
                description
                    "Object-list for BGP Route Flap Dampening User Configurable Parameters";
                leaf enable-dampening  {
                    type  leafref {
                        path  "../config/enable-dampening";
                    }
                    description "This attribute enable BGP route dampening and set various parameters
                                to default values.";
                } // END of enable-dampening definition.

                container config {
                    description
                        "BGP Route Flap Dampening User Configurable Parameters";
                    uses route-flap-dampening-param-config;
                } // END of config-container definition.
                container state {
                    config false;
                    description
                        "Operational state data related to BGP Route Flap Dampening";
                    uses route-flap-dampening-param-config;
                    uses route-flap-dampening-state;
                } // END of state-container definition.
            } // End of route-flap-dampening-list
        } // END of route-flap-dampenings-container definition.
    } // END of route-flap-dampening-config-param definition.
    grouping as-origin-validation-config {
        description
            "Grouping for BGP AS Origin Validation User Configurable Parameters";
        leaf validation-enable  {
            type  empty;
            description "Enable BGP Origin Validation feature";
        } // END of validation-enable definition.

        leaf bestpath-use-validity  {
            type  empty;
            description "Enable to use BGP Origin Validation RPKI state for the best path
                        selection";
        } // END of bestpath-use-validity definition.

        leaf bestpath-allow-invalid  {
            type  empty;
            description "Enable to handle a route with invalid  RPKI state for the best path
                        selection";
        } // END of bestpath-allow-invalid definition.

    } // END of as-origin-validation-config definition.
    grouping as-origin-validation-config-param {
        description
            "Grouping for BGP AS Origin Validation User Configurable Parameters";
        container as-origin {
            if-feature feature-list:HAVE_BGP_RPKI_ORIGIN_VALIDATION;
            description
                "BGP AS Origin Validation User Configurable Parameters";
            container config {
                description
                    "BGP AS Origin Validation User Configurable Parameters";
                uses as-origin-validation-config;
            } // END of config-container definition.
            container state {
                config false;
                description
                    "Operational state data related to BGP Route Flap Dampening";
                uses as-origin-validation-config;
            } // END of state-container definition.
        } // END of as-origin-container definition.
    } // END of as-origin-validation-config-param definition.

    grouping  address-families-grouping {
    description
        "bgp address-family";
    container address-families {
        if-feature feature-list:HAVE_BGPD;
        description
            "bgp address-family";

        list address-family {
            key "afi safi";
            description
                "bgp address-family";
            leaf afi  {
                type  leafref {
                    path  "../config/afi";
                }
                description "BGP address family identifier";
            } // END of afi definition.

            leaf safi  {
                type  leafref {
                    path  "../config/safi";
                }
                description "BGP sub address family identifier";
            } // END of safi definition.

            container config {
                description
                    "Configuration data for bgp address family";
                uses address-family-config;
                uses address-family-common-config;
            } // END of config-container definition.
            container state {
                config false;
                description
                    "Operational state data for bgp address family";
                uses address-family-config;
                uses address-family-common-config;
            } // END of state-container definition.
            container network-lists {
                description
                    "Top level container for List of networks advertised by BGP";

                list network-list {
                    key "local-network-prefix";
                    description
                        "List of networks advertised by BGP";
                    leaf local-network-prefix  {
                        type  leafref {
                            path  "../config/local-network-prefix";
                        }
                        description "Use this attribute to specify the networks to be advertised by the BGP
                                    routing process. A unicast network address without a mask is accepted
                                    if it falls into the natural boundary of its class. A class-boundary
                                    mask is derived if the address matches its natural class-boundary.";
                    } // END of local-network-prefix definition.

                    container config {
                        description
                            "configuration parameters for address-family network list";
                        uses bgp-address-family-network-list-config;
                    } // END of config-container definition.
                    container state {
                        config false;
                        description
                            "state parameters for address-family network list";
                        uses bgp-network-list-state;
                        uses bgp-address-family-network-list-config;
                    } // END of state-container definition.
                } // End of network-list-list
            } // END of network-lists-container definition.
            uses aggregate-address-top;
            uses administrative-disatance-top;
            uses maximum-paths-top;
            uses table-map-top;
            uses route-flap-dampening-config-param;
            uses address-family-redist-list-top;
            uses bgp-redistribute-ospf-top;
            uses bgp-srv6-vpnv4-config;
            uses as-origin-validation-config-param;
        } // End of address-family-list
    } // END of address-families-container definition.
    } // END of address-families-grouping definition.


}
