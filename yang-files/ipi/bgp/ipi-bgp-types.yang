/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-bgp-types.yang
*
*/

module ipi-bgp-types {

    yang-version 1.1;

    namespace   "http://www.ipinfusion.com/yang/ocnos/ipi-bgp-types";

    prefix "ipi-bgp-types";

    import ietf-inet-types {
        prefix inet;
        revision-date 2013-07-15;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "YANG version of the ipi-bgp-types";


    revision "2025-12-22" {
        description "Added origin Autonomous System (AS) validation state enumarate";
        reference " 0.16.0.";
    }

    revision "2025-10-10" {
        description "Dlink 'disable-oper-logs' from 'debug bgp all'";
        reference " 0.15.4.";
    }

    revision "2025-09-15" {
        description "Revert updated BGP_ROUTE_TARGET_TYPE_T for EVPN VXLAN feature";
        reference " 0.15.3.";
    }

    revision "2025-09-11" {
        description "Updated BGP_ROUTE_TARGET_TYPE_T for EVPN VXLAN feature";
        reference " 0.15.3.";
    }

    revision "2025-08-20" {
        description "Introduced  new bgp debug options 'debug bgp rpki' ";
        reference " 0.15.2.";
    }

    revision "2025-08-08" {
        description "Added two new bgp debug options to disable oper logs";
        reference " 0.15.1.";
    }

    revision "2025-06-13" {
        description "Updated the description for the large community";
        reference " 0.15.0.";
    }

    revision "2025-01-20" {
        description "Added datattypes BGP_STANDARD_LIST_T and BGP_STANDARD_LIST_TYPE_T for large-community-list";
        reference " 0.14.9.";
    }

    revision "2025-01-15" {
        description "Updated the helpstring for ospf for redistributed routes";
        reference " 0.14.8.";
    }

    revision "2024-11-15" {
        description "Updated value of datatype BGP_VERSION_T";
        reference " 0.14.7.";
    }

    revision "2024-11-13" {
        description "Introduced new bgp debug option 'debug bgp peer'";
        reference " 0.14.6.";
    }

    revision "2024-11-11" {
        description "Introduced  new bgp debug options 'debug bgp route-process' and 'debug bgp evpn'  ";
        reference " 0.14.5.";
    }

    revision "2024-09-11" {
        description "Fix BGP address-family CLI helpstrings";
        reference " 0.14.4.";
    }

    revision "2024-09-05" {
        description "Updated if-feature for datatype BGP_REDISTRIBUTE_TYPE_T";
        reference " 0.14.3.";
    }

    revision "2024-09-03" {
        description "Added 'auto-policy-soft-reset enable' option under router bgp";
        reference " 0.14.2.";
    }

    revision "2024-08-22" {
        description "Removed datatype 'BGP_CONFIG_T'";
        reference " 0.14.1.";
    }

    revision "2024-06-20" {
        description "Added packet send and received elements under BGP_DEBUG_T attribute";
        reference " 0.14.0.";
    }

    revision "2024-06-04" {
        description "Introduced new bgp debug option 'debug bgp route-scan'";
        reference " 0.13.3.";
    }

    revision "2024-05-17" {
        description "Introduced a new bgp debug option 'debug bgp adj-out'";
        reference " 0.13.2.";
    }

    revision "2024-02-06" {
        description "Removed 'BGP_UPDATE_DEBUG_T' datatype and added updates in and updates out elements under 'BGP_DEBUG_T' datatype.";
        reference " 0.13.1.";
    }

    revision "2023-11-27" {
        description "Added new type BGP_UPDATE_CLEAR_T";
        reference " 0.13.0.";
    }

    revision "2023-11-17" {
        description "Added add-path debug option";
        reference " 0.12.5.";
    }

    revision "2023-10-29" {
        description "Added if-features to BGP_DEBUG_T";
        reference " 0.12.4.";
    }

    revision "2023-09-22" {
        description "Added new type BGP_PEER_TYPE_T";
        reference " 0.12.3.";
    }

    revision "2023-08-03" {
        description "Added new type BGP_EXT_COMMUNITY_RECV_TYPE_T";
        reference " 0.12.2.";
    }

    revision "2023-02-22" {
        description "Corrected the version and ref number";
        reference " 0.12.1.";
    }

    revision "2023-02-21" {
        description "BGP flowspec support";
        reference " 0.12.0.";
    }

    revision "2022-12-21" {
        description "Updated bgp debug options";
        reference " 0.11.1.";
    }

    revision "2022-11-11" {
        description "Added new type connected-host-route in redistribute types for EVPN IRB";
        reference " 0.11.0.";
    }

    revision "2022-09-26" {
        description "Updated the yang file for Large community feature";
        reference " 0.10.1.";
    }

    revision "2022-08-10" {
        description "Debug hierarchy change";
        reference " 0.10.0.";
    }

    revision "2022-06-01" {
        description "Updated the yang file with feature";
        reference " 0.9.0.";
    }

    revision "2022-04-28" {
        description "Updated BGP clear RPCs to remove unwanted attributes";
        reference " 0.8.1.";
    }

    revision "2022-04-04" {
        description "Defined New Datatype for BGP AIGP";
        reference " 0.8.0.";
    }

    revision "2022-01-17" {
        description "Defined New Datatype";
        reference " 0.7.1.";
    }

    revision "2022-01-07" {
        description "Defined New Datatype";
        reference " 0.7.0.";
    }

    revision "2021-09-03" {
        description "Update descriptions of attribute";
        reference " 0.6.1.";
    }

    revision "2021-08-16" {
        description "Updated the datatype from enum to bits for the additional-paths-mode attribute";
        reference " 0.6.0.";
    }

    revision "2021-05-27" {
        description "Corrected typo error in BGP_PEERFLAG_SHUTDOWN_T enum datatype";
        reference " 0.5.1.";
    }

    revision "2021-05-05" {
        description "Change related to BGP Unnumbered";
        reference " 0.5.0.";
    }

    revision "2021-04-09" {
        description "Change related to Peer group remodelling";
        reference " 0.4.0.";
    }

    revision "2021-03-05" {
        description "Community-list related changes";
        reference " 0.3.0.";
    }

    revision "2020-12-15" {
        description "Change to have data-types in lower case instead of camel case";
        reference " 0.2.0.";
    }

    revision "2020-09-10" {
        description "Initial Version";
        reference " 0.1.0.";
    }



    typedef  bgp_aigp_metric_cost_community_poi_t {
        type enumeration {
            enum pre-bestpath {
                value 128;
                description "insert before pre-bestpath criteria";
            }
            enum igp-cost {
                value 129;
                description "insert before igp-cost criteria";
            }
        }
        description "type definition for BGP_AIGP_METRIC_COST_COMMUNITY_POI_T";
    }

    typedef  cml_ospf_string_t {
        type string {
            pattern "[^?' =,>|]*";
        }
        description "type definition for CML_OSPF_STRING_T";
    }

    typedef  cml_ospf_area_id_t {
        type union {
            type cml_ospf_string_t {

            }
            type uint16 {
                range "1..65535";

            }
        }
        description "type definition for CML_OSPF_AREA_ID_T";
    }

    typedef  bgp_hostname_t {
        type union {
            type bgp_ip_addr_t {

            }
            type string {

            }
        }
        description "type definition for BGP_HOSTNAME_T";
    }

    typedef  bgp_md5_password_t {
        type string {
            pattern "[^? ]*";
        }
        description "type definition for BGP_MD5_PASSWORD_T";
    }

    typedef  bgp_dampening_t {
        type enumeration {
            enum enable-dampening {
                value 1;
                description "enable-dampening";
            }
        }
        description "type definition for BGP_DAMPENING_T";
    }

    typedef  bgp_afi_type_t {
        type enumeration {
            enum ipv4 {
                value 1;
                description "IPv4 address family";
            }
            enum ipv6 {
                value 2;
                description "IPv6 address family";
            }
            enum vpnv4 {
                value 3;
                description "VPNv4 address family";
            }
            enum vpnv6 {
                value 4;
                description "VPNv6 address family";
            }
            enum rtfilter {
                value 5;
                description "Route Target Filtering address family";
            }
            enum l2vpn {
                value 25;
                description "L2VPN address family";
            }
            enum link-state {
                value 16388;
                description "Link State address family";
            }
        }
        description "type definition for BGP_AFI_TYPE_T";
    }

    typedef  bgp_vrf_afi_type_t {
        type enumeration {
            enum ipv4 {
                value 1;
                description "IPv4 address family";
            }
            enum ipv6 {
                value 2;
                description "IPv6 address family";
            }
        }
        description "type definition for BGP_VRF_AFI_TYPE_T";
    }

    typedef  bgp_vrf_safi_type_t {
        type enumeration {
            enum unicast {
                value 1;
                description "Unicast address family modifier";
            }
            enum flowspec {
                value 133;
                description "Flow Specification address family modifier";
            }
        }
        description "type definition for BGP_VRF_SAFI_TYPE_T";
    }

    typedef  bgp_safi_type_t {
        type enumeration {
            enum unicast {
                value 1;
                description "Unicast address family modifier";
            }
            enum multicast {
                value 2;
                description "Multicast address family modifier";
            }
            enum labeled-unicast {
                value 4;
                description "Labeled Unicast address family modifier";
            }
            enum vpls {
                value 65;
                description "VPLS address family modifier";
            }
            enum evpn {
                value 70;
                description "EVPN address family modifier";
            }
            enum link-state {
                value 71;
                description "Link State address family modifier";
            }
            enum vpn-unicast {
                value 128;
                description "VPN Unicast address family modifier";
            }
            enum rtfilter-unicast {
                value 132;
                description "Route Target Filtering address family modifier";
            }
            enum flowspec {
                value 133;
                description "Flow Specification address family modifier";
            }
            enum flowspec-mpls-vpn {
                value 134;
                description "Flow Specification MPLS VPN address family modifier";
            }
        }
        description "type definition for BGP_SAFI_TYPE_T";
    }

    typedef  bgp_ip_network_t {
        type union {
            type inet:ipv4-address {

            }
            type inet:ipv4-prefix {

            }
            type inet:ipv6-prefix {

            }
        }
        description "type definition for BGP_IP_NETWORK_T";
    }

    typedef  bgp_route_target_t {
        type enumeration {
            enum rt {
                value 0;
                description "Specify route target";
            }
            enum soo {
                value 1;
                description "specify site of origin";
            }
        }
        description "type definition for BGP_ROUTE_TARGET_T";
    }

    typedef  bgp_af_config_t {
        type enumeration {
            enum all-afs {
                value 0;
                description "configure for all vpn address-families";
            }
            enum vpnv4 {
                value 1;
                description "Virtual Private Network version 4(VPNv4)";
            }
            enum vpnv6 {
                value 2;
                description "Virtual Private Network version 6(VPNv6)";
            }
        }
        description "type definition for BGP_AF_CONFIG_T";
    }

    typedef  bgp_all_vrf_t {
        type enumeration {
            enum all-vrfs {
                value 0;
                description "all-vrfs";
            }
        }
        description "type definition for BGP_ALL_VRF_T";
    }

    typedef  bgp_vrf_name_t {
        type string;
        description "type definition for BGP_VRF_NAME_T";
    }

    typedef  bgp_vrf_type_t {
        type union {
            type bgp_vrf_name_t {

            }
            type bgp_all_vrf_t {

            }
        }
        description "type definition for BGP_VRF_TYPE_T";
    }

    typedef  bgp_l3vpn_label_alloc_mode_t {
        type enumeration {
            enum per-prefix {
                value 0;
                description "configure mode to be per-prefix";
            }
            enum per-vrf {
                value 1;
                description "configure mode to be per-vrf";
            }
        }
        description "type definition for BGP_L3VPN_LABEL_ALLOC_MODE_T";
    }

    typedef  bgp_med_type_t {
        type bits {
            bit confed {
                position 0;
                description "Compare MED among confederation paths";
            }
            bit missing-as-worst {
                position 1;
                description "Treat missing MED as the least preferred one";
            }
            bit remove-recv-med {
                position 2;
                description "To remove rcvd MED attribute";
            }
            bit remove-send-med {
                position 3;
                description "To remove send MED attribute";
            }
        }
        description "type definition for BGP_MED_TYPE_T";
    }

    typedef  bgp_orf_prefix_type_t {
        type bits {
            bit receive {
                position 1;
                description "Capability to RECEIVE the ORF from this neighbor";
            }
            bit send {
                position 2;
                description "Capability to SEND the ORF to this neighbor";
            }
        }
        description "type definition for BGP_ORF_PREFIX_TYPE_T";
    }

    typedef  bgp_community_list_action_t {
        type enumeration {
            enum deny {
                value 1;
                description "Specify community to reject";
            }
            enum permit {
                value 2;
                description "Specify community to accept";
            }
        }
        description "type definition for BGP_COMMUNITY_LIST_ACTION_T";
    }

    typedef  bgp_community_list_type_t {
        type enumeration {
            enum standard {
                value 1;
                description "Specify standard community list";
            }
        }
        description "type definition for BGP_COMMUNITY_LIST_TYPE_T";
    }

    typedef  bgp_expanded_list_t {
        type enumeration {
            enum expanded {
                value 1;
                description "Specify expanded community list";
            }
        }
        description "type definition for BGP_EXPANDED_LIST_T";
    }

    typedef  bgp_expanded_list_type_t {
        type union {
            type uint32 {
                range "100..500";

            }
            type string {

            }
        }
        description "type definition for BGP_EXPANDED_LIST_TYPE_T";
    }

    typedef  bgp_ext_expanded_list_t {
        type enumeration {
            enum expanded {
                value 1;
                description "Specify expanded extcommunity-list";
            }
        }
        description "type definition for BGP_EXT_EXPANDED_LIST_T";
    }

    typedef  bgp_large_expanded_list_t {
        type enumeration {
            enum expanded {
                value 1;
                description "Specify expanded large-community list";
            }
        }
        description "type definition for BGP_LARGE_EXPANDED_LIST_T";
    }

    typedef  bgp_standard_list_t {
        type enumeration {
            enum standard {
                value 1;
                description "Specify standard large-community list";
            }
        }
        description "type definition for BGP_STANDARD_LIST_T";
    }

    typedef  bgp_standard_list_type_t {
        type union {
            type uint32 {
                range "1..99";

            }
            type string {

            }
        }
        description "type definition for BGP_STANDARD_LIST_TYPE_T";
    }

    typedef  bgp_additional_path_type_t {
        type bits {
            bit receive {
                position 1;
                description "Receive additional paths from neighbors";
            }
            bit send {
                position 2;
                description "Send additional paths to neighbors";
            }
        }
        description "type definition for BGP_ADDITIONAL_PATH_TYPE_T";
    }

    typedef  bgp_peer_additional_path_type_t {
        type bits {
            bit receive {
                position 1;
                description "Receive additional paths from neighbors";
            }
            bit send {
                position 2;
                description "Send additional paths to neighbors";
            }
            bit disable {
                position 4;
                description "disable additional-paths";
            }
        }
        description "type definition for BGP_PEER_ADDITIONAL_PATH_TYPE_T";
    }

    typedef  bgp_adv_rcv_type_t {
        type enumeration {
            enum advertise {
                value 1;
                description "advertised";
            }
            enum receive {
                value 2;
                description "received";
            }
            enum advertise-receive {
                value 3;
                description "advertised and received both";
            }
        }
        description "type definition for BGP_ADV_RCV_TYPE_T";
    }

    typedef  bgp_send_commu_type_t {
        type bits {
            bit standard {
                position 1;
                description "Send Standard Community attributes";
            }
            bit extended {
                position 2;
                description "Send Extended Community attributes";
            }
            bit large {
                position 3;
                description "Send Large Community attributes";
            }
        }
        description "type definition for BGP_SEND_COMMU_TYPE_T";
    }

    typedef  bgp_attribute_unchanged_type_t {
        type bits {
            bit as-path {
                position 1;
                description "As-path attribute";
            }
            bit next-hop {
                position 2;
                description "Next-hop attribute";
            }
            bit med {
                position 3;
                description "Med attribute";
            }
        }
        description "type definition for BGP_ATTRIBUTE_UNCHANGED_TYPE_T";
    }

    typedef  bgp_debug_t {
        type bits {
            bit nht {
                position 1;
                description "NHT message";
            }
            bit nsm {
                position 2;
                description "NSM message";
            }
            bit fsm {
                position 3;
                description "Finite state machine";
            }
            bit events {
                position 4;
                description "BGP events";
            }
            bit filters {
                position 5;
                description "BGP filter";
            }
            bit keepalives {
                position 6;
                description "BGP keepalives";
            }
            bit updates-in {
                position 7;
                description "BGP updates, Inbound";
            }
            bit updates-out {
                position 8;
                description "BGP updates, Outbound";
            }
            bit dampening {
                position 9;
                description "BGP Dampening";
            }
            bit bfd {
                position 10;
                if-feature feature-list:HAVE_BFD;
                description "Bidirectional Forwarding Detection (BFD)";
            }
            bit mpls {
                position 11;
                if-feature feature-list:HAVE_MPLS;
                description "BGP mpls";
            }
            bit vpls {
                position 12;
                if-feature feature-list:HAVE_BGP_VPLS;
                description "BGP vpls";
            }
            bit link-state {
                position 13;
                if-feature feature-list:HAVE_BGP_LS;
                description "BGP Link State";
            }
            bit rib {
                position 14;
                if-feature feature-list:HAVE_RIBD;
                description "BGP rib";
            }
            bit ha {
                position 15;
                if-feature feature-list:HAVE_HA;
                description "BGP HA";
            }
            bit srv6 {
                position 16;
                if-feature feature-list:HAVE_SRV6;
                description "BGP Srv6";
            }
            bit normal {
                position 17;
                description "BGP normal";
            }
            bit add-path {
                position 18;
                description "BGP additional-paths information";
            }
            bit adj-out {
                position 19;
                description "BGP advertise out updates";
            }
            bit route-scan {
                position 20;
                description "BGP Route Update scanning";
            }
            bit packet-send {
                position 21;
                description "BGP Packet send";
            }
            bit packet-received {
                position 22;
                description "BGP packet received";
            }
            bit soft-clear {
                position 23;
                description "BGP Soft clear Reset";
            }
            bit route-process {
                position 24;
                description "BGP route-process";
            }
            bit evpn {
                position 25;
                description "BGP EVPN";
            }
            bit peer {
                position 26;
                description "BGP Peer";
            }
            bit disable-evpn-info-oplog {
                position 27;
                description "Disable all EVPN Related BGP INFO level OPER_LOGS";
            }
            bit disable-all-info-oplog {
                position 28;
                description "Disable all BGP INFO level OPER_LOGS";
            }
            bit rpki {
                position 29;
                description "BGP RPKI AS Validation";
            }
        }
        description "type definition for BGP_DEBUG_T";
    }

    typedef  bgp_distribute_list_direction_t {
        type enumeration {
            enum in {
                value 0;
                description "Filter incoming updates";
            }
            enum out {
                value 1;
                description "Filter outgoing updates";
            }
        }
        description "type definition for BGP_DISTRIBUTE_LIST_DIRECTION_T";
    }

    typedef  bgp_redistribute_type_t {
        type enumeration {
            enum kernel {
                value 1;
                if-feature feature-list:HAVE_SWFWDR;
                description "Kernel routes";
            }
            enum connected {
                value 2;
                description "Connected";
            }
            enum static {
                value 3;
                description "Static routes";
            }
            enum rip {
                value 4;
                description "Routing Information Protocol(RIP)";
            }
            enum ospf {
                value 5;
                description "Open Shortest Path First (OSPF)";
            }
            enum isis {
                value 6;
                description "ISO IS-IS";
            }
            enum connected-host-routes {
                value 7;
                description "Connected host to routes";
            }
        }
        description "type definition for BGP_REDISTRIBUTE_TYPE_T";
    }

    typedef  bgp_peer_status_t {
        type enumeration {
            enum idle {
                value 1;
                description "Idle";
            }
            enum connect {
                value 2;
                description "Connect";
            }
            enum active {
                value 3;
                description "Active";
            }
            enum opensent {
                value 4;
                description "Opensent";
            }
            enum openconfirm {
                value 5;
                description "Openconfirm";
            }
            enum established {
                value 6;
                description "Established";
            }
        }
        description "type definition for BGP_PEER_STATUS_T";
    }

    typedef  bgp_peerflag_shutdown_t {
        type enumeration {
            enum idle {
                value 1;
                description "Idle";
            }
            enum connect {
                value 2;
                description "Connect";
            }
            enum active {
                value 3;
                description "Active";
            }
            enum opensent {
                value 4;
                description "Opensent";
            }
            enum openconfirm {
                value 5;
                description "Openconfirm";
            }
            enum established {
                value 6;
                description "Established";
            }
            enum idle-admin {
                value 7;
                description "Idle Admin";
            }
            enum idle-pfxct {
                value 8;
                description "Idle PfxCt";
            }
            enum idle-g-shut {
                value 9;
                description "Idle G-shut";
            }
        }
        description "type definition for BGP_PEERFLAG_SHUTDOWN_T";
    }

    typedef  bgp_prefix_entry_type_t {
        type enumeration {
            enum no_match {
                value 1;
                description "No match";
            }
            enum deny {
                value 2;
                description "Deny";
            }
            enum permit {
                value 3;
                description "Permit";
            }
        }
        description "type definition for BGP_PREFIX_ENTRY_TYPE_T";
    }

    typedef  bgp_ri_type_t {
        type enumeration {
            enum internal {
                value 1;
                description "internal";
            }
            enum confed-external {
                value 2;
                description "confed-external";
            }
            enum external {
                value 3;
                description "external";
            }
            enum aggregated-and-local {
                value 4;
                description "aggregated,and,local";
            }
            enum sourced {
                value 5;
                description "sourced";
            }
            enum sourced-and-local {
                value 6;
                description "sourced,and,local";
            }
        }
        description "type definition for BGP_RI_TYPE_T";
    }

    typedef  bgp_origin_t {
        type enumeration {
            enum igp {
                value 0;
                description "IGP";
            }
            enum egp {
                value 1;
                description "EGP";
            }
            enum incomplete {
                value 2;
                description "incomplete";
            }
        }
        description "type definition for BGP_ORIGIN_T";
    }

    typedef  bgp_link_type_t {
        type enumeration {
            enum internal {
                value 0;
                description "internal";
            }
            enum external {
                value 1;
                description "external";
            }
        }
        description "type definition for BGP_LINK_TYPE_T";
    }

    typedef  bgp_connection_type_t {
        type enumeration {
            enum shared {
                value 0;
                description "shared network";
            }
            enum non_shared {
                value 1;
                description "non shared network";
            }
        }
        description "type definition for BGP_CONNECTION_TYPE_T";
    }

    typedef  bgp_cluster_id_t {
        type union {
            type inet:ipv4-address {

            }
            type uint32 {
                range "1..4294967295";

            }
        }
        description "type definition for BGP_CLUSTER_ID_T";
    }

    typedef  bgp_md5_t {
        type enumeration {
            enum 0 {
                value 1;
                description "Unencrypted password (key)";
            }
            enum 1 {
                value 2;
                description "Encrypted password (key)";
            }
        }
        description "type definition for BGP_MD5_T";
    }

    typedef  bgp_target_route_type_t {
        type bits {
            bit import {
                position 0;
                description "import";
            }
            bit export {
                position 1;
                description "export";
            }
        }
        description "type definition for BGP_TARGET_ROUTE_TYPE_T";
    }

    typedef  bgp_aggregate_type_t {
        type enumeration {
            enum as-set {
                value 1;
                description "shared network";
            }
            enum summary-only {
                value 2;
                description "non shared network";
            }
            enum as-set-and-summary-only {
                value 3;
                description "non shared network";
            }
        }
        description "type definition for BGP_AGGREGATE_TYPE_T";
    }

    typedef  bgp_capability_type_t {
        type enumeration {
            enum advertised {
                value 1;
                description "Advertised Capability";
            }
            enum received {
                value 2;
                description "Received Capability";
            }
            enum advertised-and-received {
                value 3;
                description "Advertised,and,Received Capability";
            }
        }
        description "type definition for BGP_CAPABILITY_TYPE_T";
    }

    typedef  bgp_version_t {
        type enumeration {
            enum 4 {
                value 4;
                description "BGP Version 4";
            }
        }
        description "type definition for BGP_VERSION_T";
    }

    typedef  bgp_route_refresh_cap_type_t {
        type enumeration {
            enum advertised {
                value 1;
                description "advertised";
            }
            enum received-old {
                value 2;
                description "received old";
            }
            enum received-new {
                value 3;
                description "received new";
            }
            enum received-old-and-new {
                value 4;
                description "received old and new";
            }
            enum advertised-and-received-old {
                value 5;
                description "advertised and received old";
            }
            enum advertised-and-received-new {
                value 6;
                description "advertised and received new";
            }
            enum advertised-and-received-old-and-new {
                value 7;
                description "advertised and received old and new";
            }
        }
        description "type definition for BGP_ROUTE_REFRESH_CAP_TYPE_T";
    }

    typedef  bgp_vrf_rt_t {
        type string {
            pattern ".*:.*";
        }
        description "type definition for BGP_VRF_RT_T";
    }

    typedef  bgp_evpn_auto_rt_t {
        type enumeration {
            enum evpn-auto-rt {
                value 1;
                description "EVPN Auto RT";
            }
        }
        description "type definition for BGP_EVPN_AUTO_RT_T";
    }

    typedef  bgp_route_target_type_t {
        type union {
            type bgp_vrf_rt_t {

            }
            type bgp_evpn_auto_rt_t {

            }
        }
        description "type definition for BGP_ROUTE_TARGET_TYPE_T";
    }

    typedef  bgp_peer_group_static_t {
        type enumeration {
            enum static {
                value 0;
                description "static";
            }
        }
        description "type definition for BGP_PEER_GROUP_STATIC_T";
    }

    typedef  bgp_peer_group_range_t {
        type string;
        description "type definition for BGP_PEER_GROUP_RANGE_T";
    }

    typedef  bgp_peer_group_type_t {
        type union {
            type bgp_peer_group_range_t {

            }
            type bgp_peer_group_static_t {

            }
        }
        description "type definition for BGP_PEER_GROUP_TYPE_T";
    }

    typedef  bgp_as_t {
        type enumeration {
            enum internal {
                value -2;
                description "internal for iBGP peer";
            }
            enum external {
                value -1;
                description "external for eBGP peer";
            }
        }
        description "type definition for BGP_AS_T";
    }

    typedef  bgp_as_type_t {
        type union {
            type bgp_as_t {

            }
            type int64 {
                range "1..4294967295";

            }
        }
        description "type definition for BGP_AS_TYPE_T";
    }

    typedef  bgp_ip_addr_t {
        type union {
            type inet:ipv4-address {

            }
            type inet:ipv6-address {

            }
            type string {

            }
        }
        description "type definition for BGP_IP_ADDR_T";
    }

    typedef  bgp_sid_alloc_type_t {
        type enumeration {
            enum per-vrf {
                value 1;
                description "per-vrf";
            }
        }
        description "type definition for BGP_SID_ALLOC_TYPE_T";
    }

    typedef  bgp_peer_type_t {
        type enumeration {
            enum ibgp {
                value 0;
                description "iBGP peer";
            }
            enum ebgp {
                value 1;
                description "eBGP peer";
            }
            enum internal {
                value 2;
                description "internal peer";
            }
            enum confed {
                value 3;
                description "confederation peer";
            }
            enum eibgp {
                value 4;
                description "eibgp peer";
            }
        }
        description "type definition for BGP_PEER_TYPE_T";
    }

    typedef  bgp_update_clear_t {
        type enumeration {
            enum out {
                value 2;
                description "Outbound updates";
            }
            enum in {
                value 3;
                description "Inbound updates";
            }
            enum soft-only {
                value 4;
                description "soft only config";
            }
        }
        description "type definition for BGP_UPDATE_CLEAR_T";
    }

    typedef  bgp_rpki_o_as_validation_state {
        type enumeration {
            enum Valid {
                value 0;
                description "At least one Validated ROA Payload Matches the Route Prefix";
            }
            enum Not-found {
                value 1;
                description "No Validated ROA Payload Covers the Route Prefix";
            }
            enum Invalid {
                value 2;
                description "At least one Validated ROA Payload Covers the Route Prefix but no Validated ROA Payload Matches it";
            }
            enum Disabled {
                value 3;
                description "The router is aware of the RPKI data but is not actively validating this route";
            }
        }
        description "type definition for BGP_RPKI_O_AS_VALIDATION_STATE";
    }

}
