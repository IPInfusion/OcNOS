/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-bgp-flowspec.yang
*
*/

submodule ipi-bgp-flowspec {

    yang-version 1.1;

    belongs-to  ipi-bgp { prefix ipi-bgp; }

    import feature-list {
        prefix feature-list;
        revision-date 2026-09-15;
    }

    import ipi-bgp-types {
        prefix ipi-bgp-types;
        revision-date 2025-12-22;
    }

    import ipi-bgp-flowspec-types {
        prefix ipi-bgp-flowspec-types;
        revision-date 2026-02-04;
    }

    import ipi-enhanced-pbr-types {
        prefix ipi-enhanced-pbr-types;
        revision-date 2023-02-28;
    }

    organization
        "IP Infusion Inc.";

    contact
        "Address: 3965 Freedom Circle, Suite 200, Santa Clara, CA 95054
         Phone: +1 408-400-1900
         E-mail: support@ipinfusion.com
         Web: http://www.ipinfusion.com/";

    description
        "BGP FLow Specification (FLOWSPEC)";


    revision "2026-02-12" {
        description "Change the DSCP data type to be displayed in HEX format";
        reference " 0.2.1.";
    }

    revision "2026-02-04" {
        description "Add state attributes for BGP Flow Specification";
        reference " 0.2.0.";
    }

    revision "2025-01-09" {
        description "afi-type internal error correction";
        reference " 0.1.2.";
    }

    revision "2024-06-25" {
        description "added needed dependacies to contorller and vrf";
        reference " 0.1.0.";
    }

    revision "2024-02-08" {
        description "Added enclosing containers for objectlists";
        reference " 0.2.0.";
    }

    revision "2023-03-12" {
        description "packet-length attribute corrections";
        reference " 0.1.3.";
    }

    revision "2023-03-08" {
        description "db-sync issue correction";
        reference " 0.1.2.";
    }

    revision "2023-02-28" {
        description "split class-map/policy-map configuration to enhanced-pbr.xml";
        reference " 0.1.1.";
    }

    revision "2023-01-23" {
        description "Initial Version";
        reference " 0.1.0.";
    }

    grouping flowspec-controller-config {
        description
            "grouping for FLOWSPEC controller config";
        leaf enable-flowspec-controller  {
            type  empty;
            description "Use this attribute to controllersly enable or disable FLOWSPEC
                        controller";
        } // END of enable-flowspec-controller definition.

        leaf local-install  {
            type  ipi-bgp-flowspec-types:flowspec_local_install_t;
            default "interface-all";
            description "Use this attribute to specify local-install for policy-map PBR";
        } // END of local-install definition.

    } // END of flowspec-controller-config definition.
    grouping flowspec-default-vrf_address-family-config {
        description
            "grouping for FLOWSPEC default VRF address-family config";
        leaf afi-type  {
            type  ipi-bgp-flowspec-types:flowspec_afi_type_t;
            description "specify an address-family";
        } // END of afi-type definition.

        leaf local-install  {
            type  ipi-bgp-flowspec-types:flowspec_local_install_t;
            default "interface-all";
            description "Use this attribute to specify local-install for policy-map PBR";
        } // END of local-install definition.

    } // END of flowspec-default-vrf_address-family-config definition.
    grouping flowspec-default_vrf_service_policy-config {
        description
            "grouping for FLOWSPEC default VRF service-policy config";
        leaf attached-policy-map-name  {
            type  string {
                length "1..1965";
                pattern "[^?' =,>|]+";
            }
            description "Use this attribute to specify attached-policy-map-name";
        } // END of attached-policy-map-name definition.

        leaf service-policy-type  {
            type  ipi-enhanced-pbr-types:epbr_policy_map_t;
            description "Use this attribute to specify service-policy-type";
        } // END of service-policy-type definition.

    } // END of flowspec-default_vrf_service_policy-config definition.
    grouping flowspec-vrf-config {
        description
            "grouping for FLOWSPEC VRF config";
        leaf vrf-name  {
            type  string {
                length "1..1965";
                pattern "[^?' =,>|]+";
            }
            description "Use this attribute to show the VRF name";
        } // END of vrf-name definition.

        leaf local-install  {
            type  ipi-bgp-flowspec-types:flowspec_local_install_t;
            default "interface-all";
            description "Use this attribute to specify local-install for policy-map PBR";
        } // END of local-install definition.

    } // END of flowspec-vrf-config definition.
    grouping flowspec-vrf-address-family_config {
        description
            "grouping for FLOWSPEC VRF address-family config";
        leaf afi-type  {
            type  ipi-bgp-flowspec-types:flowspec_afi_type_t;
            description "specify afi type for an address-family";
        } // END of afi-type definition.

        leaf local-install  {
            type  ipi-bgp-flowspec-types:flowspec_local_install_t;
            default "interface-all";
            description "Use this attribute to specify local-install for policy-map PBR";
        } // END of local-install definition.

    } // END of flowspec-vrf-address-family_config definition.
    grouping flowspec-vrf-service-policy_config {
        description
            "grouping for FLOWSPEC VRF service-policy config";
        leaf attached-policy-map-name  {
            type  string {
                length "1..1965";
                pattern "[^?' =,>|]+";
            }
            description "Use this attribute to specify attached-policy-map-name";
        } // END of attached-policy-map-name definition.

        leaf service-policy-type  {
            type  ipi-enhanced-pbr-types:epbr_policy_map_t;
            description "Use this attribute to specify service-policy-type";
        } // END of service-policy-type definition.

    } // END of flowspec-vrf-service-policy_config definition.
    grouping flowspec-top {
        description
            "Top-level grouping for FLOWSPEC";

        list controller {
        // when " ipi-bgp-instance:bgp-instances/bgp-instance/bgp-as ";
            key "enable-flowspec-controller";
            description
                "Configuration data for FLOWSPEC";
            leaf enable-flowspec-controller  {
                type  leafref {
                    path  "../config/enable-flowspec-controller";
                }
                description "Use this attribute to controllersly enable or disable FLOWSPEC
                            controller";
            } // END of enable-flowspec-controller definition.

            container config {
                description
                    "Configuration data for FLOWSPEC";
                uses flowspec-controller-config;
            } // END of config-container definition.
            container state {
                config false;
                description
                    "Operational state data for class for FLOWSPEC controller";
                uses flowspec-controller-config;
            } // END of state-container definition.
            container address-families {
                description
                    "Configuration data for address family of FLOWSPEC";

                list address-family {
                    key "afi-type";
                    description
                        "configuring address-family";
                    leaf afi-type  {
                        type  leafref {
                            path  "../config/afi-type";
                        }
                        description "specify AFI_TYPE for an address-family";
                    } // END of afi-type definition.

                    container config {
                        description
                            "configuring for address-family";
                        uses flowspec-default-vrf_address-family-config;
                    } // END of config-container definition.
                    container state {
                        config false;
                        description
                            "Operational state data for class for FLOWSPEC default VRF
                                    address-family";
                        uses flowspec-default-vrf_address-family-config;
                    } // END of state-container definition.
                    container service-policies {
                        description
                            "Enclosing container of  service-policy for BGP_FLOWSPEC";

                        list service-policy {
                            key "attached-policy-map-name service-policy-type";
                            description
                                "Attach service-policy for BGP_FLOWSPEC";
                            leaf attached-policy-map-name  {
                                type  leafref {
                                    path  "../config/attached-policy-map-name";
                                }
                                description "Use this attribute to specify attached-policy-map-name";
                            } // END of attached-policy-map-name definition.

                            leaf service-policy-type  {
                                type  leafref {
                                    path  "../config/service-policy-type";
                                }
                                description "Use this attribute to specify service-policy-type";
                            } // END of service-policy-type definition.

                            container config {
                                description
                                    "config";
                                uses flowspec-default_vrf_service_policy-config;
                            } // END of config-container definition.
                            container state {
                                config false;
                                description
                                    "Operational state data for class for FLOWSPEC default VRF
                                            address-family";
                                uses flowspec-default_vrf_service_policy-config;
                            } // END of state-container definition.
                        } // End of service-policy-list
                    } // END of service-policies-container definition.
                } // End of address-family-list
            } // END of address-families-container definition.
            container vrfs {
                description
                    "Configuration data for vrfs of FLOWSPEC";

                list vrf {
                // when " ipi-bgp-vrf:bgp-vrf/config/rd-string ";
                    key "vrf-name";
                    description
                        "Configuratoin data list for BGP FLOWSPEC VRF";
                    leaf vrf-name  {
                        type  leafref {
                            path  "../config/vrf-name";
                        }
                        description "Use this attribute to show the VRF name";
                    } // END of vrf-name definition.

                    container config {
                        description
                            "config";
                        uses flowspec-vrf-config;
                    } // END of config-container definition.
                    container state {
                        config false;
                        description
                            "Operational state data for FLOWSPEC default VRF config";
                        uses flowspec-vrf-config;
                    } // END of state-container definition.
                    container address-families {
                        description
                            "configuring address-families";

                        list address-family {
                            key "afi-type";
                            description
                                "configuring address-family";
                            leaf afi-type  {
                                type  leafref {
                                    path  "../config/afi-type";
                                }
                                description "specify afi type for an address-family";
                            } // END of afi-type definition.

                            container config {
                                description
                                    "config";
                                uses flowspec-vrf-address-family_config;
                            } // END of config-container definition.
                            container state {
                                config false;
                                description
                                    "Operational state data for FLOWSPEC VRF address-family config";
                                uses flowspec-vrf-address-family_config;
                            } // END of state-container definition.
                            container service-policies {
                                description
                                    "Enclosing container of service-policy for BGP_FLOWSPEC";

                                list service-policy {
                                    key "attached-policy-map-name service-policy-type";
                                    description
                                        "Attach service-policy for BGP_FLOWSPEC";
                                    leaf attached-policy-map-name  {
                                        type  leafref {
                                            path  "../config/attached-policy-map-name";
                                        }
                                        description "Use this attribute to specify attached-policy-map-name";
                                    } // END of attached-policy-map-name definition.

                                    leaf service-policy-type  {
                                        type  leafref {
                                            path  "../config/service-policy-type";
                                        }
                                        description "Use this attribute to specify service-policy-type";
                                    } // END of service-policy-type definition.

                                    container config {
                                        description
                                            "config";
                                        uses flowspec-vrf-service-policy_config;
                                    } // END of config-container definition.
                                    container state {
                                        config false;
                                        description
                                            "Operational state data for FLOWSPEC VRF service-policy config";
                                        uses flowspec-vrf-service-policy_config;
                                    } // END of state-container definition.
                                } // End of service-policy-list
                            } // END of service-policies-container definition.
                        } // End of address-family-list
                    } // END of address-families-container definition.
                } // End of vrf-list
            } // END of vrfs-container definition.
        } // End of controller-list
    } // END of flowspec-top definition.
    grouping flowspec-controllers-top {
        description
            "Top-level grouping for FLOWSPEC";
        container controllers {
            description
                "Configuration data for controllers FLOWSPEC";
            uses flowspec-top;
        } // END of controllers-container definition.
    } // END of flowspec-controllers-top definition.
    grouping flowspec-info-ip-addresses-state {
        description
            "Grouping for BGP Flow Specification IP addresses attributes";
        leaf destination-address  {
            type  ipi-bgp-types:bgp_ip_addr_t;
            description "Destination IP address";
        } // END of destination-address definition.

        leaf source-address  {
            type  ipi-bgp-types:bgp_ip_addr_t;
            description "Source IP address";
        } // END of source-address definition.

    } // END of flowspec-info-ip-addresses-state definition.
    grouping flowspec-info-traffic-rate-action-state {
        description
            "Grouping for BGP Flow Specification Traffic Rate action attributes";
        leaf rate  {
            type  uint32;
            description "BGP Flow Specification policy rate value";
        } // END of rate definition.

        leaf rate-unit  {
            type  ipi-bgp-flowspec-types:bgp_flowspec_rate_unit_t;
            description "BGP Flow Specification policy rate unit";
        } // END of rate-unit definition.

    } // END of flowspec-info-traffic-rate-action-state definition.
    grouping flowspec-info-traffic-action-state {
        description
            "Grouping for BGP Flow Specification Traffic Action attributes";
        leaf terminal-action  {
            type  empty;
            description "BGP Flow Specification terminal action set";
        } // END of terminal-action definition.

        leaf sample-action  {
            type  empty;
            description "BGP Flow Specification sample action set";
        } // END of sample-action definition.

    } // END of flowspec-info-traffic-action-state definition.
    grouping flowspec-info-traffic-redirect-action-state {
        description
            "Grouping for BGP Flow Specification Traffic Redirect action attributes";
        leaf as-type  {
            type  ipi-bgp-flowspec-types:bgp_flowspec_redirect_as_type_t;
            description "BGP Flow Specification Autonomous System type";
        } // END of as-type definition.

        leaf route-target-as  {
            type  string {
                length "1..1965";
                pattern "[^?' =,>|]+";
            }
            description "BGP Flow Specification Route Target AS - (AS:nn)";
        } // END of route-target-as definition.

        leaf vrf-id  {
            type  uint32;
            description "BGP Flow Specification VRF id";
        } // END of vrf-id definition.

        leaf fib-id  {
            type  uint32;
            description "BGP Flow Specification VRF FIB id";
        } // END of fib-id definition.

        leaf route-target-ip  {
            type  string {
                length "1..1965";
                pattern "[^?' =,>|]+";
            }
            description "BGP Flow Specification Route Target IP - (IP:nn)";
        } // END of route-target-ip definition.

    } // END of flowspec-info-traffic-redirect-action-state definition.
    grouping flowspec-info-set-dscp-action-state {
        description
            "Grouping for BGP Flow Specification Set DSCP Action attributes";
        leaf dscp  {
            type  ipi-enhanced-pbr-types:epbr_hex_dscp_t;
            description "BGP Flow Specification DSCP value to be used on flow action";
        } // END of dscp definition.

    } // END of flowspec-info-set-dscp-action-state definition.
    grouping flowspec-info-flow-actions-top {
        description
            "Top level grouping for BGP Flow Specification Actions";
        container actions {
            config false;
            description
                "Top level container for BGP Flow Specification actions";
            container traffic-rate {
                config false;
                description
                    "BGP Flow Specification Traffic Rate action";
                container state {
                    config false;
                    description
                        "Operational state data for BGP Flow Specification Traffic Rate action";
                    uses flowspec-info-traffic-rate-action-state;
                } // END of state-container definition.
            } // END of traffic-rate-container definition.
            container traffic-action {
                config false;
                description
                    "BGP Flow Specification Traffic Action field";
                container state {
                    config false;
                    description
                        "Operational state data for BGP Flow Specification Traffic Rate action";
                    uses flowspec-info-traffic-action-state;
                } // END of state-container definition.
            } // END of traffic-action-container definition.
            container traffic-redirect {
                config false;
                description
                    "BGP Flow Specification Traffic Redirect action";
                container state {
                    config false;
                    description
                        "Operational state data for BGP Flow Specification Traffic Redirect
                                action";
                    uses flowspec-info-traffic-redirect-action-state;
                } // END of state-container definition.
            } // END of traffic-redirect-container definition.
            container set-dscp {
                config false;
                description
                    "BGP Flow Specification Traffic Rate Set DSCP action";
                container state {
                    config false;
                    description
                        "Operational state data for BGP Flow Specification Set DSCP action";
                    uses flowspec-info-set-dscp-action-state;
                } // END of state-container definition.
            } // END of set-dscp-container definition.
        } // END of actions-container definition.
    } // END of flowspec-info-flow-actions-top definition.
    grouping flowspec-info-flow-matches-top {
        description
            "Top level grouping for BGP Flow Specification Matches";
        container matches {
            config false;
            description
                "Top level container for BGP Flow Specification matches";
            container ip-addresses {
                config false;
                description
                    "BGP Flow Specification IP Addresses";
                container state {
                    config false;
                    description
                        "Operational state data for BGP Flow Specification IP addresses";
                    uses flowspec-info-ip-addresses-state;
                } // END of state-container definition.
            } // END of ip-addresses-container definition.
            container state {
                config false;
                description
                    "Operational state data for BGP Flow Specification match components";
                leaf-list ip-protocol-operator-value  {
                    type  string {
                        length "1..1965";
                    }
                    description "Display the bitmap and value for BGP Flow Specification IP protocol
                                component - RFC-8955(4.2.1.)";
                } // END of ip-protocol-operator-value definition.

                leaf-list tcp-udp-port-operator-value  {
                    type  string {
                        length "1..1965";
                    }
                    description "Display the bitmap and value for BGP Flow Specification TCP/UDP port
                                component - RFC-8955(4.2.1.)";
                } // END of tcp-udp-port-operator-value definition.

                leaf-list tcp-udp-destination-port-operator-value  {
                    type  string {
                        length "1..1965";
                    }
                    description "Display the bitmap and value for BGP Flow Specification UDP
                                destination port component - RFC-8955(4.2.1.)";
                } // END of tcp-udp-destination-port-operator-value definition.

                leaf-list tcp-udp-source-port-operator-value  {
                    type  string {
                        length "1..1965";
                    }
                    description "Display the bitmap and value for BGP Flow Specification UDP source
                                port component - RFC-8955(4.2.1.)";
                } // END of tcp-udp-source-port-operator-value definition.

                leaf-list packet-length-operator-value  {
                    type  string {
                        length "1..1965";
                    }
                    description "Display the bitmap and value for BGP Flow Specification packet length
                                component - RFC-8955(4.2.1.)";
                } // END of packet-length-operator-value definition.

                leaf-list tcp-flags-operator-value  {
                    type  string {
                        length "1..1965";
                    }
                    description "Display the bitmap and value for BGP Flow Specification TCP flags
                                component - RFC-8955(4.2.1.)";
                } // END of tcp-flags-operator-value definition.

                leaf-list icmp-type-operator-value  {
                    type  string {
                        length "1..1965";
                    }
                    description "Display the bitmap and value for BGP Flow Specification ICMP type
                                component - RFC-8955(4.2.1.)";
                } // END of icmp-type-operator-value definition.

                leaf-list icmp-code-operator-value  {
                    type  string {
                        length "1..1965";
                    }
                    description "Display the bitmap and value for BGP Flow Specification ICMP code
                                component - RFC-8955(4.2.1.)";
                } // END of icmp-code-operator-value definition.

                leaf-list dscp-operator-value  {
                    type  string {
                        length "1..1965";
                    }
                    description "Display the bitmap and value for BGP Flow Specification DSCP component
                                - RFC-8955(4.2.1.)";
                } // END of dscp-operator-value definition.

                leaf-list fragment-operator-value  {
                    type  string {
                        length "1..1965";
                    }
                    description "Display the bitmap and value for BGP Flow Specification fragment
                                component - RFC-8955(4.2.1.)";
                } // END of fragment-operator-value definition.

            } // END of state-container definition.
        } // END of matches-container definition.
    } // END of flowspec-info-flow-matches-top definition.
    grouping flowspec-info-flow-state {
        description
            "Grouping for BGP Flow Specification Info attributes";
        leaf flow-key  {
            type  string {
                length "1..1965";
            }
            description "Use this attribute to show the BGP Flow Specification key name";
        } // END of flow-key definition.

    } // END of flowspec-info-flow-state definition.
    grouping flowspec-info-flows-top {
        description
            "Top-level grouping for BGP Flow Specification Info";
        container flows {
            config false;
            description
                "Top level container for BGP Flow Specification";

            list flow {
                key "flow-key";
                config false;
                description
                    "BGP Flow Specification list";
                leaf flow-key  {
                    type  leafref {
                        path  "../state/flow-key";
                    }
                    description "Use this attribute to show the BGP Flow Specification key name";
                } // END of flow-key definition.

                container state {
                    config false;
                    description
                        "Operational state data for BGP Flow Specification";
                    uses flowspec-info-flow-state;
                } // END of state-container definition.
                uses flowspec-info-flow-matches-top;
                uses flowspec-info-flow-actions-top;
            } // End of flow-list
        } // END of flows-container definition.
    } // END of flowspec-info-flows-top definition.
    grouping flowspec-info-vrf-state {
        description
            "Grouping for BGP Flow Specification Info VRFs";
        leaf vrf-name  {
            type  string {
                length "1..1965";
                pattern "[^?' =,>|]+";
            }
            description "Use this attribute to show the VRF name";
        } // END of vrf-name definition.

    } // END of flowspec-info-vrf-state definition.
    grouping flowspec-info-vrfs-top {
        description
            "Top-level grouping for BGP Flow Specification Info VRFs";
        container vrfs {
            config false;
            description
                "Top level container for BGP Flow Specification on each VRF";

            list vrf {
                key "vrf-name";
                config false;
                description
                    "VRF list for BGP Flow Specification";
                leaf vrf-name  {
                    type  leafref {
                        path  "../state/vrf-name";
                    }
                    description "Use this attribute to show the VRF name";
                } // END of vrf-name definition.

                container state {
                    config false;
                    description
                        "Operational state data for BGP Flow Specification VRFs";
                    uses flowspec-info-vrf-state;
                } // END of state-container definition.
                uses flowspec-info-flows-top;
            } // End of vrf-list
        } // END of vrfs-container definition.
    } // END of flowspec-info-vrfs-top definition.

    grouping  flowspec-grouping {
    description
        "BGP Flow Specification (FLOWSPEC)";
    container flowspec {
        if-feature feature-list:HAVE_BGP_FLOWSPEC;
        if-feature feature-list:HAVE_BGPD;
        description
            "BGP Flow Specification (FLOWSPEC)";
        uses flowspec-controllers-top;
    } // END of flowspec-container definition.
    } // END of flowspec-grouping definition.

    grouping  flowspec-info-grouping {
    description
        "BGP Flow Specification Info";
    container flowspec-info {
        if-feature feature-list:HAVE_BGP_FLOWSPEC;
        if-feature feature-list:HAVE_BGPD;
        config false;
        description
            "BGP Flow Specification Info";
        uses flowspec-info-vrfs-top;
    } // END of flowspec-info-container definition.
    } // END of flowspec-info-grouping definition.


}
