/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-bgp-evpn-rib.yang
*
*/

submodule ipi-bgp-evpn-rib {

    yang-version 1.1;

    belongs-to  ipi-bgp { prefix ipi-bgp; }

    import feature-list {
        prefix feature-list;
        revision-date 2026-09-15;
    }

    import cml-data-types {
        prefix cml-data-types;
        revision-date 2026-05-15;
    }

    import ietf-inet-types {
        prefix inet;
        revision-date 2013-07-15;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for bgp evpn rib";


    revision "2023-09-12" {
        description "Added enclosing container for all objectlists";
        reference " 0.4.1.";
    }

    revision "2023-04-24" {
        description "Changed data-type for host-ip-address";
        reference " 0.4.0.";
    }

    revision "2022-06-01" {
        description "Updated the yang file with feature";
        reference " 0.3.0.";
    }

    revision "2021-09-03" {
        description "Update descriptions of attribute";
        reference "Initial Version";
    }

    revision "2021-07-21" {
        description "Initial Version. Added get api related attributes";
        reference "Initial Version";
    }

    grouping bgp-evpn-route-state {
        description
            "State parameter for BGP-EVPN routes";
        leaf route-distinguisher  {
            type  string {
                length "1..1965";
                pattern "[^?' =,>|]+";
            }
            description "Route distinguisher";
        } // END of route-distinguisher definition.

        leaf vrf-name  {
            type  string {
                length "1..1965";
                pattern "[^?' =,>|]+";
            }
            description "vrf under which routes are distributed";
        } // END of vrf-name definition.

    } // END of bgp-evpn-route-state definition.
    grouping bgp-evpn-mac-ip-route-state {
        description
            "State parameter for BGP-EVPN mac-ip route-type";
        leaf host-mac-address  {
            type  cml-data-types:cml_mac_addr_t {
                length "1..1965";
            }
            description "Host Mac Address of BGP-EVPN route";
        } // END of host-mac-address definition.

        leaf host-ip-address  {
            type  inet:ip-address;
            description "Host Ip-Address of BGP-EVPN route";
        } // END of host-ip-address definition.

        leaf ethernet-tag-identifier  {
            type  uint32;
            description "Ethernet tag ID of BGP-EVPN route";
        } // END of ethernet-tag-identifier definition.

        leaf next-hop-address  {
            type  inet:ipv4-address;
            description "Next Hop IP-address of mac-ip route";
        } // END of next-hop-address definition.

        leaf encapsulation-type  {
            type  string {
                length "1..1965";
                pattern "[^?' =,>|]+";
            }
            description "tunnel encapsulation type of mac-ip route";
        } // END of encapsulation-type definition.

        leaf ethernet-segment-identifier  {
            type  string {
                length "1..1965";
                pattern "[^?' =,>|]+";
            }
            description "ESI value of BGP-EVPN route";
        } // END of ethernet-segment-identifier definition.

        leaf l2-label  {
            type  uint32;
            description "l2-vnid of bgp-evpn route";
        } // END of l2-label definition.

        leaf l3-label  {
            type  uint32;
            description "l3-vnid of bgp-evpn route";
        } // END of l3-label definition.

    } // END of bgp-evpn-mac-ip-route-state definition.
    grouping bgp-evpn-mcast-route-state {
        description
            "State parameter for BGP-EVPN mcastroute-type";
        leaf ethernet-tag-identifier  {
            type  uint32;
            description "Ethernet tag ID of BGP-EVPN route";
        } // END of ethernet-tag-identifier definition.

        leaf originating-router-ip-address  {
            type  inet:ipv4-address;
            description "Router IP-address of mcast route";
        } // END of originating-router-ip-address definition.

        leaf next-hop-address  {
            type  inet:ipv4-address;
            description "Next Hop IP-address of mcast route";
        } // END of next-hop-address definition.

        leaf encapsulation-type  {
            type  string {
                length "1..1965";
                pattern "[^?' =,>|]+";
            }
            description "tunnel encapsulation type of mcast route";
        } // END of encapsulation-type definition.

    } // END of bgp-evpn-mcast-route-state definition.
    grouping bgp-evpn-es-route-state {
        description
            "State parameter for BGP-EVPN es route-type";
        leaf ethernet-segment-identifier  {
            type  string {
                length "1..1965";
                pattern "[^?' =,>|]+";
            }
            description "ESI value of ethernet-segment route";
        } // END of ethernet-segment-identifier definition.

        leaf originating-router-ip-address  {
            type  inet:ipv4-address;
            description "Router IP-address of ethernet-segment route";
        } // END of originating-router-ip-address definition.

        leaf next-hop-address  {
            type  inet:ipv4-address;
            description "Next Hop IP-address of ethernet-segment route";
        } // END of next-hop-address definition.

        leaf encapsulation-type  {
            type  string {
                length "1..1965";
                pattern "[^?' =,>|]+";
            }
            description "tunnel encapsulation type of ethernet-segment route";
        } // END of encapsulation-type definition.

    } // END of bgp-evpn-es-route-state definition.
    grouping bgp-evpn-ad-route-state {
        description
            "State parameter for BGP-EVPN ad route-type";
        leaf ethernet-segment-identifier  {
            type  string {
                length "1..1965";
                pattern "[^?' =,>|]+";
            }
            description "ESI value of ethernet-ad route";
        } // END of ethernet-segment-identifier definition.

        leaf ethernet-tag-identifier  {
            type  uint32;
            description "Ethernet tag ID of BGP-EVPN route";
        } // END of ethernet-tag-identifier definition.

        leaf next-hop-address  {
            type  inet:ipv4-address;
            description "Next Hop IP-address of ethernet-ad route";
        } // END of next-hop-address definition.

        leaf encapsulation-type  {
            type  string {
                length "1..1965";
                pattern "[^?' =,>|]+";
            }
            description "tunnel encapsulation type of ethernet-ad route";
        } // END of encapsulation-type definition.

        leaf label  {
            type  uint32;
            description "MPLS Label/l2-vnid of BGP-EVPN route";
        } // END of label definition.

    } // END of bgp-evpn-ad-route-state definition.
    grouping bgp-evpn-prefix-route-state {
        description
            "State parameter for BGP-EVPN ip-prefix route-type";
        leaf ethernet-segment-identifier  {
            type  string {
                length "1..1965";
                pattern "[^?' =,>|]+";
            }
            description "ESI value of ethernet-prefix route";
        } // END of ethernet-segment-identifier definition.

        leaf ethernet-tag-identifier  {
            type  uint32;
            description "Ethernet tag ID of BGP-EVPN route";
        } // END of ethernet-tag-identifier definition.

        leaf originating-router-ip-address  {
            type  inet:ipv4-address;
            description "router ip-address of prefix route";
        } // END of originating-router-ip-address definition.

        leaf next-hop-address  {
            type  inet:ipv4-address;
            description "Next Hop IP-address of ethernet-ad route";
        } // END of next-hop-address definition.

        leaf encapsulation-type  {
            type  string {
                length "1..1965";
                pattern "[^?' =,>|]+";
            }
            description "tunnel encapsulation type of ethernet-ad route";
        } // END of encapsulation-type definition.

        leaf l3-label  {
            type  uint32;
            description "MPLS Label/l2-vnid of BGP-EVPN route";
        } // END of l3-label definition.

    } // END of bgp-evpn-prefix-route-state definition.
    grouping mac-ip-route-top {
        description
            "Top level Grouping for mac-ip-route";

        list mac-ip-route {
            key "host-mac-address host-ip-address ethernet-tag-identifier next-hop-address";
            config false;
            description
                "List of mac-ip route of bgp-evpn address family";
            leaf host-mac-address  {
                type  leafref {
                    path  "../state/host-mac-address";
                }
                description "Host Mac Address of BGP-EVPN route";
            } // END of host-mac-address definition.

            leaf host-ip-address  {
                type  leafref {
                    path  "../state/host-ip-address";
                }
                description "Host Ip-Address of BGP-EVPN route";
            } // END of host-ip-address definition.

            leaf ethernet-tag-identifier  {
                type  leafref {
                    path  "../state/ethernet-tag-identifier";
                }
                description "Ethernet tag ID of BGP-EVPN route";
            } // END of ethernet-tag-identifier definition.

            leaf next-hop-address  {
                type  leafref {
                    path  "../state/next-hop-address";
                }
                description "Next Hop IP-address of MAC-IP route";
            } // END of next-hop-address definition.

            container state {
                config false;
                description
                    "State attributes for next-hop";
                uses bgp-evpn-mac-ip-route-state;
            } // END of state-container definition.
        } // End of mac-ip-route-list
    } // END of mac-ip-route-top definition.
    grouping inclusive-multicast-route-top {
        description
            "Top level Grouping for inclusive-multicast-route";

        list inclusive-multicast-route {
            key "ethernet-tag-identifier originating-router-ip-address";
            config false;
            description
                "List of mcast route of bgp-evpn address family";
            leaf ethernet-tag-identifier  {
                type  leafref {
                    path  "../state/ethernet-tag-identifier";
                }
                description "Ethernet tag ID of BGP-EVPN route";
            } // END of ethernet-tag-identifier definition.

            leaf originating-router-ip-address  {
                type  leafref {
                    path  "../state/originating-router-ip-address";
                }
                description "Router IP-address of mcast route";
            } // END of originating-router-ip-address definition.

            container state {
                config false;
                description
                    "State attributes for next-hop";
                uses bgp-evpn-mcast-route-state;
            } // END of state-container definition.
        } // End of inclusive-multicast-route-list
    } // END of inclusive-multicast-route-top definition.
    grouping ethernet-segment-route-top {
        description
            "Top level Grouping for ethernet-segment-route";

        list ethernet-segment-route {
            key "ethernet-segment-identifier originating-router-ip-address";
            config false;
            description
                "List of esi route of bgp-evpn address family";
            leaf ethernet-segment-identifier  {
                type  leafref {
                    path  "../state/ethernet-segment-identifier";
                }
                description "ESI value of ethernet-segment route";
            } // END of ethernet-segment-identifier definition.

            leaf originating-router-ip-address  {
                type  leafref {
                    path  "../state/originating-router-ip-address";
                }
                description "Router IP-address of mcast route";
            } // END of originating-router-ip-address definition.

            container state {
                config false;
                description
                    "State attributes for next-hop";
                uses bgp-evpn-es-route-state;
            } // END of state-container definition.
        } // End of ethernet-segment-route-list
    } // END of ethernet-segment-route-top definition.
    grouping ethernet-auto-discovery-route-top {
        description
            "Top level Grouping for ethernet-auto-discovery-route";

        list ethernet-auto-discovery-route {
            key "ethernet-segment-identifier ethernet-tag-identifier next-hop-address";
            config false;
            description
                "List of eth-ad route of bgp-evpn address family";
            leaf ethernet-segment-identifier  {
                type  leafref {
                    path  "../state/ethernet-segment-identifier";
                }
                description "ESI value of ethernet-segment route";
            } // END of ethernet-segment-identifier definition.

            leaf ethernet-tag-identifier  {
                type  leafref {
                    path  "../state/ethernet-tag-identifier";
                }
                description "Ethernet tag ID of BGP-EVPN route";
            } // END of ethernet-tag-identifier definition.

            leaf next-hop-address  {
                type  leafref {
                    path  "../state/next-hop-address";
                }
                description "Next Hop IP-address of ethernet-ad route";
            } // END of next-hop-address definition.

            container state {
                config false;
                description
                    "State attributes for next-hop";
                uses bgp-evpn-ad-route-state;
            } // END of state-container definition.
        } // End of ethernet-auto-discovery-route-list
    } // END of ethernet-auto-discovery-route-top definition.
    grouping ip-prefix-route-top {
        description
            "Top level Grouping for ip-prefix-route";

        list ip-prefix-route {
            key "ethernet-segment-identifier ethernet-tag-identifier originating-router-ip-address";
            config false;
            description
                "List of eth-prefix route of bgp-evpn address family";
            leaf ethernet-segment-identifier  {
                type  leafref {
                    path  "../state/ethernet-segment-identifier";
                }
                description "ESI value of ethernet-prefix route";
            } // END of ethernet-segment-identifier definition.

            leaf ethernet-tag-identifier  {
                type  leafref {
                    path  "../state/ethernet-tag-identifier";
                }
                description "Ethernet tag ID of BGP-EVPN route";
            } // END of ethernet-tag-identifier definition.

            leaf originating-router-ip-address  {
                type  leafref {
                    path  "../state/originating-router-ip-address";
                }
                description "router ip-address of prefix route";
            } // END of originating-router-ip-address definition.

            container state {
                config false;
                description
                    "State attributes for next-hop";
                uses bgp-evpn-prefix-route-state;
            } // END of state-container definition.
        } // End of ip-prefix-route-list
    } // END of ip-prefix-route-top definition.

    grouping  evpn-routes-grouping {
    description
        "Container for BGP evpn-routes announced and accepted for a BGP Address
                family";
    container evpn-routes {
        if-feature feature-list:HAVE_BGP_EVPN;
        if-feature feature-list:HAVE_BGPD;
        config false;
        description
            "Container for BGP evpn-routes announced and accepted for a BGP Address
                    family";

        list evpn-route {
            key "route-distinguisher";
            config false;
            description
                "List of BGP-EVPN routes announced and accepted for the address family";
            leaf route-distinguisher  {
                type  leafref {
                    path  "../state/route-distinguisher";
                }
                description "Route distinguisher";
            } // END of route-distinguisher definition.

            container state {
                config false;
                description
                    "State parameters relating to BGP route";
                uses bgp-evpn-route-state;
            } // END of state-container definition.
            uses mac-ip-route-top;
            uses inclusive-multicast-route-top;
            uses ethernet-segment-route-top;
            uses ethernet-auto-discovery-route-top;
            uses ip-prefix-route-top;
        } // End of evpn-route-list
    } // END of evpn-routes-container definition.
    } // END of evpn-routes-grouping definition.


}
