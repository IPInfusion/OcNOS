/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-bgp-flowspec-types.yang
*
*/

module ipi-bgp-flowspec-types {

    yang-version 1.1;

    namespace   "http://www.ipinfusion.com/yang/ocnos/ipi-bgp-flowspec-types";

    prefix "ipi-bgp-flowspec-types";

    organization
        "IP Infusion Inc.";

    contact
        "Address: 3965 Freedom Circle, Suite 200, Santa Clara, CA 95054
         Phone: +1 408-400-1900
         E-mail: support@ipinfusion.com
         Web: http://www.ipinfusion.com/";

    description
        "BGP FLow Specification (FLOWSPEC)";


    revision "2026-02-04" {
        description "Add state attributes for BGP Flow Specification";
        reference " 0.2.0.";
    }

    revision "2023-02-28" {
        description "split class-map/policy-map configuration to enhanced-pbr.xml";
        reference " 0.1.1.";
    }

    revision "2023-01-23" {
        description "Initial Version";
        reference " 0.1.0.";
    }



    typedef  flowspec_afi_type_t {
        type enumeration {
            enum ipv4 {
                value 1;
                description "Address Family IPv4";
            }
        }
        description "type definition for FLOWSPEC_AFI_TYPE_T";
    }

    typedef  flowspec_local_install_t {
        type enumeration {
            enum interface-all {
                value 1;
                description "interface all";
            }
        }
        description "type definition for FLOWSPEC_LOCAL_INSTALL_T";
    }

    typedef  bgp_flowspec_rate_unit_t {
        type enumeration {
            enum bps {
                value 1;
                description "Specifies the unit in bits per second";
            }
            enum pps {
                value 2;
                description "Specifies the unit in packets per second";
            }
        }
        description "type definition for BGP_FLOWSPEC_RATE_UNIT_T";
    }

    typedef  bgp_flowspec_redirect_as_type_t {
        type enumeration {
            enum as-2-octet {
                value 1;
                description "Route-target encode type 2-octet AS and 4-octet value";
            }
            enum ipv4 {
                value 2;
                description "Route-target encode type 4-octet IPv4 address and 4-octet value";
            }
            enum as-4-octet {
                value 3;
                description "Route-target encode type 4-octet AS and 2-octet value";
            }
        }
        description "type definition for BGP_FLOWSPEC_REDIRECT_AS_TYPE_T";
    }

}
