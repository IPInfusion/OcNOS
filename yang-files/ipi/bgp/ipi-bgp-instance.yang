/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-bgp-instance.yang
*
*/

submodule ipi-bgp-instance {

    yang-version 1.1;

    belongs-to  ipi-bgp { prefix ipi-bgp; }

    import feature-list {
        prefix feature-list;
        revision-date 2026-09-15;
    }

    import ietf-inet-types {
        prefix inet;
        revision-date 2013-07-15;
    }

    import cml-data-types {
        prefix cml-data-types;
        revision-date 2026-05-15;
    }

    import ipi-bgp-types {
        prefix ipi-bgp-types;
        revision-date 2025-12-22;
    }

    include ipi-bgp-common { revision-date 2025-12-22;}
    include ipi-bgp-evpn-rib { revision-date 2023-09-12;}
    include ipi-bgp-link-state { revision-date 2023-09-12;}
    include ipi-bgp-flowspec { revision-date 2026-02-12;}
    include ipi-bgp-address-family { revision-date 2026-09-04;}
    include ipi-bgp-peer-group { revision-date 2026-09-05;}
    include ipi-bgp-peer { revision-date 2026-09-05;}
    include ipi-bgp-address-family-vrf { revision-date 2026-07-28;}
    include ipi-bgp-epe { revision-date 2024-02-08;}
    include ipi-bgp-rpki { revision-date 2025-12-22;}
    organization
        "IP Infusion Inc.";

    contact
        "Address: 3965 Freedom Circle, Suite 200, Santa Clara, CA 95054
         Phone: +1 408-400-1900
         E-mail: support@ipinfusion.com
         Web: http://www.ipinfusion.com/";

    description
        "";


    revision "2026-05-28" {
        description "Added dependencies between route-map prefix-list access-list and bgp instance config";
        reference " 0.14.7.";
    }

    revision "2025-10-15" {
        description "Added cliprependstr tags for helpstring generation";
        reference " 0.14.6.";
    }

    revision "2025-05-29" {
        description "Added dependency between segment-routing global block and bgp instance config";
        reference " 0.14.5.";
    }

    revision "2025-01-03" {
        description "Added skip-dependency-validation flag for when tag in confederation-vrfs container";
        reference " 0.14.4.";
    }

    revision "2024-12-23" {
        description "Added a container 'confederation-vrfs' for BGP vrf confederation.";
        reference " 0.14.3.";
    }

    revision "2024-09-13" {
        description "XPATH correction for bgp-as and external-route-leak-disable attr in new CLIs for external route leak";
        reference " 0.14.2.";
    }

    revision "2024-09-10" {
        description "Added new CLI 'no bgp external-route-leak'";
        reference " 0.14.1.";
    }

    revision "2024-09-03" {
        description "Added 'auto-policy-soft-reset enable' option under router bgp";
        reference " 0.14.0.";
    }

    revision "2024-06-06" {
        description "Added dependency between g-shut-capable and g-shut-local-preferences";
        reference " 0.13.1.";
    }

    revision "2024-05-20" {
        description "Added utils functions for source ip prefix list";
        reference " 0.13.0.";
    }

    revision "2024-03-20" {
        description "Removed state attributes for dampenning ";
        reference " 0.12.1.";
    }

    revision "2024-03-19" {
        description "Updated attribute 'inbound-route-filter-enable' to 'inbound-route-filter-disable' ";
        reference " 0.12.0.";
    }

    revision "2023-10-11" {
        description "Updated attribute 'graceful-shutdown-capable' and 'graceful-shutdown' ";
        reference " 0.11.4.";
    }

    revision "2023-09-22" {
        description "Removed ext-communities list and related grouping to rib container";
        reference " 0.11.3.";
    }

    revision "2023-09-12" {
        description "Added enclosing container for all objectlists";
        reference " 0.11.2.";
    }

    revision "2023-08-03" {
        description "Adding ext-communities list and related grouping to rib container";
        reference " 0.11.1.";
    }

    revision "2023-04-21" {
        description "Updated feature tag";
        reference " 0.11.0.";
    }

    revision "2023-02-07" {
        description "Enclosed MPLS config object lists with container";
        reference " 0.10.1.";
    }

    revision "2023-02-02" {
        description "Updated missing Description";
        reference " 0.10.0.";
    }

    revision "2023-01-05" {
        description "Modified cli-command attr path";
        reference " 0.9.3.";
    }

    revision "2023-01-03" {
        description "Updated bgp debug options";
        reference " 0.9.2.";
    }

    revision "2022-12-27" {
        description "Implicit delete tag added for 'route-selection/config' container";
        reference " 0.9.1.";
    }

    revision "2022-12-14" {
        description "Adding 'confederation' container in bgp-instance. Moving 'bgp confederation' CLIs into new heirarchy";
        reference " 0.9.0.";
    }

    revision "2022-08-10" {
        description "Debug hierarchy change";
        reference " 0.8.1.";
    }

    revision "2022-07-31" {
        description "Stop using inet:ipv4-prefix and inet:ipv6-prefix due to Cisco NSO iterop";
        reference " 0.8.0.";
    }

    revision "2022-07-26" {
        description "Modify when tag for attribute 'restart-time' and 'stale-path-max-retention-time' for BGP graceful-restart";
        reference " 0.7.3.";
    }

    revision "2022-07-06" {
        description "Skipped dependency validation for a composite constraint of peer-as and peer-group-tag for BGP peer";
        reference " 0.7.2.";
    }

    revision "2022-06-20" {
        description "Added new attribute 'de-activate' for BGP Peer-group feature.";
        reference " 0.7.1.";
    }

    revision "2022-06-01" {
        description "Updated the yang file with feature";
        reference " 0.7.0.";
    }

    revision "2022-04-04" {
        description "Added Support for BGP AIGP Feature";
        reference " 0.6.1.";
    }

    revision "2022-01-17" {
        description "Modified data type";
        reference " 0.6.0.";
    }

    revision "2021-08-27" {
        description "deprecated the bgp additional-paths CLI under bgp mode and removed the yang drop element for the additional-path attriute for the bgp-add-path feature";
        reference " 0.5.2.";
    }

    revision "2021-08-25" {
        description "Dependent object addition for bgp-vrf configs";
        reference " 0.5.1.";
    }

    revision "2021-08-09" {
        description "MPLS nexthop tracking command is added";
        reference " 0.5.0.";
    }

    revision "2021-06-11" {
        description "Added dependency constraint for graceful-restart CLI's restart-time, stale-path-max-retention-time and graceful-reset";
        reference " 0.4.1.";
    }

    revision "2021-06-09" {
        description "Removal of default ipv4 unicast activate";
        reference " 0.4.0.";
    }

    revision "2021-03-05" {
        description "Excluded yang generation for BGP Add path attributes";
        reference " 0.3.0.";
    }

    revision "2020-12-15" {
        description "Change to have data-types in lower case instead of camel case";
        reference " 0.2.0.";
    }

    revision "2020-09-10" {
        description "Initial Version";
        reference " 0.1.0.";
    }

    grouping bgp-instance-rib-address-family-state {
        description
            "State parameter for BGP routes";
        leaf afi  {
            type  ipi-bgp-types:bgp_afi_type_t;
            config false;
            description "BGP address family identifier";
        } // END of afi definition.

        leaf safi  {
            type  ipi-bgp-types:bgp_safi_type_t;
            config false;
            description "BGP sub address family identifier";
        } // END of safi definition.

    } // END of bgp-instance-rib-address-family-state definition.
    grouping bgp-instance-rib-state {
        description
            "State parameter for BGP routes";
        leaf network-address  {
            type  ipi-bgp-types:bgp_ip_network_t;
            config false;
            description "BGP route network address";
        } // END of network-address definition.

        leaf route-distinguisher  {
            type  string {
                length "1..1965";
                pattern "[^?' =,>|]+";
            }
            config false;
            description "Route distinguisher";
        } // END of route-distinguisher definition.

    } // END of bgp-instance-rib-state definition.
    grouping bgp-allocate-label-config {
        description
            "allocate label configuration for  BGP instance";
        leaf all-routes  {
            // when " !ipi-bgp-instance:bgp-instances/bgp-instance/allocate-label/config/route-map-name ";
            if-feature feature-list:HAVE_BGP_LU;
            type  empty;
            description "Use this attribute to allocate label to all the advertised routes";
        } // END of all-routes definition.

        leaf route-map-name  {
            // when " !ipi-bgp-instance:bgp-instances/bgp-instance/allocate-label/config/all-routes ";
            if-feature feature-list:HAVE_BGP_LU;
            type  string {
                length "1..1965";
                pattern "[^?' =,>|]+";
            }
            description "Use this attribute to allocate label to those advertised routes that
                        match route-map.";
        } // END of route-map-name definition.

    } // END of bgp-allocate-label-config definition.
    grouping bgp-allocate-label-top {
        description
            "allocate label configuration for  BGP instance";
        container allocate-label {
            if-feature feature-list:HAVE_BGP_LU;
            description
                "Container for Attributes related to allocate label";
            container config {
                description
                    "Configuration attributes related to allocate label";
                uses bgp-allocate-label-config;
            } // END of config-container definition.
            container state {
                config false;
                description
                    "Operational state data related to Distance for routes";
                uses bgp-allocate-label-config;
            } // END of state-container definition.
        } // END of allocate-label-container definition.
    } // END of bgp-allocate-label-top definition.
    grouping bgp-administrative-distance-config {
        description
            "attributes having bgp administrative distance configuration";
        leaf source-ip-prefix  {
            type  cml-data-types:cml_ipv4_prefix_t;
            description "Use this attribute to set the administrative distance for ip source
                        prefix.";
        } // END of source-ip-prefix definition.

        leaf distance  {
            type  uint8 {
                 range "1..255"  {
                    description "1..255: Supported range 1 - 255";
                 }
            }
            mandatory true;
            description "bgp distance <1-255>";
        } // END of distance definition.

        leaf access-list-name  {
            // when " ipi-bgp-instance:bgp-instances/bgp-instance/administrative-distances/administrative-distance/config/distance ";
            type  string {
                length "1..1965";
                pattern "[^?' =,>|]+";
            }
            description "Use this attribute to define an administrative distance along with ip
                        source prefix and access list name.";
        } // END of access-list-name definition.

    } // END of bgp-administrative-distance-config definition.
    grouping bgp-route-selection-config {
        description
            "attributes having route seletion configuration";
        leaf always-compare-med  {
            type  empty;
            description "Use this attribute to compare the Multi Exit Discriminator (MED) for
                        paths from neighbors in different autonomous systems. Multi Exit
                        Discriminator (MED) is used in best path selection by BGP. MED is
                        compared after BGP attributes weight, local preference, AS-path and
                        origin have been compared and are equal. MED comparison is done only
                        among paths from the same autonomous system (AS). Use compareMed
                        attribute to allow comparison of MEDs from different ASs. The MED
                        parameter is used to select the best path. A path with lower MED is
                        preferred.";
        } // END of always-compare-med definition.

        leaf ignore-as-path-length  {
            type  empty;
            description "Use this attribute to prevent the router from considering the
                        autonomous system (AS) path length as a factor in the algorithm for
                        choosing a best path route.";
        } // END of ignore-as-path-length definition.

        leaf best-path-compare-confed  {
            type  empty;
            description "Use this attribute to allow comparing of the confederation AS path
                        length. This attribute specifies that the AS confederation path length
                        must be used when available in the BGP best path decision process. It
                        is effective only when bestpathAspath attribute has not been used.";
        } // END of best-path-compare-confed definition.

        leaf external-compare-router-id  {
            type  empty;
            description "Use this attribute to compare router IDs for identical eBGP paths.
                        When comparing similar routes from peers, the BGP router does not
                        consider the router ID of the routes. By default, it selects the first
                        received route. Use this attribute to include router ID in the
                        selection process; similar routes are compared and the route with the
                        lowest router ID is selected. The router IS is the highest IP address
                        on the router, with preference given to loopback addresses. Router ID
                        can be manually set by using the routerIpAddr attribute.";
        } // END of external-compare-router-id definition.

    } // END of bgp-route-selection-config definition.
    grouping bgp-instance-confederation-config {
        description
            "attributes relating to bgp confederation configurations";
        leaf identifier  {
            type  uint32 {
                 range "1..4294967295"  {
                    description "1..4294967295: Supported range 1 - 4294967295";
                 }
            }
            description "Use this attribute to specify a BGP confederation identifier";
        } // END of identifier definition.

        leaf-list peer-as-number  {
            type  uint32 {
                 range "1..4294967295"  {
                    description "1..4294967295: Supported range 1 - 4294967295";
                 }
            }
            description "Use this attribute to specify peer AS number in BGP confederation";
        } // END of peer-as-number definition.

    } // END of bgp-instance-confederation-config definition.
    grouping bgp-instance-confederation-vrf-config {
        description
            "attributes relating to bgp confederation configurations";
        leaf identifier  {
            type  uint32 {
                 range "1..4294967295"  {
                    description "1..4294967295: Supported range 1 - 4294967295";
                 }
            }
            description "Use this attribute to specify a BGP confederation vrf identifier";
        } // END of identifier definition.

        leaf-list peer-as-number  {
            type  uint32 {
                 range "1..4294967295"  {
                    description "1..4294967295: Supported range 1 - 4294967295";
                 }
            }
            description "Use this attribute to specify peer AS number in BGP confederation vrf";
        } // END of peer-as-number definition.

        leaf confed-vrf-name  {
            type  string {
                length "1..1965";
                pattern "[^?' =,>|]+";
            }
            description "Bgp confederation vrf";
        } // END of confed-vrf-name definition.

    } // END of bgp-instance-confederation-vrf-config definition.
    grouping bgp-instance-common-config {
        description
            "attributes relating to bgp common config";
        leaf router-id  {
            type  inet:ipv4-address;
            description "Use this attribute to manually configure a fixed router ID as a BGP
                        router identifier. When this attribute is used to configure a fixed
                        router ID, the current router identifier is overridden and the peers
                        are reset.";
        } // END of router-id definition.

        leaf cluster-id  {
            type  ipi-bgp-types:bgp_cluster_id_t;
            description "Use this attribute to configure the cluster ID if the BGP cluster has
                        more than one route reflector. A cluster includes route reflectors and
                        its clients. Usually, each cluster is identified by the router ID of
                        its single route reflector but to increase redundancy sometimes a
                        cluster may have more than one route reflector. All router reflectors
                        in such a cluster are then identified by a cluster ID. The clusterId
                        attribute is used to configure the 4 byte cluster ID for clusters with
                        more than one route reflectors in an IPv4 address format.";
        } // END of cluster-id definition.

        leaf local-preference  {
            type  uint32 {
                 range "0..4294967295"  {
                    description "0..4294967295: Supported range 0 - 4294967295";
                 }
            }
            default "100";
            description "Use this attribute to change the default local preference value. Local
                        preference indicates the preferred path when there are multiple paths
                        to the same destination. The path having a higher preference is
                        preferred. The preference is sent to all routers and access servers in
                        the local autonomous system.";
        } // END of local-preference definition.

        leaf graceful-shutdown-capable  {
            type  empty;
            description "Use this attribute to enable the graceful shutdown capability at the
                        router level and make available the graceful-shutdown related
                        attributes at the router and BGP neighbor levels.";
        } // END of graceful-shutdown-capable definition.

        leaf graceful-shutdown  {
            type  empty;
            description "Use this attribute to gracefully shut down all BGP IPv4 sessions under
                        this router. The BGP graceful shutdown feature reduces packet loss
                        during maintenance activity.";
        } // END of graceful-shutdown definition.

        leaf graceful-shutdown-local-preference  {
            // when " ipi-bgp-instance:bgp-instances/bgp-instance/config/graceful-shutdown-capable ";
            type  uint32 {
                 range "0..4294967295"  {
                    description "0..4294967295: Supported range 0 - 4294967295";
                 }
            }
            default "0";
            description "Use this attribute to set the local preference of the router to use
                        during graceful shutdown. The local preference value indicates the
                        preferred path when there are multiple paths to the same destination
                        in a single routing database. The path with a higher preference value
                        is the preferred one. The preferred path is sent to all routers and
                        access servers in the local  autonomous system.";
        } // END of graceful-shutdown-local-preference definition.

        leaf inbound-route-filter-disable  {
            if-feature feature-list:HAVE_VRF;
            type  empty;
            description "Use this attribute to enable the MPLS (Multiprotocol Label Switching)
                        VPN/BGP inbound route filter. This attribute is used to control the
                        installation of routing information into the BGP table.
                        When a router runs MPLS VPN/BGP PE, it exchanges routing information
                        with a routing distinguisher. By default, routing information that
                        does not match the configured routing distinguisher value is not
                        installed. When the local box has two VRFs where each routing
                        distinguisher value is 10:100 and 20:200, routing information with
                        routing distinguisher 10:200 is not installed into BGP table.";
        } // END of inbound-route-filter-disable definition.

        leaf external-route-leak-disable  {
            if-feature feature-list:HAVE_VRF;
            type  empty;
            description "Use this attribute to disable external route leak.";
        } // END of external-route-leak-disable definition.

        leaf log-neighbor-changes  {
            type  empty;
            description "Use this attribute to enable logging of status change messages without
                        turning on debug bgp attributes. Product has many logging services for
                        neighbor status, including debug bgp fsm and debug bgp events.
                        However, these attributes cause system performance degradation. If you
                        need to log neighbor status changes only, IP Infusion Inc. recommends
                        turning off all debug attributes and using the setLogNbrChanges
                        attribute instead.";
        } // END of log-neighbor-changes definition.

        leaf scan-interval  {
            type  uint32 {
                 range "0..60"  {
                    description "0..60: Supported range 0 - 60";
                 }
            }
            default "60";
            description "Use this attribute to configure scanning intervals of BGP routers.
                        This interval is the period after which router checks the validity of
                        the routes in its database. To disable BGP scanning, set the scan-time
                        interval to 0 seconds.";
        } // END of scan-interval definition.

        leaf best-path-dont-compare-originator  {
            type  empty;
            description "Use this attribute to change the default bestpath selection by not
                        comparing an originator-ID for an identical EBGP path";
        } // END of best-path-dont-compare-originator definition.

        leaf no-best-path-tie-break  {
            type  empty;
            description "Use this attribute to always select a preferred older route even when
                        the bestpathCompareRouterId attribute is      configured";
        } // END of no-best-path-tie-break definition.

        leaf enable-deterministic-med  {
            type  empty;
            description "Use this attribute to compare the Multi Exit Discriminator (MED)
                        variable when choosing among routes advertised by different peers in
                        the same autonomous system. MED is compared after BGP attributes
                        weight, local preference, AS-path and origin have been compared and
                        are equal.
                        For a correct comparison result, enable this attribute on all routers
                        in a local AS. After enabling this attribute, all paths for the same
                        prefix are grouped together and arranged according to their MED value.
                        Based on this comparison, the best path is then chosen. This attribute
                        compares MED variable when choosing routes advertised by different
                        peers in the same AS, to compare MED, when choosing routes from
                        neighbors in different ASs use the compareMed attribute.
                        When the deterministicMed attribute is set, routes from the same AS
                        are grouped together, and the best routes of each group are compared.";
        } // END of enable-deterministic-med definition.

        leaf enforce-first-as-for-ebgp  {
            type  empty;
            description "Use this attribute to enforce the first AS for eBGP routes. This
                        attribute specifies that any updates received from an external
                        neighbor that do not have the neighbors configured Autonomous System
                        (AS) at the beginning of the AS_PATH in the received update must be
                        denied. Enabling this feature adds to the security of the BGP network
                        by not allowing traffic from unauthorized systems.";
        } // END of enforce-first-as-for-ebgp definition.

        leaf no-external-fail-over  {
            type  empty;
            description "Use this attribute to reset a BGP session immediately, if the
                        interface used for BGP connection goes down.";
        } // END of no-external-fail-over definition.

        leaf local-as-count  {
            type  uint8 {
                 range "2..64"  {
                    description "2..64: Supported range 2 - 64";
                 }
            }
            description "Use this attribute to set the number of times the local-AS (Autonomous
                        System) is to be prepended.";
        } // END of local-as-count definition.

        leaf no-client-route-reflection  {
            type  empty;
            description "Use this attribute to configure routers as route reflectors. Route
                        reflectors are used when all Interior Border Gateway Protocol (iBGP)
                        speakers are not fully meshed. If the clients are fully meshed the
                        route reflector is not required";
        } // END of no-client-route-reflection definition.

        leaf med-type  {
            type  ipi-bgp-types:bgp_med_type_t;
            description "Use this attribute to specify two MED (Multi Exit Discriminator)
                        attributes, confed and missing-as-worst. The confed attribute enables
                        MED comparison along paths learned from confederation peers. The MEDs
                        are compared only if there is no external Autonomous System (an AS not
                        within the confederation) in the path. If there is an external
                        autonomous system in the path, the MED comparison is not made. The
                        missing-as-worst to consider a missing MED attribute in a path as
                        having a value of infinity, making the path without a MED value the
                        least desirable path. If missing-as-worst is disabled, the missing MED
                        is assigned the value of 0,making the path with the missing MED
                        attribute the best path.";
        } // END of med-type definition.

        leaf multi-path-relax  {
            type  empty;
            description "Use this attribute to relax the same AS-Path requirement so any
                        candidate eBGP AS-Path with the same AS-path length might be used for
                        eBGP load-balancing.
                        This feature does not load-balance between eBGP and iBGP paths.
                        Normally eBGP load-balancing requires the candidate routes to be
                        equal-cost paths with identical BGP attributes having the same weight,
                        Local-Pref, AS-Path (both the AS numbers and the AS pathlength),
                        origin, MED, and different next-hop.";
        } // END of multi-path-relax definition.

        leaf enable-mpls-nexthop-tracking  {
            // when " ipi-bgp:bgp/global/config/enable-nexthop-tracking ";
            if-feature feature-list:HAVE_MPLS_LSP_TRACKING;
            type  empty;
            description "Use this attribute to enable mpls nexthop address tracking. MPLS
                        Nexthop address tracking is an event-driven notification system
                        that monitors the status of LSP installed in the NSM and reports
                        changes that affect internal BGP (iBGP) or external BGP (eBGP)
                        prefixes directly to theBGP process. This improves the overall BGP
                        convergence time, by allowing BGP to respond rapidly to nexthop
                        changes for FTN installed in the NSM. If MPLS nexthop tracking is
                        enabled after certain routes are learned, the registration of all
                        nexthops for selected BGP routes is done after the mpls nexthop
                        tracking feature is enabled. If MPLS nexthop tracking is disabled, and
                        if there are still some selected BGP routes, BGP de-registers the
                        nexthops of all selected BGP routes from NSM.";
        } // END of enable-mpls-nexthop-tracking definition.

        leaf ignore-aigp-for-bestpath  {
            if-feature feature-list:HAVE_BGP_AIGP;
            type  empty;
            description "Use this config to ignore aigp attr in BGP best-path selection
                        alogorithm.";
        } // END of ignore-aigp-for-bestpath definition.

        leaf auto-policy-soft-reset  {
            type  empty;
            description "Enable automatic soft-reset of BGP peers when their configured route
                        policy is modified";
        } // END of auto-policy-soft-reset definition.

    } // END of bgp-instance-common-config definition.
    grouping bgp-graceful-restart-config {
        description
            "attributes realting to graceful restart";
        leaf enable-graceful-restart  {
            if-feature feature-list:HAVE_RESTART;
            type  empty;
            description "Use this attribute to enable BGP graceful-restart capabilities. The
                        restart-time parameter is used for setting the maximum time that a
                        graceful-restart neighbor waits to come back up after a restart. This
                        value is applied to all neighbors unless you explicitly override it by
                        configuring the corresponding value on the neighbor. The
                        stalepath-time parameter is used to set the maximum time to preserve
                        stale paths from a gracefully restarted neighbor. All stalepaths,
                        unless reinstated by the neighbor after a re-establishment, will be
                        deleted at the expiration of this timer.";
        } // END of enable-graceful-restart definition.

        leaf restart-time  {
            if-feature feature-list:HAVE_RESTART;
            type  uint32 {
                 range "1..3600"  {
                    description "1..3600: Supported range 1 - 3600";
                 }
            }
            default "90";
            description "Use this attribute to enable BGP graceful-restart capabilities. The
                        restart-time parameter is used for setting the maximum time that a
                        graceful-restart neighbor waits to come back up after a restart. This
                        value is applied to all neighbors unless you explicitly override it by
                        configuring the corresponding value on the neighbor.";
        } // END of restart-time definition.

        leaf stale-path-max-retention-time  {
            if-feature feature-list:HAVE_RESTART;
            type  uint32 {
                 range "1..3600"  {
                    description "1..3600: Supported range 1 - 3600";
                 }
            }
            default "360";
            description "Use this attribute to enable BGP graceful-restart capabilities. The
                        stalepath-time parameter is used to set the maximum time to preserve
                        stale paths from a gracefully restarted neighbor. All stalepaths,
                        unless reinstated by the neighbor after a re-establishment, will be
                        deleted at the expiration of this timer.";
        } // END of stale-path-max-retention-time definition.

        leaf route-selection-max-defer-time  {
            if-feature feature-list:HAVE_RESTART;
            type  uint32 {
                 range "1..3600"  {
                    description "1..3600: Supported range 1 - 3600";
                 }
            }
            default "120";
            description "Use this attribute to specify the update-delay value for a
                        graceful-restart capable router. The update-delay value is the maximum
                        time a graceful-restart capable router, which is restarting, will
                        defer route-selection and advertisements to all its graceful-restart
                        capable neighbors. This maximum time starts from the instance the
                        first neighbor attains established state after restart. The restarting
                        router prematurely terminates this timer when end-of-rib markers are
                        received from all its graceful-restart capable neighbors.";
        } // END of route-selection-max-defer-time definition.

        leaf graceful-reset  {
            type  empty;
            description "Use this attribute to enable BGP graceful-restart capabilities. The
                        restart-time parameter is used for setting the maximum time that a
                        graceful-restart neighbor waits to come back up after a restart. This
                        value is applied to all neighbors unless you explicitly override it by
                        configuring the corresponding value on the neighbor.";
        } // END of graceful-reset definition.

    } // END of bgp-graceful-restart-config definition.
    grouping bgp-instance-common-state {
        description
            "attributes relating to bgp instance common state";
        leaf version  {
            type  ipi-bgp-types:bgp_version_t;
            config false;
            description "BGP version";
        } // END of version definition.

        leaf table-version  {
            type  int32;
            default "0";
            config false;
            description "BGP table version";
        } // END of table-version definition.

        leaf total-prefixes  {
            type  int32;
            default "0";
            config false;
            description "Network prefix count";
        } // END of total-prefixes definition.

        leaf router-run-time-ip-address  {
            type  inet:ipv4-address;
            config false;
            description "router-id";
        } // END of router-run-time-ip-address definition.

        leaf scan-remain-time  {
            type  uint32;
            units "seconds";
            config false;
            description "Time remaining for the next scan";
        } // END of scan-remain-time definition.

    } // END of bgp-instance-common-state definition.
    grouping bgp-instance-view-config {
        description
            "View configuration attributes of bgp instance";
        leaf view-name  {
            type  string {
                length "1..1965";
                pattern "[^?' =,>|]+";
            }
            description "Use this attribute for multiple bgp";
        } // END of view-name definition.

    } // END of bgp-instance-view-config definition.
    grouping bgp-instance-base-config {
        description
            "base configuration for bgp instance";
        leaf bgp-as  {
            type  uint32 {
                 range "1..4294967295"  {
                    description "1..4294967295: Supported range 1 - 4294967295";
                 }
            }
            description "Use this attribute to start a BGP process.";
        } // END of bgp-as definition.

    } // END of bgp-instance-base-config definition.
    grouping bgp-instance-timers-config {
        description
            "attributes having bgp timer configuration";
        leaf keep-alive  {
            type  uint16 {
                 range "0..65535"  {
                    description "0..65535: Supported range 0 - 65535";
                 }
            }
            mandatory true;
            description "Use this attribute to globally set or reset the keepalive values for
                        all the neighbors";
        } // END of keep-alive definition.

        leaf hold-time  {
            type  uint16 {
                 range "0..65535"  {
                    description "0..65535: Supported range 0 - 65535";
                 }
            }
            mandatory true;
            description "Use this attribute to globally set or reset the holdtime values for
                        all the neighbors.";
        } // END of hold-time definition.

    } // END of bgp-instance-timers-config definition.

    grouping  bgp-instances-grouping {
    description
        "Top level contanier for bgp-instance";
    container bgp-instances {
        if-feature feature-list:HAVE_BGPD;
        description
            "Top level contanier for bgp-instance";

        list bgp-instance {
            key "bgp-as";
            description
                "bgp-instance list inside bgp conatiner";
            leaf bgp-as  {
                type  leafref {
                    path  "../config/bgp-as";
                }
                description "Use this attribute to start a BGP process.";
            } // END of bgp-as definition.

            container config {
                description
                    "Configuration parameters relating to the BGP instance";
                uses bgp-instance-base-config;
                uses bgp-instance-common-config;
            } // END of config-container definition.
            container confederation {
                description
                    "Container for confederation parameters";
                container config {
                    description
                        "configuration parameters relating to confederation";
                    uses bgp-instance-confederation-config;
                } // END of config-container definition.
                container state {
                    config false;
                    description
                        "state parameters relating to confederation";
                    uses bgp-instance-confederation-config;
                } // END of state-container definition.
            } // END of confederation-container definition.
            container confederation-vrfs {
                description
                    "Container for confederation vrf parameters";

                list confederation-vrf {
                    key "confed-vrf-name";
                    description
                        "confederation list inside confederation-vrf container";
                    leaf confed-vrf-name  {
                        type  leafref {
                            path  "../config/confed-vrf-name";
                        }
                        description "Bgp confederation vrf";
                    } // END of confed-vrf-name definition.

                    container config {
                        description
                            "configuration parameters relating to confederation vrf";
                        uses bgp-instance-confederation-vrf-config;
                    } // END of config-container definition.
                    container state {
                        config false;
                        description
                            "state parameters relating to confederation";
                        uses bgp-instance-confederation-vrf-config;
                    } // END of state-container definition.
                } // End of confederation-vrf-list
            } // END of confederation-vrfs-container definition.
            container view-lists {
                description
                    "Top level container for parameters relating to the BGP view";

                list view-list {
                    key "view-name";
                    description
                        "List of parameters relating to the BGP view";
                    leaf view-name  {
                        type  leafref {
                            path  "../config/view-name";
                        }
                        description "Use this attribute for multiple bgp";
                    } // END of view-name definition.

                    container config {
                        description
                            "Configuration parameters relating to the BGP view";
                        uses bgp-instance-view-config;
                    } // END of config-container definition.
                    container state {
                        config false;
                        description
                            "state parameters relating to the BGP view";
                        uses bgp-instance-view-config;
                    } // END of state-container definition.
                } // End of view-list-list
            } // END of view-lists-container definition.
            container state {
                config false;
                description
                    "state parameters relating to the BGP statistics";
                uses bgp-instance-common-state;
                uses bgp-instance-base-config;
                uses bgp-instance-common-config;
            } // END of state-container definition.
            container graceful-restart {
                description
                    "container for bgp graceful-restart attributes";
                container config {
                    description
                        "configuration parameters relating to timers";
                    uses bgp-graceful-restart-config;
                } // END of config-container definition.
                container state {
                    config false;
                    description
                        "state parameters relating to graceful-restart attributes";
                    uses bgp-graceful-restart-config;
                } // END of state-container definition.
            } // END of graceful-restart-container definition.
            container timers {
                description
                    "container for bgp timers";
                container config {
                    presence "To configure timers";
                    description
                        "configuration parameters relating to timers";
                    uses bgp-instance-timers-config;
                } // END of config-container definition.
                container state {
                    config false;
                    description
                        "state parameters relating to timers";
                    uses bgp-instance-timers-config;
                } // END of state-container definition.
            } // END of timers-container definition.
            container route-selection {
                description
                    "container for bgp route selection";
                container config {
                    description
                        "configuration parameters relating to route selection";
                    uses bgp-route-selection-config;
                } // END of config-container definition.
                container state {
                    config false;
                    description
                        "state parameters relating to route selection";
                    uses bgp-route-selection-config;
                } // END of state-container definition.
            } // END of route-selection-container definition.
            container administrative-distances {
                description
                    "Top level container for bgp administrative distance prameters";

                list administrative-distance {
                    key "source-ip-prefix";
                    description
                        "container for bgp administrative distance prameters";
                    leaf source-ip-prefix  {
                        type  leafref {
                            path  "../config/source-ip-prefix";
                        }
                        description "Use this attribute to set the administrative distance for ip source
                                    prefix.";
                    } // END of source-ip-prefix definition.

                    container config {
                        description
                            "configuration parameters relating to distance prameters";
                        uses bgp-administrative-distance-config;
                    } // END of config-container definition.
                    container state {
                        config false;
                        description
                            "state parameters relating to distance prameters";
                        uses bgp-administrative-distance-config;
                    } // END of state-container definition.
                } // End of administrative-distance-list
            } // END of administrative-distances-container definition.
            container rib {
                config false;
                description
                    "Container for List of BGP routes announced and accepted per address
                            family";

                list address-family {
                    key "afi safi";
                    config false;
                    description
                        "List of address families which have announced and accepted BGP routes";
                    leaf afi  {
                        type  leafref {
                            path  "../state/afi";
                        }
                        description "BGP address family identifier";
                    } // END of afi definition.

                    leaf safi  {
                        type  leafref {
                            path  "../state/safi";
                        }
                        description "BGP sub address family identifier";
                    } // END of safi definition.

                    container state {
                        config false;
                        description
                            "State parameters relating to BGP RIB address family";
                        uses bgp-instance-rib-address-family-state;
                    } // END of state-container definition.
                    container routes {
                        config false;
                        description
                            "Container for BGP routes announced and accepted for a BGP Address
                                    family";

                        list route {
                            key "network-address route-distinguisher";
                            config false;
                            description
                                "List of BGP routes announced and accepted for the address family";
                            leaf network-address  {
                                type  leafref {
                                    path  "../state/network-address";
                                }
                                description "Network address of the route";
                            } // END of network-address definition.

                            leaf route-distinguisher  {
                                type  leafref {
                                    path  "../state/route-distinguisher";
                                }
                                description "Route distinguisher";
                            } // END of route-distinguisher definition.


                            list next-hop {
                                key "next-hop-address";
                                config false;
                                description
                                    "next hop address and state list";
                                leaf next-hop-address  {
                                    type  leafref {
                                        path  "../state/next-hop-address";
                                    }
                                    description "Nexthop address  of BGP route";
                                } // END of next-hop-address definition.

                                container state {
                                    config false;
                                    description
                                        "State attributes for next-hop";
                                    uses bgp-next-hop-state;
                                    uses bgp-next-hop-mpls-state;
                                } // END of state-container definition.
                            } // End of next-hop-list
                            container state {
                                config false;
                                description
                                    "State parameters relating to BGP route";
                                uses bgp-instance-rib-state;
                            } // END of state-container definition.
                        } // End of route-list
                    } // END of routes-container definition.
                    uses evpn-routes-grouping;
                    uses link-state-grouping;
                    uses flowspec-info-grouping;
                } // End of address-family-list
            } // END of rib-container definition.
            uses bgp-allocate-label-top;
            uses address-families-grouping;
            uses peer-groups-grouping;
            uses peers-grouping;
            uses address-family-vrfs-grouping;
            uses peer-engineering-grouping;
            uses rpki-grouping;
        } // End of bgp-instance-list
    } // END of bgp-instances-container definition.
    } // END of bgp-instances-grouping definition.


}
