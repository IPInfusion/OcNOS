/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-bgp-rpki-types.yang
*
*/

module ipi-bgp-rpki-types {

    yang-version 1.1;

    namespace   "http://www.ipinfusion.com/yang/ocnos/ipi-bgp-rpki-types";

    prefix "ipi-bgp-rpki-types";

    import ietf-inet-types {
        prefix inet;
        revision-date 2013-07-15;
    }

    organization
        "IP Infusion Inc.";

    contact
        "Address: 3965 Freedom Circle, Suite 200, Santa Clara, CA 95054
         Phone: +1 408-400-1900
         E-mail: support@ipinfusion.com
         Web: http://www.ipinfusion.com/";

    description
        "YANG version of the ipi-bgp-rpki-types";


    revision "2025-12-16" {
        description "Added runtime attributes for submodule RPKI servers and ROA tables";
        reference " 0.2.0.";
    }

    revision "2025-04-01" {
        description "initial revision";
        reference " 0.1.0.";
    }



    typedef  bgp_rpki_server_ip_addr_t {
        type union {
            type inet:ipv4-address {

            }
            type inet:ipv6-address {

            }
        }
        description "type definition for BGP_RPKI_SERVER_IP_ADDR_T";
    }

    typedef  bgp_rpki_server_protocol_t {
        type enumeration {
            enum tcp {
                value 1;
                description "TCP protocol";
            }
            enum ssh {
                value 2;
                description "SSH protocol";
            }
        }
        description "type definition for BGP_RPKI_SERVER_PROTOCOL_T";
    }

    typedef  bgp_rpki_rtr_client_state {
        type enumeration {
            enum closed {
                value 0;
                description "Connection between client and server has been terminated";
            }
            enum connecting {
                value 1;
                description "Connection between client and server is in the proccess of being established";
            }
            enum established {
                value 2;
                description "Connection between client and server has been established successfully";
            }
            enum error {
                value 3;
                description "There is an issue in the connection between client and server";
            }
            enum unknown {
                value 4;
                description "Unable to determine the status of the session due to a lack of communication";
            }
        }
        description "type definition for BGP_RPKI_RTR_CLIENT_STATE";
    }

}
