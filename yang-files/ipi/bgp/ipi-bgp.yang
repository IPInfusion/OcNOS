/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-bgp.yang
*
*/

module ipi-bgp {

    yang-version 1.1;

    namespace   "http://www.ipinfusion.com/yang/ocnos/ipi-bgp";

    prefix "ipi-bgp";

    import cml-data-types {
        prefix cml-data-types;
        revision-date 2026-05-15;
    }

    import ipi-bgp-types {
        prefix ipi-bgp-types;
        revision-date 2025-12-22;
    }

    import feature-list {
        prefix feature-list;
        revision-date 2026-09-15;
    }

    include ipi-bgp-instance { revision-date 2026-05-28;}
    include ipi-bgp-flowspec { revision-date 2026-02-12;}
    include ipi-bgp-common { revision-date 2025-12-22;}
    include ipi-bgp-address-family { revision-date 2026-09-04;}
    include ipi-bgp-evpn-rib { revision-date 2023-09-12;}
    include ipi-bgp-peer-group { revision-date 2026-09-05;}
    include ipi-bgp-peer { revision-date 2026-09-05;}
    include ipi-bgp-address-family-vrf { revision-date 2026-07-28;}
    include ipi-bgp-link-state { revision-date 2023-09-12;}
    include ipi-bgp-epe { revision-date 2024-02-08;}
    include ipi-bgp-rpki { revision-date 2025-12-22;}
    organization
        "IP Infusion Inc.";

    contact
        "Address: 3965 Freedom Circle, Suite 200, Santa Clara, CA 95054
         Phone: +1 408-400-1900
         E-mail: support@ipinfusion.com
         Web: http://www.ipinfusion.com/";

    description
        "YANG version of the ipi-bgp";


    revision "2026-09-08" {
        description "Added attribute 'nexthop-tracking-delay-msec' for BGP NHT support";
        reference " 0.19.3.";
    }

    revision "2026-09-05" {
        description "Removed auto-populate of 'activate' for a peer/peer-group when allow-ebgp-vpn is configured";
        reference " 0.19.2.";
    }

    revision "2026-09-04" {
        description "Removed add-path commands for Ipv4 LU Address-family";
        reference " 0.19.1.";
    }

    revision "2026-07-28" {
        description "Added autoPopulate-custom for object-list 'peers/peer' for peer-group update";
        reference " 0.19.0.";
    }

    revision "2026-06-24" {
        description "Added peer-group allowas-in for BGP LU address-family";
        reference " 0.18.43.";
    }

    revision "2026-06-22" {
        description "Updated 'attribute-unchanged' help description to clarify applicability for iBGP to eBGP reflected routes";
        reference " 0.18.42.";
    }

    revision "2026-06-11" {
        description "Added flag 'CML_NO_DELETE_API' for attribute 'afi'and 'safi 'for 'peers/peer/address-families/address-famil' and 'peer-groups/peer-group/address-families/address-family'";
        reference " 0.18.41.";
    }

    revision "2026-06-01" {
        description "Added support for 'attribute-unchanged' in IPv4 Labeled-Unicast address-family for peer and peer-group";
        reference " 0.18.40.";
    }

    revision "2026-05-28" {
        description "Added dependencies between route-map prefix-list access-list and bgp instance config";
        reference " 0.18.39.";
    }

    revision "2026-02-12" {
        description "Change the DSCP data type to be displayed in HEX format";
        reference " 0.18.38.";
    }

    revision "2026-02-04" {
        description "Add state attributes for BGP Flow Specification";
        reference " 0.18.37.";
    }

    revision "2026-01-19" {
        description "Added dependentObject tag for container 'ipi-bgp:bgp/global/config'";
        reference " 0.18.36.";
    }

    revision "2026-01-08" {
        description "Added added when tag for object-list 'peers/peer' for inteface vrf bind";
        reference " 0.18.34.";
    }

    revision "2026-01-06" {
        description "Enable multi-path CLI for x86 builds";
        reference " 0.18.35.";
    }

    revision "2025-12-29" {
        description "Order action-values by user";
        reference " 0.18.33.";
    }

    revision "2025-12-23" {
        description "Added when tag for the peer-as at the object list level";
        reference " 0.18.31.";
    }

    revision "2025-12-22" {
        description "Added rest of time to refresh and expire interval expiration attributes under the RPKI submodule. Added origin AS validation state attribute under BGP instance submodule";
        reference " 0.18.32.";
    }

    revision "2025-12-18" {
        description "Added CML_SKIP_HITLESS_MERGE for the attribute 'additional-paths-mode'";
        reference " 0.18.30.";
    }

    revision "2025-12-17" {
        description "Added delete instance flag to the attributes 'send-cost-community-id' and 'enable-transitive'";
        reference " 0.18.29.";
    }

    revision "2025-12-16" {
        description "Added runtime attributes for submodule RPKI servers and ROA tables";
        reference " 0.18.28.";
    }

    revision "2025-12-15" {
        description "Hide multi-path CLI only for Data Centers (DC) builds";
        reference " 0.18.27.";
    }

    revision "2025-12-09" {
        description "Updated cli-command for attribute 'peer-as'";
        reference " 0.18.26.";
    }

    revision "2025-12-04" {
        description "Added when tag for the attribute mapped-peer-group-tag-af";
        reference " 0.18.25.";
    }

    revision "2025-11-28" {
        description "Updated datatype for attribute 'route-community-string'";
        reference " 0.18.24.";
    }

    revision "2025-11-25" {
        description "Updated datatype for attribute 'additional-path-receive-capability' and 'additional-path-send-capability'";
        reference " 0.18.23.";
    }

    revision "2025-11-17" {
        description " Added hidden flag for disable-capability-negotiation";
        reference " 0.18.22.";
    }

    revision "2025-11-05" {
        description " Split aggregate-address CLI for VRF address-family into IPv4 and IPv6 specific modes. Added AF-based input_display and input_helpStr to restrict help output to correct address family.";
        reference " 0.18.21.";
    }

    revision "2025-10-30" {
        description "Added length check for Community-list";
        reference " 0.18.20.";
    }

    revision "2025-10-15" {
        description "Add peer-type-fabric-external to peer-group grouping";
        reference " 0.18.19.";
    }

    revision "2025-10-10" {
        description "Dlink 'disable-oper-logs' from 'debug bgp all'";
        reference " 0.18.18.";
    }

    revision "2025-10-09" {
        description "Added pattern check for community and ext-community standard options";
        reference " 0.18.17.";
    }

    revision "2025-10-08" {
        description "Added pattern verification for Large-community standard.";
        reference " 0.18.16.";
    }

    revision "2025-09-25" {
        description "Removed attribute 'bgp-port' for Peer and Peer-group";
        reference " 0.18.15.";
    }

    revision "2025-09-24" {
        description "Added added when tag for object-list 'peers/peer' for L2 inteface";
        reference " 0.18.14.";
    }

    revision "2025-09-23" {
        description "Update helpstrings with vni-list and ";
        reference " 0.18.13.";
    }

    revision "2025-09-18" {
        description "Inclusion of streaming telemetry yaml file for BGP peer-groups";
        reference " 0.18.12.";
    }

    revision "2025-09-17" {
        description "Added length check for AS Path Prepend for extended community";
        reference " 0.18.11.";
    }

    revision "2025-09-15" {
        description "Revert updated BGP_ROUTE_TARGET_TYPE_T for EVPN VXLAN feature";
        reference " 0.18.10.";
    }

    revision "2025-09-11" {
        description "Updated submodule to support EVPN VXLAN stitching";
        reference " 0.18.9.";
    }

    revision "2025-09-10" {
        description "Added hidden flag for add-path commands in LU Address-family";
        reference " 0.18.8.";
    }

    revision "2025-09-04" {
        description "Deprecated 'max-paths ibgp' CLI and added 'multi-path' CLI for L2VPN EVPN Address-family";
        reference " 0.18.7.";
    }

    revision "2025-09-03" {
        description "Added leaf ref to vrf name to handle validation of non existing vrf commit dry run";
        reference " 0.18.6.";
    }

    revision "2025-08-21" {
        description "initial revion for BGP RPKI Origin Validation";
        reference " 0.18.5.";
    }

    revision "2025-08-11" {
        description "Added two new bgp debug options to disable oper logs";
        reference " 0.18.4.";
    }

    revision "2025-07-14" {
        description "Added added when tag for object-list 'peers/peer' for member-aggregation inteface";
        reference " 0.18.3.";
    }

    revision "2025-06-13" {
        description "Updated the description for the large community";
        reference " 0.18.2.";
    }

    revision "2025-06-06" {
        description "Added support for EVPN route maps";
        reference " 0.18.1.";
    }

    revision "2025-06-02" {
        description "Enabled Additional-paths for IPv4 LU Address-family";
        reference " 0.18.0.";
    }

    revision "2025-05-29" {
        description "Added dependency between segment-routing global block and bgp instance config";
        reference " 0.17.10.";
    }

    revision "2025-05-08" {
        description "Changed help string for numbered, named standard large community list";
        reference " 0.17.9.";
    }

    revision "2025-05-06" {
        description "Updated input displayString for attribute 'password' and Added cli-commands for 'password' delete";
        reference " 0.17.8.";
    }

    revision "2025-04-30" {
        description "CLIs generated for un numbered mode are using create, modified to update";
        reference " 0.17.7.";
    }

    revision "2025-04-29" {
        description "Made attr redist-route-map-name mandatory for redistribute configuration";
        reference " 0.17.6.";
    }

    revision "2025-04-24" {
        description "Added dependentObject tag for 'address-families/address-family/config'";
        reference " 0.17.5.";
    }

    revision "2025-04-09" {
        description "Updated range for group-limit attribute ";
        reference " 0.17.4.";
    }

    revision "2025-04-08" {
        description "Removed table-map-filter cli-command from BGP_6PE_MODE";
        reference " 0.17.3.";
    }

    revision "2025-04-03" {
        description "Updated helpstring of peer-group for attribute 'advertisement-interval' and 'as-origination-interval' ";
        reference " 0.17.2.";
    }

    revision "2025-04-01" {
        description "Removed Neighbor BGP port from IPv6 labeled-unicast";
        reference " 0.17.1.";
    }

    revision "2025-03-10" {
        description "Added support for AIGP in peer group";
        reference " 0.17.0.";
    }

    revision "2025-03-05" {
        description "Added new CLI for multi-path under address-families";
        reference " 0.16.9.";
    }

    revision "2025-03-04" {
        description "Updated pattern tag for attribute 'access-list-regular-expression'";
        reference " 0.16.8.";
    }

    revision "2025-02-28" {
        description "Added option to accept RT and SOO in ip extended-community-list 1-99 CLI";
        reference " 0.16.7.";
    }

    revision "2025-02-25" {
        description "Removed disable-adj-out command";
        reference " 0.16.6.";
    }

    revision "2025-02-20" {
        description "Added peer-adj-out-routes container for dynamic-peers peer-group container";
        reference " 0.16.5.";
    }

    revision "2025-02-19" {
        description "Added runtime attributes local-ip and local-as to bgp peers";
        reference " 0.16.4.";
    }

    revision "2025-02-17" {
        description "Removed table-map option from IPv6-LU AF";
        reference " 0.16.3.";
    }

    revision "2025-02-14" {
        description "Added 'large-community-list'";
        reference " 0.16.2.";
    }

    revision "2025-02-13" {
        description "Added utils api for attribute 'aggregate-address'";
        reference " 0.16.1.";
    }

    revision "2025-01-28" {
        description "Added aggregrate-address for vrf address-family";
        reference " 0.16.0.";
    }

    revision "2025-01-27" {
        description "Added dynamic-peers container inside peer-group address-family state container";
        reference " 0.15.45.";
    }

    revision "2025-01-21" {
        description "Corrected helpstring for BGP peer authentication";
        reference " 0.15.44.";
    }

    revision "2025-01-18" {
        description "corrected the ref id";
        reference " 0.15.43.";
    }

    revision "2025-01-17" {
        description "Updated the helpstring for ospf for redistributed routes";
        reference " 0.15.42.";
    }

    revision "2025-01-16" {
        description "Added implicit_delete tag for aigp container";
        reference " 0.15.41.";
    }

    revision "2025-01-10" {
        description "BGP Flowspec afi-type internal error correction";
        reference " 0.15.40.";
    }

    revision "2025-01-07" {
        description "Added delete api for the cli 'ip community-list standard WORD deny/permit'";
        reference " 0.15.39.";
    }

    revision "2025-01-03" {
        description "Added skip-dependency-validation flag for when tag in confederation-vrfs container";
        reference " 0.15.38.";
    }

    revision "2024-12-23" {
        description "Added container 'confederation-vrfs' in bgp instance and removed 'confederation' container in vrf address-family";
        reference " 0.15.37.";
    }

    revision "2024-12-19" {
        description "Added a skip-dependency validation flag for bgp-passwords";
        reference " 0.15.36.";
    }

    revision "2024-11-27" {
        description "Updated helpstring of AS:nn for the attribute 'site-origin-identifier'";
        reference " 0.15.35.";
    }

    revision "2024-11-19" {
        description "Added Utils_api func for attribute 'community-value-standard'";
        reference " 0.15.34.";
    }

    revision "2024-11-16" {
        description "Updated helpstring for ip extcommunity";
        reference " 0.15.33.";
    }

    revision "2024-11-15" {
        description "Updated value of datatype BGP_VERSION_T";
        reference " 0.15.32.";
    }

    revision "2024-11-13" {
        description "Introduced new bgp debug option 'debug bgp peer'";
        reference " 0.15.31.";
    }

    revision "2024-11-12" {
        description "Updated pattern tag for attribute 'access-list-regular-expression'";
        reference " 0.15.30.";
    }

    revision "2024-11-11" {
        description "Introduced new bgp debug options 'debug bgp route-process' and 'debug bgp evpn' ";
        reference " 0.15.29.";
    }

    revision "2024-10-29" {
        description "Updated neighbor password size limits";
        reference " 0.15.28.";
    }

    revision "2024-10-16" {
        description "Added peer-allow-ebgp-vpn when tag to peer-group activate of vrf address-family";
        reference " 0.15.27.";
    }

    revision "2024-10-15" {
        description "Updated create and delete operation of table-map in address-family-vrf and address-family";
        reference " 0.15.26.";
    }

    revision "2024-10-10" {
        description "Added when tag for peer member deletion from DB when mapped peergroup remote-as is deleted";
        reference " 0.15.25.";
    }

    revision "2024-10-04" {
        description "Added when tag peer-allow-ebgp-vpn to activate in address-family-vrf";
        reference " 0.15.24.";
    }

    revision "2024-10-03" {
        description "Updated When tag constraints for attribute 'site-origin-identifier'";
        reference " 0.15.23.";
    }

    revision "2024-09-17" {
        description "Updated cli-command for create function";
        reference " 0.15.22.";
    }

    revision "2024-09-14" {
        description "Added Streaming Telemetry yaml file";
        reference " 0.15.21.";
    }

    revision "2024-09-13" {
        description "XPATH correction for bgp-as and external-route-leak-disable attr in new CLIs for external route leak";
        reference " 0.15.20.";
    }

    revision "2024-09-11" {
        description "Fix BGP address-family CLI helpstrings";
        reference " 0.15.19.";
    }

    revision "2024-09-10" {
        description "Added new CLI 'no bgp external-route-leak'";
        reference " 0.15.18.";
    }

    revision "2024-09-07" {
        description "For operation create Changed flag for cli-install-default-family for BGP_IPV4_MODE and BGP_IPV6_MODE to apply address-family-exit";
        reference " 0.15.17.";
    }

    revision "2024-09-06" {
        description "Added new CLI 'bgp enable-bogon-filtering";
        reference " 0.15.16.";
    }

    revision "2024-09-05" {
        description "Updated if-feature for datatype BGP_REDISTRIBUTE_TYPE_T";
        reference " 0.15.15.";
    }

    revision "2024-09-03" {
        description "Added 'auto-policy-soft-reset enable' option under router bgp";
        reference " 0.15.14.";
    }

    revision "2024-08-30" {
        description "Changed display string for unset cli in site-origin-identifier";
        reference " 0.15.13.";
    }

    revision "2024-08-29" {
        description "Updated if-feature 'HAVE_MPLS' for VPN address-family";
        reference " 0.15.12.";
    }

    revision "2024-08-28" {
        description "Updated When tag constraints for object-list 'distribute-list-filter', 'as-list-filters', 'prefix-list-filter' and 'route-map-filter'";
        reference " 0.15.11.";
    }

    revision "2024-08-27" {
        description "Fix data-sync issue when address-family flowspec vrf removed'";
        reference " 0.15.10.";
    }

    revision "2024-08-23" {
        description "Added when tag for mpls label mode command";
        reference " 0.15.9.";
    }

    revision "2024-08-22" {
        description "Removed attribute 'config-type'";
        reference " 0.15.8.";
    }

    revision "2024-08-14" {
        description "Added when tag for prefix-list under vrf in bgp";
        reference " 0.15.7.";
    }

    revision "2024-08-06" {
        description "Implicit delete tag add for 'peers/peer/address-families/address-family/config' container";
        reference " 0.15.6.";
    }

    revision "2024-08-02" {
        description "Removed autopopulate for bgp implicit null command'";
        reference " 0.15.5.";
    }

    revision "2024-07-19" {
        description "Added whan tag wrt removal of address-family vpnv6 unicast";
        reference " 0.15.4.";
    }

    revision "2024-07-12" {
        description "Added dependentObject tag for container 'bgp-vrf";
        reference " 0.15.3.";
    }

    revision "2024-07-08" {
        description "Updated the when tag for peer-port";
        reference " 0.15.2.";
    }

    revision "2024-06-26" {
        description "added needed dependacies to contorller and vrf";
        reference " 0.15.1.";
    }

    revision "2024-06-20" {
        description "Added packet send and received elements under BGP_DEBUG_T attribute";
        reference " 0.15.0.";
    }

    revision "2024-06-19" {
        description "Fix Copyright issue in bgp-peer";
        reference " 0.14.30.";
    }

    revision "2024-06-13" {
        description "Corrected BGP neighbor commands' helpstrings";
        reference " 0.14.29.";
    }

    revision "2024-06-06" {
        description "Added dependency between g-shut-capable and g-shut-local-preferences";
        reference " 0.14.28.";
    }

    revision "2024-06-04" {
        description "Introduced new bgp debug option 'debug bgp route-scan'";
        reference " 0.14.27.";
    }

    revision "2024-05-20" {
        description "Added utils functions for source ip prefix list";
        reference " 0.14.26.";
    }

    revision "2024-05-17" {
        description "Introduced a new bgp debug option 'debug bgp adj-out'";
        reference " 0.14.25.";
    }

    revision "2024-05-16" {
        description "Added When tag constraints for attribute 'additional-path-select-all' and 'additional-paths-best-select-count'";
        reference " 0.14.24.";
    }

    revision "2024-04-25" {
        description "Added when tag for srv6-locator";
        reference " 0.14.23.";
    }

    revision "2024-04-15" {
        description "Added new CLI 'bgp disable-rfc7606-error-handling'";
        reference " 0.14.22.";
    }

    revision "2024-04-02" {
        description "Dependency for the 'enable-peer-bfd-multihop' was missing at the config level, added when tag for the config attribute";
        reference " 0.14.21.";
    }

    revision "2024-03-29" {
        description "Modified flag 'skip-dependency-deletion' to'skip-dependency-validation' in activate attribute and added when tag mapped-peer-group-tag-af to peer-as attribute in bgp-vrf-address-family";
        reference " 0.14.20.";
    }

    revision "2024-03-21" {
        description "Updated When tag constraints for attribute 'password'";
        reference " 0.14.19.";
    }

    revision "2024-03-20" {
        description "Added state attribute for dampenning feature";
        reference " 0.14.18.";
    }

    revision "2024-03-19" {
        description "Updated attribute 'inbound-route-filter-enable' to 'inbound-route-filter-disable' ";
        reference " 0.14.17.";
    }

    revision "2024-02-28" {
        description "Removed installtion mode not suppported for attribute 'additional-paths-mode', 'additional-path-select-all' and 'additional-paths-best-select-count'";
        reference " 0.14.16.";
    }

    revision "2024-02-08" {
        description "Added enclosing container for missing objectlists";
        reference " 0.14.15.";
    }

    revision "2024-02-06" {
        description "Updated debug bgp cli options.Removed datatype 'BGP_UPDATE_DEBUG_T' and updated option for datatype 'BGP_DEBUG_T'";
        reference " 0.14.14.";
    }

    revision "2024-01-31" {
        description "Add utils function 'check_vrf_name_is_default' to vrf-name for validation";
        reference " 0.14.13.";
    }

    revision "2024-01-05" {
        description "Removed 'ebgp-max-path' cli for address-family l2vpn evpn";
        reference " 0.14.12.";
    }

    revision "2024-01-04" {
        description "Update datatype for attributes: 'graceful-restart', 'orf-type-prefix-send-mode', 'orf-type-prefix-receive-mode','orf-type-prefix-send-mode-old' and 'orf-type-prefix-receive-mode-old'";
        reference " 0.14.10.";
    }

    revision "2024-01-02" {
        description "Added new attribute 'enable-bgp-implicit-null'for BGP-LU Implicit Null support";
        reference " 0.14.11.";
    }

    revision "2023-12-27" {
        description "Updated help string for expanded option for extended community ";
        reference " 0.14.9.";
    }

    revision "2023-12-14" {
        description "Updated datatype for attribute 'orf-type-prefix-send-mode', 'orf-type-prefix-receive-mode','orf-type-prefix-receive-mode'and 'orf-type-prefix-send-mode-old' ";
        reference " 0.14.8.";
    }

    revision "2023-12-05" {
        description "Added support of 'orf-prefix-capability' and 'prefix-list-name' for address-family VPNV4, VPNV6 Ipv4 LU and IPv6 LU";
        reference " 0.14.7.";
    }

    revision "2023-11-30" {
        description "Added support for configuring multi-path relax option for BGP peer under VRF addressfamily ipv4/v6";
        reference " 0.14.6.";
    }

    revision "2023-11-29" {
        description "Updated displaystring as 'fall-over bfd multihop'";
        reference " 0.14.5.";
    }

    revision "2023-11-28" {
        description "RPC Implementation to clear bgp peer-group for l2vpn evpn";
        reference " 0.11.1.";
    }

    revision "2023-11-27" {
        description "RPC Implementation to clear bgp for l2vpn evpn";
        reference " 0.14.4.";
    }

    revision "2023-11-26" {
        description "Added soft-reconfig attribute";
        reference " 0.14.3.";
    }

    revision "2023-11-17" {
        description "Added BGP add-path option";
        reference " 0.14.2.";
    }

    revision "2023-11-16" {
        description "Added nexthop delay measuremment(sec)";
        reference " 0.14.1.";
    }

    revision "2023-11-02" {
        description "Updated cliFlag for attribute 'ibgp-max-path' and 'ebgp-max-path'";
        reference " 0.14.0.";
    }

    revision "2023-10-29" {
        description "Added if-features to BGP_DEBUG_T datatype";
        reference " 0.13.23.";
    }

    revision "2023-10-13" {
        description "Updated cliFlag for attribute 'peer-address'";
        reference " 0.13.22.";
    }

    revision "2023-10-11" {
        description "Updated attribute 'graceful-shutdown-capable' and 'graceful-shutdown' ";
        reference " 0.13.21.";
    }

    revision "2023-10-09" {
        description "Updated When tag constraints for attribute 'enable-peer-bfd-multihop' and 'enable-peer-bfd'";
        reference " 0.13.20.";
    }

    revision "2023-10-04" {
        description "Updated cliFlag for attribute 'enable-dynamic-capability'";
        reference " 0.13.19.";
    }

    revision "2023-09-22" {
        description "Updated bgp-instance/peer/state attribute";
        reference " 0.13.18.";
    }

    revision "2023-09-12" {
        description "Added enclosing container for all objectlists";
        reference " 0.13.17.";
    }

    revision "2023-09-07" {
        description "Updated bgp-instance/peer/state heirarchy";
        reference " 0.13.16.";
    }

    revision "2023-09-06" {
        description "Updated utils api for attribute 'peer-address'";
        reference " 0.13.15.";
    }

    revision "2023-09-05" {
        description "Updated When tag constraints for attribute 'peer-route-map-orig-name' and 'default-peer-route-map-name'";
        reference " 0.13.14.";
    }

    revision "2023-09-04" {
        description "Remove unnecessary imports to fix XP build";
        reference " 0.13.13.";
    }

    revision "2023-08-31" {
        description "When tag constraints for attribute 'fall-over bfd' and 'enable-peer-bfd-multihop'";
        reference " 0.13.12.";
    }

    revision "2023-08-22" {
        description "Added When tag constraints for object-list 'peer'";
        reference " 0.13.10.";
    }

    revision "2023-08-21" {
        description "Implicit delete tag removed for 'local-as/config' container";
        reference " 0.13.9.";
    }

    revision "2023-08-16" {
        description "New patch Added option 'no-prepend' and 'replace-as' for BGP neighbor local-as";
        reference " 0.13.8.";
    }

    revision "2023-08-15" {
        description "Revert patch Added option 'no-prepend' and 'replace-as' for BGP neighbor local-as";
        reference " 0.13.7.";
    }

    revision "2023-08-11" {
        description "Added option 'no-prepend' and 'replace-as' for BGP neighbor local-as";
        reference " 0.13.6.";
    }

    revision "2023-08-07" {
        description "Added support for BGP addpath for ebgp neighbors";
        reference " 0.13.5.";
    }

    revision "2023-08-03" {
        description "Adding new runtime attributes to bgp-peer,bgp-peer-group and rib heirarchies. Added related datatypes.";
        reference " 0.13.4.";
    }

    revision "2023-07-20" {
        description "Added support for TCP Maximum Segment Size per BGP neighbor";
        reference " 0.13.3.";
    }

    revision "2023-07-07" {
        description "container to presence container changes for adjacency";
        reference " 0.13.2.";
    }

    revision "2023-05-17" {
        description "address-family ipv4 flowspec vrf support";
        reference " 0.13.1.";
    }

    revision "2023-05-12" {
        description "container to presence container changes for adjacency";
        reference " 0.13.0.";
    }

    revision "2023-04-25" {
        description "Updated feature tag for import statements";
        reference " 0.12.4.";
    }

    revision "2023-04-24" {
        description "Added pattern tag for attribute 'access-list-regular-expression'";
        reference " 0.12.3.";
    }

    revision "2023-04-21" {
        description "Updated feature tag";
        reference " 0.12.2.";
    }

    revision "2023-04-17" {
        description "Added custom-error-code for attribute 'no-send-community' and 'no-send-community-type'";
        reference " 0.12.1.";
    }

    revision "2023-04-11" {
        description "Removed attribute 'soft-reconfig-inbound'";
        reference " 0.12.0.";
    }

    revision "2023-03-30" {
        description "Added Proper if-feature tag for Additional-paths cli";
        reference " 0.11.15.";
    }

    revision "2023-03-21" {
        description "Updating helpstrings for allow-as-number inputs in bgp-peer, bgp-peer-group and bgp-address-family-vrf";
        reference " 0.11.14.";
    }

    revision "2023-03-17" {
        description "Removed when tag constraints from all sub-objectlist's of 'community-lists'";
        reference " 0.11.13.";
    }

    revision "2023-03-16" {
        description "BGP password string length addition'";
        reference " 0.11.12.";
    }

    revision "2023-03-14" {
        description "BGP flowspec packet-length attribute corrections";
        reference " 0.11.11.";
    }

    revision "2023-03-11" {
        description "db-sync issue correction";
        reference " 0.11.10.";
    }

    revision "2023-03-09" {
        description "Added 'suppress-unset-cli' flag to peer-address and changed operation type to 'create' for peer-as attribute cli-commands";
        reference " 0.11.9.";
    }

    revision "2023-03-02" {
        description "BGP flowspec support, correct revision issue";
        reference " 0.11.7.";
    }

    revision "2023-02-28" {
        description "Updating when expression for vrf-peer maximum-prefixes and route-map-filter objectlists";
        reference " 0.11.6.";
    }

    revision "2023-02-23" {
        description "Removed installtion mode not suppported for attribute 'enable-additional-path-pic'";
        reference " 0.13.11.";
    }

    revision "2023-02-22" {
        description "Added support for BGP ADD Path in vrf address-family";
        reference " 0.11.5.";
    }

    revision "2023-02-21" {
        description "BGP flowspec support";
        reference " 0.11.4.";
    }

    revision "2023-02-08" {
        description "Updated validate api for ebgp-multihop";
        reference " 0.11.3.";
    }

    revision "2023-02-07" {
        description "Enclosed MPLS config object lists with container";
        reference " 0.11.8.";
    }

    revision "2023-02-06" {
        description "Removing optional-attribute flag from allow-as-number cli-commands";
        reference " 0.11.2.";
    }

    revision "2023-02-02" {
        description "Updated missing Description";
        reference " 0.11.1.";
    }

    revision "2023-01-30" {
        description "Added support of 'orf-prefix-capability' for address-family VPNV4, VPNV6 and IPv6 LU";
        reference " 0.11.0.";
    }

    revision "2023-01-21" {
        description "Updated validate api for threshold percentage for 6PE";
        reference " 0.10.9.";
    }

    revision "2023-01-09" {
        description "Added new container for EBGP multihop attributes";
        reference " 0.10.8.";
    }

    revision "2023-01-05" {
        description "Modified cli-command attr path";
        reference " 0.10.7.";
    }

    revision "2023-01-03" {
        description "Updated bgp debug options";
        reference " 0.10.6.";
    }

    revision "2022-12-27" {
        description "Implicit delete tag added for 'route-selection/config' container";
        reference " 0.10.5.";
    }

    revision "2022-12-22" {
        description "Added if-feature 'HAVE_MPLS' for VPN address-family";
        reference " 0.10.4.";
    }

    revision "2022-12-16" {
        description "Updated cli-command flag for attribute 'soft-reconfig-inbound'";
        reference " 0.10.3.";
    }

    revision "2022-12-14" {
        description "Changes made in address-family-vrf and bgp-instance for 'bgp confederation' CLI heirarchy and attributes";
        reference " 0.10.2.";
    }

    revision "2022-12-01" {
        description "Updated When tag constraints for attribute 'activate'";
        reference " 0.10.1.";
    }

    revision "2022-11-11" {
        description "Added new type connected-host-route in redistribute types for EVPN IRB";
        reference " 0.10.0.";
    }

    revision "2022-11-08" {
        description "Updated When tag constraints for attribute 'fall-over bfd' and 'enable-peer-bfd-multihop'";
        reference " 0.9.8.";
    }

    revision "2022-10-20" {
        description "Updated When tag constraints and removed Default value from attribute 'ebgp-maximum-hop-count' and 'enable-ebgp-multihop'";
        reference " 0.9.7.";
    }

    revision "2022-09-27" {
        description "Removed Default value from attribute 'min-route-advertisement-interval' and 'peer-as-origin-interval'";
        reference " 0.9.6.";
    }

    revision "2022-09-26" {
        description "Import xml file updated for BGP Large community";
        reference " 0.9.5.";
    }

    revision "2022-09-06" {
        description "Added CML_RUNTIME flag in aigp state container";
        reference " 0.9.4.";
    }

    revision "2022-08-18" {
        description "Implicit delete tag added for  bgp debug all container";
        reference " 0.9.3.";
    }

    revision "2022-08-10" {
        description "Debug hierarchy change";
        reference " 0.9.2.";
    }

    revision "2022-07-31" {
        description "Stop using inet:ipv4-prefix and inet:ipv6-prefix due to Cisco NSO iterop";
        reference " 0.9.1.";
    }

    revision "2022-07-30" {
        description "Updated implicit delete for config container";
        reference " 0.9.0.";
    }

    revision "2022-07-26" {
        description "Modify when tag for attribute 'restart-time' and 'stale-path-max-retention-time' for BGP graceful-restart, Removed impicit delele for object-list 'address-family-vrf'";
        reference " 0.8.27.";
    }

    revision "2022-07-16" {
        description "Issues in SRv6 containter deletion with address-family ipv4";
        reference " 0.8.26.";
    }

    revision "2022-07-06" {
        description "Skipped dependency validation for a composite constraint of peer-as and peer-group-tag for BGP peer";
        reference " 0.8.25.";
    }

    revision "2022-06-27" {
        description "Added support for 'allow-as-number' in 'address-family ipv4 labeled-unicast' mode.";
        reference " 0.8.24.";
    }

    revision "2022-06-21" {
        description "Updated when tag constraints for peer's mapped peer-group tag attribute";
        reference " 0.8.23.";
    }

    revision "2022-06-20" {
        description "Modified Submodule";
        reference " 0.8.22.";
    }

    revision "2022-06-01" {
        description "Updated the yang file with feature";
        reference " 0.8.21.";
    }

    revision "2022-04-28" {
        description "Modified Submodule";
        reference " 0.8.20.";
    }

    revision "2022-04-19" {
        description "Updated sub-module for support of BGP Administrative Shutdown Communication feature.";
        reference " 0.8.19.";
    }

    revision "2022-04-04" {
        description "Added support for BGP AIGP Feature";
        reference " 0.8.18.";
    }

    revision "2022-02-28" {
        description "Modified EPE Backup attributes heirarchy";
        reference " 0.8.17.";
    }

    revision "2022-02-09" {
        description "Added When tag constraints for 'debug' container";
        reference " 0.11.3.";
    }

    revision "2022-01-17" {
        description "Modified Submodule";
        reference " 0.8.16.";
    }

    revision "2022-01-11" {
        description "Modified Submodule";
        reference " 0.8.15.";
    }

    revision "2022-01-10" {
        description "Added depenedency constraint between 'vrf address-family and route-redistribu
tion' and rd_string/IP-VRF";
        reference " 0.8.14.";
    }

    revision "2021-11-17" {
        description "SKU compilation error fixes";
        reference " 0.8.13.";
    }

    revision "2021-10-03" {
        description "Added new BGP-LS-EPE runtime attributes";
        reference " 0.8.12.";
    }

    revision "2021-09-20" {
        description "Spelling has been corrected for an attribute";
        reference " 0.8.11.";
    }

    revision "2021-09-15" {
        description "deprecated the bgp additional-paths CLI under bgp mode and removed the yang drop element for the additional-path attriute for the bgp-add-path feature";
        reference " 0.8.10.";
    }

    revision "2021-09-03" {
        description "Update descriptions of attribute";
        reference " 0.8.9.";
    }

    revision "2021-08-26" {
        description "Added dependency constraint between auth-key-encrypt and password attrs for the peer authentication password CLI";
        reference " 0.8.8.";
    }

    revision "2021-08-25" {
        description "Dependent object addition for bgp-vrf configs";
        reference " 0.8.7.";
    }

    revision "2021-08-19" {
        description "MPLS nexthop tracking command is added";
        reference " 0.8.6.";
    }

    revision "2021-08-16" {
        description "Removed the Yang drop element and updated the datatype from enum to bits for the additional-paths-mode attribute";
        reference " 0.8.5.";
    }

    revision "2021-08-13" {
        description "BGP ECMP Support for EIBGP routes";
        reference " 0.8.4.";
    }

    revision "2021-08-09" {
        description "Added support for BGP-EPE feature";
        reference " 0.8.2.";
    }

    revision "2021-08-03" {
        description "Added new attribute for enabling Enhe capability for IPv6 VPNv4 peer";
        reference " 0.8.3.";
    }

    revision "2021-07-27" {
        description "Added support for BGP-LS operational attributes";
        reference " 0.8.1.";
    }

    revision "2021-07-21" {
        description "Added bgp evpn get api attributes in dependent data models";
        reference " 0.8.0.";
    }

    revision "2021-07-05" {
        description "Remodelled authentication password object list for BGP peer, VRF peer and peer-group";
        reference " 0.7.0.";
    }

    revision "2021-06-25" {
        description "Modified dependency for neighbor activate attribute";
        reference " 0.6.9.";
    }

    revision "2021-06-21" {
        description "Corrected the CLI for the RPC bgp-debug-updates-type-on";
        reference " 0.6.8.";
    }

    revision "2021-06-11" {
        description "Added dependency constraint between name and direction attrs for the distribute-list, prefix-list, filter-list and route-map CLI's Added dependency constraint for graceful-restart CLI's restart-time, stale-path-max-retention-time and graceful-reset";
        reference " 0.6.7.";
    }

    revision "2021-06-09" {
        description "Removal of default ipv4 unicast activate and fix for DB sync issues";
        reference " 0.6.6.";
    }

    revision "2021-06-07" {
        description "Deprecated 'connect-retry-interval', duplicate of 'peer-connect-interval'";
        reference " 0.6.5.";
    }

    revision "2021-05-31" {
        description "Deprecated prefix-list-count attribute and added length for route map name";
        reference " 0.6.4.";
    }

    revision "2021-05-28" {
        description "Changed type of the attribute default-originate-information-sent";
        reference " 0.6.3.";
    }

    revision "2021-05-26" {
        description "Deprecated the as-local-count run-time attribute is same as the configured local-as attribute";
        reference " 0.6.2.";
    }

    revision "2021-05-13" {
        description "Removed dependency validation on AF activate for allow-ebgp-vpn attribute";
        reference " 0.6.1.";
    }

    revision "2021-05-05" {
        description "Added change for bgp unnumbered feature ";
        reference " 0.6.0.";
    }

    revision "2021-04-27" {
        description "Added leafref for vrf-name in mpls-l3vpn-label-mode ";
        reference " 0.6.0.";
    }

    revision "2021-04-09" {
        description "Change related to Peer group remodelling";
        reference " 0.5.0.";
    }

    revision "2021-03-31" {
        description "Added support for configuring BFD for BGP peer under VRF address family";
        reference " 0.4.0.";
    }

    revision "2021-03-05" {
        description "Community-list related changes";
        reference " 0.3.0.";
    }

    revision "2020-12-15" {
        description "Change to have data-types in lower case instead of camel case";
        reference " 0.2.0.";
    }

    revision "2020-09-10" {
        description "Initial Version";
        reference " 0.1.0.";
    }

    grouping bgp-global-common-config {
        description
            "global common configuration in BGP";
        leaf enable-aggregate-nexthop  {
            type  empty;
            description "Use this attribute to set the BGP option to perform aggregation only
                        when next-hop matches the specified IP address.";
        } // END of enable-aggregate-nexthop definition.

        leaf enable-path-select  {
            type  empty;
            description "Use this attribute to set RFC 1771 compatible path selection";
        } // END of enable-path-select definition.

        leaf disable-rfc7606-error-handling  {
            type  empty;
            description "Use this attribute to Disable RFC7606 revised error handling.";
        } // END of disable-rfc7606-error-handling definition.

        leaf enable-bogon-filtering  {
            type  empty;
            description "Use this attribute to enable BOGON filtering";
        } // END of enable-bogon-filtering definition.

        leaf enable-extended-asn-capability  {
            if-feature feature-list:HAVE_EXT_CAP_ASN;
            type  empty;
            description "Use this attribute to configure a BGP router to send 4-octet ASN
                        capabilities. If attempting to change the AS capability from 2 to 4 or
                        4 to 2, a prompt occurs to remove the VRF configuration (if it
                        exists), and reconfiguration is required,because the route
                        distinguisher (RD) configuration would have been created with the
                        current (2 octet or 4 octet) capability, and must be reconfigured
                        before attempting to change the capability. While loading from a saved
                        configuration with AS4 capability and BGP VRF configuration, the
                        capability will not be changed because of the above described reason.";
        } // END of enable-extended-asn-capability definition.

        leaf enable-nexthop-tracking  {
            type  empty;
            description "Use this attribute to enable nexthop address tracking. Nexthop address
                        tracking is an event-driven notification system that monitors the
                        status of routes installed in the Routing Information Base (RIB) and
                        reports nexthop changes that affect internal BGP (iBGP) or external
                        BGP (eBGP) prefixes directly to the BGP process. This improves the
                        overall BGP convergence time, by allowing BGP to respond rapidly to
                        nexthop changes for routes installed in the RIB. If nexthop tracking
                        is enabled after certain routes are learned, the registration of all
                        nexthops for selected BGP routes is done after the nexthop tracking
                        feature is enabled. If nexthop tracking is disabled, and if there are
                        still some selected BGP routes, BGP de-registers the nexthops of all
                        selected BGP routes from NSM.";
        } // END of enable-nexthop-tracking definition.

        leaf nexthop-tracking-delay  {
            // when " ipi-bgp:bgp/global/config/enable-nexthop-tracking + !ipi-bgp:bgp/global/config/nexthop-tracking-delay-msec ";
            type  uint8 {
                 range "1..100"  {
                    description "1..100: Supported range 1 - 100";
                 }
            }
            default "5";
            description "Use this attribute to set the delay time for nexthop address tracking.
                        This attribute configures the delayinterval between routing table
                        walks for nexthop delay tracking, after which BGP does a routing table
                        scan on receiving a nexthop change trigger from NSM. The time period
                        determines how long BGP waits before it walks the full BGP table to
                        determine which prefixes are affected by the nexthop changes, after it
                        receives the trigger from NSM about one or more nexthop changes.";
        } // END of nexthop-tracking-delay definition.

        leaf nexthop-tracking-delay-msec  {
            // when " ipi-bgp:bgp/global/config/enable-nexthop-tracking + !ipi-bgp:bgp/global/config/nexthop-tracking-delay ";
            type  uint32 {
                 range "400..60000"  {
                    description "400..60000: Supported range 400 - 60000";
                 }
            }
            default "5000";
            description "Use this attribute to set the delay time for nexthop address tracking.
                        This attribute configures the delayinterval between routing table
                        walks for nexthop delay tracking, after which BGP does a routing table
                        scan on receiving a nexthop change trigger from NSM. The time period
                        determines how long BGP waits before it walks the full BGP table to
                        determine which prefixes are affected by the nexthop changes, after it
                        receives the trigger from NSM about one or more nexthop changes.";
        } // END of nexthop-tracking-delay-msec definition.

        leaf enable-rfc-1771-strict-origin  {
            type  empty;
            description "Use this attribute to set the origin path attribute to IGP when the
                        origin is a protocol such as RIP, OSPF,or ISIS as specified in RFC
                        1771. Otherwise, the origin is always set to incomplete which is the
                        industry standard.";
        } // END of enable-rfc-1771-strict-origin definition.

    } // END of bgp-global-common-config definition.
    grouping bgp-global-common {
        description
            "global common configuration in BGP";
        container config {
            description
                "Configuration parameters relating to the BGP global";
            uses bgp-global-common-config;
        } // END of config-container definition.
        container state {
            config false;
            description
                "state parameters relating to the BGP global";
            uses bgp-global-common-config;
        } // END of state-container definition.
    } // END of bgp-global-common definition.
    grouping bgp-mpls-l3vpn-config {
        description
            "bgp mpls l3 vpn configuration";
        leaf address-family-name  {
            type  ipi-bgp-types:bgp_af_config_t;
            description "Use this attribute to specify address family name";
        } // END of address-family-name definition.

        leaf vrf-name  {
            if-feature feature-list:HAVE_MPLS;
            type  ipi-bgp-types:bgp_vrf_type_t;
            description "Use this attribute to specify vrf name";
        } // END of vrf-name definition.

        leaf label-alloc-type  {
            type  ipi-bgp-types:bgp_l3vpn_label_alloc_mode_t;
            mandatory true;
            description "Use this attribute to specify label alloc type";
        } // END of label-alloc-type definition.

    } // END of bgp-mpls-l3vpn-config definition.
    grouping bgp-mpls-l3-vpn {
        description
            "bgp mpls l3 vpn cnfiguration";
        container mpls-l3vpn-label-modes {
            description
                "Top level container for bgp mpls l3 vpn cnfiguration";

            list mpls-l3vpn-label-mode {
                if-feature feature-list:HAVE_MPLS;
                key "address-family-name vrf-name";
                description
                    "bgp mpls l3 vpn cnfiguration";
                leaf address-family-name  {
                    type  leafref {
                        path  "../config/address-family-name";
                    }
                    description "Use this attribute to specify address family name";
                } // END of address-family-name definition.

                leaf vrf-name  {
                    type  leafref {
                        path  "../config/vrf-name";
                    }
                    description "Use this attribute to specify vrf name";
                } // END of vrf-name definition.

                container config {
                    description
                        "configuration parameters relating to bgp mpls l3 vpn";
                    uses bgp-mpls-l3vpn-config;
                } // END of config-container definition.
                container state {
                    config false;
                    description
                        "state parameters relating to bgp mpls l3 vpn";
                    uses bgp-mpls-l3vpn-config;
                } // END of state-container definition.
            } // End of mpls-l3vpn-label-mode-list
        } // END of mpls-l3vpn-label-modes-container definition.
    } // END of bgp-mpls-l3-vpn definition.
    grouping bgp-community-list-action-value-config {
        description
            "bgp community list action config";
        leaf action  {
            type  ipi-bgp-types:bgp_community_list_action_t;
            description "community type";
        } // END of action definition.

        leaf value  {
            type  string {
                length "1..1965";
                pattern "[^?'=,>|]*";
            }
            description "Use the community-list to specify BGP community attributes. The
                        community attribute is used for implementing policy routing. It is an
                        optional, transitive attribute and facilitates transfer of local
                        policies through different autonomous systems.";
        } // END of value definition.

    } // END of bgp-community-list-action-value-config definition.
    grouping bgp-community-list-standard-number-action-any-config {
        description
            "grouping for bgp community list standard action";
        leaf action-name  {
            type  ipi-bgp-types:bgp_community_list_action_t;
            mandatory true;
            description "Use this attribute to specify a standard community list (1 to 99) that
                        specifies BGP community attributes.";
        } // END of action-name definition.

    } // END of bgp-community-list-standard-number-action-any-config definition.
    grouping bgp-community-list-standard-number-action-any {
        description
            "bgp community list standard action for any";
        container action-for-any {
            description
                "container for community-list action for any";
            container config {
                presence "To configure action for any standard community";
                description
                    "configuration parameters relating to action for any standard community";
                uses bgp-community-list-standard-number-action-any-config;
            } // END of config-container definition.
            container state {
                config false;
                description
                    "state parameters relating to standard action";
                uses bgp-community-list-standard-number-action-any-config;
            } // END of state-container definition.
        } // END of action-for-any-container definition.
    } // END of bgp-community-list-standard-number-action-any definition.
    grouping bgp-community-list-standard-number-action-value-config {
        description
            "bgp community list standard action list value";
        leaf action-standard-number  {
            type  ipi-bgp-types:bgp_community_list_action_t;
            description "Use this attribute to specify a standard community list (1 to 99) that
                        specifies BGP community attributes.";
        } // END of action-standard-number definition.

        leaf standard-number-value  {
            type  string {
                length "1..1965";
                pattern "[^?'=,>|]*";
            }
            description "Use this attribute to specify a standard community list (1 to 99) that
                        specifies BGP community attributes.";
        } // END of standard-number-value definition.

    } // END of bgp-community-list-standard-number-action-value-config definition.
    grouping bgp-community-list-standard-number-action-value {
        description
            "bgp community list standard action list value";
        container action-list-values {
            description
                "Top level container for bgp action list value";

            list action-list-value {
                key "action-standard-number standard-number-value";
                description
                    "bgp action list value";
                leaf action-standard-number  {
                    type  leafref {
                        path  "../config/action-standard-number";
                    }
                    description "Use this attribute to specify a standard community list (1 to 99) that
                                specifies BGP community attributes.";
                } // END of action-standard-number definition.

                leaf standard-number-value  {
                    type  leafref {
                        path  "../config/standard-number-value";
                    }
                    description "Use this attribute to specify a standard community list (1 to 99) that
                                specifies BGP community attributes.";
                } // END of standard-number-value definition.

                container config {
                    description
                        "configuration parameters relating to  bgp action list value";
                    uses bgp-community-list-standard-number-action-value-config;
                } // END of config-container definition.
                container state {
                    config false;
                    description
                        "state parameters relating to  bgp action list value";
                    uses bgp-community-list-standard-number-action-value-config;
                } // END of state-container definition.
            } // End of action-list-value-list
        } // END of action-list-values-container definition.
    } // END of bgp-community-list-standard-number-action-value definition.
    grouping bgp-community-list-number-config {
        description
            "bgp community list number configuration";
        leaf standard-number  {
            type  uint32 {
                 range "1..99"  {
                    description "1..99: Supported range 1 - 99";
                 }
            }
            description "Community list standard number";
        } // END of standard-number definition.

    } // END of bgp-community-list-number-config definition.
    grouping bgp-community-list-number {
        description
            "bgp community list number configuration";
        container numbered-lists {
            description
                "Top level container for bgp community list number";

            list numbered-list {
                key "standard-number";
                description
                    "bgp community list number";
                leaf standard-number  {
                    type  leafref {
                        path  "../config/standard-number";
                    }
                    description "Community list standard number";
                } // END of standard-number definition.

                container config {
                    description
                        "configuration parameters relating to bgp community list number";
                    uses bgp-community-list-number-config;
                } // END of config-container definition.
                container state {
                    config false;
                    description
                        "state parameters relating to bgp community list number";
                    uses bgp-community-list-number-config;
                } // END of state-container definition.
                uses bgp-community-list-standard-number-action-any;
                uses bgp-community-list-standard-number-action-value;
            } // End of numbered-list-list
        } // END of numbered-lists-container definition.
    } // END of bgp-community-list-number definition.
    grouping bgp-community-list-action-value-standard-config {
        description
            "bgp community list action standard list config";
        leaf action-name-standard  {
            type  ipi-bgp-types:bgp_community_list_action_t;
            description "Use the community-lists to specify BGP community attributes. The
                        community attribute is used for implementing policy routing. It is an
                        optional, transitive attribute and facilitates transfer of local
                        policies through different autonomous systems. It includes community
                        values that are 32 bits long. There are two kinds of community-lists:
                        expanded and standard. The standard community-list defines the
                        community attributes in a specified format without regular
                        expressions. The expanded community-list defines the community
                        attributes with regular expressions.Use this attribute to add a
                        standard community-list entry. The standard community-list is compiled
                        into binary format and is directly compared with the BGP communities
                        attribute in the BGP updates. The comparison is faster than the
                        expanded community-list. Any community value that does not match the
                        standard community value is automatically treated as expanded.";
        } // END of action-name-standard definition.

        leaf community-value-standard  {
            type  string {
                length "1..1965";
                pattern "[^?' =,>|]+";
            }
            description "Use this attribute to specify standard community";
        } // END of community-value-standard definition.

    } // END of bgp-community-list-action-value-standard-config definition.
    grouping bgp-community-list-action-value-standard {
        description
            "bgp community list action standard list config";
        container action-values {
            description
                "Top level container for community list action";

            list action-value {
                key "action-name-standard community-value-standard";

                ordered-by user;
                description
                    "community list action";
                leaf action-name-standard  {
                    type  leafref {
                        path  "../config/action-name-standard";
                    }
                    description "Use the community-lists to specify BGP community attributes. The
                                community attribute is used for implementing policy routing. It is an
                                optional, transitive attribute and facilitates transfer of local
                                policies through different autonomous systems. It includes community
                                values that are 32 bits long. There are two kinds of community-lists:
                                expanded and standard. The standard community-list defines the
                                community attributes in a specified format without regular
                                expressions. The expanded community-list defines the community
                                attributes with regular expressions.Use this attribute to add a
                                standard community-list entry. The standard community-list is compiled
                                into binary format and is directly compared with the BGP communities
                                attribute in the BGP updates. The comparison is faster than the
                                expanded community-list. Any community value that does not match the
                                standard community value is automatically treated as expanded.";
                } // END of action-name-standard definition.

                leaf community-value-standard  {
                    type  leafref {
                        path  "../config/community-value-standard";
                    }
                    description "Use this attribute to specify standard community";
                } // END of community-value-standard definition.

                container config {
                    description
                        "configuration parameters relating to bgp community-list-action";
                    uses bgp-community-list-action-value-standard-config;
                } // END of config-container definition.
                container state {
                    config false;
                    description
                        "state parameters relating to bgp community-list-action";
                    uses bgp-community-list-action-value-standard-config;
                } // END of state-container definition.
            } // End of action-value-list
        } // END of action-values-container definition.
    } // END of bgp-community-list-action-value-standard definition.
    grouping bgp-community-list-action-for-any-standard-config {
        description
            "grouping for bgp community list standard action";
        leaf action-name  {
            type  ipi-bgp-types:bgp_community_list_action_t;
            mandatory true;
            description "Use this attribute to specify a standard community list (1 to 99) that
                        specifies BGP community attributes.";
        } // END of action-name definition.

    } // END of bgp-community-list-action-for-any-standard-config definition.
    grouping bgp-community-list-action-for-any-standard {
        description
            "bgp community list standard action for any";
        container action-for-any {
            description
                "container for community-list action for any";
            container config {
                presence "To configure action for any standard community";
                description
                    "configuration parameters relating to action for any standard community";
                uses bgp-community-list-action-for-any-standard-config;
            } // END of config-container definition.
            container state {
                config false;
                description
                    "state parameters relating to standard action";
                uses bgp-community-list-action-for-any-standard-config;
            } // END of state-container definition.
        } // END of action-for-any-container definition.
    } // END of bgp-community-list-action-for-any-standard definition.
    grouping bgp-community-list-standard-config {
        description
            "bgp commmunity list standard configuration";
        leaf list-type  {
            type  ipi-bgp-types:bgp_community_list_type_t;
            description "Community list standard type";
        } // END of list-type definition.

        leaf name  {
            type  string {
                length "1..1965";
                pattern "[^?' =,>|]+";
            }
            description "Community list standard name";
        } // END of name definition.

    } // END of bgp-community-list-standard-config definition.
    grouping bgp-community-list-standard {
        description
            "bgp commmunity list standard configuration";
        container standards {
            description
                "Top level container for bgp extended community standard config";

            list standard {
                key "list-type name";
                description
                    "bgp community list standard";
                leaf list-type  {
                    type  leafref {
                        path  "../config/list-type";
                    }
                    description "Use this attribute to specify community list type";
                } // END of list-type definition.

                leaf name  {
                    type  leafref {
                        path  "../config/name";
                    }
                    description "Use this attribute to specify community list name";
                } // END of name definition.

                container config {
                    description
                        "configuration parameters relating to bgp community list standard";
                    uses bgp-community-list-standard-config;
                } // END of config-container definition.
                container state {
                    config false;
                    description
                        "state parameters relating to bgp community list standard";
                    uses bgp-community-list-standard-config;
                } // END of state-container definition.
                uses bgp-community-list-action-for-any-standard;
                uses bgp-community-list-action-value-standard;
            } // End of standard-list
        } // END of standards-container definition.
    } // END of bgp-community-list-standard definition.
    grouping bgp-community-list-expanded-action-value-config {
        description
            "bgp community list expanded list action";
        leaf action-expanded  {
            type  ipi-bgp-types:bgp_community_list_action_t;
            description "Community list extended type";
        } // END of action-expanded definition.

        leaf regular-expression-list  {
            type  cml-data-types:cml_line_t {
                length "1..1965";
            }
            description "Use this attribute to specify ordered list as a regular-expression.";
        } // END of regular-expression-list definition.

    } // END of bgp-community-list-expanded-action-value-config definition.
    grouping bgp-community-list-expanded-action-value {
        description
            "bgp community list expanded list action";
        container action-values {
            description
                "Top level container for bgp community list expanded list action";

            list action-value {
                key "action-expanded regular-expression-list";

                ordered-by user;
                description
                    "bgp community list expanded list action";
                leaf action-expanded  {
                    type  leafref {
                        path  "../config/action-expanded";
                    }
                    description "Community list extended type";
                } // END of action-expanded definition.

                leaf regular-expression-list  {
                    type  leafref {
                        path  "../config/regular-expression-list";
                    }
                    description "Use this attribute to specify ordered list as a regular-expression.";
                } // END of regular-expression-list definition.

                container config {
                    description
                        "configuration parameters relating to bgp community list expanded list
                                action";
                    uses bgp-community-list-expanded-action-value-config;
                } // END of config-container definition.
                container state {
                    config false;
                    description
                        "state parameters relating to bgp community list expanded list action";
                    uses bgp-community-list-expanded-action-value-config;
                } // END of state-container definition.
            } // End of action-value-list
        } // END of action-values-container definition.
    } // END of bgp-community-list-expanded-action-value definition.
    grouping bgp-community-list-expanded-config {
        description
            "bgp community list expanded";
        leaf list-type  {
            type  ipi-bgp-types:bgp_expanded_list_t;
            description "Community list extended value";
        } // END of list-type definition.

        leaf expanded-type  {
            type  ipi-bgp-types:bgp_expanded_list_type_t;
            description "Community list extended value";
        } // END of expanded-type definition.

    } // END of bgp-community-list-expanded-config definition.
    grouping bgp-community-list-expanded {
        description
            "bgp community list expanded";
        container expanded-lists {
            description
                "Top level container for bgp community list expanded";

            list expanded-list {
                key "list-type expanded-type";

                ordered-by user;
                description
                    "bgp community list expanded";
                leaf list-type  {
                    type  leafref {
                        path  "../config/list-type";
                    }
                    description "Community list expanded type";
                } // END of list-type definition.

                leaf expanded-type  {
                    type  leafref {
                        path  "../config/expanded-type";
                    }
                    description "Community list extended value";
                } // END of expanded-type definition.

                container config {
                    description
                        "configuration parameters relating to bgp community list expanded";
                    uses bgp-community-list-expanded-config;
                } // END of config-container definition.
                container state {
                    config false;
                    description
                        "state parameters relating to bgp community list expanded";
                    uses bgp-community-list-expanded-config;
                } // END of state-container definition.
                uses bgp-community-list-expanded-action-value;
            } // End of expanded-list-list
        } // END of expanded-lists-container definition.
    } // END of bgp-community-list-expanded definition.
    grouping bgp-extended-number-community-list-action-value-config {
        description
            "bgp extended community list action config";
        leaf extended-action-number  {
            type  ipi-bgp-types:bgp_community_list_action_t;
            description "Extended Community list type";
        } // END of extended-action-number definition.

        leaf extended-route-target-soo  {
            type  ipi-bgp-types:bgp_route_target_t;
            description "route-target soo";
        } // END of extended-route-target-soo definition.

        leaf extended-value  {
            type  string {
                length "1..1965";
                pattern "[^?' =,>|]+";
            }
            description "Use this attribute to create an entry for a standard extended
                        community list (1 to 99) that specifies BGP community attributes.";
        } // END of extended-value definition.

    } // END of bgp-extended-number-community-list-action-value-config definition.
    grouping bgp-extended-number-community-list-action-value {
        description
            "bgp extended community list action config";
        container action-values {
            description
                "Top level container for bgp extended community list action config";

            list action-value {
                key "extended-action-number extended-route-target-soo extended-value";

                ordered-by user;
                description
                    "bgp extended community list action config";
                leaf extended-action-number  {
                    type  leafref {
                        path  "../config/extended-action-number";
                    }
                    description "Extended Community list type";
                } // END of extended-action-number definition.

                leaf extended-route-target-soo  {
                    type  leafref {
                        path  "../config/extended-route-target-soo";
                    }
                    description "route-target soo";
                } // END of extended-route-target-soo definition.

                leaf extended-value  {
                    type  leafref {
                        path  "../config/extended-value";
                    }
                    description "Use this attribute to create an entry for a standard extended
                                community list for rt (Route target extended community) or soo
                                (Site-of-origin extended community).";
                } // END of extended-value definition.

                container config {
                    description
                        "configuration parameters relating to bgp extended community list
                                action";
                    uses bgp-extended-number-community-list-action-value-config;
                } // END of config-container definition.
                container state {
                    config false;
                    description
                        "state parameters relating to bgp extended community list action";
                    uses bgp-extended-number-community-list-action-value-config;
                } // END of state-container definition.
            } // End of action-value-list
        } // END of action-values-container definition.
    } // END of bgp-extended-number-community-list-action-value definition.
    grouping bgp-extended-community-list-number-config {
        description
            "bgp extended community list number config";
        leaf standard-number  {
            type  uint32 {
                 range "1..99"  {
                    description "1..99: Supported range 1 - 99";
                 }
            }
            description "Extended Community list number";
        } // END of standard-number definition.

    } // END of bgp-extended-community-list-number-config definition.
    grouping bgp-extended-community-list-number {
        description
            "bgp extended community list number config";
        container numbered-lists {
            description
                "Top level container for bgp extended community list number config";

            list numbered-list {
                key "standard-number";
                description
                    "List of bgp extended community list number config";
                leaf standard-number  {
                    type  leafref {
                        path  "../config/standard-number";
                    }
                    description "Extended Community list number";
                } // END of standard-number definition.

                container config {
                    description
                        "configuration parameters relating to bgp extended community list
                                number";
                    uses bgp-extended-community-list-number-config;
                } // END of config-container definition.
                container state {
                    config false;
                    description
                        "state parameters relating to bgp extended community list number";
                    uses bgp-extended-community-list-number-config;
                } // END of state-container definition.
                uses bgp-extended-number-community-list-action-value;
            } // End of numbered-list-list
        } // END of numbered-lists-container definition.
    } // END of bgp-extended-community-list-number definition.
    grouping bgp-extended-community-standard-action-value-config {
        description
            "bgp extended community standard action config";
        leaf extended-action  {
            type  ipi-bgp-types:bgp_community_list_action_t;
            description "extcommunity Community list type";
        } // END of extended-action definition.

        leaf route-target-soo  {
            type  ipi-bgp-types:bgp_route_target_t;
            description "route-target soo";
        } // END of route-target-soo definition.

        leaf value  {
            type  string {
                length "1..1965";
                pattern "[^?' =,>|]+";
            }
            description "Use this attribute to create an entry for a standard extended
                        community list for rt (Route target extended community) or soo
                        (Site-of-origin extended community).";
        } // END of value definition.

    } // END of bgp-extended-community-standard-action-value-config definition.
    grouping bgp-extended-community-standard-action-value {
        description
            "bgp extended community standard action config";
        container action-values {
            description
                "Top level container for bgp extended community standard action config";

            list action-value {
                key "extended-action route-target-soo value";

                ordered-by user;
                description
                    "bgp extended community standard action config";
                leaf extended-action  {
                    type  leafref {
                        path  "../config/extended-action";
                    }
                    description "extcommunity Community list type";
                } // END of extended-action definition.

                leaf route-target-soo  {
                    type  leafref {
                        path  "../config/route-target-soo";
                    }
                    description "route-target soo";
                } // END of route-target-soo definition.

                leaf value  {
                    type  leafref {
                        path  "../config/value";
                    }
                    description "Use this attribute to create an entry for a standard extended
                                community list for rt (Route target extended community) or soo
                                (Site-of-origin extended community).";
                } // END of value definition.

                container config {
                    description
                        "configuration parameters relating to bgp extended community standard
                                action";
                    uses bgp-extended-community-standard-action-value-config;
                } // END of config-container definition.
                container state {
                    config false;
                    description
                        "state parameters relating to bgp extended community standard action";
                    uses bgp-extended-community-standard-action-value-config;
                } // END of state-container definition.
            } // End of action-value-list
        } // END of action-values-container definition.
    } // END of bgp-extended-community-standard-action-value definition.
    grouping bgp-extended-community-standard-config {
        description
            "bgp extended community standard config";
        leaf name  {
            type  string {
                length "1..1965";
                pattern "[^?' =,>|]+";
            }
            description "extcommunity Community list name";
        } // END of name definition.

    } // END of bgp-extended-community-standard-config definition.
    grouping bgp-extended-community-standard {
        description
            "bgp extended community standard config";
        container standards {
            description
                "Top level container for bgp extended community standard config";

            list standard {
                key "name";
                description
                    "bgp extended community standard config";
                leaf name  {
                    type  leafref {
                        path  "../config/name";
                    }
                    description "Use this attribute to specify community list name";
                } // END of name definition.

                container config {
                    description
                        "configuration parametrs relating to bgp extended community list
                                standard";
                    uses bgp-extended-community-standard-config;
                } // END of config-container definition.
                container state {
                    config false;
                    description
                        "state parametrs relating to bgp extended community list standard";
                    uses bgp-extended-community-standard-config;
                } // END of state-container definition.
                uses bgp-extended-community-standard-action-value;
            } // End of standard-list
        } // END of standards-container definition.
    } // END of bgp-extended-community-standard definition.
    grouping bgp-extended-community-expanded-action-value-config {
        description
            "bgp extended community expanded action configurations";
        leaf action  {
            type  ipi-bgp-types:bgp_community_list_action_t;
            description "extcommunity Extended Community type";
        } // END of action definition.

        leaf value  {
            type  cml-data-types:cml_line_t {
                length "1..255";
            }
            description "Use this attribute to create an extended community list";
        } // END of value definition.

    } // END of bgp-extended-community-expanded-action-value-config definition.
    grouping bgp-extended-community-expanded-action-value {
        description
            "bgp extended community expanded action configurations";
        container action-values {
            description
                "Top level container for bgp extended community expanded action
                        configurations";

            list action-value {
                key "action value";

                ordered-by user;
                description
                    "bgp extended community expanded action configurations";
                leaf action  {
                    type  leafref {
                        path  "../config/action";
                    }
                    description "extcommunity Extended Community type";
                } // END of action definition.

                leaf value  {
                    type  leafref {
                        path  "../config/value";
                    }
                    description "Use this attribute to create an extended community list";
                } // END of value definition.

                container config {
                    description
                        "configuration parameters relating to  bgp extended community expanded
                                action list";
                    uses bgp-extended-community-expanded-action-value-config;
                } // END of config-container definition.
                container state {
                    config false;
                    description
                        "state parameters relating to  bgp extended community expanded action
                                list";
                    uses bgp-extended-community-expanded-action-value-config;
                } // END of state-container definition.
            } // End of action-value-list
        } // END of action-values-container definition.
    } // END of bgp-extended-community-expanded-action-value definition.
    grouping bgp-extended-community-expanded-config {
        description
            "bgp extended community expanded configurations";
        leaf list-type  {
            type  ipi-bgp-types:bgp_ext_expanded_list_t;
            description "Community list extended value";
        } // END of list-type definition.

        leaf expanded-type  {
            type  ipi-bgp-types:bgp_expanded_list_type_t;
            description "Community list extended value";
        } // END of expanded-type definition.

    } // END of bgp-extended-community-expanded-config definition.
    grouping bgp-extended-community-expanded {
        description
            "bgp extended community expanded configurations";
        container expanded-lists {
            description
                "Top level container for bgp community list expanded";

            list expanded-list {
                key "list-type expanded-type";
                description
                    "bgp extended community expanded configurations";
                leaf list-type  {
                    type  leafref {
                        path  "../config/list-type";
                    }
                    description "extcommunity Extended Community type";
                } // END of list-type definition.

                leaf expanded-type  {
                    type  leafref {
                        path  "../config/expanded-type";
                    }
                    description "extcommunity Extended Community type";
                } // END of expanded-type definition.

                container config {
                    description
                        "configuration parameters relating to bgp extended community expanded
                                list";
                    uses bgp-extended-community-expanded-config;
                } // END of config-container definition.
                container state {
                    config false;
                    description
                        "state parameters relating to bgp extended community expanded list";
                    uses bgp-extended-community-expanded-config;
                } // END of state-container definition.
                uses bgp-extended-community-expanded-action-value;
            } // End of expanded-list-list
        } // END of expanded-lists-container definition.
    } // END of bgp-extended-community-expanded definition.
    grouping bgp-extended-community-list {
        description
            "extended bgp community configuration";
        container extended-community {
            description
                "main container for the complete extended community-list";
            uses bgp-extended-community-list-number;
            uses bgp-extended-community-standard;
            uses bgp-extended-community-expanded;
        } // END of extended-community-container definition.
    } // END of bgp-extended-community-list definition.
    grouping bgp-large-number-community-list-action-value-config {
        description
            "bgp large community list action config";
        leaf large-action-number  {
            type  ipi-bgp-types:bgp_community_list_action_t;
            description "Large Community list type";
        } // END of large-action-number definition.

        leaf large-value  {
            type  cml-data-types:cml_line_t {
                length "1..1965";
            }
            description "Use this attribute to create an entry for a standard large community
                        list (1 to 99) that specifies BGP community attributes.";
        } // END of large-value definition.

    } // END of bgp-large-number-community-list-action-value-config definition.
    grouping bgp-large-number-community-list-action-value {
        description
            "bgp large community list action config";
        container action-values {
            description
                "Top level container for bgp large community list action config";

            list action-value {
                key "large-action-number large-value";

                ordered-by user;
                description
                    "bgp large community list action config";
                leaf large-action-number  {
                    type  leafref {
                        path  "../config/large-action-number";
                    }
                    description "Large Community list type";
                } // END of large-action-number definition.

                leaf large-value  {
                    type  leafref {
                        path  "../config/large-value";
                    }
                    description "Use this attribute to create an entry for a standard large community
                                list (1 to 99) that specifies BGP community attributes.";
                } // END of large-value definition.

                container config {
                    description
                        "configuration parameters relating to bgp large community list action";
                    uses bgp-large-number-community-list-action-value-config;
                } // END of config-container definition.
                container state {
                    config false;
                    description
                        "state parameters relating to bgp large community list action";
                    uses bgp-large-number-community-list-action-value-config;
                } // END of state-container definition.
            } // End of action-value-list
        } // END of action-values-container definition.
    } // END of bgp-large-number-community-list-action-value definition.
    grouping bgp-large-community-list-number-config {
        description
            "bgp large community list number config";
        leaf standard-number  {
            type  uint32 {
                 range "1..99"  {
                    description "1..99: Supported range 1 - 99";
                 }
            }
            description "Large Community list number";
        } // END of standard-number definition.

    } // END of bgp-large-community-list-number-config definition.
    grouping bgp-large-community-list-number {
        description
            "bgp large community list number config";
        container numbered-lists {
            description
                "Top level container for bgp large community list number config";

            list numbered-list {
                key "standard-number";
                description
                    "List of bgp large community list number config";
                leaf standard-number  {
                    type  leafref {
                        path  "../config/standard-number";
                    }
                    description "Large Community list number";
                } // END of standard-number definition.

                container config {
                    description
                        "configuration parameters relating to bgp large community list number";
                    uses bgp-large-community-list-number-config;
                } // END of config-container definition.
                container state {
                    config false;
                    description
                        "state parameters relating to bgp large community list number";
                    uses bgp-large-community-list-number-config;
                } // END of state-container definition.
                uses bgp-large-number-community-list-action-value;
            } // End of numbered-list-list
        } // END of numbered-lists-container definition.
    } // END of bgp-large-community-list-number definition.
    grouping bgp-large-community-standard-action-value-config {
        description
            "bgp large community standard action configurations";
        leaf action  {
            type  ipi-bgp-types:bgp_community_list_action_t;
            description "large-community Large Community type";
        } // END of action definition.

        leaf value  {
            type  cml-data-types:cml_line_t {
                length "1..1965";
            }
            description "Use this attribute to create an large community list";
        } // END of value definition.

    } // END of bgp-large-community-standard-action-value-config definition.
    grouping bgp-large-community-standard-action-value {
        description
            "bgp large community standard action configurations";
        container action-values {
            description
                "Top level container for bgp large community standard action
                        configurations";

            list action-value {
                key "action value";

                ordered-by user;
                description
                    "bgp large community standard action configurations";
                leaf action  {
                    type  leafref {
                        path  "../config/action";
                    }
                    description "large-community Large Community type";
                } // END of action definition.

                leaf value  {
                    type  leafref {
                        path  "../config/value";
                    }
                    description "Use this attribute to create an large community list";
                } // END of value definition.

                container config {
                    description
                        "configuration parameters relating to  bgp large community standard
                                action list";
                    uses bgp-large-community-standard-action-value-config;
                } // END of config-container definition.
                container state {
                    config false;
                    description
                        "state parameters relating to  bgp large community standard action list";
                    uses bgp-large-community-standard-action-value-config;
                } // END of state-container definition.
            } // End of action-value-list
        } // END of action-values-container definition.
    } // END of bgp-large-community-standard-action-value definition.
    grouping bgp-large-community-standard-config {
        description
            "bgp large community standard configurations";
        leaf list-type  {
            type  ipi-bgp-types:bgp_standard_list_t;
            description "Community list large value";
        } // END of list-type definition.

        leaf standard-type  {
            type  ipi-bgp-types:bgp_standard_list_type_t;
            description "Community list large value";
        } // END of standard-type definition.

    } // END of bgp-large-community-standard-config definition.
    grouping bgp-large-community-standard {
        description
            "bgp large community standard configurations";
        container standard-lists {
            description
                "Top level container for bgp community list standard";

            list standard-list {
                key "list-type standard-type";
                description
                    "bgp large community standard configurations";
                leaf list-type  {
                    type  leafref {
                        path  "../config/list-type";
                    }
                    description "large-community Large Community type";
                } // END of list-type definition.

                leaf standard-type  {
                    type  leafref {
                        path  "../config/standard-type";
                    }
                    description "large-community Large Community type";
                } // END of standard-type definition.

                container config {
                    description
                        "configuration parameters relating to bgp large community standard list";
                    uses bgp-large-community-standard-config;
                } // END of config-container definition.
                container state {
                    config false;
                    description
                        "state parameters relating to bgp large community standard list";
                    uses bgp-large-community-standard-config;
                } // END of state-container definition.
                uses bgp-large-community-standard-action-value;
            } // End of standard-list-list
        } // END of standard-lists-container definition.
    } // END of bgp-large-community-standard definition.
    grouping bgp-large-community-expanded-action-value-config {
        description
            "bgp large community expanded action configurations";
        leaf action  {
            type  ipi-bgp-types:bgp_community_list_action_t;
            description "large-community Large Community type";
        } // END of action definition.

        leaf value  {
            type  cml-data-types:cml_line_t {
                length "1..1965";
            }
            description "Use this attribute to create an large community list";
        } // END of value definition.

    } // END of bgp-large-community-expanded-action-value-config definition.
    grouping bgp-large-community-expanded-action-value {
        description
            "bgp large community expanded action configurations";
        container action-values {
            description
                "Top level container for bgp large community expanded action
                        configurations";

            list action-value {
                key "action value";

                ordered-by user;
                description
                    "bgp large community expanded action configurations";
                leaf action  {
                    type  leafref {
                        path  "../config/action";
                    }
                    description "large-community Large Community type";
                } // END of action definition.

                leaf value  {
                    type  leafref {
                        path  "../config/value";
                    }
                    description "Use this attribute to create an large community list";
                } // END of value definition.

                container config {
                    description
                        "configuration parameters relating to  bgp large community expanded
                                action list";
                    uses bgp-large-community-expanded-action-value-config;
                } // END of config-container definition.
                container state {
                    config false;
                    description
                        "state parameters relating to  bgp large community expanded action list";
                    uses bgp-large-community-expanded-action-value-config;
                } // END of state-container definition.
            } // End of action-value-list
        } // END of action-values-container definition.
    } // END of bgp-large-community-expanded-action-value definition.
    grouping bgp-large-community-expanded-config {
        description
            "bgp large community expanded configurations";
        leaf list-type  {
            type  ipi-bgp-types:bgp_large_expanded_list_t;
            description "Community list large value";
        } // END of list-type definition.

        leaf expanded-type  {
            type  ipi-bgp-types:bgp_expanded_list_type_t;
            description "Community list large value";
        } // END of expanded-type definition.

    } // END of bgp-large-community-expanded-config definition.
    grouping bgp-large-community-expanded {
        description
            "bgp large community expanded configurations";
        container expanded-lists {
            description
                "Top level container for bgp community list expanded";

            list expanded-list {
                key "list-type expanded-type";
                description
                    "bgp large community expanded configurations";
                leaf list-type  {
                    type  leafref {
                        path  "../config/list-type";
                    }
                    description "large-community Large Community type";
                } // END of list-type definition.

                leaf expanded-type  {
                    type  leafref {
                        path  "../config/expanded-type";
                    }
                    description "large-community Large Community type";
                } // END of expanded-type definition.

                container config {
                    description
                        "configuration parameters relating to bgp large community expanded list";
                    uses bgp-large-community-expanded-config;
                } // END of config-container definition.
                container state {
                    config false;
                    description
                        "state parameters relating to bgp large community expanded list";
                    uses bgp-large-community-expanded-config;
                } // END of state-container definition.
                uses bgp-large-community-expanded-action-value;
            } // End of expanded-list-list
        } // END of expanded-lists-container definition.
    } // END of bgp-large-community-expanded definition.
    grouping bgp-large-community-list {
        description
            "large bgp community configuration";
        container large-community {
            description
                "main container for the complete large community-list";
            uses bgp-large-community-list-number;
            uses bgp-large-community-standard;
            uses bgp-large-community-expanded;
        } // END of large-community-container definition.
    } // END of bgp-large-community-list definition.
    grouping bgp-community {
        description
            "bgp community configuration";
        container community-lists {
            description
                "main container for the complete community-list";
            uses bgp-community-list-number;
            uses bgp-community-list-standard;
            uses bgp-community-list-expanded;
            uses bgp-extended-community-list;
            uses bgp-large-community-list;
        } // END of community-lists-container definition.
    } // END of bgp-community definition.
    grouping bgp-global-access-name-config {
        description
            "bgp global access name configuration";
        leaf access-list-name  {
            type  string {
                length "1..1965";
                pattern "[^?' =,>|]+";
            }
            description "Use this attribute to define a BGP Autonomous System (AS) path access
                        list. A named community list is a filter based on regular expressions.
                        If the regular expression matches the specified string representing
                        the AS path of the route, then the permit or deny condition applies.
                        Use this attribute to define the BGP access list globally.";
        } // END of access-list-name definition.

        leaf access-list-action  {
            type  ipi-bgp-types:bgp_community_list_action_t;
            description "Action type <0-1> 0 - Deny 1 - Permit";
        } // END of access-list-action definition.

        leaf access-list-regular-expression  {
            type  cml-data-types:cml_line_t {
                length "1..1965";
                pattern "[^'=>]*";
            }
            description "Regular expression to match BGP AS paths";
        } // END of access-list-regular-expression definition.

    } // END of bgp-global-access-name-config definition.
    grouping bgp-global-access-name-config-param {
        description
            "bgp global access name configuration";
        container as-path-access-lists {
            description
                "Top level container for bgp global access list configuration";

            list as-path-access-list {
                key "access-list-name access-list-action access-list-regular-expression";
                description
                    "bgp global access list configuration";
                leaf access-list-name  {
                    type  leafref {
                        path  "../config/access-list-name";
                    }
                    description "Use this attribute to define a BGP Autonomous System (AS) path access
                                list. A named community list is a filter based on regular expressions.
                                If the regular expression matches the specified string representing
                                the AS path of the route, then the permit or deny condition applies.
                                Use this attribute to define the BGP access list globally.";
                } // END of access-list-name definition.

                leaf access-list-action  {
                    type  leafref {
                        path  "../config/access-list-action";
                    }
                    description "Action type <0-1> 0 - Deny 1 - Permit";
                } // END of access-list-action definition.

                leaf access-list-regular-expression  {
                    type  leafref {
                        path  "../config/access-list-regular-expression";
                    }
                    description "Regular expression to match BGP AS paths";
                } // END of access-list-regular-expression definition.

                container config {
                    description
                        "configuration parameters relating to bgp access list";
                    uses bgp-global-access-name-config;
                } // END of config-container definition.
                container state {
                    config false;
                    description
                        "state  parameters relating to bgp access list";
                    uses bgp-global-access-name-config;
                } // END of state-container definition.
            } // End of as-path-access-list-list
        } // END of as-path-access-lists-container definition.
    } // END of bgp-global-access-name-config-param definition.
    grouping bgp-mpls-6pe-config {
        description
            "bgp mpls 6pe configurations";
        leaf enable-per-prefix-label-mode  {
            type  empty;
            description "Use this attribute to configure mpls label mode";
        } // END of enable-per-prefix-label-mode definition.

    } // END of bgp-mpls-6pe-config definition.
    grouping bgp-mpls-6pe {
        description
            "bgp mpls 6pe configurations";
        container mpls-6pe {
            if-feature feature-list:HAVE_MPLS;
            if-feature feature-list:HAVE_6PE;
            description
                "Container for bgp mpls 6pe";
            container config {
                description
                    "configuration parameters relating to bgp mpls 6pe configurations";
                uses bgp-mpls-6pe-config;
            } // END of config-container definition.
            container state {
                config false;
                description
                    "state parameters relating to bgp mpls 6pe configurations";
                uses bgp-mpls-6pe-config;
            } // END of state-container definition.
        } // END of mpls-6pe-container definition.
    } // END of bgp-mpls-6pe definition.
    grouping bgp-global-debug-config {
        description
            "bgp global debug configurations";
        leaf options  {
            type  ipi-bgp-types:bgp_debug_t;
            description "Use this attribute to enable all BGP troubleshooting functions. Use
                        this attribute without any parameters to turn on normal bgp debug
                        information.";
        } // END of options definition.

    } // END of bgp-global-debug-config definition.
    grouping bgp-global-terminal-debug-state {
        description
            "Terminal debug status for bgp";
        leaf terminal-debug-status  {
            type  ipi-bgp-types:bgp_debug_t;
            description "Terminal debug option";
        } // END of terminal-debug-status definition.

    } // END of bgp-global-terminal-debug-state definition.
    grouping bgp-global-debug {
        description
            "bgp global debug configurations";
        container debug {
            description
                "bgp global debug configurations";
            container config {
                description
                    "config parameters relating to  bgp global debug container";
                uses bgp-global-debug-config;
            } // END of config-container definition.
            container state {
                config false;
                description
                    "state parameters relating to  bgp global debug container";
                container terminal-debug-status {
                    config false;
                    description
                        "Terminal debug status";
                    uses bgp-global-terminal-debug-state;
                } // END of terminal-debug-status-container definition.
                uses bgp-global-debug-config;
            } // END of state-container definition.
        } // END of debug-container definition.
    } // END of bgp-global-debug definition.

    grouping  bgp-grouping {
    description
        "Top-level configuration and state for the BGP router";
    container bgp {
        if-feature feature-list:HAVE_BGPD;
        description
            "Top-level configuration and state for the BGP router";
        container global {
            description
                "Global configuration for the BGP router uses bgp-global-base";
            uses bgp-global-common;
            uses bgp-community;
            uses bgp-global-access-name-config-param;
            uses bgp-mpls-l3-vpn;
            uses bgp-mpls-6pe;
            uses bgp-global-debug;
        } // END of global-container definition.
        uses bgp-instances-grouping;
        uses flowspec-grouping;
    } // END of bgp-container definition.
    } // END of bgp-grouping definition.

    uses bgp-grouping;

    rpc clear-ip-bgp-peer {
        if-feature feature-list:HAVE_BGPD;
        description "clear specific peer";
        input  {
            leaf arg  {
                type ipi-bgp-types:bgp_hostname_t;
                mandatory true;
                description "input arguments (peer Address, prefix address, peer-group name, bgp
                            As)";
            }
            leaf peer-reset-description  {
                type cml-data-types:cml_line_t {
                    length "1..255";
                }
                description "Use this attribute to send shutdown communication message to inform
                            peer the reason for the reset of the BGP session.";
            }
        }
    }

    rpc clear-peer-group-l2vpn-evpn-soft-all {
        if-feature feature-list:HAVE_BGP_EVPN;
        if-feature feature-list:HAVE_BGPD;
        description "use this RPC to clear the bgp peer-group l2vpn evpn";
        input  {
            leaf peer-group-tag  {
                type string {
                    length "1..255";
                }
                mandatory true;
                description "This attribute creates a peer-group";
            }
            leaf soft-reconfig  {
                type ipi-bgp-types:bgp_update_clear_t;
                mandatory true;
                description "This attribute is used to store the updates for soft
                            inbound and outbound configuration.";
            }
        }
    }

    rpc clear-ip-bgp-all-peer {
        if-feature feature-list:HAVE_BGPD;
        description "clear all bgp peers";
        input  {
            leaf peer-reset-description  {
                type cml-data-types:cml_line_t {
                    length "1..255";
                }
                description "Use this attribute to send shutdown communication message to inform
                            peer the reason for the reset of the BGP session.";
            }
        }
    }

    rpc clear-bgp-l2vpn-evpn-soft-all {
        if-feature feature-list:HAVE_BGP_EVPN;
        if-feature feature-list:HAVE_BGPD;
        description "use this RPC to clear all the bgp l2vpn evpn peers";
        input  {
            leaf soft-reconfig  {
                type ipi-bgp-types:bgp_update_clear_t;
                mandatory true;
                description "This attribute is used to store the updates for soft
                            inbound and outbound configuration.";
            }
        }
    }

    rpc clear-bgp-remote-as-l2vpn-evpn-soft-all {
        if-feature feature-list:HAVE_BGP_EVPN;
        if-feature feature-list:HAVE_BGPD;
        description "use this RPC to clear all the bgp remote-as l2vpn evpn peers";
        input  {
            leaf peer-as  {
                type uint32 {
                    range "1..4294967295";
                }
                mandatory true;
                description "This attribute specifies a neighbors autonomous system number";
            }
            leaf soft-reconfig  {
                type ipi-bgp-types:bgp_update_clear_t;
                mandatory true;
                description "This attribute is used to store the updates for soft
                            inbound and outbound configuration.";
            }
        }
    }

    rpc clear-bgp-peer-address-l2vpn-evpn-soft {
        if-feature feature-list:HAVE_BGP_EVPN;
        if-feature feature-list:HAVE_BGPD;
        description "Use this RPC to clear the bgp peer-address l2vpn evpn";
        input  {
            leaf peer-address  {
                type ipi-bgp-types:bgp_ip_addr_t;
                mandatory true;
                description "Address of the BGP peer, either in IPv4 or IPv6";
            }
            leaf soft-reconfig  {
                type ipi-bgp-types:bgp_update_clear_t;
                mandatory true;
                description "This attribute is used to store the updates for soft
                            inbound and outbound configuration.";
            }
        }
    }

    rpc clear-ip-bgp-all-vrf {
        if-feature feature-list:HAVE_BGPD;
        description "clear all bgp instances and peer in vrf(all|default)";
        input  {
            leaf vrf-name  {
                type string;
                mandatory true;
                description "vrf name";
            }
            leaf peer-reset-description  {
                type cml-data-types:cml_line_t {
                    length "1..255";
                }
                description "Use this attribute to send shutdown communication message to inform
                            peer the reason for the reset of the BGP session.";
            }
        }
    }

    rpc clear-ip-bgp-vrf-peer {
        if-feature feature-list:HAVE_BGPD;
        description "clear bgp peer in specific vrf";
        input  {
            leaf vrf-name  {
                type string;
                mandatory true;
                description "vrf name";
            }
            leaf address  {
                type ipi-bgp-types:bgp_hostname_t;
                mandatory true;
                description "input arguments (peer Address,prefix address, peer-group name, bgp As)";
            }
            leaf peer-reset-description  {
                type cml-data-types:cml_line_t {
                    length "1..255";
                }
                description "Use this attribute to send shutdown communication message to inform
                            peer the reason for the reset of the BGP session.";
            }
        }
    }

    rpc bgp-graceful-restart {
        if-feature feature-list:HAVE_RESTART;
        if-feature feature-list:HAVE_BGPD;
        description "Graceful restart of bgp";
    }

    rpc clear-bgp-statistics {
        if-feature feature-list:HAVE_BGPD;
        description "clear all bgp peer Statistics fields";
    }

    rpc bgp-snmp-restart {
        if-feature feature-list:HAVE_BGPD;
        description "restart SNMP in Border Gateway Protocol (BGP)";
    }

    rpc bgp-debug-on {
        if-feature feature-list:HAVE_BGPD;
        description "Use this RPC to enable debug on BGP";
        input  {
            leaf terminal-debug-options  {
                type ipi-bgp-types:bgp_debug_t;
                mandatory true;
                description "Use this command to turn on all BGP troubleshooting functions. Use
                            this command without any parameters to turn on normal bgp debug
                            information..";
            }
        }
    }

    rpc bgp-debug-off {
        if-feature feature-list:HAVE_BGPD;
        description "Use this RPC to disable debug on BGP";
        input  {
            leaf terminal-debug-options  {
                type ipi-bgp-types:bgp_debug_t;
                mandatory true;
                description "Use this command to turn off, BGP debugging at various levels.";
            }
        }
    }

    rpc bgp-all-debug-off {
        if-feature feature-list:HAVE_BGPD;
        description "Use this RPC to disable debug on BGP.";
    }

    notification bgp-established-notification {
        if-feature feature-list:HAVE_BGPD;

        description "Notify BGP Peer established notification.";

        leaf severity {
            type cml-data-types:cml_notif_severity_t;
            description "Notification severity level";
        }

        leaf eventClass {
            type cml-data-types:cml_notif_class_t;
            description "Notification event class (value: STATE)";
        }

        leaf peer-address {
            type ipi-bgp-types:bgp_ip_addr_t;
        description
            "Reference to the address of the BGP peer used as a key in the peer
                    list";
        }

        leaf bgp-as {
            type  uint32;
        description
            "Use this attribute to start a BGP process.";
        }

        leaf peer-state {
            type ipi-bgp-types:bgp_peer_status_t;
        description
            "Bgp peer session state. If there is change in state of the session ,
                    notification will be published only if the current state or the
                    previous state is in establised state";
        }
    }

    notification bgp-backward-transition-notification {
        if-feature feature-list:HAVE_BGPD;

        description "Notify Peer State backward transition notification.";

        leaf severity {
            type cml-data-types:cml_notif_severity_t;
            description "Notification severity level";
        }

        leaf eventClass {
            type cml-data-types:cml_notif_class_t;
            description "Notification event class (value: STATE)";
        }

        leaf peer-address {
            type ipi-bgp-types:bgp_ip_addr_t;
        description
            "Reference to the address of the BGP peer used as a key in the peer
                    list";
        }

        leaf bgp-as {
            type  uint32;
        description
            "Use this attribute to start a BGP process.";
        }

        leaf peer-state {
            type ipi-bgp-types:bgp_peer_status_t;
        description
            "Bgp peer session state. If there is change in state of the session ,
                    notification will be published only if the current state or the
                    previous state is in establised state";
        }
    }

}
