/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-bgp-address-family-vrf.yang
*
*/

submodule ipi-bgp-address-family-vrf {

    yang-version 1.1;

    belongs-to  ipi-bgp { prefix ipi-bgp; }

    import feature-list {
        prefix feature-list;
        revision-date 2026-09-15;
    }

    import ietf-inet-types {
        prefix inet;
        revision-date 2013-07-15;
    }

    import cml-data-types {
        prefix cml-data-types;
        revision-date 2026-05-15;
    }

    import ipi-bgp-types {
        prefix ipi-bgp-types;
        revision-date 2025-12-22;
    }

    import ipi-network-instance {
        prefix ipi-network-instance;
        revision-date 2026-08-12;
    }

    import ipi-vrf {
        prefix ipi-vrf;
        revision-date 2026-08-12;
    }

    include ipi-bgp-address-family { revision-date 2026-09-04;}
    include ipi-bgp-common { revision-date 2025-12-22;}
    organization
        "IP Infusion Inc.";

    contact
        "Address: 3965 Freedom Circle, Suite 200, Santa Clara, CA 95054
         Phone: +1 408-400-1900
         E-mail: support@ipinfusion.com
         Web: http://www.ipinfusion.com/";

    description
        "";


    revision "2026-07-28" {
        description "Added autoPopulate-custom for object-list 'vrf-peers/vrf-peer' for peer-group update";
        reference " 0.19.0.";
    }

    revision "2025-12-18" {
        description "Added CML_SKIP_HITLESS_MERGE for the attribute 'additional-paths-mode'";
        reference " 0.18.7.";
    }

    revision "2025-12-09" {
        description "Updated cli-command for attribute 'peer-as'";
        reference " 0.18.6.";
    }

    revision "2025-12-04" {
        description "Added when tag for the attribute mapped-peer-group-tag-af";
        reference " 0.18.5.";
    }

    revision "2025-11-17" {
        description " Added hidden flag for disable-capability-negotiation";
        reference " 0.18.4.";
    }

    revision "2025-11-05" {
        description " Split aggregate-address CLI for VRF address-family into IPv4 and IPv6 specific modes. Added AF-based input_display and input_helpStr to restrict help output to correct address family.";
        reference " 0.18.3.";
    }

    revision "2025-10-15" {
        description "Added cliprependstr tags for helpstring generation";
        reference " 0.18.2.";
    }

    revision "2025-09-03" {
        description "Added leaf ref to vrf name to handle validation of non existing vrf commit dry run";
        reference " 0.18.1.";
    }

    revision "2025-06-26" {
        description "initial revion for BGP RPKI Origin Validation";
        reference " 0.18.0.";
    }

    revision "2025-05-06" {
        description "Updated input displayString for attribute 'password' and Added cli-commands for 'password' delete";
        reference " 0.17.4.";
    }

    revision "2025-04-29" {
        description "Made attr redist-route-map-name mandatory for redistribute configuration";
        reference " 0.17.3.";
    }

    revision "2025-04-24" {
        description "Added dependentObject tag for 'address-family-vrfs/address-family-vrf/vrf-peers/vrf-peer/config' and 'address-family-vrfs/address-family-vrf/peer-groups/peer-group/config'";
        reference " 0.17.2.";
    }

    revision "2025-02-13" {
        description "Added utils api for attribute 'aggregate-address'";
        reference " 0.17.1.";
    }

    revision "2025-01-28" {
        description "Added aggregrate-address for vrf address-family";
        reference " 0.17.0..";
    }

    revision "2024-12-23" {
        description "Removed container 'confederation' and bgp-af-vrf-confederation-config grouping.";
        reference " 0.16.15.";
    }

    revision "2024-11-27" {
        description "Updated helpstring of AS:nn for the attribute 'site-origin-identifier'";
        reference " 0.16.14.";
    }

    revision "2024-10-29" {
        description "Updated neighbor password size limits";
        reference " 0.16.13.";
    }

    revision "2024-10-15" {
        description "Updated create and delete operation of table-map";
        reference " 0.16.12.";
    }

    revision "2024-10-10" {
        description "Added when tag for peer member deletion from DB when mapped peergroup remote-as is deleted";
        reference " 0.16.11.";
    }

    revision "2024-10-04" {
        description "Added when tag peer-allow-ebgp-vpn to activate";
        reference " 0.16.10.";
    }

    revision "2024-10-03" {
        description "Updated When tag constraints for attribute 'site-origin-identifier'";
        reference " 0.16.9.";
    }

    revision "2024-09-17" {
        description "Updated cli-command for create function";
        reference " 0.16.8.";
    }

    revision "2024-09-14" {
        description "Added Streaming Telemetry yaml file";
        reference " 0.16.7.";
    }

    revision "2024-09-11" {
        description "Fix BGP address-family CLI helpstrings";
        reference " 0.16.6.";
    }

    revision "2024-09-05" {
        description "For operation create Changed flag for cli-install-default-family for BGP_IPV4_MODE and BGP_IPV6_MODE to apply address-family-exit";
        reference " 0.16.5.";
    }

    revision "2024-08-30" {
        description "Changed display string for unset cli in site-origin-identifier";
        reference " 0.16.4.";
    }

    revision "2024-08-28" {
        description "Updated When tag constraints for object-list 'distribute-list-filter', 'as-list-filters', 'prefix-list-filter' and 'route-map-filter'";
        reference " 0.16.3.";
    }

    revision "2024-08-26" {
        description "Fix data-sync issue when address-family flowspec vrf removed'";
        reference " 0.16.2.";
    }

    revision "2024-08-14" {
        description "Added when tag for prefix-list under vrf in bgp";
        reference " 0.16.1.";
    }

    revision "2024-07-19" {
        description "Added whan tag wrt removal of address-family vpnv6 unicast";
        reference " 0.16.0.";
    }

    revision "2024-06-06" {
        description "Added dependency between g-shut-capable and g-shut-local-preference";
        reference " 0.15.7.";
    }

    revision "2024-04-25" {
        description "Added when tag for srv6-locator";
        reference " 0.15.6.";
    }

    revision "2024-03-29" {
        description "Modified flag 'skip-dependency-deletion'to'skip-dependency-validation' in activate attribute and added when tag mapped-peer-group-tag-af to peer-as attribute in bgp-vrf-address-family";
        reference " 0.15.5.";
    }

    revision "2024-03-21" {
        description "Updated When tag constraints for attribute 'password'";
        reference " 0.15.4.";
    }

    revision "2024-01-31" {
        description "Add utils function 'check_vrf_name_is_default' to vrf-name for validation";
        reference " 0.15.3.";
    }

    revision "2024-01-05" {
        description "Removed 'ebgp-max-path' cli for address-family l2vpn evpn";
        reference " 0.15.2.";
    }

    revision "2023-11-30" {
        description "Added support for configuring multi-path relax option for BGP peer under VRF addressfamily ipv4/v6";
        reference " 0.15.1.";
    }

    revision "2023-11-29" {
        description "Updated displaystring as 'fall-over bfd multihop'";
        reference " 0.15.0.";
    }

    revision "2023-11-02" {
        description "Updated cliFlag for attribute 'ibgp-max-path' and 'ebgp-max-path'";
        reference " 0.14.0.";
    }

    revision "2023-10-13" {
        description "Updated cliFlag for attribute 'peer-address'";
        reference " 0.13.13.";
    }

    revision "2023-10-04" {
        description "Updated cliFlag for attribute 'enable-dynamic-capability'";
        reference " 0.13.12.";
    }

    revision "2023-09-12" {
        description "Added enclosing container for all objectlists";
        reference " 0.13.11.";
    }

    revision "2023-09-07" {
        description "Adding new groupings bgp-address-family-vrf-peer-state,bgp-address-family-vrf-peer-counters-state";
        reference " 0.13.10.";
    }

    revision "2023-09-06" {
        description "Updated utils api for attribute 'peer-address'";
        reference " 0.13.9.";
    }

    revision "2023-09-05" {
        description "Updated When tag constraints for attribute 'peer-route-map-orig-name' and 'default-peer-route-map-name'";
        reference " 0.13.8.";
    }

    revision "2023-08-21" {
        description "Implicit delete tag removed for 'local-as/config' container";
        reference " 0.13.7.";
    }

    revision "2023-08-16" {
        description "New patch Added option 'no-prepend' and 'replace-as' for BGP neighbor local-as";
        reference " 0.13.6.";
    }

    revision "2023-08-15" {
        description "Revert patch Added option 'no-prepend' and 'replace-as' for BGP neighbor local-as";
        reference " 0.13.5.";
    }

    revision "2023-08-11" {
        description "Added option 'no-prepend' and 'replace-as' for BGP neighbor local-as";
        reference " 0.13.4.";
    }

    revision "2023-08-07" {
        description "Added support for BGP addpath for ebgp neighbors";
        reference " 0.13.3.";
    }

    revision "2023-07-20" {
        description "Added support for TCP Maximum Segment Size per BGP neighbor";
        reference " 0.13.2.";
    }

    revision "2023-05-06" {
        description "address-family ipv4 flowspec vrf support";
        reference " 0.13.1.";
    }

    revision "2023-04-11" {
        description "Removed attribute 'soft-reconfig-inbound'";
        reference " 0.13.0.";
    }

    revision "2023-03-30" {
        description "Added Proper if-feature tag for Additional-paths cli";
        reference " 0.12.8.";
    }

    revision "2023-03-21" {
        description "Updating helpstrings for allow-as-number input";
        reference " 0.12.7.";
    }

    revision "2023-03-10" {
        description "BGP password string length addition'";
        reference " 0.12.6.";
    }

    revision "2023-03-02" {
        description "BGP Flow Spec, split policy-map/class-map to enhanced-pbr, and VRF peer-group support for F";
        reference " 0.12.5.";
    }

    revision "2023-02-28" {
        description "Updating when expression for vrf-peer maximum-prefixes and route-map-filter objectlists";
        reference " 0.12.4.";
    }

    revision "2023-02-22" {
        description "Added support for BGP ADD Path in vrf address-family";
        reference " 0.12.3.";
    }

    revision "2023-02-21" {
        description "BGP Flow Specification support'";
        reference " 0.12.2.";
    }

    revision "2023-02-06" {
        description "Removing optional-attribute flag from allow-as-number cli-commands";
        reference " 0.12.1.";
    }

    revision "2023-02-02" {
        description "Updated missing Description";
        reference " 0.12.0.";
    }

    revision "2023-01-09" {
        description "Added new container for ebgp multihop";
        reference " 0.11.3.";
    }

    revision "2023-01-05" {
        description "Modified cli-command attr path";
        reference " 0.11.2.";
    }

    revision "2023-01-03" {
        description "Updated bgp debug options'";
        reference " 0.11.1.";
    }

    revision "2022-12-16" {
        description "Updated cli-command flag for attribute 'soft-reconfig-inbound'";
        reference " 0.11.0.";
    }

    revision "2022-12-14" {
        description "Changing heirarchy of 'bgp confederation' CLIs and changing from list to container.";
        reference " 0.10.10.";
    }

    revision "2022-12-01" {
        description "Updated When tag constraints for attribute 'activate'";
        reference " 0.10.9.";
    }

    revision "2022-11-08" {
        description "Updated When tag constraints for attribute 'fall-over bfd' and 'enable-peer-bfd-multihop'";
        reference " 0.10.8.";
    }

    revision "2022-10-20" {
        description "Updated When tag constraints and removed Default value from attribute 'ebgp-maximum-hop-count' and 'enable-ebgp-multihop'";
        reference " 0.10.7.";
    }

    revision "2022-09-27" {
        description "Removed Default value from attribute 'min-route-advertisement-interval' and 'peer-as-origin-interval'";
        reference " 0.10.6.";
    }

    revision "2022-07-26" {
        description "Removed impicit delele for object-list 'address-family-vrf'";
        reference " 0.10.5.";
    }

    revision "2022-07-06" {
        description "Skipped dependency validation for a composite constraint of peer-as and peer-group-tag for BGP peer";
        reference " 0.10.4.";
    }

    revision "2022-06-20" {
        description "Added new attribute 'de-activate' for BGP Peer-group feature.";
        reference " 0.10.3.";
    }

    revision "2022-06-01" {
        description "Updated the yang file with feature";
        reference " 0.10.2.";
    }

    revision "2022-04-28" {
        description "Updated BGP clear RPCs to remove unwanted attributes";
        reference " 0.10.1.";
    }

    revision "2022-04-19" {
        description "Added new attribute 'peer-shutdown-description' for support of BGP Administrative Shutdown Communication feature.";
        reference " 0.9.1.";
    }

    revision "2022-03-20" {
        description "Added new attribute for RFC-9072";
        reference " 0.10.0.";
    }

    revision "2022-01-17" {
        description "Modified data type";
        reference " 0.9.0.";
    }

    revision "2022-01-10" {
        description "Added depenedency constraint between 'vrf address-family and route-redistribution' and rd_string/IP-VRF";
        reference " 0.8.14.";
    }

    revision "2022-01-07" {
        description "Modified Data Type";
        reference " 0.9.0.";
    }

    revision "2021-11-15" {
        description "Moved BFD depenedecies under HAVE_BFD";
        reference " 0.8.0.";
    }

    revision "2021-08-26" {
        description "Added dependency constraint between auth-key-encrypt and password attrs for the peer authentication password CLI";
        reference " 0.7.0.";
    }

    revision "2021-07-05" {
        description "Remodelled BGP VRF address family peer authentication password object list";
        reference " 0.6.0.";
    }

    revision "2021-06-25" {
        description "Modified dependency for activate attribute";
        reference " 0.5.6.";
    }

    revision "2021-06-11" {
        description "Added dependency constraint between name and direction attrs for the distribute-list, prefix-list, filter-list and route-map CLI's";
        reference " 0.5.5.";
    }

    revision "2021-06-09" {
        description "Removal of default ipv4 unicast activate and fix for DB sync issues";
        reference " 0.5.4.";
    }

    revision "2021-06-07" {
        description "Deprecated 'connection-retry-interval', duplicate of 'peer-connection-interval'";
        reference " 0.5.3.";
    }

    revision "2021-05-31" {
        description "Added length for route map name";
        reference " 0.5.2.";
    }

    revision "2021-05-13" {
        description "Removed dependency validation on AF activate for allow-ebgp-vpn attribute";
        reference " 0.5.1.";
    }

    revision "2021-04-09" {
        description "Change related to Peer group remodelling";
        reference " 0.5.0.";
    }

    revision "2021-03-31" {
        description "Added support for configuring BFD for BGP peer under VRF address family";
        reference " 0.4.0.";
    }

    revision "2021-03-05" {
        description "Excluded yang generation for BGP Add path attributes";
        reference " 0.3.0.";
    }

    revision "2020-12-15" {
        description "Change to have data-types in lower case instead of camel case";
        reference " 0.2.0.";
    }

    revision "2020-09-10" {
        description "Initial Version";
        reference " 0.1.0.";
    }

    grouping bgp-vrf-aggregate-address-config {
        description
            "Configuration data for Aggregate Address List";
        leaf aggregate-address  {
            type  cml-data-types:cml_ip_prefix_t;
            description "Aggregates are used to minimize the size of routing tables.
                        Aggregation combines the characteristics of several different routes
                        and advertises a single route.The aggregateAddr attribute creates an
                        aggregate entry in the BGP routing table if any more-specific BGP
                        routes are available in the specified range.";
        } // END of aggregate-address definition.

        leaf aggregate-type  {
            type  ipi-bgp-types:bgp_aggregate_type_t;
            description "The aggregate-type attribute creates an aggregate entry advertising
                        the path for this route, consisting of all elements contained in all
                        paths being summarized. Use this parameter to reduce the size of path
                        information by listing the AS number only once, even if it was
                        included in multiple paths that were aggregated.";
        } // END of aggregate-type definition.

    } // END of bgp-vrf-aggregate-address-config definition.
    grouping bgp-vrf-distribute-list-filter-config {
        description
            "Grouping for BGP distribute list filter configuration";
        leaf access-list-identifier  {
            type  string {
                length "1..1965";
                pattern "[^?' =,>|]+";
            }
            mandatory true;
            description "Access List information";
        } // END of access-list-identifier definition.

        leaf filter-direction  {
            type  ipi-bgp-types:bgp_distribute_list_direction_t;
            description "This attribute sets the direction of the filter (0=FILTER_IN
                        |1=FILTER_OUT). This attribute is used to filter route updates from a
                        particular BGP neighbor for specified address-family. Only one
                        distribute-list per BGP neighbor.";
        } // END of filter-direction definition.

    } // END of bgp-vrf-distribute-list-filter-config definition.
    grouping bgp-vrf-srv6-config {
        description
            "config attribute for SRv6 for SR Policies";
        leaf bgpSRv6enable  {
            type  empty;
            mandatory true;
            description "This attribute enable Segment Routing V6";
        } // END of bgpSRv6enable definition.

    } // END of bgp-vrf-srv6-config definition.
    grouping prefer-sid-alloc-per-vrf-config {
        description
            "sid-alloc";
        leaf sid-alloc-type  {
            type  ipi-bgp-types:bgp_sid_alloc_type_t;
            description "sid-alloc";
        } // END of sid-alloc-type definition.

    } // END of prefer-sid-alloc-per-vrf-config definition.
    grouping bgp-vrf-as-list-filter-config {
        description
            "Grouping for BGP AS list filter configuration";
        leaf as-access-list-identifier  {
            type  string {
                length "1..1965";
                pattern "[^?' =,>|]+";
            }
            mandatory true;
            description "Access-list number. This attribute sets a BGP filter. This attribute
                        specifies an access list filter on updates based on the BGP autonomous
                        system paths. Each filter is an access list based on regular
                        expressions";
        } // END of as-access-list-identifier definition.

        leaf as-list-direction  {
            type  ipi-bgp-types:bgp_distribute_list_direction_t;
            description "Direction of the filter (0=FILTER_IN |1=FILTER_OUT)";
        } // END of as-list-direction definition.

    } // END of bgp-vrf-as-list-filter-config definition.
    grouping bgp-vrf-prefix-list-filter-config {
        description
            "Grouping for BGP prefix list filter configuration";
        leaf prefix-list-name  {
            type  string {
                length "1..1965";
                pattern "[^?' =,>|]+";
            }
            mandatory true;
            description "This attribute specify a prefix list for filtering BGP advertisements
                        for specified address-family. Filtering by prefix list matches the
                        prefixes of routes with those listed in the prefix list. If there is a
                        match, the route is used. An empty prefix list permits all prefixes.
                        If a given prefix does not match any entries of a prefix list, the
                        route is denied access. When multiple entries of a prefix list match a
                        prefix, the entry with the smallest sequence number is considered to
                        be a real match.The router begins the search at the top of the prefix
                        list, with the sequence number 1. Once a match or deny occurs, the
                        router does not need to go through the rest of the prefix list. For
                        efficiency the most common matches or denies are listed at the top.";
        } // END of prefix-list-name definition.

        leaf prefix-filter-direction  {
            type  ipi-bgp-types:bgp_distribute_list_direction_t;
            description "Direction of the filter (0=FILTER_IN |1=FILTER_OUT)";
        } // END of prefix-filter-direction definition.

    } // END of bgp-vrf-prefix-list-filter-config definition.
    grouping bgp-vrf-route-map-filter-config {
        description
            "Grouping for BGP route map filter configuration";
        leaf route-map-name  {
            type  string {
                length "1..63";
                pattern "[^?' =,>|]+";
            }
            mandatory true;
            description "Use this attribute to apply a route map to incoming or outgoing
                        routes. This attribute filters updates and modifies attributes. A
                        route map is applied to inbound or outbound updates. Only the routes
                        that pass the route map are sent or accepted in updates.";
        } // END of route-map-name definition.

        leaf route-map-direction  {
            type  ipi-bgp-types:bgp_distribute_list_direction_t;
            description "Use this attribute to configure the direction in which the route map
                        is to be applied. Direction of the filter (0=FILTER_IN |1=FILTER_OUT).";
        } // END of route-map-direction definition.

    } // END of bgp-vrf-route-map-filter-config definition.
    grouping bgp-address-family-vrf-maximum-prefixes-config {
        description
            "Configuration parameters for peer maximum prefixes";
        leaf prefix-count  {
            type  uint32 {
                 range "1..4294967295"  {
                    description "1..4294967295: Supported range 1 - 4294967295";
                 }
            }
            description "This attribute specifies number of prefixes that a BGP router is
                        allowed to receive from a neighbor. When the maximum-prefix-warning
                        attribute is not set and extra prefixes are received, the router ends
                        the peering.";
        } // END of prefix-count definition.

        leaf stop-update  {
            type  empty;
            description "Stop installing the routes when limit is exceeded.";
        } // END of stop-update definition.

        leaf maximum-prefix-warning  {
            type  empty;
            description "This attribute when enabled only give warning message when limit is
                        exceeded. When it is not set and extra prefixes are received, the
                        router ends the peering.";
        } // END of maximum-prefix-warning definition.

        leaf threshold-percentage  {
            type  uint8 {
                 range "1..100"  {
                    description "1..100: Supported range 1 - 100";
                 }
            }
            default "75";
            description "Threshold-value in percen. This attribute controls the number of
                        prefixes that can be received from a neighbor. This attribute allows
                        the configuration of a specified number of prefixes that a BGP router
                        is allowed to receive from a neighbor. When the maximum-prefix-warning
                        attribute is not set and extra prefixes are received, the router ends
                        the peering.";
        } // END of threshold-percentage definition.

        leaf warning-only  {
            type  empty;
            description "Throw warning if exceeds threshold-value";
        } // END of warning-only definition.

    } // END of bgp-address-family-vrf-maximum-prefixes-config definition.
    grouping bgp-address-family-peer-vrf-config {
        description
            "Configuration parameters common for peer VRFs";
        leaf bgp-port  {
            // when " ipi-bgp-address-family-vrf:address-family-vrfs/address-family-vrf/vrf-peers/vrf-peer/config/activate + ipi-bgp-address-family-vrf:address-family-vrfs/address-family-vrf/vrf-peers/vrf-peer/config/mapped-peer-group-tag-af ";
            type  uint16 {
                 range "0..65535"  {
                    description "0..65535: Supported range 0 - 65535";
                 }
            }
            default "179";
            description "The BGP port number of a neighbor";
        } // END of bgp-port definition.

        leaf activate  {
            type  empty;
            description "Activate/Deactivate neighbor. This attribute enables or disables the
                        exchange of AF information with a neighboring router.";
        } // END of activate definition.

        leaf de-activate  {
            // when " ipi-bgp-address-family-vrf:address-family-vrfs/address-family-vrf/vrf-peers/vrf-peer/config/mapped-peer-group-tag-af ";
            type  empty;
            description "Deactivate neighbor. This attribute disables the exchange of AF
                        information with a neighboring router.";
        } // END of de-activate definition.

        leaf default-peer-route-map-name  {
            // when " ipi-bgp-address-family-vrf:address-family-vrfs/address-family-vrf/vrf-peers/vrf-peer/config/activate ";
            type  empty;
            description "This attribute allows a BGP local router to send the default route
                        0.0.0.0 to a neighbor for use as a default route for specified
                        address-family.";
        } // END of default-peer-route-map-name definition.

        leaf peer-route-map-orig-name  {
            // when " ipi-bgp-address-family-vrf:address-family-vrfs/address-family-vrf/vrf-peers/vrf-peer/config/activate ";
            type  string {
                length "1..63";
                pattern "[^?' =,>|]+";
            }
            description "This attribute configures route map to be used for a BGP local router
                        to send the default route 0.0.0.0 to a neighbor for use as a default
                        route for specified address-family. This attribute can be used with
                        standard or extended access lists.";
        } // END of peer-route-map-orig-name definition.

        leaf weight  {
            // when " ipi-bgp-address-family-vrf:address-family-vrfs/address-family-vrf/vrf-peers/vrf-peer/config/activate + ipi-bgp-address-family-vrf:address-family-vrfs/address-family-vrf/vrf-peers/vrf-peer/config/mapped-peer-group-tag-af ";
            type  uint16 {
                 range "0..65535"  {
                    description "0..65535: Supported range 0 - 65535";
                 }
            }
            default "0";
            description "This attribute specifies a weight value, for specified address-family,
                        to all routes learned from a neighbor for specified address-family.
                        The route with the highest weight gets preference when the same prefix
                        is learned from more than one peer. Unlike the local-preference
                        attribute, the weight attribute is relevant only to the local router.
                        When the weight is set for a peer group, all members of the peer group
                        get the same weight. This attribute can also be used to assign a
                        different weight to an individual peer-group member. When an
                        individually-configured weight of a peer-group member is removed, its
                        weight is reset to its peer groups weight.";
        } // END of weight definition.

        leaf flowspec-validation-disable  {
            // when " ipi-bgp-address-family-vrf:address-family-vrfs/address-family-vrf/vrf-peers/vrf-peer/config/activate + !ipi-bgp-address-family-vrf:address-family-vrfs/address-family-vrf/vrf-peers/vrf-peer/config/mapped-peer-group-tag-af ";
            if-feature feature-list:HAVE_BGP_FLOWSPEC;
            type  empty;
            description "This attribute specifies if FLOWSPEC validation should be disabled for
                        a specific peer. By default, the flowspec validation is enabled,
                        unless this option is specified.";
        } // END of flowspec-validation-disable definition.

        leaf peer-route-reflector  {
            // when " ipi-bgp-address-family-vrf:address-family-vrfs/address-family-vrf/vrf-peers/vrf-peer/config/activate + !ipi-bgp-address-family-vrf:address-family-vrfs/address-family-vrf/vrf-peers/vrf-peer/config/mapped-peer-group-tag-af ";
            type  empty;
            description "This attribute configures the router as a BGP route reflector and
                        configure the specified neighbor as its client for specified
                        address-family.
                        Route reflectors are a solution for the explosion of iBGP peering
                        within an autonomous system. By route reflection the number of iBGP
                        peers within an AS is reduced. Use this attribute to configure the
                        local router as the route reflector and specify neighbors as its
                        client. An AS can have more than one route reflector. One route
                        reflector treats the other route reflector as another iBGP speaker.";
        } // END of peer-route-reflector definition.

        leaf peer-remove-private-as  {
            // when " ipi-bgp-address-family-vrf:address-family-vrfs/address-family-vrf/vrf-peers/vrf-peer/config/activate + !ipi-bgp-address-family-vrf:address-family-vrfs/address-family-vrf/vrf-peers/vrf-peer/config/mapped-peer-group-tag-af ";
            type  empty;
            description "This attribute removes the private Autonomous System (AS) number from
                        outbound updates. Private AS numbers are not advertised to the
                        Internet. This attribute is used with external BGP peers only. The
                        router removes the AS numbers only if the update includes private AS
                        numbers. If the update includes both private and public AS numbers,
                        the system treats it as an error.";
        } // END of peer-remove-private-as definition.

        leaf no-send-community  {
            // when " ipi-bgp-address-family-vrf:address-family-vrfs/address-family-vrf/vrf-peers/vrf-peer/config/activate + !ipi-bgp-address-family-vrf:address-family-vrfs/address-family-vrf/vrf-peers/vrf-peer/config/mapped-peer-group-tag-af ";
            type  empty;
            description "This attribute specifies if a community attribute should be sent to a
                        BGP neighbor for specified address-family. The community attribute
                        groups destinations in a certain community and applies routing
                        decisions according to those communities. By default, both standard
                        and extended community attributes are sent to a neighbor";
        } // END of no-send-community definition.

        leaf no-send-community-type  {
            // when " ipi-bgp-address-family-vrf:address-family-vrfs/address-family-vrf/vrf-peers/vrf-peer/config/activate + !ipi-bgp-address-family-vrf:address-family-vrfs/address-family-vrf/vrf-peers/vrf-peer/config/mapped-peer-group-tag-af ";
            type  ipi-bgp-types:bgp_send_commu_type_t;
            description "This attribute specifies the type of community attribute to be sent to
                        a BGP neighbor.";
        } // END of no-send-community-type definition.

        leaf neighbor-attribute-unchanged  {
            // when " ipi-bgp-address-family-vrf:address-family-vrfs/address-family-vrf/vrf-peers/vrf-peer/config/activate + !ipi-bgp-address-family-vrf:address-family-vrfs/address-family-vrf/vrf-peers/vrf-peer/config/mapped-peer-group-tag-af ";
            type  ipi-bgp-types:bgp_attribute_unchanged_type_t;
            description "This attribute advertises unchanged BGP AS path, next hop and med to
                        the specified neighbor.";
        } // END of neighbor-attribute-unchanged definition.

        leaf orf-prefix-capability  {
            // when " ipi-bgp-address-family-vrf:address-family-vrfs/address-family-vrf/vrf-peers/vrf-peer/config/activate + !ipi-bgp-address-family-vrf:address-family-vrfs/address-family-vrf/vrf-peers/vrf-peer/config/mapped-peer-group-tag-af ";
            type  ipi-bgp-types:bgp_orf_prefix_type_t;
            description "This attribute enables Outbound Router Filtering (ORF), and advertise
                        the ORF capability to its neighbors. The ORFs send and receive
                        capabilities to lessen the number of updates exchanged between
                        neighbors. By filtering updates, this option minimizes generating and
                        processing of updates. The two routers exchange updates to maintain
                        the ORF for each router.";
        } // END of orf-prefix-capability definition.

        leaf peer-allow-ebgp-vpn  {
            if-feature feature-list:HAVE_VRF;
            type  empty;
            description "This attribute allows an eBGP neighbor to be a VPN peer. By default,
                        BGP VPN functionality is allowed only for iBGP peers. Using the
                        peer-allow-ebgp-vpn attribute allows the VPN connection to be
                        established to an eBGP peer.";
        } // END of peer-allow-ebgp-vpn definition.

        leaf allow-as-number  {
            // when " ipi-bgp-address-family-vrf:address-family-vrfs/address-family-vrf/vrf-peers/vrf-peer/config/activate + ipi-bgp-address-family-vrf:address-family-vrfs/address-family-vrf/vrf-peers/vrf-peer/config/mapped-peer-group-tag-af ";
            type  uint32 {
                 range "1..10"  {
                    description "1..10: Supported range 1 - 10";
                 }
            }
            default "3";
            description "This attribute advertises prefixes (routes) even when the source of
                        the prefixes is from the same Autonomous System (AS) number for
                        specified address-family.
                        Use this attribute in a scenario where two routers at different
                        locations use the same Autonomous System number and are connected via
                        an ISP. Once prefixes arrive from one branch at the ISP, they are
                        tagged with the customers AS number. By default, when the ISP passes
                        the prefixes to the other router, the prefixes are dropped if the
                        other router uses the same AS number. Use this attribute to advertise
                        the prefixes at the other side. Control the number of times an AS
                        number is advertised by specifying a number.
                        In a hub and spoke configuration in a VPN, a PE (Provider Edge) router
                        advertises all prefixes containing duplicate AS numbers. Use this
                        attribute to configure two VRFs on each PE router to receive and
                        advertise prefixes. One of the VRFs receives prefixes with AS numbers
                        from all PE routers and then advertises them to neighboring PE
                        routers. The other VRF receives prefixes with AS numbers from the CE
                        (Customer Edge) router and advertises them to all PE routers in the
                        hub and spoke configuration.";
        } // END of allow-as-number definition.

        leaf capability-graceful-restart  {
            // when " ipi-bgp-address-family-vrf:address-family-vrfs/address-family-vrf/vrf-peers/vrf-peer/config/activate ";
            type  empty;
            description "This attribute configures the router to advertise the Graceful Restart
                        Capability to the neighbors. This configuration indicates that the BGP
                        speaker has the ability to preserve its forwarding state for the
                        address family when BGP restarts. Use this attribute to advertise to
                        the neighbor routers the capability of graceful restart.";
        } // END of capability-graceful-restart definition.

        leaf mapped-peer-group-tag-af  {
            // when " ipi-bgp-address-family-vrf:address-family-vrfs/address-family-vrf/peer-groups/peer-group/config/peer-as ";
            type  string {
                length "1..1965";
                pattern "[^?' =,>|]+";
            }
            description "BGP peer group name. Adds  a neighbor to an existing peer group.
                        Neighbors with the same update policies are grouped into peer groups.
                        This facilitates the updates of various policies, such as distribute
                        and filter lists. The peer group is then configured easily with any of
                        the neighbor attributes. Any changes made to the peer group affect all
                        members.";
        } // END of mapped-peer-group-tag-af definition.

        leaf unsuppress-route-map-name  {
            // when " ipi-bgp-address-family-vrf:address-family-vrfs/address-family-vrf/vrf-peers/vrf-peer/config/activate + !ipi-bgp-address-family-vrf:address-family-vrfs/address-family-vrf/vrf-peers/vrf-peer/config/mapped-peer-group-tag-af ";
            type  string {
                length "1..1965";
                pattern "[^?' =,>|]+";
            }
            description "unsuppress map name. This attribute is used to selectively leak
                        more-specific routes to a particular neighbor.";
        } // END of unsuppress-route-map-name definition.

        leaf enable-ext-opt-param-len  {
            // when " ipi-bgp-address-family-vrf:address-family-vrfs/address-family-vrf/vrf-peers/vrf-peer/config/peer-as + !ipi-bgp-address-family-vrf:address-family-vrfs/address-family-vrf/vrf-peers/vrf-peer/config/mapped-peer-group-tag-af ";
            type  empty;
            description "Use this attribute for a specific peer to encode extended optional
                        parameter length.";
        } // END of enable-ext-opt-param-len definition.

        leaf additional-paths-mode  {
            // when " ipi-bgp-address-family-vrf:address-family-vrfs/address-family-vrf/vrf-peers/vrf-peer/config/peer-as + !ipi-bgp-address-family-vrf:address-family-vrfs/address-family-vrf/vrf-peers/vrf-peer/config/mapped-peer-group-tag-af ";
            if-feature feature-list:HAVE_BGP_ADD_PATH;
            type  ipi-bgp-types:bgp_peer_additional_path_type_t;
            description "Adds additional paths in the BGP table";
        } // END of additional-paths-mode definition.

        leaf additional-path-select-all  {
            // when " ipi-bgp-address-family-vrf:address-family-vrfs/address-family-vrf/vrf-peers/vrf-peer/config/peer-as + !ipi-bgp-address-family-vrf:address-family-vrfs/address-family-vrf/vrf-peers/vrf-peer/config/mapped-peer-group-tag-af ";
            if-feature feature-list:HAVE_BGP_ADD_PATH;
            type  empty;
            description "Attribute to select advertise additional path";
        } // END of additional-path-select-all definition.

        leaf additional-paths-best-select-count  {
            // when " ipi-bgp-address-family-vrf:address-family-vrfs/address-family-vrf/vrf-peers/vrf-peer/config/peer-as + !ipi-bgp-address-family-vrf:address-family-vrfs/address-family-vrf/vrf-peers/vrf-peer/config/mapped-peer-group-tag-af ";
            if-feature feature-list:HAVE_BGP_ADD_PATH;
            type  uint8 {
                 range "2..3"  {
                    description "2..3: Supported range 2 - 3";
                 }
            }
            description "Attribute to select best advertise additional path";
        } // END of additional-paths-best-select-count definition.

        leaf tcp-adjust-mss  {
            type  uint16 {
                 range "40..1440"  {
                    description "40..1440: Supported range 40 - 1440";
                 }
            }
            description "Use this attribute to set the BGP TCP MSS value of a neighbor.";
        } // END of tcp-adjust-mss definition.

        leaf site-origin-identifier  {
            // when " ipi-bgp-address-family-vrf:address-family-vrfs/address-family-vrf/vrf-peers/vrf-peer/config/activate + ipi-bgp-address-family-vrf:address-family-vrfs/address-family-vrf/vrf-peers/vrf-peer/config/mapped-peer-group-tag-af ";
            if-feature feature-list:HAVE_VRF;
            type  string {
                length "1..1965";
                pattern "[^?' =,>|]+";
            }
            description "Use this attribute to enable the site-of-origin (SOO) feature. If the
                        customer AS is multi-homed to the ISP, this attribute ensures that the
                        PE does not advertise the routes back to the same AS.";
        } // END of site-origin-identifier definition.

    } // END of bgp-address-family-peer-vrf-config definition.
    grouping bgp-address-family-vrf-table-map-config {
        description
            "Table map configuration for  BGP Address Family";
        leaf map-name  {
            if-feature feature-list:HAVE_BGP_TABLE_MAP;
            type  string {
                length "1..63";
                pattern "[^?' =,>|]+";
            }
            mandatory true;
            description "Use this attribute to enable or disable suppression/modification of
                        incoming BGP updates to IP RIB/FIB table installation.
                        In a dedicated route reflector, all the routes it receives may not be
                        required to be stored or only few selected routes need to be stored,
                        because it may not lie in the data path.
                        Table maps are particularly useful to attain this restriction.
                        When map-name attribute is set, the route map referenced in the
                        map-name attribute shall be used to set certain properties (such as
                        the traffic index) of the routes for installation into the RIB. The
                        route is always downloaded, regardless of whether it is permitted or
                        denied by the route map.";
        } // END of map-name definition.

        leaf table-map-filter  {
            // when " ipi-bgp-address-family-vrf:address-family-vrfs/address-family-vrf/table-map/config/map-name ";
            if-feature feature-list:HAVE_BGP_TABLE_MAP;
            type  boolean;
            description "When tableMapFilter attribute is given in the table map attribute, the
                        route map referenced is used to control whether a BGP route is to be
                        downloaded to the IP RIB (hence the filter). A BGP route is not
                        downloaded to the RIB if it is denied by the route map.";
        } // END of table-map-filter definition.

    } // END of bgp-address-family-vrf-table-map-config definition.
    grouping bgp-address-family-vrf-peer-group {
        description
            "Grouping for peer-group list";
        container peer-groups {
            description
                "Top level container for peer-groups";

            list peer-group {
                key "peer-group-tag";
                description
                    "List of peer-group";
                leaf peer-group-tag  {
                    type  leafref {
                        path  "../config/peer-group-tag";
                    }
                    description "Creates a peer group. Neighbors with the same update policies are
                                grouped into peer groups. This facilitates the updates of various
                                policies, such as distribute and filter lists. The peer group is then
                                configured easily with any of the neighbor attributes. Any changes
                                made to the peer group affect all members.";
                } // END of peer-group-tag definition.

                container config {
                    description
                        "Configuration parameters relating to the VRF address family";
                    uses bgp-address-family-vrf-peer-group-config;
                    uses bgp-address-family-peer-group-vrf-config;
                } // END of config-container definition.
                container state {
                    config false;
                    description
                        "State parameters relating to the VRF address family";
                    uses bgp-address-family-vrf-peer-group-config;
                    uses bgp-address-family-peer-group-vrf-config;
                } // END of state-container definition.
                container optional-as-lists {
                    description
                        "Top level container for optional AS";

                    list optional-as-list {
                        key "optional-as";
                        description
                            "List of optional AS";
                        leaf optional-as  {
                            type  leafref {
                                path  "../config/optional-as";
                            }
                            description "Use this attribute to specify optional AS for BGP dynamic peer-group";
                        } // END of optional-as definition.

                        container config {
                            description
                                "Configuration of optional AS list";
                            uses bgp-optional-as-list-config;
                        } // END of config-container definition.
                        container state {
                            config false;
                            description
                                "State parameters of optional AS list";
                            uses bgp-optional-as-list-config;
                        } // END of state-container definition.
                    } // End of optional-as-list-list
                } // END of optional-as-lists-container definition.
                container bgp-passwords {
                    description
                        "Top level container for BGP password";

                    list bgp-password {
                    // when " ipi-bgp-address-family-vrf:address-family-vrfs/address-family-vrf/peer-groups/peer-group/bgp-passwords/bgp-password/config/auth-key-encrypt + ipi-bgp-address-family-vrf:address-family-vrfs/address-family-vrf/peer-groups/peer-group/config/peer-as ";
                        key "password";
                        max-elements 1;
                        description
                            "list for BGP password";
                        leaf password  {
                            type  leafref {
                                path  "../config/password";
                            }
                            description "Use this attribute to specify BGP encrypted password";
                        } // END of password definition.

                        container config {
                            description
                                "Configuration parameters relating to the BGP password";
                            uses bgp-password-config;
                        } // END of config-container definition.
                        container state {
                            config false;
                            description
                                "State parameters relating to the BGP password";
                            uses bgp-password-config;
                        } // END of state-container definition.
                    } // End of bgp-password-list
                } // END of bgp-passwords-container definition.
                container timers {
                    description
                        "container for bgp timers";
                    container config {
                        presence "To configure timers";
                        description
                            "configuration parameters relating to timers";
                        uses bgp-peer-timers-config;
                    } // END of config-container definition.
                    container state {
                        config false;
                        description
                            "state parameters relating to timers";
                        uses bgp-peer-timers-config;
                    } // END of state-container definition.
                } // END of timers-container definition.
                container local-as {
                    description
                        "Container for Local AS";

                    list local-as-list {
                    // when " ipi-bgp-address-family-vrf:address-family-vrfs/address-family-vrf/peer-groups/peer-group/config/peer-as ";
                        key "peer-local-as";
                        max-elements 1;
                        description
                            "Objectlist for Local AS";
                        leaf peer-local-as  {
                            type  leafref {
                                path  "../config/peer-local-as";
                            }
                            description "Specifies an AS (autonomous system) number to use with BGP neighbor.";
                        } // END of peer-local-as definition.

                        container config {
                            description
                                "Configuration parameters relating to Local AS";
                            uses bgp-peer-local-as-config;
                        } // END of config-container definition.
                        container state {
                            config false;
                            description
                                "state parameters relating to local-as";
                            uses bgp-peer-local-as-config;
                        } // END of state-container definition.
                    } // End of local-as-list-list
                } // END of local-as-container definition.
                container ebgp-multihop {
                    description
                        "container for EBGP multhop";
                    container config {
                        presence "To configure EBGP multihop";
                        description
                            "configuration parameters relating to EBGP multihop";
                        uses bgp-peer-ebgp-multhop-config;
                    } // END of config-container definition.
                    container state {
                        config false;
                        description
                            "state parameters relating to timers";
                        uses bgp-peer-ebgp-multhop-config;
                    } // END of state-container definition.
                } // END of ebgp-multihop-container definition.
                container maximum-prefixes {
                    description
                        "Top level container for Prefix related configuration";

                    list maximum-prefix {
                    // when " ipi-bgp-address-family-vrf:address-family-vrfs/address-family-vrf/peer-groups/peer-group/config/activate ";
                        key "prefix-count";
                        max-elements 1;
                        description
                            "List for Prefix related configuration";
                        leaf prefix-count  {
                            type  leafref {
                                path  "../config/prefix-count";
                            }
                            description "This attribute specifies number of prefixes that a BGP router is
                                        allowed to receive from a neighbor. When the maximum-prefix-warning
                                        attribute is not set and extra prefixes are received, the router ends
                                        the peering.";
                        } // END of prefix-count definition.

                        container config {
                            description
                                "Configuration parameters relating to the number of prefixes that can
                                        be received from a neighbor";
                            uses bgp-address-family-vrf-maximum-prefixes-config;
                        } // END of config-container definition.
                        container state {
                            config false;
                            description
                                "State parameters relating to the VRF address family";
                            uses bgp-address-family-vrf-maximum-prefixes-config;
                        } // END of state-container definition.
                    } // End of maximum-prefix-list
                } // END of maximum-prefixes-container definition.
                container distribute-list-filters {
                    description
                        "Container for distribute list filters";

                    list distribute-list-filter {
                    // when " ipi-bgp-address-family-vrf:address-family-vrfs/address-family-vrf/peer-groups/peer-group/distribute-list-filters/distribute-list-filter/config/access-list-identifier ";
                        key "filter-direction";
                        description
                            "List of Distribute list Filter";
                        leaf filter-direction  {
                            type  leafref {
                                path  "../config/filter-direction";
                            }
                            description "This attribute sets the direction of the filter (0=FILTER_IN
                                        |1=FILTER_OUT). This attribute is used to filter route updates from a
                                        particular BGP neighbor for specified address-family. Only one
                                        distribute-list per BGP neighbor.";
                        } // END of filter-direction definition.

                        container config {
                            description
                                "Configuration parameters relating to BGP Distribute list Filter";
                            uses bgp-vrf-distribute-list-filter-config;
                        } // END of config-container definition.
                        container state {
                            config false;
                            description
                                "State parameters relating to BGP Distribute list Filter";
                            uses bgp-vrf-distribute-list-filter-config;
                        } // END of state-container definition.
                    } // End of distribute-list-filter-list
                } // END of distribute-list-filters-container definition.
                container as-list-filters {
                    description
                        "Container for  AS list Filters";

                    list as-list-filter {
                    // when " ipi-bgp-address-family-vrf:address-family-vrfs/address-family-vrf/peer-groups/peer-group/as-list-filters/as-list-filter/config/as-access-list-identifier ";
                        key "as-list-direction";
                        description
                            "List of AS list Filter";
                        leaf as-list-direction  {
                            type  leafref {
                                path  "../config/as-list-direction";
                            }
                            description "Direction of the filter (0=FILTER_IN |1=FILTER_OUT)";
                        } // END of as-list-direction definition.

                        container config {
                            description
                                "Configuration parameters relating to BGP AS list Filter";
                            uses bgp-vrf-as-list-filter-config;
                        } // END of config-container definition.
                        container state {
                            config false;
                            description
                                "State parameters relating to BGP AS list Fileter";
                            uses bgp-vrf-as-list-filter-config;
                        } // END of state-container definition.
                    } // End of as-list-filter-list
                } // END of as-list-filters-container definition.
                container prefix-list-filters {
                    description
                        "Container for Prefix list Filters";

                    list prefix-list-filter {
                    // when " ipi-bgp-address-family-vrf:address-family-vrfs/address-family-vrf/peer-groups/peer-group/prefix-list-filters/prefix-list-filter/config/prefix-list-name ";
                        key "prefix-filter-direction";
                        description
                            "List of Prefix list Filter";
                        leaf prefix-filter-direction  {
                            type  leafref {
                                path  "../config/prefix-filter-direction";
                            }
                            description "Direction of the filter (0=FILTER_IN |1=FILTER_OUT)";
                        } // END of prefix-filter-direction definition.

                        container config {
                            description
                                "Configuration parameters relating to BGP Prefix list Filter";
                            uses bgp-vrf-prefix-list-filter-config;
                        } // END of config-container definition.
                        container state {
                            config false;
                            description
                                "State parameters relating to BGP Prefix list Filter";
                            uses bgp-vrf-prefix-list-filter-config;
                        } // END of state-container definition.
                    } // End of prefix-list-filter-list
                } // END of prefix-list-filters-container definition.
                container route-map-filters {
                    description
                        "Container for Route map Filters";

                    list route-map-filter {
                    // when " ipi-bgp-address-family-vrf:address-family-vrfs/address-family-vrf/peer-groups/peer-group/route-map-filters/route-map-filter/config/route-map-name ";
                        key "route-map-direction";
                        description
                            "List of Route map Filter";
                        leaf route-map-direction  {
                            type  leafref {
                                path  "../config/route-map-direction";
                            }
                            description "Use this attribute to configure the direction in which the route map.";
                        } // END of route-map-direction definition.

                        container config {
                            description
                                "Configuration parameters relating to BGP Route map Filter";
                            uses bgp-vrf-route-map-filter-config;
                        } // END of config-container definition.
                        container state {
                            config false;
                            description
                                "State parameters relating to BGP Route map Filter";
                            uses bgp-vrf-route-map-filter-config;
                        } // END of state-container definition.
                    } // End of route-map-filter-list
                } // END of route-map-filters-container definition.
            } // End of peer-group-list
        } // END of peer-groups-container definition.
    } // END of bgp-address-family-vrf-peer-group definition.
    grouping bgp-address-family-vrf-peer-state {
        description
            "State parameters common for BGP address family VRF peers";
        leaf connection-established-count  {
            type  int32;
            description "BGP state established count";
        } // END of connection-established-count definition.

        leaf error-notify-sent  {
            type  boolean;
            description "Last reset due to notification type 0(sent), 1(received)";
        } // END of error-notify-sent definition.

        leaf notify-code-string  {
            type  cml-data-types:cml_line_t {
                length "1..1965";
            }
            description "Notification Error Message code and subcode";
        } // END of notify-code-string definition.

        leaf bgp-peer-state  {
            type  ipi-bgp-types:bgp_peer_status_t;
            description "The bgp state of the session with following representation 1(Idle),
                        2(Connect), 3(Active), 4(Opensent), 5(Openconfirm), 6(Established)";
        } // END of bgp-peer-state definition.

    } // END of bgp-address-family-vrf-peer-state definition.
    grouping bgp-address-family-vrf-peer-counters-state {
        description
            "State counter parameters common for BGP address family VRF peers";
        leaf notification-in  {
            type  int32;
            config false;
            description "Notify input count";
        } // END of notification-in definition.

        leaf notification-out  {
            type  int32;
            config false;
            description "Notify output count";
        } // END of notification-out definition.

        leaf update-message-in  {
            type  int32;
            default "0";
            config false;
            description "Update message input count";
        } // END of update-message-in definition.

        leaf update-message-out  {
            type  int32;
            default "0";
            config false;
            description "Update message ouput count";
        } // END of update-message-out definition.

    } // END of bgp-address-family-vrf-peer-counters-state definition.
    grouping bgp-address-family-vrf-peer-config {
        description
            "Configuration parameters common for BGP address family VRF peers";
        leaf peer-address  {
            type  inet:ip-address;
            description "The peer address or Tag of a neighbor. This attribute adds a neighbor.
                        The specified neighbor when activated using the activate attribute
                        exchanges routing information.";
        } // END of peer-address definition.

        leaf peer-as  {
            type  uint32 {
                 range "1..4294967295"  {
                    description "1..4294967295: Supported range 1 - 4294967295";
                 }
            }
            description "This attribute specifies a neighbors autonomous system number. If the
                        specified ASN matches the ASN number specified in the router bgp
                        global configuration, the neighbor is identified as internal. If the
                        ASN does not match, it is identified as external to the local AS.";
        } // END of peer-as definition.

        leaf source-identifier  {
            // when " ipi-bgp-address-family-vrf:address-family-vrfs/address-family-vrf/vrf-peers/vrf-peer/config/peer-as + ipi-bgp-address-family-vrf:address-family-vrfs/address-family-vrf/vrf-peers/vrf-peer/config/mapped-peer-group-tag-af ";
            type  string {
                length "1..1965";
                pattern "[^?' =,>|]+";
            }
            default "NULL";
            description "This attribute allows internal BGP sessions to use any operational
                        interface for TCP connections. Use this attribute in conjunction with
                        any specified interface on the router. The loopback interface is the
                        interface that is most commonly used with this attribute. The use of
                        loopback interface eliminates a dependency and BGP does not have to
                        rely on the availability of a particular interface for making TCP
                        connections.";
        } // END of source-identifier definition.

        leaf bgp-version  {
            type  uint8;
            default "4";
            description "BGP Version. This attribute configures router to accept only a
                        particular BGP version. By default, the system uses BGP version 4 and
                        on request dynamically negotiates down to version 2. Using this
                        attribute disables the routers version-negotiation capability and
                        forces the router to use only a specified version with the neighbor.";
        } // END of bgp-version definition.

        leaf peer-connection-interval  {
            // when " ipi-bgp-address-family-vrf:address-family-vrfs/address-family-vrf/vrf-peers/vrf-peer/config/peer-as + !ipi-bgp-address-family-vrf:address-family-vrfs/address-family-vrf/vrf-peers/vrf-peer/config/mapped-peer-group-tag-af ";
            type  uint32 {
                 range "1..65535"  {
                    description "1..65535: Supported range 1 - 65535";
                 }
            }
            default "1";
            description "Connect timer value. This attribute sets the timers for a specific BGP
                        neighbor. Keepalive messages are sent by a router to inform another
                        router that the BGP connection between the two is still active. The
                        keepalive interval is the period of time between each keepalive
                        message sent by the router. The holdtime interval is the time the
                        router waits to receive a keepalive message and if it does not receive
                        a message for this period it declares the neighbor dead.";
        } // END of peer-connection-interval definition.

        leaf enforce-multihop  {
            // when " ipi-bgp-address-family-vrf:address-family-vrfs/address-family-vrf/vrf-peers/vrf-peer/config/peer-as + ipi-bgp-address-family-vrf:address-family-vrfs/address-family-vrf/vrf-peers/vrf-peer/config/mapped-peer-group-tag-af ";
            type  empty;
            description "This attribute turns on the enforcement of eBGP neighbors perform
                        multihop.";
        } // END of enforce-multihop definition.

        leaf peer-shutdown  {
            // when " ipi-bgp-address-family-vrf:address-family-vrfs/address-family-vrf/vrf-peers/vrf-peer/config/peer-as + ipi-bgp-address-family-vrf:address-family-vrfs/address-family-vrf/vrf-peers/vrf-peer/config/mapped-peer-group-tag-af ";
            type  empty;
            description "This attribute disables a neighbor administratively.
                        Use this attribute to terminate any active session for a specified
                        neighbor and clear all related routing information. In case a peer
                        group is specified for shutdown, a large number of peering sessions
                        could be terminated.";
        } // END of peer-shutdown definition.

        leaf peer-shutdown-description  {
            // when " ipi-bgp-address-family-vrf:address-family-vrfs/address-family-vrf/vrf-peers/vrf-peer/config/peer-as + ipi-bgp-address-family-vrf:address-family-vrfs/address-family-vrf/vrf-peers/vrf-peer/config/mapped-peer-group-tag-af + ipi-bgp-address-family-vrf:address-family-vrfs/address-family-vrf/vrf-peers/vrf-peer/config/peer-shutdown ";
            type  cml-data-types:cml_line_t {
                length "1..255";
            }
            description "Use this attribute to send shutdown communication message to inform
                        peer the reason for the shutdown of the BGP session.";
        } // END of peer-shutdown-description definition.

        leaf neighbor-passive  {
            // when " ipi-bgp-address-family-vrf:address-family-vrfs/address-family-vrf/vrf-peers/vrf-peer/config/peer-as + ipi-bgp-address-family-vrf:address-family-vrfs/address-family-vrf/vrf-peers/vrf-peer/config/mapped-peer-group-tag-af ";
            type  empty;
            description "Use this attribute to set a BGP neighbor as passive.";
        } // END of neighbor-passive definition.

        leaf enable-dynamic-capability  {
            // when " ipi-bgp-address-family-vrf:address-family-vrfs/address-family-vrf/vrf-peers/vrf-peer/config/peer-as + ipi-bgp-address-family-vrf:address-family-vrfs/address-family-vrf/vrf-peers/vrf-peer/config/mapped-peer-group-tag-af ";
            type  empty;
            description "Use this attribute to enable the dynamic capability for a specific
                        peer. This attribute allows a BGP speaker to advertise or withdraw an
                        address family capability to a peer in a non-disruptive manner.";
        } // END of enable-dynamic-capability definition.

        leaf min-route-advertisement-interval  {
            // when " ipi-bgp-address-family-vrf:address-family-vrfs/address-family-vrf/vrf-peers/vrf-peer/config/peer-as + !ipi-bgp-address-family-vrf:address-family-vrfs/address-family-vrf/vrf-peers/vrf-peer/config/mapped-peer-group-tag-af ";
            type  uint32 {
                 range "0..65535"  {
                    description "0..65535: Supported range 0 - 65535";
                 }
            }
            description "Minimum route advertisement interval. Sets minimum interval between
                        the sending of BGP routing updates. To reduce the flapping of routes
                        to internet, a minimum advertisement interval is set, so that the BGP
                        routing updates are sent only per interval seconds. BGP dampening can
                        also be used to control the effects of flapping routes.";
        } // END of min-route-advertisement-interval definition.

        leaf peer-as-origin-interval  {
            // when " ipi-bgp-address-family-vrf:address-family-vrfs/address-family-vrf/vrf-peers/vrf-peer/config/peer-as + !ipi-bgp-address-family-vrf:address-family-vrfs/address-family-vrf/vrf-peers/vrf-peer/config/mapped-peer-group-tag-af ";
            type  uint32 {
                 range "1..65535"  {
                    description "1..65535: Supported range 1 - 65535";
                 }
            }
            description "Time interval. This attribute adjust the interval of sending AS
                        origination routing updates. This attribute is used to change the
                        minimum interval between the sending of AS-origination routing
                        updates.";
        } // END of peer-as-origin-interval definition.

        leaf neighbor-as-override  {
            // when " ipi-bgp-address-family-vrf:address-family-vrfs/address-family-vrf/vrf-peers/vrf-peer/config/peer-as + !ipi-bgp-address-family-vrf:address-family-vrfs/address-family-vrf/vrf-peers/vrf-peer/config/mapped-peer-group-tag-af ";
            type  empty;
            description "Use this attribute to configure a PE router to override the Autonomous
                        System Number (ASN) of a site with the ASN of a provider. BGP normally
                        ignores the routes from the same AS. However, this attribute is used
                        to override the customers ASN in BGP, so that the customer CE accepts
                        and installs routes from the same AS.
                        Typically, this attribute is used when Customer Edge (CE) routers have
                        the same ASN in some or all sites. As per BGP requirement, a BGP
                        speaker rejects a route that has the same ASN as itself, in the
                        AS_PATH attribute. Thus the CE routers having the same ASN do not
                        accept routes from each other. Set neighborAsOverrideAf attribute on
                        the PE router removes the CE neighbors ASN from the AS_PATH attribute
                        allowing CE routers with the same ASN to accept routes from each
                        other.";
        } // END of neighbor-as-override definition.

        leaf peer-interface-name  {
            // when " ipi-bgp-address-family-vrf:address-family-vrfs/address-family-vrf/vrf-peers/vrf-peer/config/peer-as + ipi-bgp-address-family-vrf:address-family-vrfs/address-family-vrf/vrf-peers/vrf-peer/config/mapped-peer-group-tag-af ";
            if-feature feature-list:HAVE_VRF;
            type  string {
                length "1..1965";
                pattern "[^?' =,>|]+";
            }
            description "Interface name. Configures IP address or IPv6 address on interface";
        } // END of peer-interface-name definition.

        leaf peer-description  {
            // when " ipi-bgp-address-family-vrf:address-family-vrfs/address-family-vrf/vrf-peers/vrf-peer/config/peer-as + ipi-bgp-address-family-vrf:address-family-vrfs/address-family-vrf/vrf-peers/vrf-peer/config/mapped-peer-group-tag-af ";
            type  cml-data-types:cml_line_t {
                length "1..1965";
            }
            description "Use this attribute to associate a description with a neighbor. This
                        attribute helps in identifying a neighbor quickly. It is useful for an
                        ISP that has multiple neighbor relationships.";
        } // END of peer-description definition.

        leaf peer-restart-time  {
            // when " ipi-bgp-address-family-vrf:address-family-vrfs/address-family-vrf/vrf-peers/vrf-peer/config/peer-as + ipi-bgp-address-family-vrf:address-family-vrfs/address-family-vrf/vrf-peers/vrf-peer/config/mapped-peer-group-tag-af ";
            if-feature feature-list:HAVE_RESTART;
            if-feature feature-list:HAVE_VRF;
            type  uint32 {
                 range "1..3600"  {
                    description "1..3600: Supported range 1 - 3600";
                 }
            }
            description "This attribute sets a different restart-time other than the global
                        restart-time. This attribute takes precedence over the restart-time
                        value specified using the graceful-restart-set attribute. The
                        restart-time value is the maximum time that a graceful-restart
                        neighbor waits to come back up after a restart. The default value is
                        120 seconds.";
        } // END of peer-restart-time definition.

        leaf graceful-shut  {
            // when " ipi-bgp-address-family-vrf:address-family-vrfs/address-family-vrf/vrf-peers/vrf-peer/config/peer-as + !ipi-bgp-address-family-vrf:address-family-vrfs/address-family-vrf/vrf-peers/vrf-peer/config/mapped-peer-group-tag-af ";
            type  empty;
            description "Use this attribute to start a graceful shutdown for the BGP session of
                        the specified BGP neighbor. The BGP session for this neighbor is shut
                        down after the graceful shutdown timer expires.
                        If there is no alternate path available for traffic to flow prior the
                        actual shutdown of the BGP session, this path is made available for 60
                        seconds or for configured time after which the path is no longer
                        available and traffic is dropped.";
        } // END of graceful-shut definition.

        leaf graceful-shut-timer  {
            // when " ipi-bgp-address-family-vrf:address-family-vrfs/address-family-vrf/vrf-peers/vrf-peer/config/peer-as + ipi-bgp-address-family-vrf:address-family-vrfs/address-family-vrf/vrf-peers/vrf-peer/config/mapped-peer-group-tag-af ";
            type  uint32 {
                 range "10..65535"  {
                    description "10..65535: Supported range 10 - 65535";
                 }
            }
            description "Use this attribute to configure the value of the graceful shutdown
                        timer. After the timer expires, the BGP session initiated for graceful
                        shutdown is shut down.";
        } // END of graceful-shut-timer definition.

        leaf enable-peer-bfd  {
            // when " ipi-bgp-address-family-vrf:address-family-vrfs/address-family-vrf/vrf-peers/vrf-peer/config/peer-as + !ipi-bgp-address-family-vrf:address-family-vrfs/address-family-vrf/vrf-peers/vrf-peer/config/mapped-peer-group-tag-af + !ipi-bgp-address-family-vrf:address-family-vrfs/address-family-vrf/vrf-peers/vrf-peer/config/enable-peer-bfd-multihop ";
            if-feature feature-list:HAVE_BFD;
            type  empty;
            description "Enable bidirectional forwarding detection (BFD) for the BGP peer";
        } // END of enable-peer-bfd definition.

        leaf enable-peer-bfd-multihop  {
            // when " !ipi-bgp-address-family-vrf:address-family-vrfs/address-family-vrf/vrf-peers/vrf-peer/config/enable-peer-bfd ";
            if-feature feature-list:HAVE_BFD;
            type  empty;
            description "Enable bidirectional forwarding detection (BFD) for the BGP peer with
                        multihop";
        } // END of enable-peer-bfd-multihop definition.

    } // END of bgp-address-family-vrf-peer-config definition.
    grouping bgp-address-family-vrf-config {
        description
            "Configuration parameters common for BGP peer address family vrf";
        leaf afi  {
            type  ipi-bgp-types:bgp_vrf_afi_type_t;
            description "BGP address family identifier";
        } // END of afi definition.

        leaf safi  {
            type  ipi-bgp-types:bgp_vrf_safi_type_t;
            description "BGP sub address family identifier";
        } // END of safi definition.

        leaf vrf-name  {
            type  leafref {
                path  "/ipi-network-instance:network-instances/ipi-network-instance:network-instance/ipi-vrf:vrf/ipi-vrf:config/ipi-vrf:vrf-name";
            }
            description "vrf name";
        } // END of vrf-name definition.

        leaf multipath-relax  {
            type  empty;
            description "This attribute to specifies a BGP as-path relax configuration.";
        } // END of multipath-relax definition.

        leaf graceful-shutdown  {
            type  empty;
            description "Gracefully shut down all sessions of the AFI/SAFI beloging to the vrf
                        under this router. The BGP graceful shutdown feature reduces packet
                        loss during maintenance activity.";
        } // END of graceful-shutdown definition.

        leaf graceful-shutdown-capable  {
            type  empty;
            description "This attribute to enable the graceful shutdown capability";
        } // END of graceful-shutdown-capable definition.

        leaf graceful-shutdown-local-preference  {
            // when " ipi-bgp-address-family-vrf:address-family-vrfs/address-family-vrf/config/graceful-shutdown-capable ";
            type  uint32 {
                 range "0..4294967295"  {
                    description "0..4294967295: Supported range 0 - 4294967295";
                 }
            }
            default "0";
            description "This attribute sets the local preference of the router to use during
                        graceful shutdown. The local preference value indicates the preferred
                        path when there are multiple paths to the same destination in a single
                        routing database. The path with a higher preference value is the
                        preferred one. The preferred path is sent to all routers and access
                        servers in the local autonomous system.";
        } // END of graceful-shutdown-local-preference definition.

        leaf additional-paths-mode  {
            if-feature feature-list:HAVE_BGP_ADD_PATH;
            type  ipi-bgp-types:bgp_additional_path_type_t;
            description ">Use this attribute to add additional paths in the BGP table";
        } // END of additional-paths-mode definition.

        leaf additional-path-select-all  {
            if-feature feature-list:HAVE_BGP_ADD_PATH;
            type  empty;
            description "Use this attribute to select criteria to pick the paths";
        } // END of additional-path-select-all definition.

        leaf additional-paths-best-select-count  {
            if-feature feature-list:HAVE_BGP_ADD_PATH;
            type  uint8 {
                 range "2..3"  {
                    description "2..3: Supported range 2 - 3";
                 }
            }
            description "Use this attribute to select best N paths";
        } // END of additional-paths-best-select-count definition.

        leaf enable-pic  {
            if-feature feature-list:HAVE_BGP_PIC_CORE_EDGE;
            type  empty;
            description "Use this attribute to enable the additional paths in the BGP
                        table,install the indirect nexthop in RIB";
        } // END of enable-pic definition.

    } // END of bgp-address-family-vrf-config definition.
    grouping bgp-af-vrf-network-list {
        description
            "Grouping for BGP network list";
        container network-lists {
            description
                "Top levle container for networks announced by BGP";

            list network-list {
                key "local-network-prefix";
                description
                    "List of networks announced by BGP";
                leaf local-network-prefix  {
                    type  leafref {
                        path  "../config/local-network-prefix";
                    }
                    description "Use this attribute to specify the network to be announced via BGP";
                } // END of local-network-prefix definition.

                container config {
                    description
                        "configuration parameters for address-family network list";
                    uses bgp-address-family-network-list-config;
                } // END of config-container definition.
                container state {
                    config false;
                    description
                        "state parameters for address-family network list";
                    uses bgp-address-family-network-list-config;
                    uses bgp-network-list-state;
                } // END of state-container definition.
            } // End of network-list-list
        } // END of network-lists-container definition.
    } // END of bgp-af-vrf-network-list definition.
    grouping as-origin-validation-vrf-config-param {
        description
            "Grouping for BGP AS Origin Validation User Configurable Parameters";
        container as-origin {
            if-feature feature-list:HAVE_BGP_RPKI_ORIGIN_VALIDATION;
            description
                "BGP AS Origin Validation User Configurable Parameters";
            container config {
                description
                    "BGP AS Origin Validation User Configurable Parameters";
                uses as-origin-validation-config;
            } // END of config-container definition.
            container state {
                config false;
                description
                    "Operational state data related to BGP Route Flap Dampening";
                uses as-origin-validation-config;
            } // END of state-container definition.
        } // END of as-origin-container definition.
    } // END of as-origin-validation-vrf-config-param definition.

    grouping  address-family-vrfs-grouping {
    description
        "Top level container for VRF address family";
    container address-family-vrfs {
        if-feature feature-list:HAVE_BGPD;
        description
            "Top level container for VRF address family";

        list address-family-vrf {
            key "afi safi vrf-name";
            description
                "List of VRF address family";
            leaf afi  {
                type  leafref {
                    path  "../config/afi";
                }
                description "BGP address family identifier";
            } // END of afi definition.

            leaf safi  {
                type  leafref {
                    path  "../config/safi";
                }
                description "BGP sub address family identifier";
            } // END of safi definition.

            leaf vrf-name  {
                type  leafref {
                    path  "../config/vrf-name";
                }
                description "vrf name";
            } // END of vrf-name definition.

            container config {
                description
                    "Configuration parameters relating to the VRF address family";
                uses bgp-address-family-vrf-config;
                uses address-family-common-config;
            } // END of config-container definition.
            container state {
                config false;
                description
                    "State parameters relating to the VRF address family";
                uses bgp-address-family-vrf-config;
                uses address-family-common-config;
            } // END of state-container definition.
            container distances {
                description
                    "Top level Container for Attributes related to Distance for routes";

                list distance {
                    key "ebgp ibgp local";
                    max-elements 1;
                    description
                        "List of Attributes related to Distance for routes";
                    leaf ebgp  {
                        type  leafref {
                            path  "../config/ebgp";
                        }
                        description "Distance for routes external to the AS <1-255>";
                    } // END of ebgp definition.

                    leaf ibgp  {
                        type  leafref {
                            path  "../config/ibgp";
                        }
                        description "Distance for routes internal to the AS <1-255>";
                    } // END of ibgp definition.

                    leaf local  {
                        type  leafref {
                            path  "../config/local";
                        }
                        description "Use this attribute to specify distance value for local routes";
                    } // END of local definition.

                    container config {
                        description
                            "Configuration attributes related to Distance for routes";
                        uses bgp-af-distance-config;
                    } // END of config-container definition.
                    container state {
                        config false;
                        description
                            "Operational state data related to Distance for routes";
                        uses bgp-af-distance-config;
                    } // END of state-container definition.
                } // End of distance-list
            } // END of distances-container definition.
            container aggregate-address-lists {
                description
                    "This container defines Aggregate address lists";

                list aggregate-address-list {
                    key "aggregate-address";
                    description
                        "Aggregate address list";
                    leaf aggregate-address  {
                        type  leafref {
                            path  "../config/aggregate-address";
                        }
                        description "Aggregates are used to minimize the size of routing tables.
                                    Aggregation combines the characteristics of several different routes
                                    and advertises a single route.The aggregate-address attribute creates
                                    an aggregate entry in the BGP routing table if any more-specific BGP
                                    routes are available in the specified range.";
                    } // END of aggregate-address definition.

                    container config {
                        description
                            "Configuration data for Aggregate Address List";
                        uses bgp-vrf-aggregate-address-config;
                    } // END of config-container definition.
                    container state {
                        config false;
                        description
                            "Operational state data for bgp aggregate address list";
                        uses bgp-vrf-aggregate-address-config;
                    } // END of state-container definition.
                } // End of aggregate-address-list-list
            } // END of aggregate-address-lists-container definition.
            container maximum-paths {
                description
                    "Container for attributes related to multipath ECMP numbers";
                container config {
                    description
                        "Configuration attributes related to multipath ECMP numbers";
                    uses bgp-af-maximum-paths-config;
                } // END of config-container definition.
                container state {
                    config false;
                    description
                        "Operational state data related to multipath ECMP numbers";
                    uses bgp-af-maximum-paths-config;
                } // END of state-container definition.
            } // END of maximum-paths-container definition.
            container table-map {
                if-feature feature-list:HAVE_BGP_TABLE_MAP;
                description
                    "Container for Attributes related to Table map";
                container config {
                    presence "To configure table map";
                    description
                        "Configuration attributes related to Table map";
                    uses bgp-address-family-vrf-table-map-config;
                } // END of config-container definition.
                container state {
                    config false;
                    description
                        "Operational state data related to Distance for routes";
                    uses bgp-address-family-vrf-table-map-config;
                } // END of state-container definition.
            } // END of table-map-container definition.
            container route-flap-dampenings {
                description
                    "Top level Container for BGP Route Flap Dampening User Configurable
                            Parameters";

                list route-flap-dampening {
                    key "enable-dampening";
                    max-elements 1;
                    description
                        "List of BGP Route Flap Dampening User Configurable Parameters";
                    leaf enable-dampening  {
                        type  leafref {
                            path  "../config/enable-dampening";
                        }
                        description "Use this attribute to enable route flap dampening";
                    } // END of enable-dampening definition.

                    container config {
                        description
                            "BGP Route Flap Dampening User Configurable Parameters";
                        uses route-flap-dampening-param-config;
                    } // END of config-container definition.
                    container state {
                        config false;
                        description
                            "Operational state data related to BGP Route Flap Dampening";
                        uses route-flap-dampening-param-config;
                    } // END of state-container definition.
                } // End of route-flap-dampening-list
            } // END of route-flap-dampenings-container definition.
            container route-redistribute-lists {
                description
                    "Top level container of redistribute for address-family";

                list route-redistribute-list {
                    key "protocol-type";
                    description
                        "List of redistribute for address-family";
                    leaf protocol-type  {
                        type  leafref {
                            path  "../config/protocol-type";
                        }
                        description "Use this attribute to inject routes from one routing process into
                                    another. Redistribution is used by routing protocols to advertise
                                    routes that are learned by some other means, such as by another
                                    routing protocol or by static routes. Since all internal routes are
                                    dumped into BGP, careful filtering is applied to make sure that only
                                    routes to be advertised reach the internet, not everything. This
                                    attribute allows redistribution by injecting prefixes from one routing
                                    protocol into another routing protocol.";
                    } // END of protocol-type definition.

                    container config {
                        description
                            "Configuration data for redistribute for address-family";
                        uses address-family-redist-list-config;
                    } // END of config-container definition.
                    container state {
                        config false;
                        description
                            "Operational state data for redistribute for address-family";
                        uses address-family-redist-list-config;
                    } // END of state-container definition.
                } // End of route-redistribute-list-list
            } // END of route-redistribute-lists-container definition.
            container bgp-srv6 {
                if-feature feature-list:HAVE_SRV6;
                description
                    "SRv6 container for BGP segment routing";
                container config {
                    presence "yes";
                    description
                        "Segment routing SRv6 configuration and other CLIs inside srv6";
                    uses bgp-vrf-srv6-config;
                } // END of config-container definition.
                container state {
                    config false;
                    description
                        "Segment routing V6 runtime parameters";
                    uses bgp-vrf-srv6-config;
                } // END of state-container definition.
                container sid-alloc-mode {
                    // when " ipi-bgp-address-family-vrf:address-family-vrfs/address-family-vrf/bgp-srv6/config/bgpSRv6enable ";
                    description
                        "To configure sid-alloc-mode";
                    container config {
                        description
                            "config attribute for sid-alloc mode";
                        uses prefer-sid-alloc-per-vrf-config;
                    } // END of config-container definition.
                    container state {
                        config false;
                        description
                            "State attribute for sid-alloc";
                        uses prefer-sid-alloc-per-vrf-config;
                    } // END of state-container definition.
                } // END of sid-alloc-mode-container definition.
            } // END of bgp-srv6-container definition.
            container bgp-redistribute-ospfs {
                description
                    "Top level container for redistribute with ospf proc Id for address
                            family";

                list bgp-redistribute-ospf {
                    key "ospf-instance-number";
                    description
                        "List of redistribute with ospf proc Id for address family";
                    leaf ospf-instance-number  {
                        type  leafref {
                            path  "../config/ospf-instance-number";
                        }
                        description "Use this attribute to inject routes from one routing process into
                                    another. Redistribution is used by routing protocols to advertise
                                    routes that are learned by some other means, such as by another
                                    routing protocol or by static routes. Since all internal routes are
                                    dumped into BGP, careful filtering is applied to make sure that only
                                    routes to be advertised reach the internet, not everything. This
                                    attribute allows redistribution by injecting prefixes from one routing
                                    protocol into another routing protocol.";
                    } // END of ospf-instance-number definition.

                    container config {
                        description
                            "Configuration data for redistribute with ospf proc Id for address
                                    family";
                        uses bgp-redistribute-ospf-config;
                    } // END of config-container definition.
                    container state {
                        config false;
                        description
                            "Operational state data related to redistribute with ospf proc Id for
                                    address family";
                        uses bgp-redistribute-ospf-config;
                    } // END of state-container definition.
                } // End of bgp-redistribute-ospf-list
            } // END of bgp-redistribute-ospfs-container definition.
            container vrf-peers {
                description
                    "Top level container for VRF peers";

                list vrf-peer {
                    key "peer-address";
                    description
                        "List of VRF peer";
                    leaf peer-address  {
                        type  leafref {
                            path  "../config/peer-address";
                        }
                        description "The peer address or Tag of a neighbor. This attribute adds a neighbor.
                                    The specified neighbor when activated using the activate attribute
                                    exchanges routing information.";
                    } // END of peer-address definition.


                    list peer-adj-out-route {
                        key "network-address";
                        config false;
                        description
                            "List of BGP Peer adj out route";
                        leaf network-address  {
                            type  leafref {
                                path  "../state/network-address";
                            }
                            description "Peer Adj-Out Network address";
                        } // END of network-address definition.


                        list next-hop {
                            key "next-hop-address";
                            config false;
                            description
                                "next hop address and state list";
                            leaf next-hop-address  {
                                type  leafref {
                                    path  "../state/next-hop-address";
                                }
                                description "Peer Adj-Out Nexthop address";
                            } // END of next-hop-address definition.

                            container state {
                                config false;
                                description
                                    "State attributes for next-hop";
                                uses bgp-next-hop-state;
                            } // END of state-container definition.
                        } // End of next-hop-list
                        container state {
                            config false;
                            description
                                "State parameters relating to Adj out route";
                            uses bgp-peer-adj-out-route-state;
                        } // END of state-container definition.
                    } // End of peer-adj-out-route-list

                    list peer-adj-in-route {
                        key "network-address";
                        config false;
                        description
                            "List of BGP Peer adj  in route";
                        leaf network-address  {
                            type  leafref {
                                path  "../state/network-address";
                            }
                            description "Peer Adj-In Network address";
                        } // END of network-address definition.


                        list next-hop {
                            key "next-hop-address";
                            config false;
                            description
                                "next hop address and state list";
                            leaf next-hop-address  {
                                type  leafref {
                                    path  "../state/next-hop-address";
                                }
                                description "Peer Adj-In Nexthop address";
                            } // END of next-hop-address definition.

                            container state {
                                config false;
                                description
                                    "State attributes for next-hop";
                                uses bgp-next-hop-state;
                            } // END of state-container definition.
                        } // End of next-hop-list
                        container state {
                            config false;
                            description
                                "State parameters relating to Adj In route";
                            uses bgp-peer-adj-in-route-state;
                        } // END of state-container definition.
                    } // End of peer-adj-in-route-list
                    container config {
                        description
                            "Configuration parameters relating to the VRF address family";
                        uses bgp-address-family-vrf-peer-config;
                        uses bgp-address-family-peer-vrf-config;
                    } // END of config-container definition.
                    container state {
                        config false;
                        description
                            "State parameters relating to the VRF address family";
                        container counters {
                            config false;
                            description
                                "Container for the peer runtime counters";
                            uses bgp-peer-run-time-counters-state;
                            uses bgp-address-family-vrf-peer-counters-state;
                        } // END of counters-container definition.
                        uses bgp-address-family-vrf-peer-config;
                        uses bgp-address-family-peer-vrf-config;
                        uses bgp-address-family-vrf-peer-state;
                        uses bgp-peer-run-time-attribute-state;
                    } // END of state-container definition.
                    container timers {
                        description
                            "container for bgp timers";
                        container config {
                            presence "To configure timers";
                            description
                                "configuration parameters relating to timers";
                            uses bgp-peer-timers-config;
                        } // END of config-container definition.
                        container state {
                            config false;
                            description
                                "state parameters relating to timers";
                            uses bgp-peer-timers-config;
                        } // END of state-container definition.
                    } // END of timers-container definition.
                    container ebgp-multihop {
                        description
                            "container for EBGP multhop";
                        container config {
                            presence "To configure EBGP multihop";
                            description
                                "configuration parameters relating to EBGP multihop";
                            uses bgp-peer-ebgp-multhop-config;
                        } // END of config-container definition.
                        container state {
                            config false;
                            description
                                "state parameters relating to timers";
                            uses bgp-peer-ebgp-multhop-config;
                        } // END of state-container definition.
                    } // END of ebgp-multihop-container definition.
                    container maximum-prefixes {
                        description
                            "Top level container for Prefix related configuration";

                        list maximum-prefix {
                            key "prefix-count";
                            max-elements 1;
                            description
                                "List for Prefix related configuration";
                            leaf prefix-count  {
                                type  leafref {
                                    path  "../config/prefix-count";
                                }
                                description "This attribute specifies number of prefixes that a BGP router is
                                            allowed to receive from a neighbor. When the maximum-prefix-warning
                                            attribute is not set and extra prefixes are received, the router ends
                                            the peering.";
                            } // END of prefix-count definition.

                            container config {
                                description
                                    "Configuration parameters relating to the number of prefixes that can
                                            be received from a neighbor";
                                uses bgp-address-family-vrf-maximum-prefixes-config;
                            } // END of config-container definition.
                            container state {
                                config false;
                                description
                                    "State parameters relating to the VRF address family";
                                uses bgp-address-family-vrf-maximum-prefixes-config;
                            } // END of state-container definition.
                        } // End of maximum-prefix-list
                    } // END of maximum-prefixes-container definition.
                    container bgp-passwords {
                        description
                            "Top level container for BGP password";

                        list bgp-password {
                        // when " ipi-bgp-address-family-vrf:address-family-vrfs/address-family-vrf/vrf-peers/vrf-peer/bgp-passwords/bgp-password/config/auth-key-encrypt ";
                            key "password";
                            max-elements 1;
                            description
                                "List for BGP password";
                            leaf password  {
                                type  leafref {
                                    path  "../config/password";
                                }
                                description "Use this attribute to specify BGP encrypted password";
                            } // END of password definition.

                            container config {
                                description
                                    "Configuration parameters relating to the BGP password";
                                uses bgp-password-config;
                            } // END of config-container definition.
                            container state {
                                config false;
                                description
                                    "State parameters relating to the BGP password";
                                uses bgp-password-config;
                            } // END of state-container definition.
                        } // End of bgp-password-list
                    } // END of bgp-passwords-container definition.
                    container distribute-list-filters {
                        description
                            "List of Distribute list Filter";

                        list distribute-list-filter {
                        // when " ipi-bgp-address-family-vrf:address-family-vrfs/address-family-vrf/vrf-peers/vrf-peer/distribute-list-filters/distribute-list-filter/config/access-list-identifier ";
                            key "filter-direction";
                            description
                                "List of Distribute list Filter";
                            leaf filter-direction  {
                                type  leafref {
                                    path  "../config/filter-direction";
                                }
                                description "This attribute sets the direction of the filter (0=FILTER_IN
                                            |1=FILTER_OUT). This attribute is used to filter route updates from a
                                            particular BGP neighbor for specified address-family. Only one
                                            distribute-list per BGP neighbor.";
                            } // END of filter-direction definition.

                            container config {
                                description
                                    "Configuration parameters relating to BGP Distribute list Filter";
                                uses bgp-vrf-distribute-list-filter-config;
                            } // END of config-container definition.
                            container state {
                                config false;
                                description
                                    "State parameters relating to BGP Distribute list Filter";
                                uses bgp-vrf-distribute-list-filter-config;
                            } // END of state-container definition.
                        } // End of distribute-list-filter-list
                    } // END of distribute-list-filters-container definition.
                    container as-list-filters {
                        description
                            "Top level container of AS list Filter";

                        list as-list-filter {
                        // when " ipi-bgp-address-family-vrf:address-family-vrfs/address-family-vrf/vrf-peers/vrf-peer/as-list-filters/as-list-filter/config/as-access-list-identifier ";
                            key "as-list-direction";
                            description
                                "List of AS list Filter";
                            leaf as-list-direction  {
                                type  leafref {
                                    path  "../config/as-list-direction";
                                }
                                description "Direction of the filter (0=FILTER_IN |1=FILTER_OUT)";
                            } // END of as-list-direction definition.

                            container config {
                                description
                                    "Configuration parameters relating to BGP AS list Filter";
                                uses bgp-vrf-as-list-filter-config;
                            } // END of config-container definition.
                            container state {
                                config false;
                                description
                                    "State parameters relating to BGP AS list Fileter";
                                uses bgp-vrf-as-list-filter-config;
                            } // END of state-container definition.
                        } // End of as-list-filter-list
                    } // END of as-list-filters-container definition.
                    container prefix-list-filters {
                        description
                            "Top level container for Prefix list Filter";

                        list prefix-list-filter {
                        // when " ipi-bgp-address-family-vrf:address-family-vrfs/address-family-vrf/vrf-peers/vrf-peer/prefix-list-filters/prefix-list-filter/config/prefix-list-name ";
                            key "prefix-filter-direction";
                            description
                                "List of Prefix list Filter";
                            leaf prefix-filter-direction  {
                                type  leafref {
                                    path  "../config/prefix-filter-direction";
                                }
                                description "Direction of the filter (0=FILTER_IN |1=FILTER_OUT)";
                            } // END of prefix-filter-direction definition.

                            container config {
                                description
                                    "Configuration parameters relating to BGP Prefix list Filter";
                                uses bgp-vrf-prefix-list-filter-config;
                            } // END of config-container definition.
                            container state {
                                config false;
                                description
                                    "State parameters relating to BGP Prefix list Filter";
                                uses bgp-vrf-prefix-list-filter-config;
                            } // END of state-container definition.
                        } // End of prefix-list-filter-list
                    } // END of prefix-list-filters-container definition.
                    container route-map-filters {
                        description
                            "Top level container for Route map Filter";

                        list route-map-filter {
                        // when " ipi-bgp-address-family-vrf:address-family-vrfs/address-family-vrf/vrf-peers/vrf-peer/route-map-filters/route-map-filter/config/route-map-name ";
                            key "route-map-direction";
                            description
                                "List of Route map Filter";
                            leaf route-map-direction  {
                                type  leafref {
                                    path  "../config/route-map-direction";
                                }
                                description "Use this attribute to configure the direction in which the route map.";
                            } // END of route-map-direction definition.

                            container config {
                                description
                                    "Configuration parameters relating to BGP Route map Filter";
                                uses bgp-vrf-route-map-filter-config;
                            } // END of config-container definition.
                            container state {
                                config false;
                                description
                                    "State parameters relating to BGP Route map Filter";
                                uses bgp-vrf-route-map-filter-config;
                            } // END of state-container definition.
                        } // End of route-map-filter-list
                    } // END of route-map-filters-container definition.
                    container local-as {
                        description
                            "Container for Local AS";

                        list local-as-list {
                        // when " ipi-bgp-address-family-vrf:address-family-vrfs/address-family-vrf/vrf-peers/vrf-peer/config/peer-as + !ipi-bgp-address-family-vrf:address-family-vrfs/address-family-vrf/vrf-peers/vrf-peer/config/mapped-peer-group-tag-af ";
                            key "peer-local-as";
                            max-elements 1;
                            description
                                "Objectlist for Local AS";
                            leaf peer-local-as  {
                                type  leafref {
                                    path  "../config/peer-local-as";
                                }
                                description "Specifies an AS (autonomous system) number to use with BGP neighbor.";
                            } // END of peer-local-as definition.

                            container config {
                                description
                                    "Configuration parameters relating to Local AS";
                                uses bgp-peer-local-as-config;
                            } // END of config-container definition.
                            container state {
                                config false;
                                description
                                    "state parameters relating to Local AS";
                                uses bgp-peer-local-as-config;
                            } // END of state-container definition.
                        } // End of local-as-list-list
                    } // END of local-as-container definition.
                    container outbound-route-filter {
                        config false;
                        description
                            "Container for the peer runtime outbound route filter";
                        container state {
                            config false;
                            description
                                "State parameters relating to outbound route filter";
                            uses bgp-peer-run-time-orf-state;
                        } // END of state-container definition.
                    } // END of outbound-route-filter-container definition.
                    container peer-prefix {
                        config false;
                        description
                            "Container for peer prefix attributes";
                        container state {
                            config false;
                            description
                                "State parameters relating to prefix attributes";
                            uses bgp-peer-run-time-attribute-prefix-state;
                        } // END of state-container definition.
                    } // END of peer-prefix-container definition.
                    container peer-index {
                        config false;
                        description
                            "Container for peer index attributes";
                        container state {
                            config false;
                            description
                                "State parameters relating to peer index attributes";
                            uses bgp-peer-run-time-attribute-index-state;
                        } // END of state-container definition.
                    } // END of peer-index-container definition.
                } // End of vrf-peer-list
            } // END of vrf-peers-container definition.
            uses bgp-af-vrf-network-list;
            uses as-origin-validation-vrf-config-param;
            uses bgp-address-family-vrf-peer-group;
        } // End of address-family-vrf-list
    } // END of address-family-vrfs-container definition.
    } // END of address-family-vrfs-grouping definition.


}
