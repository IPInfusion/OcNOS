/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-bgp-rpki.yang
*
*/

submodule ipi-bgp-rpki {

    yang-version 1.1;

    belongs-to  ipi-bgp { prefix ipi-bgp; }

    import feature-list {
        prefix feature-list;
        revision-date 2026-09-15;
    }

    import ietf-yang-types {
        prefix yang;
        revision-date 2013-07-15;
    }

    import cml-data-types {
        prefix cml-data-types;
        revision-date 2026-05-15;
    }

    import ipi-bgp-types {
        prefix ipi-bgp-types;
        revision-date 2025-12-22;
    }

    import ipi-bgp-rpki-types {
        prefix ipi-bgp-rpki-types;
        revision-date 2025-12-16;
    }

    organization
        "IP Infusion Inc.";

    contact
        "Address: 3965 Freedom Circle, Suite 200, Santa Clara, CA 95054
         Phone: +1 408-400-1900
         E-mail: support@ipinfusion.com
         Web: http://www.ipinfusion.com/";

    description
        "BGP Resource Public Key Infrastructure (RPKI)";


    revision "2025-12-22" {
        description "Added rest time to expire runtime attributes under server state element";
        reference " 0.2.1.";
    }

    revision "2025-12-16" {
        description "Added runtime attributes for submodule RPKI servers and ROA tables";
        reference " 0.2.0.";
    }

    revision "2025-04-01" {
        description "initial revion for BGP RPKI Origin Validation";
        reference " 0.1.0.";
    }

    grouping rpki-server-config {
        description
            "Grouping for RPKI server config";
        leaf server-address  {
            type  ipi-bgp-rpki-types:bgp_rpki_server_ip_addr_t;
            description "Use this attribute to configure an RPKI server";
        } // END of server-address definition.

        leaf server-protocol-type  {
            type  ipi-bgp-rpki-types:bgp_rpki_server_protocol_t;
            default "tcp";
            description "Use this attribute to specify protocol type (SSH/TCP) for an RPKI
                        server. The default protocol is TCP.";
        } // END of server-protocol-type definition.

        leaf port  {
            type  uint16 {
                 range "0..65535"  {
                    description "0..65535: Supported range 0 - 65535";
                 }
            }
            default "0";
            description "Use this attribute to specify a port number for RPKI server SSH/TCP
                        connection. The default number is 22 for ssh, 3323 for tcp.";
        } // END of port definition.

        leaf user  {
            type  string {
                length "1..1965";
                pattern "[^?' =,>|]+";
            }
            default "0";
            description "Use this attribute to specify a user name for RPKI server SSH
                        connection";
        } // END of user definition.

        leaf password  {
            // when " ipi-bgp-rpki:rpki/servers/server/config/user ";
            type  ipi-bgp-types:bgp_md5_password_t {
                length "1..1965";
            }
            default "0";
            description "Use this attribute to specify a password for a user for RPKI server
                        SSH connection";
        } // END of password definition.

        leaf auth-key-encrypt  {
            // when " ipi-bgp-rpki:rpki/servers/server/config/user ";
            type  ipi-bgp-types:bgp_md5_t;
            default "1";
            description "Use this attribute to configure the authentication key to specify if
                        the password is to be encrypted or not.";
        } // END of auth-key-encrypt definition.

        leaf refresh-interval  {
            type  uint32 {
                 range "1..86400"  {
                    description "1..86400: Supported range 1 - 86400";
                 }
            }
            default "3600";
            description "Use this attribute to specify a value of refresh interval RTR
                        connection for an RPKI server. 3600 seconds by default.";
        } // END of refresh-interval definition.

        leaf retry-interval  {
            type  uint32 {
                 range "1..7200"  {
                    description "1..7200: Supported range 1 - 7200";
                 }
            }
            default "600";
            description "Use this attribute to specify a value of retry interval RTR connection
                        for an RPKI server. 600 seconds by default.";
        } // END of retry-interval definition.

        leaf expire-interval  {
            type  uint32 {
                 range "600..17200"  {
                    description "600..17200: Supported range 600 - 17200";
                 }
            }
            default "7200";
            description "Use this attribute to specify a value of expire interval RTR
                        connection for an RPKI server. 7200 seconds by default.";
        } // END of expire-interval definition.

    } // END of rpki-server-config definition.
    grouping rpki-server-state {
        description
            "Grouping for RPKI Server state data attributes";
        leaf route-to-route-version  {
            type  uint8;
            description "Version of Route-to-Route RPKI Protocol";
        } // END of route-to-route-version definition.

        leaf route-to-route-client-state  {
            type  ipi-bgp-rpki-types:bgp_rpki_rtr_client_state;
            description "State of RTR RPKI client session";
        } // END of route-to-route-client-state definition.

        leaf route-to-route-sockets-sync  {
            type  boolean;
            description "Indicates if a set of sockets is fully synchronized with at least one
                        group";
        } // END of route-to-route-sockets-sync definition.

        leaf rpki-uptime  {
            type  yang:timeticks;
            units "seconds";
            description "RPKI Server uptime";
        } // END of rpki-uptime definition.

        leaf ipv4-route-origin-authorizations-count  {
            type  uint32;
            description "Count of IPv4 ROA entries";
        } // END of ipv4-route-origin-authorizations-count definition.

        leaf ipv6-route-origin-authorizations-count  {
            type  uint32;
            description "Count of IPv6 ROA entries";
        } // END of ipv6-route-origin-authorizations-count definition.

        leaf actual-refresh-interval  {
            type  uint32;
            units "seconds";
            description "Actual value of refresh interval RTR connection for an RPKI server";
        } // END of actual-refresh-interval definition.

        leaf actual-retry-interval  {
            type  uint32;
            units "seconds";
            description "Actual value of retry interval RTR connection for an RPKI server";
        } // END of actual-retry-interval definition.

        leaf actual-expire-interval  {
            type  uint32;
            units "seconds";
            description "Actual value of expire interval RTR connection for an RPKI server";
        } // END of actual-expire-interval definition.

        leaf rest-of-time-to-refresh-interval-expiration  {
            type  uint32;
            units "seconds";
            description "Rest of time to Refresh-Interval expiration";
        } // END of rest-of-time-to-refresh-interval-expiration definition.

        leaf rest-of-time-to-expire-interval-expiration  {
            type  uint32;
            units "seconds";
            description "Rest of time to Expire-Interval expiration";
        } // END of rest-of-time-to-expire-interval-expiration definition.

        leaf client-session-to-be-deleted  {
            type  boolean;
            description "Indicates if client session is about to be deleted";
        } // END of client-session-to-be-deleted definition.

    } // END of rpki-server-state definition.
    grouping rpki-table-ipv4-state {
        description
            "Grouping for RPKI IPv4 table attributes";
        leaf prefix-ipv4  {
            type  cml-data-types:cml_ipv4_prefix_t;
            description "Prefix IPv4";
        } // END of prefix-ipv4 definition.

        leaf max-length  {
            type  uint8;
            description "The maximum length for a prefix record";
        } // END of max-length definition.

        leaf as-number  {
            type  uint32;
            description "Identifier to an Autonomous System";
        } // END of as-number definition.

        leaf server-address  {
            type  ipi-bgp-rpki-types:bgp_rpki_server_ip_addr_t;
            description "RTR RPKI server address";
        } // END of server-address definition.

    } // END of rpki-table-ipv4-state definition.
    grouping rpki-table-ipv6-state {
        description
            "Grouping for RPKI IPv6 table attributes";
        leaf prefix-ipv6  {
            type  cml-data-types:cml_ipv6_prefix_t;
            description "Prefix IPv6";
        } // END of prefix-ipv6 definition.

        leaf max-length  {
            type  uint8;
            description "The maximum length for a prefix record";
        } // END of max-length definition.

        leaf as-number  {
            type  uint32;
            description "Identifier to a Autonomous System";
        } // END of as-number definition.

        leaf server-address  {
            type  ipi-bgp-rpki-types:bgp_rpki_server_ip_addr_t;
            description "RTR RPKI server address";
        } // END of server-address definition.

    } // END of rpki-table-ipv6-state definition.
    grouping rpki-tables-ipv4 {
        description
            "Grouping for RPKI IPv4 table state data";

        list table-ipv4 {
            key "prefix-ipv4 max-length as-number server-address";
            config false;
            description
                "RPKI IPv4 table state data";
            leaf prefix-ipv4  {
                type  leafref {
                    path  "../state/prefix-ipv4";
                }
                description "Prefix IPv4";
            } // END of prefix-ipv4 definition.

            leaf max-length  {
                type  leafref {
                    path  "../state/max-length";
                }
                description "The maximum length for a prefix record";
            } // END of max-length definition.

            leaf as-number  {
                type  leafref {
                    path  "../state/as-number";
                }
                description "Identifier to an Autonomous System";
            } // END of as-number definition.

            leaf server-address  {
                type  leafref {
                    path  "../state/server-address";
                }
                description "RTR RPKI server address";
            } // END of server-address definition.

            container state {
                config false;
                description
                    "Operational state data for RPKI server";
                uses rpki-table-ipv4-state;
            } // END of state-container definition.
        } // End of table-ipv4-list
    } // END of rpki-tables-ipv4 definition.
    grouping rpki-tables-ipv6 {
        description
            "Grouping for RPKI IPv6 table state data";

        list table-ipv6 {
            key "prefix-ipv6 max-length as-number server-address";
            config false;
            description
                "RPKI IPv6 table state data";
            leaf prefix-ipv6  {
                type  leafref {
                    path  "../state/prefix-ipv6";
                }
                description "Prefix IPv6";
            } // END of prefix-ipv6 definition.

            leaf max-length  {
                type  leafref {
                    path  "../state/max-length";
                }
                description "The maximum length for a prefix record";
            } // END of max-length definition.

            leaf as-number  {
                type  leafref {
                    path  "../state/as-number";
                }
                description "Identifier to an Autonomous System";
            } // END of as-number definition.

            leaf server-address  {
                type  leafref {
                    path  "../state/server-address";
                }
                description "RTR RPKI server address";
            } // END of server-address definition.

            container state {
                config false;
                description
                    "Operational state data for RPKI server";
                uses rpki-table-ipv6-state;
            } // END of state-container definition.
        } // End of table-ipv6-list
    } // END of rpki-tables-ipv6 definition.
    grouping rpki-server-top {
        description
            "Top-level grouping for RPKI server";

        list server {
        // when " ipi-bgp-instance:bgp-instances/bgp-instance/bgp-as ";
            key "server-address";
            description
                "Configuration data for RPKI server";
            leaf server-address  {
                type  leafref {
                    path  "../config/server-address";
                }
                description "Use this attribute to configure an RPKI server";
            } // END of server-address definition.

            container config {
                description
                    "Configuration data for RPKI server";
                uses rpki-server-config;
            } // END of config-container definition.
            container state {
                config false;
                description
                    "Operational state data for class for RPKI server";
                uses rpki-server-config;
                uses rpki-server-state;
            } // END of state-container definition.
        } // End of server-list
    } // END of rpki-server-top definition.
    grouping rpki-servers-top {
        description
            "Top-level grouping for RPKI";
        container servers {
            description
                "Configuration data for RPKI servers";
            uses rpki-server-top;
        } // END of servers-container definition.
    } // END of rpki-servers-top definition.
    grouping rpki-tables-ipv4-top {
        description
            "Top-level grouping for RPKI tables IPv4";
        container tables-ipv4 {
            config false;
            description
                "Container state data for RPKI tables IPv4";
            uses rpki-tables-ipv4;
        } // END of tables-ipv4-container definition.
    } // END of rpki-tables-ipv4-top definition.
    grouping rpki-tables-ipv6-top {
        description
            "Top-level grouping for RPKI tables IPv6";
        container tables-ipv6 {
            config false;
            description
                "Container state data for RPKI tables IPv6";
            uses rpki-tables-ipv6;
        } // END of tables-ipv6-container definition.
    } // END of rpki-tables-ipv6-top definition.

    grouping  rpki-grouping {
    description
        "BGP Resource Public Key Infrastructure (RPKI)";
    container rpki {
        if-feature feature-list:HAVE_BGP_RPKI_ORIGIN_VALIDATION;
        if-feature feature-list:HAVE_BGPD;
        description
            "BGP Resource Public Key Infrastructure (RPKI)";
        uses rpki-servers-top;
        uses rpki-tables-ipv4-top;
        uses rpki-tables-ipv6-top;
    } // END of rpki-container definition.
    } // END of rpki-grouping definition.


}
