/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-bgp-common.yang
*
*/

submodule ipi-bgp-common {

    yang-version 1.1;

    belongs-to  ipi-bgp { prefix ipi-bgp; }

    import feature-list {
        prefix feature-list;
        revision-date 2026-09-15;
    }

    import cml-data-types {
        prefix cml-data-types;
        revision-date 2026-05-15;
    }

    import ipi-bgp-types {
        prefix ipi-bgp-types;
        revision-date 2025-12-22;
    }

    import ietf-yang-types {
        prefix yang;
        revision-date 2013-07-15;
    }

    import ietf-inet-types {
        prefix inet;
        revision-date 2013-07-15;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for bgp network list";


    revision "2025-12-22" {
        description "Added origin Autonomous System (AS) validation state attribute";
        reference " 0.14.2.";
    }

    revision "2025-12-18" {
        description "Added CML_SKIP_HITLESS_MERGE for the attribute 'additional-paths-mode'";
        reference " 0.13.8.";
    }

    revision "2025-11-28" {
        description "Updated datatype for attribute 'route-community-string'";
        reference " 0.13.7.";
    }

    revision "2025-11-25" {
        description "Updated datatype for attribute 'additional-path-receive-capability' and 'additional-path-send-capability'";
        reference " 0.13.6.";
    }

    revision "2025-11-17" {
        description " Added hidden flag for disable-capability-negotiation";
        reference " 0.13.5.";
    }

    revision "2025-09-24" {
        description "Removed attribute 'bgp-port' for Peer and Peer-group";
        reference " 0.13.4.";
    }

    revision "2025-09-11" {
        description "Added peer-type fabric-external attribute for EVPN VXLAN feature";
        reference " 0.13.3.";
    }

    revision "2025-04-29" {
        description "Made attr redist-route-map-name mandatory for redistribute configuration";
        reference " 0.13.2.";
    }

    revision "2025-04-09" {
        description "Updated range for group-limit attribute ";
        reference " 0.13.1.";
    }

    revision "2025-04-03" {
        description "Updated helpstring of peer-group for attribute 'advertisement-interval' and 'as-origination-interval' ";
        reference " 0.13.0.";
    }

    revision "2025-01-27" {
        description "Added dynamic-peer-address attribute inside bgp-peer-run-time-attribute-state grouping";
        reference " 0.12.5.";
    }

    revision "2024-11-27" {
        description "Updated helpstring of AS:nn for the attribute 'site-origin-identifier'";
        reference " 0.12.4.";
    }

    revision "2024-10-29" {
        description "Updated neighbor password size limits";
        reference " 0.12.3.";
    }

    revision "2024-10-16" {
        description "Added peer-allow-ebgp-vpn when tag to peer-group activate of vrf address-family";
        reference " 0.12.2.";
    }

    revision "2024-10-03" {
        description "Updated When tag constraints for attribute 'site-origin-identifier'";
        reference " 0.12.1.";
    }

    revision "2024-09-11" {
        description "Fix BGP address-family CLI helpstrings";
        reference " 0.12.0.";
    }

    revision "2024-08-26" {
        description "Fix data-sync issue when address-family flowspec vrf removed'";
        reference " 0.11.4.";
    }

    revision "2024-01-05" {
        description "Removed 'ebgp-max-path' cli for address-family l2vpn evpn";
        reference " 0.11.3.";
    }

    revision "2024-01-04" {
        description "Update datatype for attributes: 'graceful-restart', 'orf-type-prefix-send-mode', 'orf-type-prefix-receive-mode','orf-type-prefix-send-mode-old' and 'orf-type-prefix-receive-mode-old'";
        reference " 0.11.2.";
    }

    revision "2023-12-14" {
        description "Updated datatype for attribute 'orf-type-prefix-send-mode', 'orf-type-prefix-receive-mode','orf-type-prefix-receive-mode'and 'orf-type-prefix-send-mode-old' ";
        reference " 0.11.1.";
    }

    revision "2023-11-27" {
        description "Added soft-reconfig attribute";
        reference " 0.11.0.";
    }

    revision "2023-10-09" {
        description "Updated When tag constraints for attribute 'enable-peer-bfd-multihop' and 'enable-peer-bfd'";
        reference " 0.10.11.";
    }

    revision "2023-09-22" {
        description "Updated attribute to bgp-peer-run-time-attribute-state ";
        reference " 0.10.10.";
    }

    revision "2023-09-12" {
        description "Added enclosing container for all objectlists";
        reference " 0.10.9.";
    }

    revision "2023-09-07" {
        description "Removing attributes from bgp-peer-run-time-attribute-state,bgp-peer-run-time-counters-state";
        reference " 0.10.8.";
    }

    revision "2023-09-05" {
        description "Updated When tag constraints for attribute 'peer-route-map-orig-name' and 'default-peer-route-map-name'";
        reference " 0.10.7.";
    }

    revision "2023-08-16" {
        description "New patch Added option 'no-prepend' and 'replace-as' for BGP neighbor local-as";
        reference " 0.10.6.";
    }

    revision "2023-08-15" {
        description "Revert patch Added option 'no-prepend' and 'replace-as' for BGP neighbor local-as";
        reference " 0.10.5.";
    }

    revision "2023-08-11" {
        description "Added option 'no-prepend' and 'replace-as' for BGP neighbor local-as";
        reference " 0.10.4.";
    }

    revision "2023-08-03" {
        description "Added attr capability-ipv4-unicast to bgp-peer-run-time-attribute-state";
        reference " 0.10.3.";
    }

    revision "2023-07-20" {
        description "Added support for TCP Maximum Segment Size per BGP neighbor";
        reference " 0.10.2.";
    }

    revision "2023-05-06" {
        description "address-family ipv4 flowspec vrf support";
        reference " 0.10.1.";
    }

    revision "2023-04-11" {
        description "Removed attribute 'soft-reconfig-inbound'";
        reference " 0.10.0.";
    }

    revision "2023-02-22" {
        description "Added support for BGP ADD Path in vrf address-family";
        reference " 0.9.1.";
    }

    revision "2023-02-21" {
        description "BGP flowspec support";
        reference " 0.9.0.";
    }

    revision "2023-01-09" {
        description "added new container for ebgp multihop command";
        reference " 0.8.9.";
    }

    revision "2023-01-03" {
        description "Updated bgp debug options";
        reference " 0.8.8.";
    }

    revision "2022-10-20" {
        description "Updated When tag constraints and removed Default value from attribute 'ebgp-maximum-hop-count' and 'enable-ebgp-multihop'";
        reference " 0.8.7.";
    }

    revision "2022-09-27" {
        description "Removed Default value from attribute 'ebgp-max-path', 'ibgp-max-path' and 'eibgp-max-path'";
        reference " 0.8.6.";
    }

    revision "2022-07-06" {
        description "Skipped dependency validation for a composite constraint of peer-as and peer-group-tag for BGP peer";
        reference " 0.8.5.";
    }

    revision "2022-06-20" {
        description "Added new attribute 'de-activate' for BGP Peer-group feature.";
        reference " 0.8.4.";
    }

    revision "2022-06-01" {
        description "Updated the yang file with feature";
        reference " 0.8.3.";
    }

    revision "2022-04-19" {
        description "Added new attribute 'peer-shutdown-description' for support of BGP Administrative Shutdown Communication feature.";
        reference " 0.8.2.";
    }

    revision "2022-01-17" {
        description "Modified data type";
        reference " 0.8.1.";
    }

    revision "2022-01-07" {
        description "Modified Data type";
        reference " 0.8.0.";
    }

    revision "2021-11-16" {
        description "SKU compilation error fixes";
        reference " 0.7.5.";
    }

    revision "2021-09-20" {
        description "Spelling has been corrected for an attribute";
        reference " 0.7.4.";
    }

    revision "2021-09-15" {
        description "removed yang drop element for the additional-path attributes for the bgp-add-path feature.";
        reference " 0.7.3.";
    }

    revision "2021-09-03" {
        description "Update descriptions of attribute";
        reference " 0.7.2.";
    }

    revision "2021-08-13" {
        description "BGP ECMP Support for EIBGP routes";
        reference " 0.7.1.";
    }

    revision "2021-08-03" {
        description "Added new attribute for enabling Enhe capability for IPv6 VPNv4 peer";
        reference " 0.7.0.";
    }

    revision "2021-07-21" {
        description "Added per peer runtime attributes for BGP EVPN route counters";
        reference " 0.6.0.";
    }

    revision "2021-07-05" {
        description "Remodelled authentication password object list for BGP peer, VRF peer and peer-group";
        reference " 0.5.0.";
    }

    revision "2021-06-25" {
        description "Modified dependency for activate attribute";
        reference " 0.4.7.";
    }

    revision "2021-06-11" {
        description "Added dependency constraint between name and direction attrs for the distribute-list, prefix-list, filter-list and route-map CLI's";
        reference " 0.4.6.";
    }

    revision "2021-06-09" {
        description "Removal of default ipv4 unicast activate and fix for DB sync issues";
        reference " 0.4.5.";
    }

    revision "2021-05-31" {
        description "Deprecated prefix-list-count attribute and added length for route map name";
        reference " 0.4.4.";
    }

    revision "2021-05-28" {
        description "Changed type of the attribute default-originate-information-sent";
        reference " 0.4.3.";
    }

    revision "2021-05-26" {
        description "Deprecated the as-local-count run-time attribute is same as the configured local-as attribute";
        reference " 0.4.2.";
    }

    revision "2021-05-13" {
        description "Removed dependency validation on AF activate for allow-ebgp-vpn attribute";
        reference " 0.4.1.";
    }

    revision "2021-04-09" {
        description "Change related to Peer group remodelling";
        reference " 0.4.0.";
    }

    revision "2021-03-05" {
        description "Excluded yang generation for BGP Add path attributes";
        reference " 0.3.0.";
    }

    revision "2020-12-15" {
        description "Change to have data-types in lower case instead of camel case";
        reference " 0.2.0.";
    }

    revision "2020-09-10" {
        description "Initial Version";
        reference " 0.1.0.";
    }

    grouping bgp-af-maximum-paths-config {
        description
            "Configuration attributes related to multipath ECMP numbers";
        leaf ebgp-max-path  {
            type  int32 {
                 range "2..64"  {
                    description "2..64: Supported range 2 - 64";
                 }
            }
            description "Use this attribute to set the number of equal-cost multi-path (ECMP)
                        routes for eBGP. You can install multiple BGP paths to the same
                        destination to balance the load on the forwarding path";
        } // END of ebgp-max-path definition.

        leaf ibgp-max-path  {
            type  int32 {
                 range "2..64"  {
                    description "2..64: Supported range 2 - 64";
                 }
            }
            description "Use this attribute to set the number of equal-cost multi-path (ECMP)
                        routes for iBGP. You can install multiple BGP paths to the same
                        destination to balance the load on the forwarding path.";
        } // END of ibgp-max-path definition.

        leaf eibgp-max-path  {
            type  int32 {
                 range "2..64"  {
                    description "2..64: Supported range 2 - 64";
                 }
            }
            description "Use this attribute to set the number of equal-cost multi-path (ECMP)
                        routes for eiBGP. You can install multiple BGP paths to the same
                        destination to balance the load on the forwarding path";
        } // END of eibgp-max-path definition.

    } // END of bgp-af-maximum-paths-config definition.
    grouping address-family-redist-list-config {
        description
            "Configuration attributes related to redistribute for address-family";
        leaf protocol-type  {
            type  ipi-bgp-types:bgp_redistribute_type_t;
            description "Use this attribute to configure the protocol type of the routes that
                        are to be redistributed by BGP. Redistribution is used by routing
                        protocols to advertise routes that are learned by some other means,
                        such as by another routing protocol or by static routes.";
        } // END of protocol-type definition.

        leaf redist-route-map-name  {
            type  string {
                length "1..63";
                pattern "[^?' =,>|]+";
            }
            mandatory true;
            description "Use this attribute to configure route map to be used for redistributed
                        routes.";
        } // END of redist-route-map-name definition.

    } // END of address-family-redist-list-config definition.
    grouping bgp-network-list-state {
        description
            "Operational state data for bgp network list";
        leaf network-path-route-count  {
            type  int32;
            config false;
            description "Network path count";
        } // END of network-path-route-count definition.

        leaf no-advertise-route  {
            type  string {
                length "1..1965";
                pattern "[^?' =,>|]+";
            }
            config false;
            description "Not advertised route";
        } // END of no-advertise-route definition.

        leaf no-export-route  {
            type  boolean;
            config false;
            description "Not advertised to EBGP peer";
        } // END of no-export-route definition.

        leaf local-as-route  {
            type  boolean;
            config false;
            description "Not advertised outside local AS";
        } // END of local-as-route definition.

        leaf suppress-route  {
            type  boolean;
            config false;
            description "Advertisements suppressed by an aggregate.";
        } // END of suppress-route definition.

        leaf network-best-path-route-count  {
            type  int32;
            config false;
            description "best";
        } // END of network-best-path-route-count definition.

        leaf ip-routing-table  {
            type  string {
                length "1..1965";
                pattern "[^?' =,>|]+";
            }
            config false;
            description "IP Routing Table";
        } // END of ip-routing-table definition.

        leaf-list advertised-non-peer-group-address  {
            type  ipi-bgp-types:bgp_hostname_t;
            config false;
            description "Advertised non peer-group peers.";
        } // END of advertised-non-peer-group-address definition.

        leaf-list advertised-peer-group-name-route  {
            type  string {
                length "1..1965";
                pattern "[^?' =,>|]+";
            }
            config false;
            description "Advertised peer-groups";
        } // END of advertised-peer-group-name-route definition.

        leaf advertised-any-peer  {
            type  boolean;
            config false;
            description "Advertised to any peer";
        } // END of advertised-any-peer definition.

        leaf route-distinguisher-string  {
            if-feature feature-list:HAVE_MPLS;
            type  string {
                length "1..1965";
                pattern "[^?' =,>|]+";
            }
            config false;
            description "Route distinguisher";
        } // END of route-distinguisher-string definition.

    } // END of bgp-network-list-state definition.
    grouping bgp-next-hop-state {
        description
            "Operational state data for nexthop";
        leaf next-hop-address  {
            type  ipi-bgp-types:bgp_hostname_t;
            config false;
            description "NextHop Address";
        } // END of next-hop-address definition.

        leaf peer-network-weight  {
            type  uint32;
            config false;
            description "BGP attribute weight";
        } // END of peer-network-weight definition.

        leaf flap-time-reuse-list  {
            type  string {
                length "1..1965";
                pattern "[^?' =,>|]+";
            }
            config false;
            description "Dampinfo: reuse in";
        } // END of flap-time-reuse-list definition.

        leaf flap-record-duration  {
            type  string {
                length "1..1965";
                pattern "[^?' =,>|]+";
            }
            config false;
            description "Flap record duration";
        } // END of flap-record-duration definition.

        leaf damp-time-to-reuse  {
            type  string {
                length "1..1965";
                pattern "[^?' =,>|]+";
            }
            config false;
            description "Damp time to reuse";
        } // END of damp-time-to-reuse definition.

        leaf bgp-med-value  {
            type  uint32;
            config false;
            description "BGP multi-exit discriminator attribute used in BGP route selection
                        process";
        } // END of bgp-med-value definition.

        leaf-list bgp-as-path-string  {
            type  cml-data-types:cml_line_t {
                length "1..1965";
            }
            config false;
            description "AS-path";
        } // END of bgp-as-path-string definition.

        leaf-list bgp-as-path-4-byte-string  {
            type  string {
                length "1..1965";
                pattern "[^?' =,>|]+";
            }
            config false;
            description "AS-path for extended asn capability";
        } // END of bgp-as-path-4-byte-string definition.

        leaf bgp-as-path-4-byte-origin  {
            type  ipi-bgp-types:bgp_origin_t;
            config false;
            description "Origin: 0(IGP), 1(EGP), 2(Incomplete)";
        } // END of bgp-as-path-4-byte-origin definition.

        leaf ibgp-metric-route  {
            type  int32;
            config false;
            description "IGP metric value for route selection.";
        } // END of ibgp-metric-route definition.

        leaf aggregate-as-route  {
            type  int32;
            config false;
            description "Aggregated by as";
        } // END of aggregate-as-route definition.

        leaf aggregator-address-route  {
            type  ipi-bgp-types:bgp_hostname_t;
            config false;
            description "Aggregated by address";
        } // END of aggregator-address-route definition.

        leaf network-remote-address-route  {
            type  ipi-bgp-types:bgp_hostname_t;
            config false;
            description "Remote id";
        } // END of network-remote-address-route definition.

        leaf originator-id-route  {
            type  ipi-bgp-types:bgp_hostname_t;
            config false;
            description "Originator id";
        } // END of originator-id-route definition.

        leaf route-peer-address  {
            type  ipi-bgp-types:bgp_hostname_t;
            config false;
            description "Address of the peer";
        } // END of route-peer-address definition.

        leaf route-local-preference  {
            type  uint32;
            config false;
            description "Local preference";
        } // END of route-local-preference definition.

        leaf route-prefix-label  {
            type  uint32;
            config false;
            description "label";
        } // END of route-prefix-label definition.

        leaf route-community-string  {
            type  cml-data-types:cml_line_t {
                length "1..1965";
            }
            config false;
            description "Community";
        } // END of route-community-string definition.

        leaf-list cluster-list-route  {
            type  ipi-bgp-types:bgp_hostname_t;
            config false;
            description "Cluster list";
        } // END of cluster-list-route definition.

        leaf route-penalty  {
            type  int32;
            config false;
            description "Dampinfo: penalty";
        } // END of route-penalty definition.

        leaf route-flap-count  {
            type  int32;
            config false;
            description "Dampinfo: no of times flapped";
        } // END of route-flap-count definition.

        leaf last-update-route  {
            type  yang:date-and-time {
                pattern "\\d{4}-\\d{2}-\\d{2}T\\d{2}:\\d{2}:\\d{2}(\\.\\d+)?(Z|[\\+\\-]\\d{2}:\\d{2})";
                }
                config false;
                description "Last Update";
            } // END of last-update-route definition.

            leaf reflector-client-route  {
                type  boolean;
                config false;
                description "Received from a RR-client";
            } // END of reflector-client-route definition.

            leaf route-dampening-active  {
                type  boolean;
                config false;
                description "suppressed due to dampening";
            } // END of route-dampening-active definition.

            leaf history-route  {
                type  boolean;
                config false;
                description "history entry";
            } // END of history-route definition.

            leaf nexthop-valid-route  {
                type  boolean;
                config false;
                description "Inactive redistribute routes";
            } // END of nexthop-valid-route definition.

            leaf med-flag-type-route  {
                type  boolean;
                config false;
                description "if REMOVE-MED flag is enabled";
            } // END of med-flag-type-route definition.

            leaf valid-route  {
                type  boolean;
                config false;
                description "Check if state is valid";
            } // END of valid-route definition.

            leaf stale-route  {
                type  boolean;
                config false;
                description "Check BGP info stale";
            } // END of stale-route definition.

            leaf route-type  {
                type  ipi-bgp-types:bgp_ri_type_t;
                config false;
                description "BGP route info type - internal, confed-external, external, sourced,
                            aggregated, local";
            } // END of route-type definition.

            leaf ecmp-multi-candidate-route  {
                type  boolean;
                config false;
                description "if ecmp multipath candidate";
            } // END of ecmp-multi-candidate-route definition.

            leaf multi-installed-route  {
                type  boolean;
                config false;
                description "if bgp info multi install- 1(installed)";
            } // END of multi-installed-route definition.

            leaf route-synchronized-flag-route  {
                type  boolean;
                config false;
                description "BGP info status - 0(not synchronized) 1(synchronized)";
            } // END of route-synchronized-flag-route definition.

            leaf atomic-aggregate-route  {
                type  boolean;
                config false;
                description "atomic-aggregate";
            } // END of atomic-aggregate-route definition.

            leaf selected-route  {
                type  boolean;
                config false;
                description "BGP info best selected route";
            } // END of selected-route definition.

            leaf bgp-tx-path-id  {
                if-feature feature-list:HAVE_BGP_ADD_PATH;
                type  int16;
                config false;
                description "bgp add path Tx Id";
            } // END of bgp-tx-path-id definition.

            leaf bgp-rx-path-id  {
                if-feature feature-list:HAVE_BGP_ADD_PATH;
                type  int16;
                config false;
                description "bgp add path Rx Id";
            } // END of bgp-rx-path-id definition.

            leaf ipv4-multicast-capability  {
                type  string {
                    length "1..1965";
                    pattern "[^?' =,>|]+";
                }
                config false;
                description "IPV4 Multicast neighbour Capability";
            } // END of ipv4-multicast-capability definition.

            leaf vpnv4-unicast-capability  {
                type  string {
                    length "1..1965";
                    pattern "[^?' =,>|]+";
                }
                config false;
                description "Vpnv4 Unicast neighbour Capability";
            } // END of vpnv4-unicast-capability definition.

            leaf rtfilter-unicast-capability  {
                type  string {
                    length "1..1965";
                    pattern "[^?' =,>|]+";
                }
                config false;
                description "Route target filter Unicast neighbour Capability";
            } // END of rtfilter-unicast-capability definition.

            leaf l2vpn-evpn-capability  {
                type  string {
                    length "1..1965";
                    pattern "[^?' =,>|]+";
                }
                config false;
                description "L2vpn Evpn neighbour Capability";
            } // END of l2vpn-evpn-capability definition.

            leaf ipv6-unicast-capability  {
                type  string {
                    length "1..1965";
                    pattern "[^?' =,>|]+";
                }
                config false;
                description "Ipv6 Unicast neighbour Capability";
            } // END of ipv6-unicast-capability definition.

            leaf ipv6-multicast-capability  {
                type  string {
                    length "1..1965";
                    pattern "[^?' =,>|]+";
                }
                config false;
                description "Ipv6 Multicast neighbour Capability";
            } // END of ipv6-multicast-capability definition.

            leaf ipv6-label-unicast-capability  {
                type  string {
                    length "1..1965";
                    pattern "[^?' =,>|]+";
                }
                config false;
                description "Ipv6 Label Unicast neighbour Capability";
            } // END of ipv6-label-unicast-capability definition.

            leaf in-label  {
                if-feature feature-list:HAVE_BGP_LU;
                type  uint32;
                config false;
                description "bgp LU In Label";
            } // END of in-label definition.

            leaf out-label  {
                if-feature feature-list:HAVE_BGP_LU;
                type  uint32;
                config false;
                description "bgp LU Out Label";
            } // END of out-label definition.

            leaf as-origin-validation-state  {
                if-feature feature-list:HAVE_BGP_RPKI_ORIGIN_VALIDATION;
                type  ipi-bgp-types:bgp_rpki_o_as_validation_state;
                config false;
                description "The validation state of an origin Autonomous System (AS)";
            } // END of as-origin-validation-state definition.

    } // END of bgp-next-hop-state definition.
    grouping bgp-next-hop-mpls-state {
        description
            "Operational state data for nexthop related to MPLS";
        leaf vrf-name  {
            if-feature feature-list:HAVE_MPLS;
            type  string {
                length "1..1965";
                pattern "[^?' =,>|]+";
            }
            config false;
            description "VRF name";
        } // END of vrf-name definition.

        leaf route-distinguisher  {
            if-feature feature-list:HAVE_MPLS;
            type  string {
                length "1..1965";
                pattern "[^?' =,>|]+";
            }
            config false;
            description "Route distinguisher";
        } // END of route-distinguisher definition.

    } // END of bgp-next-hop-mpls-state definition.
    grouping bgp-peer-adj-out-route-state {
        description
            "State parameter for Peer  Adj out route";
        leaf network-address  {
            type  ipi-bgp-types:bgp_ip_network_t;
            config false;
            description "Peer Adj-Out Network address";
        } // END of network-address definition.

    } // END of bgp-peer-adj-out-route-state definition.
    grouping bgp-peer-adj-in-route-state {
        description
            "State parameter for Peer  Adj in route";
        leaf network-address  {
            type  ipi-bgp-types:bgp_ip_network_t;
            config false;
            description "Peer Adj-In Nexthop address";
        } // END of network-address definition.

    } // END of bgp-peer-adj-in-route-state definition.
    grouping bgp-optional-as-list-config {
        description
            "Configuration parameters for BGP peer groups";
        leaf optional-as  {
            type  uint32 {
                 range "1..4294967295"  {
                    description "1..4294967295: Supported range 1 - 4294967295";
                 }
            }
            description "This attribute specifies an  optional AS Number to a dynamic
                        peer-group";
        } // END of optional-as definition.

    } // END of bgp-optional-as-list-config definition.
    grouping bgp-address-family-peer-config {
        description
            "Configuration parameters for peer";
        leaf activate  {
            type  empty;
            description "Activate/Deactivate neighbor. This attribute enables or disables the
                        exchange of AF information with a neighboring router.";
        } // END of activate definition.

        leaf de-activate  {
            // when " ipi-bgp-peer:peers/peer/config/mapped-peer-group-tag ";
            type  empty;
            description "Deactivate neighbor. This attribute disables the exchange of AF
                        information with a neighboring router.";
        } // END of de-activate definition.

        leaf default-peer-route-map-name  {
            type  empty;
            description "This attribute allows a BGP local router to send the default route
                        0.0.0.0 to a neighbor for use as a default route for specified
                        address-family.";
        } // END of default-peer-route-map-name definition.

        leaf peer-route-map-orig-name  {
            type  string {
                length "1..1965";
                pattern "[^?' =,>|]+";
            }
            description "This attribute configures route map to be used for a BGP local router
                        to send the default route 0.0.0.0 to a neighbor for use as a default
                        route for specified address-family. This attribute can be used with
                        standard or extended access lists.";
        } // END of peer-route-map-orig-name definition.

        leaf soft-reconfig  {
            type  ipi-bgp-types:bgp_update_clear_t;
            description "This attribute is used to store the updates for soft
                        inbound and outbound configuration.";
        } // END of soft-reconfig definition.

        leaf weight  {
            type  uint16 {
                 range "0..65535"  {
                    description "0..65535: Supported range 0 - 65535";
                 }
            }
            default "0";
            description "This attribute specifies a weight value, for specified address-family,
                        to all routes learned from a neighbor for specified address-family.
                        The route with the highest weight gets preference when the same prefix
                        is learned from more than one peer. Unlike the local-preference
                        attribute, the weight attribute is relevant only to the local router.
                        When the weight is set for a peer group, all members of the peer group
                        get the same weight. This attribute can also be used to assign a
                        different weight to an individual peer-group member. When an
                        individually-configured weight of a peer-group member is removed, its
                        weight is reset to its peer groups weight.";
        } // END of weight definition.

        leaf flowspec-validation-disable  {
            if-feature feature-list:HAVE_BGP_FLOWSPEC;
            type  empty;
            description "This attribute specifies if FLOWSPEC validiation should be disabled
                        for a specific peer";
        } // END of flowspec-validation-disable definition.

        leaf peer-route-reflector  {
            type  empty;
            description "This attribute configures the router as a BGP route reflector and
                        configure the specified neighbor as its client for specified
                        address-family.
                        Route reflectors are a solution for the explosion of iBGP peering
                        within an autonomous system. By route reflection the number of iBGP
                        peers within an AS is reduced. Use this attribute to configure the
                        local router as the route reflector and specify neighbors as its
                        client. An AS can have more than one route reflector. One route
                        reflector treats the other route reflector as another iBGP speaker.";
        } // END of peer-route-reflector definition.

        leaf peer-type-fabric-external  {
            if-feature feature-list:HAVE_EVPN_VXLAN_STITCHING;
            type  empty;
            description "Use this attribute to set BGP peer fabric type in Data Center
                        Interconnect (DCI). This denotes whether the peer belongs to local or
                        remote data center";
        } // END of peer-type-fabric-external definition.

        leaf peer-remove-private-as  {
            type  empty;
            description "This attribute removes the private Autonomous System (AS) number from
                        outbound updates. Private AS numbers are not advertised to the
                        Internet. This attribute is used with external BGP peers only. The
                        router removes the AS numbers only if the update includes private AS
                        numbers. If the update includes both private and public AS numbers,
                        the system treats it as an error.";
        } // END of peer-remove-private-as definition.

        leaf no-send-community  {
            type  empty;
            description "This attribute specifies if a community attribute should be sent to a
                        BGP neighbor for specified address-family. The community attribute
                        groups destinations in a certain community and applies routing
                        decisions according to those communities. By default, both standard
                        and extended community attributes are sent to a neighbor";
        } // END of no-send-community definition.

        leaf no-send-community-type  {
            type  ipi-bgp-types:bgp_send_commu_type_t;
            description "This attribute specifies the type of community attribute to be sent to
                        a BGP neighbor.";
        } // END of no-send-community-type definition.

        leaf neighbor-attribute-unchanged  {
            type  ipi-bgp-types:bgp_attribute_unchanged_type_t;
            description "This attribute advertises unchanged BGP AS path, next hop and med to
                        the specified neighbor.";
        } // END of neighbor-attribute-unchanged definition.

        leaf orf-prefix-capability  {
            type  ipi-bgp-types:bgp_orf_prefix_type_t;
            description "This attribute enables Outbound Router Filtering (ORF), and advertise
                        the ORF capability to its neighbors. The ORFs send and receive
                        capabilities to lessen the number of updates exchanged between
                        neighbors. By filtering updates, this option minimizes generating and
                        processing of updates. The two routers exchange updates to maintain
                        the ORF for each router.";
        } // END of orf-prefix-capability definition.

        leaf peer-allow-ebgp-vpn  {
            if-feature feature-list:HAVE_VRF;
            type  empty;
            description "This attribute allows an eBGP neighbor to be a VPN peer. By default,
                        BGP VPN functionality is allowed only for iBGP peers. Using the
                        peer-allow-ebgp-vpn attribute allows the VPN connection to be
                        established to an eBGP peer.";
        } // END of peer-allow-ebgp-vpn definition.

        leaf allow-as-number  {
            type  uint32 {
                 range "1..10"  {
                    description "1..10: Supported range 1 - 10";
                 }
            }
            default "3";
            description "This attribute advertises prefixes (routes) even when the source of
                        the prefixes is from the same Autonomous System (AS) number for
                        specified address-family.
                        Use this attribute in a scenario where two routers at different
                        locations use the same Autonomous System number and are connected via
                        an ISP. Once prefixes arrive from one branch at the ISP, they are
                        tagged with the customers AS number. By default, when the ISP passes
                        the prefixes to the other router, the prefixes are dropped if the
                        other router uses the same AS number. Use this attribute to advertise
                        the prefixes at the other side. Control the number of times an AS
                        number is advertised by specifying a number.
                        In a hub and spoke configuration in a VPN, a PE (Provider Edge) router
                        advertises all prefixes containing duplicate AS numbers. Use this
                        attribute to configure two VRFs on each PE router to receive and
                        advertise prefixes. One of the VRFs receives prefixes with AS numbers
                        from all PE routers and then advertises them to neighboring PE
                        routers. The other VRF receives prefixes with AS numbers from the CE
                        (Customer Edge) router and advertises them to all PE routers in the
                        hub and spoke configuration.";
        } // END of allow-as-number definition.

        leaf capability-graceful-restart  {
            // when " ipi-bgp-peer:peers/peer/address-families/address-family/config/activate ";
            type  empty;
            description "This attribute configures the router to advertise the Graceful Restart
                        Capability to the neighbors. This configuration indicates that the BGP
                        speaker has the ability to preserve its forwarding state for the
                        address family when BGP restarts. Use this attribute to advertise to
                        the neighbor routers the capability of graceful restart.";
        } // END of capability-graceful-restart definition.

        leaf extended-nexthop-encode  {
            // when " ipi-bgp-peer:peers/peer/address-families/address-family/config/activate ";
            type  empty;
            description "A BGP speaker that wishes to advertise an IPv6 next hop for IPv4 NLRI
                        for VPN-IPv4 NLRI to a BGP peer as per this specification MUST use the
                        Capability Advertisement procedures defined with the Extended Next Hop
                        Encoding capability to determine whether its peer supports this for
                        the NLRI AFI/SAFI pair(s) of interest.";
        } // END of extended-nexthop-encode definition.

        leaf mapped-peer-group-tag-af  {
            // when " ipi-bgp-peer:peers/peer/address-families/address-family/config/activate ";
            type  string {
                length "1..1965";
                pattern "[^?' =,>|]+";
            }
            description "BGP peer group name. Adds  a neighbor to an existing peer group.
                        Neighbors with the same update policies are grouped into peer groups.
                        This facilitates the updates of various policies, such as distribute
                        and filter lists. The peer group is then configured easily with any of
                        the neighbor attributes. Any changes made to the peer group affect all
                        members.";
        } // END of mapped-peer-group-tag-af definition.

        leaf unsuppress-route-map-name  {
            type  string {
                length "1..1965";
                pattern "[^?' =,>|]+";
            }
            description "unsuppress map name. This attribute is used to selectively leak
                        more-specific routes to a particular neighbor.";
        } // END of unsuppress-route-map-name definition.

    } // END of bgp-address-family-peer-config definition.
    grouping bgp-address-family-maximum-prefixes-config {
        description
            "Configuration parameters for peer maximum prefixes";
        leaf prefix-count  {
            type  uint32 {
                 range "1..4294967295"  {
                    description "1..4294967295: Supported range 1 - 4294967295";
                 }
            }
            description "This attribute specifies number of prefixes that a BGP router is
                        allowed to receive from a neighbor. When the maximum-prefix-warning
                        attribute is not set and extra prefixes are received, the router ends
                        the peering.";
        } // END of prefix-count definition.

        leaf stop-update  {
            type  empty;
            description "Stop installing the routes when limit is exceeded.";
        } // END of stop-update definition.

        leaf maximum-prefix-warning  {
            type  empty;
            description "This attribute when enabled only give warning message when limit is
                        exceeded. When it is not set and extra prefixes are received, the
                        router ends the peering.";
        } // END of maximum-prefix-warning definition.

        leaf threshold-percentage  {
            type  uint8 {
                 range "1..100"  {
                    description "1..100: Supported range 1 - 100";
                 }
            }
            default "75";
            description "Threshold-value in percen. This attribute controls the number of
                        prefixes that can be received from a neighbor. This attribute allows
                        the configuration of a specified number of prefixes that a BGP router
                        is allowed to receive from a neighbor. When the maximum-prefix-warning
                        attribute is not set and extra prefixes are received, the router ends
                        the peering.";
        } // END of threshold-percentage definition.

        leaf warning-only  {
            type  empty;
            description "Throw warning if exceeds threshold-value";
        } // END of warning-only definition.

    } // END of bgp-address-family-maximum-prefixes-config definition.
    grouping bgp-distribute-list-filter-config {
        description
            "Grouping for BGP distribute list filter configuration";
        leaf access-list-identifier  {
            type  string {
                length "1..1965";
                pattern "[^?' =,>|]+";
            }
            mandatory true;
            description "Access List information";
        } // END of access-list-identifier definition.

        leaf filter-direction  {
            type  ipi-bgp-types:bgp_distribute_list_direction_t;
            description "This attribute sets the direction of the filter (0=FILTER_IN
                        |1=FILTER_OUT). This attribute is used to filter route updates from a
                        particular BGP neighbor for specified address-family. Only one
                        distribute-list per BGP neighbor.";
        } // END of filter-direction definition.

    } // END of bgp-distribute-list-filter-config definition.
    grouping bgp-as-list-filter-config {
        description
            "Grouping for BGP AS list filter configuration";
        leaf as-access-list-identifier  {
            type  string {
                length "1..1965";
                pattern "[^?' =,>|]+";
            }
            mandatory true;
            description "Access-list number. This attribute sets a BGP filter. This attribute
                        specifies an access list filter on updates based on the BGP autonomous
                        system paths. Each filter is an access list based on regular
                        expressions";
        } // END of as-access-list-identifier definition.

        leaf as-list-direction  {
            type  ipi-bgp-types:bgp_distribute_list_direction_t;
            description "Direction of the filter (0=FILTER_IN |1=FILTER_OUT)";
        } // END of as-list-direction definition.

    } // END of bgp-as-list-filter-config definition.
    grouping bgp-prefix-list-filter-config {
        description
            "Grouping for BGP prefix list filter configuration";
        leaf prefix-list-name  {
            type  string {
                length "1..1965";
                pattern "[^?' =,>|]+";
            }
            mandatory true;
            description "This attribute specify a prefix list for filtering BGP advertisements
                        for specified address-family. Filtering by prefix list matches the
                        prefixes of routes with those listed in the prefix list. If there is a
                        match, the route is used. An empty prefix list permits all prefixes.
                        If a given prefix does not match any entries of a prefix list, the
                        route is denied access. When multiple entries of a prefix list match a
                        prefix, the entry with the smallest sequence number is considered to
                        be a real match.
                        The router begins the search at the top of the prefix list, with the
                        sequence number 1. Once a match or deny occurs, the router does not
                        need to go through the rest of the prefix list. For efficiency the
                        most common matches or denies are listed at the top.";
        } // END of prefix-list-name definition.

        leaf prefix-filter-direction  {
            type  ipi-bgp-types:bgp_distribute_list_direction_t;
            description "Direction of the filter (0=FILTER_IN |1=FILTER_OUT)";
        } // END of prefix-filter-direction definition.

    } // END of bgp-prefix-list-filter-config definition.
    grouping bgp-route-map-filter-config {
        description
            "Grouping for BGP route map filter configuration";
        leaf route-map-name  {
            type  string {
                length "1..63";
                pattern "[^?' =,>|]+";
            }
            mandatory true;
            description "Use this attribute to apply a route map to incoming or outgoing
                        routes. This attribute filters updates and modifies attributes. A
                        route map is applied to inbound or outbound updates. Only the routes
                        that pass the route map are sent or accepted in updates.";
        } // END of route-map-name definition.

        leaf route-map-direction  {
            type  ipi-bgp-types:bgp_distribute_list_direction_t;
            description "Use this attribute to configure the direction in which the route map
                        is to be applied. Direction of the filter (0=FILTER_IN |1=FILTER_OUT)";
        } // END of route-map-direction definition.

    } // END of bgp-route-map-filter-config definition.
    grouping bgp-password-config {
        description
            "Configuration parameters BGP address family VRF password";
        leaf password  {
            if-feature feature-list:HAVE_TCP_MD5SIG;
            type  ipi-bgp-types:bgp_md5_password_t {
                length "1..1965";
            }
            description "Enable authentication-key on this interface to be used in message
                        digest5 (MD5) authentication on a TCP connection between two BGP
                        peers. Configuring MD5 authentication between two BGP peers, means
                        that each segment sent on the TCP connection between the peers is
                        verified. MD5 authentication must be configured with the same password
                        on both BGP peers; otherwise, the connection between them will not be
                        established.";
        } // END of password definition.

        leaf auth-key-encrypt  {
            type  ipi-bgp-types:bgp_md5_t;
            mandatory true;
            description "Use this attribute to configure the authentication key to specify if
                        the password is to be encrypted or not.";
        } // END of auth-key-encrypt definition.

    } // END of bgp-password-config definition.
    grouping bgp-peer-timers-config {
        description
            "attributes having bgp timer configuration";
        leaf keep-alive  {
            type  uint16 {
                 range "0..65535"  {
                    description "0..65535: Supported range 0 - 65535";
                 }
            }
            mandatory true;
            description "Use this attribute to globally set or reset the keepalive values for
                        all the neighbors";
        } // END of keep-alive definition.

        leaf hold-time  {
            type  uint16 {
                 range "0..65535"  {
                    description "0..65535: Supported range 0 - 65535";
                 }
            }
            mandatory true;
            description "Use this attribute to globally set or reset the holdtime values for
                        all the neighbors.";
        } // END of hold-time definition.

    } // END of bgp-peer-timers-config definition.
    grouping bgp-peer-ebgp-multhop-config {
        description
            "attributes having EBGP multihop configuration";
        leaf maximum-hop-count  {
            type  uint8 {
                 range "1..255"  {
                    description "1..255: Supported range 1 - 255";
                 }
            }
            description "Use this attribute to configure the the maximum hop count for EBGP
                        multihop.";
        } // END of maximum-hop-count definition.

        leaf enabled  {
            type  empty;
            mandatory true;
            description "Use this attribute to accept and attempt BGP connections to external
                        peers on indirectly connected networks. Multihop is not established if
                        the only route to the multihop peer is a default route. This avoids
                        loop formation.";
        } // END of enabled definition.

    } // END of bgp-peer-ebgp-multhop-config definition.
    grouping bgp-peer-local-as-config {
        description
            "attributes having Local-as configuration";
        leaf peer-local-as  {
            type  uint32 {
                 range "1..4294967295"  {
                    description "1..4294967295: Supported range 1 - 4294967295";
                 }
            }
            description "Specifies an AS (autonomous system) number to use with BGP neighbor.";
        } // END of peer-local-as definition.

        leaf no-prepend-local-as  {
            type  empty;
            description "Use this attribute to stop the alternate ASN from being prepended when
                        receiving routes from EBGP bgp neighbor.";
        } // END of no-prepend-local-as definition.

        leaf replace-local-as  {
            type  empty;
            description "Use this attribute to stop the alternate ASN from being prepended when
                        sending routes to EBGP bgp neighbor.";
        } // END of replace-local-as definition.

    } // END of bgp-peer-local-as-config definition.
    grouping bgp-address-family-table-map-config {
        description
            "Table map configuration for  BGP Address Family";
        leaf map-name  {
            if-feature feature-list:HAVE_BGP_TABLE_MAP;
            type  string {
                length "1..63";
                pattern "[^?' =,>|]+";
            }
            mandatory true;
            description "Use this attribute to enable or disable suppression/modification of
                        incoming BGP updates to IP RIB/FIB table installation.
                        In a dedicated route reflector, all the routes it receives may not be
                        required to be stored or only few selected routes need to be stored,
                        because it may not lie in the data path.
                        Table maps are particularly useful to attain this restriction.
                        When map-name attribute is set, the route map referenced in the
                        map-name attribute shall be used to set certain properties (such as
                        the traffic index) of the routes for installation into the RIB. The
                        route is always downloaded, regardless of whether it is permitted or
                        denied by the route map.";
        } // END of map-name definition.

        leaf table-map-filter  {
            // when " ipi-bgp-address-family:address-families/address-family/table-map/config/map-name ";
            if-feature feature-list:HAVE_BGP_TABLE_MAP;
            type  boolean;
            description "When tableMapFilter attribute is given in the table map attribute, the
                        route map referenced is used to control whether a BGP route is to be
                        downloaded to the IP RIB (hence the filter). A BGP route is not
                        downloaded to the RIB if it is denied by the route map.";
        } // END of table-map-filter definition.

    } // END of bgp-address-family-table-map-config definition.
    grouping table-map-top {
        description
            "Grouping for attributes related to Table map";
        container table-map {
            if-feature feature-list:HAVE_BGP_TABLE_MAP;
            description
                "Container for Attributes related to Table map";
            container config {
                presence "To configure table map";
                description
                    "Configuration attributes related to Table map";
                uses bgp-address-family-table-map-config;
            } // END of config-container definition.
            container state {
                config false;
                description
                    "Operational state data related to Distance for routes";
                uses bgp-address-family-table-map-config;
            } // END of state-container definition.
        } // END of table-map-container definition.
    } // END of table-map-top definition.
    grouping bgp-peer-run-time-attribute-prefix-state {
        description
            "Runtime parameters for BGP peer prefix";
        leaf entry-sequence  {
            type  int32;
            config false;
            description "Prefix sequence number";
        } // END of entry-sequence definition.

        leaf entry-type  {
            type  ipi-bgp-types:bgp_prefix_entry_type_t;
            config false;
            description "Prefix type 1(no_match), 2(deny), 3(permit)";
        } // END of entry-type definition.

        leaf entry-max-length  {
            type  int32;
            config false;
            description "Maximum prefix length to be matched";
        } // END of entry-max-length definition.

        leaf entry-min-length  {
            type  int32;
            config false;
            description "Minimum prefix length to be matched";
        } // END of entry-min-length definition.

        leaf prefix-length  {
            type  int32;
            config false;
            description "Prefix length";
        } // END of prefix-length definition.

    } // END of bgp-peer-run-time-attribute-prefix-state definition.
    grouping bgp-peer-run-time-attribute-index-state {
        description
            "Runtime parameters for BGP peer index";
        leaf peer-index  {
            type  int32;
            config false;
            description "Peer index";
        } // END of peer-index definition.

        leaf offset  {
            type  int32;
            config false;
            description "Peer offset";
        } // END of offset definition.

        leaf mask  {
            type  string {
                length "1..1965";
                pattern "[^?' =,>|]+";
            }
            config false;
            description "Peer mask";
        } // END of mask definition.

    } // END of bgp-peer-run-time-attribute-index-state definition.
    grouping bgp-peer-run-time-counters-state {
        description
            "Runtime parameters for BGP peers";
        leaf keepalive-in-messages  {
            type  int32;
            config false;
            description "Keepalive input count";
        } // END of keepalive-in-messages definition.

        leaf keepalive-out-messages  {
            type  int32;
            config false;
            description "Keepalive output count";
        } // END of keepalive-out-messages definition.

        leaf open-messages-in  {
            type  int32;
            config false;
            description "Open message input count";
        } // END of open-messages-in definition.

        leaf open-messages-out  {
            type  int32;
            config false;
            description "Open message output count";
        } // END of open-messages-out definition.

        leaf as-path-count  {
            type  int32;
            config false;
            description "BGP AS-PATH entries";
        } // END of as-path-count definition.

        leaf as-path-extended-count  {
            type  int32;
            config false;
            description "BGP AS-PATH entries";
        } // END of as-path-extended-count definition.

        leaf received-packet-count  {
            type  int32;
            config false;
            description "Received messages";
        } // END of received-packet-count definition.

        leaf packet-in-queue  {
            type  int32;
            config false;
            description "messages queued to be processed from the neighbor";
        } // END of packet-in-queue definition.

        leaf packet-out-queue  {
            type  int32;
            config false;
            description "messages queued to be sent to the neighbor";
        } // END of packet-out-queue definition.

        leaf sent-packet-count  {
            type  int32;
            config false;
            description "Sent messages";
        } // END of sent-packet-count definition.

        leaf refresh-received-packet-count  {
            type  int32;
            config false;
            description "Route Refresh input count";
        } // END of refresh-received-packet-count definition.

        leaf refresh-sent-packet-count  {
            type  int32;
            config false;
            description "Route Refresh output count";
        } // END of refresh-sent-packet-count definition.

    } // END of bgp-peer-run-time-counters-state definition.
    grouping bgp-peer-run-time-orf-state {
        description
            "Runtime ORF parameters for BGP peers";
        leaf orf-prefix-string  {
            type  boolean;
            config false;
            description "Outbound Route Filter (ORF)";
        } // END of orf-prefix-string definition.

        leaf orf-prefix-send  {
            type  string {
                length "1..1965";
                pattern "[^?' =,>|]+";
            }
            config false;
            description "Outbound Route Filter (ORF) sent";
        } // END of orf-prefix-send definition.

        leaf orf-prefix-count  {
            type  string {
                length "1..1965";
                pattern "[^?' =,>|]+";
            }
            config false;
            description "Outbound Route Filter (ORF) received entries";
        } // END of orf-prefix-count definition.

        leaf orf-wait-refresh  {
            type  boolean;
            config false;
            description "First update is deferred until ORF or ROUTE-REFRESH is received";
        } // END of orf-wait-refresh definition.

    } // END of bgp-peer-run-time-orf-state definition.
    grouping bgp-peer-run-time-attribute-state {
        description
            "Runtime parameters for BGP peers";
        leaf dynamic-peer-address  {
            type  ipi-bgp-types:bgp_ip_addr_t;
            config false;
            description "BGP dynamic peer address";
        } // END of dynamic-peer-address definition.

        leaf max-paths-ibgp  {
            type  int16;
            config false;
            description "ECMP multipath ibgp maxpath";
        } // END of max-paths-ibgp definition.

        leaf configured-max-paths-ebgp  {
            type  int16;
            config false;
            description "Configured ebgp ECMP multipath";
        } // END of configured-max-paths-ebgp definition.

        leaf max-paths-ebgp  {
            type  int16;
            config false;
            description "ECMP multipath ebgp maxpath";
        } // END of max-paths-ebgp definition.

        leaf configured-max-paths-ibgp  {
            type  int16;
            config false;
            description "Configured ibgp ECMP multipath";
        } // END of configured-max-paths-ibgp definition.

        leaf max-paths-eibgp  {
            type  int16;
            config false;
            description "ECMP multipath eibgp maxpath";
        } // END of max-paths-eibgp definition.

        leaf configured-max-paths-eibgp  {
            type  int16;
            config false;
            description "Configured eibgp ECMP multipath";
        } // END of configured-max-paths-eibgp definition.

        leaf community-count  {
            type  int32;
            config false;
            description "bgp community count";
        } // END of community-count definition.

        leaf confederation-id-check  {
            type  boolean;
            config false;
            description "Check if AS is part of the confed";
        } // END of confederation-id-check definition.

        leaf peer-and-extended-asn-capability  {
            type  ipi-bgp-types:bgp_adv_rcv_type_t;
            config false;
            description "4-Octet ASN Capability: 1(advertise), 2(receive), 3(both advertise and
                        receive)";
        } // END of peer-and-extended-asn-capability definition.

        leaf address-family-capability  {
            type  ipi-bgp-types:bgp_adv_rcv_type_t;
            config false;
            description "Address family IPv4 Unicast: 1(advertise), 2(receive),3(both advertise
                        and receive)";
        } // END of address-family-capability definition.

        leaf ipv6-next-hop-global  {
            type  inet:ipv6-address;
            config false;
            description "Nexthop global";
        } // END of ipv6-next-hop-global definition.

        leaf ipv6-next-hop-local  {
            type  inet:ipv6-address;
            config false;
            description "Nexthop local";
        } // END of ipv6-next-hop-local definition.

        leaf remote-port  {
            type  int32;
            config false;
            description "Peer remote port";
        } // END of remote-port definition.

        leaf remote-address  {
            type  ipi-bgp-types:bgp_hostname_t;
            config false;
            description "Peer remote address";
        } // END of remote-address definition.

        leaf local-host  {
            type  ipi-bgp-types:bgp_hostname_t;
            config false;
            description "Peer Local host";
        } // END of local-host definition.

        leaf ipv4-next-hop  {
            type  inet:ipv4-address;
            config false;
            description "Nexthop";
        } // END of ipv4-next-hop definition.

        leaf local-port  {
            type  int32;
            config false;
            description "Peer local port";
        } // END of local-port definition.

        leaf default-information-originate  {
            type  boolean;
            config false;
            description "Default information originate";
        } // END of default-information-originate definition.

        leaf inbound-path-policy  {
            type  boolean;
            config false;
            description "Inbound path policy configured";
        } // END of inbound-path-policy definition.

        leaf outbound-path-policy  {
            type  boolean;
            config false;
            description "Outbound path policy configured";
        } // END of outbound-path-policy definition.

        leaf default-originate-information-sent  {
            type  cml-data-types:cml_line_t {
                length "1..1965";
            }
            config false;
            description "default sent";
        } // END of default-originate-information-sent definition.

        leaf graceful-restart  {
            type  ipi-bgp-types:bgp_adv_rcv_type_t;
            config false;
            description "Graceful restart-advertised/received";
        } // END of graceful-restart definition.

        leaf address-family-dependent-capability  {
            type  boolean;
            config false;
            description "AF-dependant capabilities";
        } // END of address-family-dependent-capability definition.

        leaf peer-address-family-table-version  {
            type  int32;
            config false;
            description "neighbor version";
        } // END of peer-address-family-table-version definition.

        leaf address-family-table-version  {
            type  int32;
            config false;
            description "BGP table version";
        } // END of address-family-table-version definition.

        leaf forward-status-preserve  {
            type  string {
                length "1..1965";
                pattern "[^?' =,>|]+";
            }
            config false;
            description "Graceful restart:Forwarding states are being preserved";
        } // END of forward-status-preserve definition.

        leaf orf-type-prefix  {
            type  cml-data-types:cml_line_t {
                length "1..1965";
            }
            config false;
            description "Outbound Route Filter (ORF) type Prefix-list";
        } // END of orf-type-prefix definition.

        leaf orf-type-prefix-send-mode  {
            type  ipi-bgp-types:bgp_adv_rcv_type_t;
            config false;
            description "ORF Send-mode advertised and received";
        } // END of orf-type-prefix-send-mode definition.

        leaf orf-type-prefix-receive-mode  {
            type  ipi-bgp-types:bgp_adv_rcv_type_t;
            config false;
            description "ORF Receive-mode advertised and received";
        } // END of orf-type-prefix-receive-mode definition.

        leaf orf-type-prefix-old  {
            type  cml-data-types:cml_line_t {
                length "1..1965";
            }
            config false;
            description "Outbound Route Filter (ORF) type Prefix-list";
        } // END of orf-type-prefix-old definition.

        leaf orf-type-prefix-send-mode-old  {
            type  ipi-bgp-types:bgp_adv_rcv_type_t;
            config false;
            description "peer afi orf cap Send-Mode";
        } // END of orf-type-prefix-send-mode-old definition.

        leaf orf-type-prefix-receive-mode-old  {
            type  ipi-bgp-types:bgp_adv_rcv_type_t;
            config false;
            description "peer afi orf cap Receive-mode";
        } // END of orf-type-prefix-receive-mode-old definition.

        leaf prefix-count  {
            type  int32;
            config false;
            description "accepted prefixes";
        } // END of prefix-count definition.

        leaf send-prefix-count  {
            type  int32;
            config false;
            description "announced prefixes";
        } // END of send-prefix-count definition.

        leaf flag-shut-down  {
            type  ipi-bgp-types:bgp_peerflag_shutdown_t;
            config false;
            description "peer flag shutdown status: 1(Idle), 2(Connect), 3(Active),
                        4(Opensent), 5(Openconfirm), 6(Established), 7(Idle Admin), 8(Idle
                        PfxCt), 9(Idle G-shut)";
        } // END of flag-shut-down definition.

        leaf count  {
            type  int32;
            config false;
            description "peer count";
        } // END of count definition.

        leaf notify-info  {
            type  boolean;
            config false;
            description "BGP notify open error";
        } // END of notify-info definition.

        leaf notify-last-reset-time  {
            type  string {
                length "1..1965";
                pattern "[^?' =,>|]+";
            }
            config false;
            description "Last reset in week:day:hour:min:sec format string";
        } // END of notify-last-reset-time definition.

        leaf connection-type  {
            type  ipi-bgp-types:bgp_connection_type_t;
            config false;
            description "Connection: shared network, non shared network";
        } // END of connection-type definition.

        leaf next-connection-timer  {
            type  int32;
            config false;
            description "Next connect timer due in seconds";
        } // END of next-connection-timer definition.

        leaf connection-dropped-count  {
            type  int32;
            config false;
            description "BGP state drop count";
        } // END of connection-dropped-count definition.

        leaf graceful-restart-status  {
            type  string {
                length "1..1965";
                pattern "[^?' =,>|]+";
            }
            config false;
            description "Graceful Restart Status";
        } // END of graceful-restart-status definition.

        leaf graceful-restart-time  {
            type  int32;
            config false;
            description "Remote restart-time in sec";
        } // END of graceful-restart-time definition.

        leaf bgp-established-up-time  {
            type  string {
                length "1..1965";
                pattern "[^?' =,>|]+";
            }
            config false;
            description "Indicated up-time for the neighbor.If the uptime is less than a day
                        then the format is hour:min:sec.If the uptime is less than a week then
                        format is day:hour:min.If the uptime is more than a week then the
                        format is week:day:hour";
        } // END of bgp-established-up-time definition.

        leaf last-read-time  {
            type  string {
                length "1..1965";
                pattern "[^?' =,>|]+";
            }
            config false;
            description "Indicated last update received time from the peer.If the time is less
                        than a day then the format is hour:min:sec.If the time is less than a
                        week then format is day:hour:min.If the time is more than a week then
                        the format is week:day:hour";
        } // END of last-read-time definition.

        leaf link-type  {
            type  ipi-bgp-types:bgp_link_type_t;
            config false;
            description "Link type: internal, external";
        } // END of link-type definition.

        leaf ebgp-hop-away-count  {
            type  int32;
            config false;
            description "External BGP neighbor may be up to given hops away.";
        } // END of ebgp-hop-away-count definition.

        leaf router-id  {
            type  inet:ipv4-address;
            config false;
            description "peer router id";
        } // END of router-id definition.

        leaf advertisement-interval  {
            type  int32;
            config false;
            description "Minimum time between advertisement runs in seconds";
        } // END of advertisement-interval definition.

        leaf calculated-hold-time  {
            type  int32;
            config false;
            description "hold time in seconds";
        } // END of calculated-hold-time definition.

        leaf calculated-keepalive  {
            type  int32;
            config false;
            description "keepalive interval in seconds";
        } // END of calculated-keepalive definition.

        leaf dynamic-capability  {
            type  cml-data-types:cml_line_t {
                length "1..1965";
            }
            config false;
            description "Advertised capability";
        } // END of dynamic-capability definition.

        leaf route-refresh-capability  {
            type  ipi-bgp-types:bgp_route_refresh_cap_type_t;
            config false;
            description "Route Refresh";
        } // END of route-refresh-capability definition.

        leaf no-interface-binding  {
            type  boolean;
            config false;
            description "No Interfaces bound to BGP Instance";
        } // END of no-interface-binding definition.

        leaf additional-path-receive-capability  {
            if-feature feature-list:HAVE_BGP_ADD_PATH;
            type  ipi-bgp-types:bgp_capability_type_t;
            config false;
            description "Add-Path Receive Capability";
        } // END of additional-path-receive-capability definition.

        leaf additional-path-send-capability  {
            if-feature feature-list:HAVE_BGP_ADD_PATH;
            type  ipi-bgp-types:bgp_capability_type_t;
            config false;
            description "Add-Path Send Capability";
        } // END of additional-path-send-capability definition.

        leaf capability-ipv4-unicast  {
            type  ipi-bgp-types:bgp_capability_type_t;
            config false;
            description "IPv4 Unicast neighbour Capability";
        } // END of capability-ipv4-unicast definition.

        leaf capability-label-unicast  {
            if-feature feature-list:HAVE_BGP_LU;
            type  ipi-bgp-types:bgp_capability_type_t;
            config false;
            description "Label Unicast neighbour Capability";
        } // END of capability-label-unicast definition.

        leaf capability-ipv4-multicast  {
            type  ipi-bgp-types:bgp_capability_type_t;
            config false;
            description "IPV4 Multicast neighbour Capability";
        } // END of capability-ipv4-multicast definition.

        leaf capability-vpnv4-unicast  {
            type  ipi-bgp-types:bgp_capability_type_t;
            config false;
            description "Vpnv4 Unicast neighbour Capability";
        } // END of capability-vpnv4-unicast definition.

        leaf capability-vpnv6-unicast  {
            type  ipi-bgp-types:bgp_capability_type_t;
            config false;
            description "Vpnv6 Unicast neighbour Capability";
        } // END of capability-vpnv6-unicast definition.

        leaf capability-rtfilter-unicast  {
            type  ipi-bgp-types:bgp_capability_type_t;
            config false;
            description "Route target filter Unicast neighbour Capability";
        } // END of capability-rtfilter-unicast definition.

        leaf capability-l2vpn-evpn  {
            type  ipi-bgp-types:bgp_capability_type_t;
            config false;
            description "L2vpn Evpn neighbour Capability";
        } // END of capability-l2vpn-evpn definition.

        leaf capability-ipv6-unicast  {
            type  ipi-bgp-types:bgp_capability_type_t;
            config false;
            description "Ipv6 Unicast neighbour Capability";
        } // END of capability-ipv6-unicast definition.

        leaf capability-ipv6-multicast  {
            type  ipi-bgp-types:bgp_capability_type_t;
            config false;
            description "Ipv6 Multicast neighbour Capability";
        } // END of capability-ipv6-multicast definition.

        leaf capability-ipv6-label-unicast  {
            type  ipi-bgp-types:bgp_capability_type_t;
            config false;
            description "Ipv6 Label Unicast neighbour Capability";
        } // END of capability-ipv6-label-unicast definition.

        leaf evpn-ad-route-count  {
            if-feature feature-list:HAVE_BGP_EVPN;
            type  uint32;
            config false;
            description "L2VPN EVPN Auto Discovery route count";
        } // END of evpn-ad-route-count definition.

        leaf evpn-mac-ip-route-count  {
            if-feature feature-list:HAVE_BGP_EVPN;
            type  uint32;
            config false;
            description "L2VPN EVPN MAC/IP route count";
        } // END of evpn-mac-ip-route-count definition.

        leaf evpn-inclusive-multicast-route-count  {
            if-feature feature-list:HAVE_BGP_EVPN;
            type  uint32;
            config false;
            description "L2VPN EVPN Inclusive Multicast route count";
        } // END of evpn-inclusive-multicast-route-count definition.

        leaf evpn-segment-route-count  {
            if-feature feature-list:HAVE_BGP_EVPN;
            type  uint32;
            config false;
            description "L2VPN EVPN ESI route count";
        } // END of evpn-segment-route-count definition.

        leaf evpn-ip-prefix-route-count  {
            if-feature feature-list:HAVE_BGP_EVPN;
            type  uint32;
            config false;
            description "L2VPN EVPN IP prefix route count";
        } // END of evpn-ip-prefix-route-count definition.

    } // END of bgp-peer-run-time-attribute-state definition.
    grouping bgp-address-family-vrf-peer-group-config {
        description
            "Configuration parameters common for BGP address family VRF peer groups";
        leaf peer-group-range  {
            type  ipi-bgp-types:bgp_peer_group_type_t;
            mandatory true;
            description "this attribute creates a Dynamic peer group for address family.
                        IPv4/IPv6 prefix range Must be specified to create dynamic peer group.";
        } // END of peer-group-range definition.

        leaf group-limit  {
            type  uint16 {
                 range "1..512"  {
                    description "1..512: Supported range 1 - 512";
                 }
            }
            description "Use this attribute to specify max number of peers in a dynamic
                        peer-group for address family";
        } // END of group-limit definition.

        leaf peer-group-tag  {
            type  string {
                length "1..1965";
                pattern "[^?' =,>|]+";
            }
            description "The peer address or Tag of a neighbor. This attribute adds a neighbor.
                        The specified neighbor when activated using the activate attribute
                        exchanges routing information.";
        } // END of peer-group-tag definition.

        leaf peer-as  {
            type  uint32 {
                 range "1..4294967295"  {
                    description "1..4294967295: Supported range 1 - 4294967295";
                 }
            }
            description "This attribute specifies a neighbors autonomous system number. If the
                        specified ASN matches the ASN number specified in the router bgp
                        global configuration, the neighbor is identified as internal. If the
                        ASN does not match, it is identified as external to the local AS.";
        } // END of peer-as definition.

        leaf source-identifier  {
            // when " ipi-bgp-address-family-vrf:address-family-vrfs/address-family-vrf/peer-groups/peer-group/config/peer-as ";
            type  string {
                length "1..1965";
                pattern "[^?' =,>|]+";
            }
            default "NULL";
            description "This attribute allows internal BGP sessions to use any operational
                        interface for TCP connections. Use this attribute in conjunction with
                        any specified interface on the router. The loopback interface is the
                        interface that is most commonly used with this attribute. The use of
                        loopback interface eliminates a dependency and BGP does not have to
                        rely on the availability of a particular interface for making TCP
                        connections.";
        } // END of source-identifier definition.

        leaf bgp-version  {
            // when " ipi-bgp-address-family-vrf:address-family-vrfs/address-family-vrf/peer-groups/peer-group/config/peer-as ";
            type  uint8;
            default "4";
            description "BGP Version. This attribute configures router to accept only a
                        particular BGP version. By default, the system uses BGP version 4 and
                        on request dynamically negotiates down to version 2. Using this
                        attribute disables the routers version-negotiation capability and
                        forces the router to use only a specified version with the neighbor.";
        } // END of bgp-version definition.

        leaf peer-connection-interval  {
            // when " ipi-bgp-address-family-vrf:address-family-vrfs/address-family-vrf/peer-groups/peer-group/config/peer-as ";
            type  uint32 {
                 range "1..65535"  {
                    description "1..65535: Supported range 1 - 65535";
                 }
            }
            default "1";
            description "Connect timer value. This attribute sets the timers for a specific BGP
                        neighbor. Keepalive messages are sent by a router to inform another
                        router that the BGP connection between the two is still active. The
                        keepalive interval is the period of time between each keepalive
                        message sent by the router. The holdtime interval is the time the
                        router waits to receive a keepalive message and if it does not receive
                        a message for this period it declares the neighbor dead.";
        } // END of peer-connection-interval definition.

        leaf enforce-multihop  {
            // when " ipi-bgp-address-family-vrf:address-family-vrfs/address-family-vrf/peer-groups/peer-group/config/peer-as ";
            type  empty;
            description "This attribute turns on the enforcement of eBGP neighbors perform
                        multihop.";
        } // END of enforce-multihop definition.

        leaf peer-shutdown  {
            // when " ipi-bgp-address-family-vrf:address-family-vrfs/address-family-vrf/peer-groups/peer-group/config/peer-as ";
            type  empty;
            description "This attribute disables a neighbor administratively.
                        Use this attribute to terminate any active session for a specified
                        neighbor and clear all related routing information. In case a peer
                        group is specified for shutdown, a large number of peering sessions
                        could be terminated.";
        } // END of peer-shutdown definition.

        leaf peer-shutdown-description  {
            // when " ipi-bgp-address-family-vrf:address-family-vrfs/address-family-vrf/peer-groups/peer-group/config/peer-as + ipi-bgp-address-family-vrf:address-family-vrfs/address-family-vrf/peer-groups/peer-group/config/peer-shutdown ";
            type  cml-data-types:cml_line_t {
                length "1..255";
            }
            description "Use this attribute to send shutdown communication message to inform
                        peer the reason for the shutdown of the BGP session.";
        } // END of peer-shutdown-description definition.

        leaf neighbor-passive  {
            // when " ipi-bgp-address-family-vrf:address-family-vrfs/address-family-vrf/peer-groups/peer-group/config/peer-as ";
            type  empty;
            description "Use this attribute to set a BGP neighbor as passive.";
        } // END of neighbor-passive definition.

        leaf connection-retry-interval  {
            // when " ipi-bgp-address-family-vrf:address-family-vrfs/address-family-vrf/peer-groups/peer-group/config/peer-as ";
            type  int32 {
                 range "1..65535"  {
                    description "1..65535: Supported range 1 - 65535";
                 }
            }
            default "120";
            description "Connect timer value. Sets the connection retry time for a specific BGP
                        neighbor.";
        } // END of connection-retry-interval definition.

        leaf enable-dynamic-capability  {
            // when " ipi-bgp-address-family-vrf:address-family-vrfs/address-family-vrf/peer-groups/peer-group/config/peer-as ";
            type  empty;
            description "Use this attribute to enable the dynamic capability for a specific
                        peer. This attribute allows a BGP speaker to advertise or withdraw an
                        address family capability to a peer in a non-disruptive manner.";
        } // END of enable-dynamic-capability definition.

        leaf min-route-advertisement-interval  {
            // when " ipi-bgp-address-family-vrf:address-family-vrfs/address-family-vrf/peer-groups/peer-group/config/peer-as ";
            type  uint32 {
                 range "0..65535"  {
                    description "0..65535: Supported range 0 - 65535";
                 }
            }
            description "Minimum route advertisement interval. Sets minimum interval between
                        the sending of BGP routing updates. To reduce the flapping of routes
                        to internet, a minimum advertisement interval is set, so that the BGP
                        routing updates are sent only per interval seconds. BGP dampening can
                        also be used to control the effects of flapping routes.";
        } // END of min-route-advertisement-interval definition.

        leaf peer-as-origin-interval  {
            // when " ipi-bgp-address-family-vrf:address-family-vrfs/address-family-vrf/peer-groups/peer-group/config/peer-as ";
            type  uint32 {
                 range "1..65535"  {
                    description "1..65535: Supported range 1 - 65535";
                 }
            }
            description "Time interval. This attribute adjust the interval of sending AS
                        origination routing updates. This attribute is used to change the
                        minimum interval between the sending of AS-origination routing
                        updates.";
        } // END of peer-as-origin-interval definition.

        leaf neighbor-as-override  {
            // when " ipi-bgp-address-family-vrf:address-family-vrfs/address-family-vrf/peer-groups/peer-group/config/peer-as ";
            type  empty;
            description "Use this attribute to configure a PE router to override the Autonomous
                        System Number (ASN) of a site with the ASN of a provider. BGP normally
                        ignores the routes from the same AS. However, this attribute is used
                        to override the customers ASN in BGP, so that the customer CE accepts
                        and installs routes from the same AS.
                        Typically, this attribute is used when Customer Edge (CE) routers have
                        the same ASN in some or all sites. As per BGP requirement, a BGP
                        speaker rejects a route that has the same ASN as itself, in the
                        AS_PATH attribute. Thus the CE routers having the same ASN do not
                        accept routes from each other. Set neighborAsOverrideAf attribute on
                        the PE router removes the CE neighbors ASN from the AS_PATH attribute
                        allowing CE routers with the same ASN to accept routes from each
                        other.";
        } // END of neighbor-as-override definition.

        leaf peer-description  {
            // when " ipi-bgp-address-family-vrf:address-family-vrfs/address-family-vrf/peer-groups/peer-group/config/peer-as ";
            type  cml-data-types:cml_line_t {
                length "1..1965";
            }
            description "Use this attribute to associate a description with a neighbor. This
                        attribute helps in identifying a neighbor quickly. It is useful for an
                        ISP that has multiple neighbor relationships.";
        } // END of peer-description definition.

        leaf peer-restart-time  {
            // when " ipi-bgp-address-family-vrf:address-family-vrfs/address-family-vrf/peer-groups/peer-group/config/peer-as ";
            if-feature feature-list:HAVE_RESTART;
            if-feature feature-list:HAVE_VRF;
            type  uint32 {
                 range "1..3600"  {
                    description "1..3600: Supported range 1 - 3600";
                 }
            }
            description "This attribute sets a different restart-time other than the global
                        restart-time. This attribute takes precedence over the restart-time
                        value specified using the graceful-restart-set attribute. The
                        restart-time value is the maximum time that a graceful-restart
                        neighbor waits to come back up after a restart. The default value is
                        120 seconds.";
        } // END of peer-restart-time definition.

        leaf graceful-shut  {
            // when " ipi-bgp-address-family-vrf:address-family-vrfs/address-family-vrf/peer-groups/peer-group/config/peer-as ";
            type  empty;
            description "Use this attribute to start a graceful shutdown for the BGP session of
                        the specified BGP neighbor. The BGP session for this neighbor is shut
                        down after the graceful shutdown timer expires.
                        If there is no alternate path available for traffic to flow prior the
                        actual shutdown of the BGP session, this path is made available for 60
                        seconds or for configured time after which the path is no longer
                        available and traffic is dropped.";
        } // END of graceful-shut definition.

        leaf graceful-shut-timer  {
            // when " ipi-bgp-address-family-vrf:address-family-vrfs/address-family-vrf/peer-groups/peer-group/config/peer-as ";
            type  uint32 {
                 range "10..65535"  {
                    description "10..65535: Supported range 10 - 65535";
                 }
            }
            description "Use this attribute to configure the value of the graceful shutdown
                        timer. After the timer expires, the BGP session initiated for graceful
                        shutdown is shut down.";
        } // END of graceful-shut-timer definition.

        leaf enable-peer-bfd  {
            // when " ipi-bgp-address-family-vrf:address-family-vrfs/address-family-vrf/peer-groups/peer-group/config/peer-as + !ipi-bgp-address-family-vrf:address-family-vrfs/address-family-vrf/peer-groups/peer-group/config/enable-peer-bfd-multihop ";
            if-feature feature-list:HAVE_BFD;
            type  empty;
            description "Enable bidirectional forwarding detection (BFD) for the BGP peer";
        } // END of enable-peer-bfd definition.

        leaf enable-peer-bfd-multihop  {
            // when " !ipi-bgp-address-family-vrf:address-family-vrfs/address-family-vrf/peer-groups/peer-group/config/enable-peer-bfd ";
            if-feature feature-list:HAVE_BFD;
            type  empty;
            description "Enable bidirectional forwarding detection (BFD) for the BGP peer with
                        multihop";
        } // END of enable-peer-bfd-multihop definition.

        leaf enable-ext-opt-param-len  {
            // when " ipi-bgp-address-family-vrf:address-family-vrfs/address-family-vrf/peer-groups/peer-group/config/peer-as ";
            type  empty;
            description "Use this attribute for a specific peer to encode extended optional
                        parameter length.";
        } // END of enable-ext-opt-param-len definition.

        leaf tcp-adjust-mss  {
            // when " ipi-bgp-address-family-vrf:address-family-vrfs/address-family-vrf/peer-groups/peer-group/config/peer-as ";
            type  uint16 {
                 range "40..1440"  {
                    description "40..1440: Supported range 40 - 1440";
                 }
            }
            description "Use this attribute to set the BGP TCP MSS value of a neighbor.";
        } // END of tcp-adjust-mss definition.

    } // END of bgp-address-family-vrf-peer-group-config definition.
    grouping bgp-address-family-peer-group-vrf-config {
        description
            "Configuration parameters common for peer group VRFs";
        leaf bgp-port  {
            // when " ipi-bgp-address-family-vrf:address-family-vrfs/address-family-vrf/peer-groups/peer-group/config/activate ";
            type  uint16 {
                 range "0..65535"  {
                    description "0..65535: Supported range 0 - 65535";
                 }
            }
            default "179";
            description "The BGP port number of a neighbor";
        } // END of bgp-port definition.

        leaf activate  {
            type  empty;
            description "Activate/Deactivate neighbor. This attribute enables or disables the
                        exchange of AF information with a neighboring router.";
        } // END of activate definition.

        leaf default-peer-route-map-name  {
            type  empty;
            description "This attribute allows a BGP local router to send the default route
                        0.0.0.0 to a neighbor for use as a default route for specified
                        address-family.";
        } // END of default-peer-route-map-name definition.

        leaf peer-route-map-orig-name  {
            type  string {
                length "1..63";
                pattern "[^?' =,>|]+";
            }
            description "This attribute configures route map to be used for a BGP local router
                        to send the default route 0.0.0.0 to a neighbor for use as a default
                        route for specified address-family. This attribute can be used with
                        standard or extended access lists.";
        } // END of peer-route-map-orig-name definition.

        leaf weight  {
            // when " ipi-bgp-address-family-vrf:address-family-vrfs/address-family-vrf/peer-groups/peer-group/config/activate ";
            type  uint16 {
                 range "0..65535"  {
                    description "0..65535: Supported range 0 - 65535";
                 }
            }
            default "0";
            description "This attribute specifies a weight value, for specified address-family,
                        to all routes learned from a neighbor for specified address-family.
                        The route with the highest weight gets preference when the same prefix
                        is learned from more than one peer. Unlike the local-preference
                        attribute, the weight attribute is relevant only to the local router.
                        When the weight is set for a peer group, all members of the peer group
                        get the same weight. This attribute can also be used to assign a
                        different weight to an individual peer-group member. When an
                        individually-configured weight of a peer-group member is removed, its
                        weight is reset to its peer groups weight.";
        } // END of weight definition.

        leaf flowspec-validation-disable  {
            // when " ipi-bgp-address-family-vrf:address-family-vrfs/address-family-vrf/peer-groups/peer-group/config/activate ";
            if-feature feature-list:HAVE_BGP_FLOWSPEC;
            type  empty;
            description "This attribute specifies if FLOWSPEC validiation should be disabled
                        for a specific peer";
        } // END of flowspec-validation-disable definition.

        leaf peer-route-reflector  {
            // when " ipi-bgp-address-family-vrf:address-family-vrfs/address-family-vrf/peer-groups/peer-group/config/activate ";
            type  empty;
            description "This attribute configures the router as a BGP route reflector and
                        configure the specified neighbor as its client for specified
                        address-family.
                        Route reflectors are a solution for the explosion of iBGP peering
                        within an autonomous system. By route reflection the number of iBGP
                        peers within an AS is reduced. Use this attribute to configure the
                        local router as the route reflector and specify neighbors as its
                        client. An AS can have more than one route reflector. One route
                        reflector treats the other route reflector as another iBGP speaker.";
        } // END of peer-route-reflector definition.

        leaf peer-remove-private-as  {
            // when " ipi-bgp-address-family-vrf:address-family-vrfs/address-family-vrf/peer-groups/peer-group/config/activate ";
            type  empty;
            description "This attribute removes the private Autonomous System (AS) number from
                        outbound updates. Private AS numbers are not advertised to the
                        Internet. This attribute is used with external BGP peers only. The
                        router removes the AS numbers only if the update includes private AS
                        numbers. If the update includes both private and public AS numbers,
                        the system treats it as an error.";
        } // END of peer-remove-private-as definition.

        leaf no-send-community  {
            // when " ipi-bgp-address-family-vrf:address-family-vrfs/address-family-vrf/peer-groups/peer-group/config/activate ";
            type  empty;
            description "This attribute specifies if a community attribute should be sent to a
                        BGP neighbor for specified address-family. The community attribute
                        groups destinations in a certain community and applies routing
                        decisions according to those communities. By default, both standard
                        and extended community attributes are sent to a neighbor";
        } // END of no-send-community definition.

        leaf no-send-community-type  {
            // when " ipi-bgp-address-family-vrf:address-family-vrfs/address-family-vrf/peer-groups/peer-group/config/activate ";
            type  ipi-bgp-types:bgp_send_commu_type_t;
            description "This attribute specifies the type of community attribute to be sent to
                        a BGP neighbor.";
        } // END of no-send-community-type definition.

        leaf neighbor-attribute-unchanged  {
            // when " ipi-bgp-address-family-vrf:address-family-vrfs/address-family-vrf/peer-groups/peer-group/config/activate ";
            type  ipi-bgp-types:bgp_attribute_unchanged_type_t;
            description "This attribute advertises unchanged BGP AS path, next hop and med to
                        the specified neighbor.";
        } // END of neighbor-attribute-unchanged definition.

        leaf orf-prefix-capability  {
            // when " ipi-bgp-address-family-vrf:address-family-vrfs/address-family-vrf/peer-groups/peer-group/config/activate ";
            type  ipi-bgp-types:bgp_orf_prefix_type_t;
            description "This attribute enables Outbound Router Filtering (ORF), and advertise
                        the ORF capability to its neighbors. The ORFs send and receive
                        capabilities to lessen the number of updates exchanged between
                        neighbors. By filtering updates, this option minimizes generating and
                        processing of updates. The two routers exchange updates to maintain
                        the ORF for each router.";
        } // END of orf-prefix-capability definition.

        leaf peer-allow-ebgp-vpn  {
            if-feature feature-list:HAVE_VRF;
            type  empty;
            description "This attribute allows an eBGP neighbor to be a VPN peer. By default,
                        BGP VPN functionality is allowed only for iBGP peers. Using the
                        peer-allow-ebgp-vpn attribute allows the VPN connection to be
                        established to an eBGP peer.";
        } // END of peer-allow-ebgp-vpn definition.

        leaf allow-as-number  {
            // when " ipi-bgp-address-family-vrf:address-family-vrfs/address-family-vrf/peer-groups/peer-group/config/activate ";
            type  uint32 {
                 range "1..10"  {
                    description "1..10: Supported range 1 - 10";
                 }
            }
            default "3";
            description "This attribute advertises prefixes (routes) even when the source of
                        the prefixes is from the same Autonomous System (AS) number for
                        specified address-family.
                        Use this attribute in a scenario where two routers at different
                        locations use the same Autonomous System number and are connected via
                        an ISP. Once prefixes arrive from one branch at the ISP, they are
                        tagged with the customers AS number. By default, when the ISP passes
                        the prefixes to the other router, the prefixes are dropped if the
                        other router uses the same AS number. Use this attribute to advertise
                        the prefixes at the other side. Control the number of times an AS
                        number is advertised by specifying a number.
                        In a hub and spoke configuration in a VPN, a PE (Provider Edge) router
                        advertises all prefixes containing duplicate AS numbers. Use this
                        attribute to configure two VRFs on each PE router to receive and
                        advertise prefixes. One of the VRFs receives prefixes with AS numbers
                        from all PE routers and then advertises them to neighboring PE
                        routers. The other VRF receives prefixes with AS numbers from the CE
                        (Customer Edge) router and advertises them to all PE routers in the
                        hub and spoke configuration.";
        } // END of allow-as-number definition.

        leaf capability-graceful-restart  {
            // when " ipi-bgp-address-family-vrf:address-family-vrfs/address-family-vrf/peer-groups/peer-group/config/activate ";
            type  empty;
            description "This attribute configures the router to advertise the Graceful Restart
                        Capability to the neighbors. This configuration indicates that the BGP
                        speaker has the ability to preserve its forwarding state for the
                        address family when BGP restarts. Use this attribute to advertise to
                        the neighbor routers the capability of graceful restart.";
        } // END of capability-graceful-restart definition.

        leaf unsuppress-route-map-name  {
            // when " ipi-bgp-address-family-vrf:address-family-vrfs/address-family-vrf/peer-groups/peer-group/config/activate ";
            type  string {
                length "1..1965";
                pattern "[^?' =,>|]+";
            }
            description "unsuppress map name. This attribute is used to selectively leak
                        more-specific routes to a particular neighbor.";
        } // END of unsuppress-route-map-name definition.

        leaf additional-paths-mode  {
            // when " ipi-bgp-address-family-vrf:address-family-vrfs/address-family-vrf/peer-groups/peer-group/config/activate ";
            if-feature feature-list:HAVE_BGP_ADD_PATH;
            type  ipi-bgp-types:bgp_peer_additional_path_type_t;
            description "Adds additional paths in the BGP table";
        } // END of additional-paths-mode definition.

        leaf additional-path-select-all  {
            // when " ipi-bgp-address-family-vrf:address-family-vrfs/address-family-vrf/peer-groups/peer-group/config/activate ";
            if-feature feature-list:HAVE_BGP_ADD_PATH;
            type  empty;
            description "Attribute to select advertise additional path";
        } // END of additional-path-select-all definition.

        leaf additional-paths-best-select-count  {
            // when " ipi-bgp-address-family-vrf:address-family-vrfs/address-family-vrf/peer-groups/peer-group/config/activate ";
            if-feature feature-list:HAVE_BGP_ADD_PATH;
            type  uint8 {
                 range "2..3"  {
                    description "2..3: Supported range 2 - 3";
                 }
            }
            description "Attribute to select best advertise additional path";
        } // END of additional-paths-best-select-count definition.

        leaf site-origin-identifier  {
            // when " ipi-bgp-address-family-vrf:address-family-vrfs/address-family-vrf/peer-groups/peer-group/config/activate ";
            if-feature feature-list:HAVE_VRF;
            type  string {
                length "1..1965";
                pattern "[^?' =,>|]+";
            }
            description "Use this attribute to enable the site-of-origin (SOO) feature. If the
                        customer AS is multi-homed to the ISP, this attribute ensures that the
                        PE does not advertise the routes back to the same AS.";
        } // END of site-origin-identifier definition.

    } // END of bgp-address-family-peer-group-vrf-config definition.


}
