/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-bfd-types.yang
*
*/

module ipi-bfd-types {

    yang-version 1.1;

    namespace   "http://www.ipinfusion.com/yang/ocnos/ipi-bfd-types";

    prefix "ipi-bfd-types";

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "YANG version of the ipi-bfd-types";


    revision "2025-02-14" {
        description "Removing LDP/RSVP all option in mpls bfd command";
        reference " 0.8.4.";
    }

    revision "2023-01-23" {
        description "BFD Single Hop session on LAG feature added";
        reference " 0.8.3.";
    }

    revision "2022-08-12" {
        description "Changed name of the element in OAMBFD_MPLS_LSP_TYPE_T and MPLS_BFD_ALL_LSP_TYPE_T";
        reference " 0.8.2.";
    }

    revision "2022-06-20" {
        description "Changed name of the element in OAMBFD_MPLS_LSP_TYPE_T";
        reference " 0.8.1.";
    }

    revision "2022-06-01" {
        description "Updated the yang file with feature";
        reference " 0.8.0.";
    }

    revision "2022-01-13" {
        description "Added if-feature for data types";
        reference " 0.7.0.";
    }

    revision "2021-11-19" {
        description "Updated BFD session state type";
        reference " 0.6.0.";
    }

    revision "2021-09-03" {
        description "Update descriptions of attribute";
        reference " 0.5.0.";
    }

    revision "2021-08-12" {
        description "Added datatypes for MPLS BFD sessions";
        reference " 0.4.0.";
    }

    revision "2021-01-19" {
        description "Added micro-bfd option to BFD session type datatype";
        reference " 0.3.0.";
    }

    revision "2020-12-15" {
        description "Change to have data-types in lower case instead of camel case";
        reference " 0.2.0.";
    }

    revision "2020-11-30" {
        description "Restructured module as per open-config style";
        reference " 0.1.0.";
    }



    typedef  oambfd_image_type_t {
        type enumeration {
            enum monolithic {
                value 1;
                description "Monolithic";
            }
            enum distributed {
                value 2;
                description "Distributed - main board";
            }
            enum distribute {
                value 3;
                description "Distribute - line card";
            }
        }
        description "type definition for OAMBFD_IMAGE_TYPE_T";
    }

    typedef  oambfd_session_type_t {
        type enumeration {
            enum hardware {
                value 1;
                description "BFD Session offloaded to Forwarding Plane";
            }
            enum software {
                value 2;
                description "BFD Session running at Control Plane (Host CPU)";
            }
        }
        description "type definition for OAMBFD_SESSION_TYPE_T";
    }

    typedef  oambfd_admin_state_t {
        type enumeration {
            enum up {
                value 1;
                description "Administratively Up";
            }
            enum down {
                value 2;
                description "Administratively Down";
            }
        }
        description "type definition for OAMBFD_ADMIN_STATE_T";
    }

    typedef  bfd_multihop_auth_type_t {
        type enumeration {
            enum simple {
                value 1;
                description "Simple Password";
            }
            enum keyed-md5 {
                value 2;
                if-feature feature-list:NOT_HAVE_BFD_HW_OFFLOAD;
                description "Keyed message digest";
            }
            enum meticulous-keyed-md5 {
                value 3;
                if-feature feature-list:NOT_HAVE_BFD_HW_OFFLOAD;
                description "Meticulous Keyed message digest";
            }
            enum keyed-sha1 {
                value 4;
                description "Keyed Secure hashing algorithm";
            }
            enum meticulous-keyed-sha1 {
                value 5;
                description "Meticulous Keyed Secure hashing algorithm";
            }
        }
        description "type definition for BFD_MULTIHOP_AUTH_TYPE_T";
    }

    typedef  oambfd_encrypt_key_t {
        type enumeration {
            enum 0 {
                value 1;
                description "Plain-text password (key)";
            }
            enum 1 {
                value 2;
                description "Encrypted password (key)";
            }
        }
        description "type definition for OAMBFD_ENCRYPT_KEY_T";
    }

    typedef  oambfd_sess_lower_layer_t {
        type enumeration {
            enum unknown {
                value 0;
                description "Unknown";
            }
            enum ipv4 {
                value 1;
                description "IPv4";
            }
            enum ipv6 {
                value 2;
                description "IPv6";
            }
            enum mpls-lsp {
                value 3;
                description "MPLS LSP";
            }
            enum mpls-vccv {
                value 4;
                description "MPLS VCCV";
            }
            enum mpls-tp {
                value 5;
                description "MPLS-TP";
            }
        }
        description "type definition for OAMBFD_SESS_LOWER_LAYER_T";
    }

    typedef  oambfd_session_type_status_t {
        type enumeration {
            enum single-hop {
                value 1;
                description "Single-hop";
            }
            enum multihop-arbit-Path {
                value 2;
                description "Multi-hop arbitrary path";
            }
            enum multihop-oob-signalled {
                value 3;
                description "Multi-hop out-of-band signalled";
            }
            enum multihop-unidirectional {
                value 4;
                description "Multi-hop unidirectional";
            }
        }
        description "type definition for OAMBFD_SESSION_TYPE_STATUS_T";
    }

    typedef  oambfd_session_state_t {
        type enumeration {
            enum admin-down {
                value 1;
                description "Administratively Down";
            }
            enum down {
                value 2;
                description "Down";
            }
            enum init {
                value 3;
                description "Init";
            }
            enum up {
                value 4;
                description "Up";
            }
        }
        description "type definition for OAMBFD_SESSION_STATE_T";
    }

    typedef  oambfd_perform_diag_t {
        type enumeration {
            enum none {
                value 0;
                description "No Diagnostic";
            }
            enum control-detected-expiry {
                value 1;
                description "Control Detection Time Expired";
            }
            enum echo-failed {
                value 2;
                description "Echo Function Failed";
            }
            enum neighbor-session-down {
                value 3;
                description "Neighbor Signaled Session Down";
            }
            enum forwarding-plane-reset {
                value 4;
                description "Forwarding Plane Reset";
            }
            enum path-down {
                value 5;
                description "Path Down";
            }
            enum concatenated-path-down {
                value 6;
                description "Concatenated Path Down";
            }
            enum admin-down {
                value 7;
                description "Administratively Down";
            }
            enum reverse-concatenated-path-down {
                value 8;
                description "Reverse Concatenated Path Down";
            }
            enum configuration-error {
                value 9;
                description "Configuration Error";
            }
            enum not-forwarding {
                value 10;
                description "Not Forwarding";
            }
            enum poll-final-bit-set {
                value 11;
                description "Poll and Final Bit Set";
            }
            enum unsupported-max-detection {
                value 12;
                description "Unsupported Max Detection Time";
            }
            enum unsupported-max-period {
                value 13;
                description "Unsupported Max BFD Period";
            }
        }
        description "type definition for OAMBFD_PERFORM_DIAG_T";
    }

    typedef  bfd_storage_type_t {
        type enumeration {
            enum other {
                value 1;
                description "Other";
            }
            enum volatile {
                value 2;
                description "Volatile";
            }
            enum non-volatile {
                value 3;
                description "Non volatile";
            }
            enum permanent {
                value 4;
                description "Permanent";
            }
            enum read-only {
                value 5;
                description "Read-only";
            }
        }
        description "type definition for BFD_STORAGE_TYPE_T";
    }

    typedef  oambfd_mpls_lsp_type_t {
        type enumeration {
            enum ldp {
                value 0;
                description "LDP";
            }
            enum rsvp {
                value 1;
                description "RSVP";
            }
            enum static {
                value 2;
                description "Static";
            }
            enum sr-policy {
                value 3;
                description "Segment Routing";
            }
            enum generic {
                value 4;
                description "generic";
            }
            enum unknown {
                value 5;
                description "Unknown type";
            }
        }
        description "type definition for OAMBFD_MPLS_LSP_TYPE_T";
    }

    typedef  oambfd_mpls_path_type_t {
        type enumeration {
            enum unknown {
                value 0;
                description "Unknown";
            }
            enum tunnel {
                value 1;
                description "Tunnel";
            }
            enum vc {
                value 2;
                description "VC";
            }
            enum datalink {
                value 3;
                description "Datalink";
            }
        }
        description "type definition for OAMBFD_MPLS_PATH_TYPE_T";
    }

    typedef  oambfd_mpls_cc_type_t {
        type enumeration {
            enum none {
                value 0;
                description "None";
            }
            enum type-1 {
                value 1;
                description "Type-1";
            }
            enum type-2 {
                value 2;
                description "Type-2";
            }
            enum type-3 {
                value 3;
                description "Type-3";
            }
            enum pw-oam-1 {
                value 4;
                description "PW OAM 1";
            }
            enum pw-oam-2 {
                value 5;
                description "PW OAM 2";
            }
        }
        description "type definition for OAMBFD_MPLS_CC_TYPE_T";
    }

    typedef  oambfd_mpls_cv_type_t {
        type enumeration {
            enum none {
                value 0;
                description "None";
            }
            enum icmp-ping {
                value 1;
                description "ICMP ping";
            }
            enum lsp-ping {
                value 2;
                description "LSP ping";
            }
            enum ip-udp-fault-detection {
                value 3;
                description "IP UDP fault detection";
            }
            enum ip-udp-fault-status {
                value 4;
                description "IP UDP fault status signaling";
            }
            enum pw-ach-fault-detection {
                value 5;
                description "PW ACH fault detection";
            }
            enum pw-ach-fault-status {
                value 6;
                description "PW ACH fault status signaling";
            }
        }
        description "type definition for OAMBFD_MPLS_CV_TYPE_T";
    }

    typedef  oambfd_client_flags_t {
        type enumeration {
            enum in-restart {
                value 1;
                description "In Restart";
            }
            enum demand-mode {
                value 2;
                description "Demand mode";
            }
            enum persistent {
                value 4;
                description "Persistent";
            }
            enum admin-down {
                value 8;
                description "Administratively Down";
            }
            enum non-persistent {
                value 16;
                description "Non Persistent";
            }
        }
        description "type definition for OAMBFD_CLIENT_FLAGS_T";
    }

    typedef  oambfd_if_state_t {
        type enumeration {
            enum up {
                value 1;
                description "Up";
            }
            enum down {
                value 2;
                description "Down";
            }
        }
        description "type definition for OAMBFD_IF_STATE_T";
    }

    typedef  bfd_session_type_t {
        type enumeration {
            enum singlehop {
                value 0;
                description "Singlehop Session";
            }
            enum multihop {
                value 1;
                description "Multihop Session";
            }
        }
        description "type definition for BFD_SESSION_TYPE_T";
    }

    typedef  bfd_session_type_state_t {
        type enumeration {
            enum singlehop {
                value 0;
                description "Singlehop Session";
            }
            enum multihop {
                value 1;
                description "Multihop Session";
            }
            enum micro-bfd {
                value 2;
                description "Micro-BFD Session";
            }
        }
        description "type definition for BFD_SESSION_TYPE_STATE_T";
    }

    typedef  bfd_debug_t {
        type bits {
            bit events {
                position 0;
                description "Events";
            }
            bit packets {
                position 1;
                description "Packets";
            }
            bit ipc-error {
                position 2;
                description "IPC Error";
            }
            bit ipc-event {
                position 3;
                description "IPC Event";
            }
            bit session {
                position 4;
                description "Session State";
            }
            bit nsm {
                position 5;
                description "NSM";
            }
        }
        description "type definition for BFD_DEBUG_T";
    }

    typedef  mpls_bfd_all_lsp_type_t {
        type enumeration {
            enum static {
                value 2;
                description "Static type LSP";
            }
            enum generic {
                value 3;
                description "Any type LSP";
            }
        }
        description "type definition for MPLS_BFD_ALL_LSP_TYPE_T";
    }

    typedef  mpls_bfd_lsp_type_t {
        type enumeration {
            enum ldp {
                value 0;
                description "LDP type LSP";
            }
            enum static {
                value 2;
                description "Static type LSP";
            }
        }
        description "type definition for MPLS_BFD_LSP_TYPE_T";
    }

    typedef  mpls_bfd_te_type_t {
        type enumeration {
            enum rsvp {
                value 1;
                description "RSVP type LSP";
            }
        }
        description "type definition for MPLS_BFD_TE_TYPE_T";
    }

    typedef  mpls_bfd_session_state_t {
        type enumeration {
            enum admin-down {
                value 0;
                description "Administratively Down";
            }
            enum down {
                value 1;
                description "Down";
            }
            enum init {
                value 2;
                description "Init";
            }
            enum up {
                value 3;
                description "Up";
            }
        }
        description "type definition for MPLS_BFD_SESSION_STATE_T";
    }

    typedef  mpls_bfd_diag_info_t {
        type enumeration {
            enum none {
                value 0;
                description "No Diagnostic";
            }
            enum control-detected-expiry {
                value 1;
                description "Control Detection Time Expired";
            }
            enum echo-failed {
                value 2;
                description "Echo Function Failed";
            }
            enum neighbor-session-down {
                value 3;
                description "Neighbor Signaled Session Down";
            }
            enum forwarding-plane-reset {
                value 4;
                description "Forwarding Plane Reset";
            }
            enum path-down {
                value 5;
                description "Path Down";
            }
            enum concatenated-path-down {
                value 6;
                description "Concatenated Path Down";
            }
            enum admin-down {
                value 7;
                description "Administratively Down";
            }
            enum reverse-concatenated-path-down {
                value 8;
                description "Reverse Concatenated Path Down";
            }
            enum configuration-error {
                value 9;
                description "Configuration Error";
            }
            enum not-forwarding {
                value 10;
                description "Not Forwarding";
            }
            enum poll-final-bit-set {
                value 11;
                description "Poll and Final Bit Set";
            }
            enum unsupported-max-detection {
                value 12;
                description "Unsupported Max Detection Time";
            }
            enum unsupported-max-period {
                value 13;
                description "Unsupported Max BFD Period";
            }
        }
        description "type definition for MPLS_BFD_DIAG_INFO_T";
    }

}
