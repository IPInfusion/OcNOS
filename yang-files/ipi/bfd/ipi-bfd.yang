/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-bfd.yang
*
*/

module ipi-bfd {

    yang-version 1.1;

    namespace   "http://www.ipinfusion.com/yang/ocnos/ipi-bfd";

    prefix "ipi-bfd";

    import ipi-bfd-types {
        prefix ipi-bfd-types;
        revision-date 2025-02-14;
    }

    import ipi-bfd-common {
        prefix ipi-bfd-common;
        revision-date 2025-09-04;
    }

    import ietf-yang-types {
        prefix yang;
        revision-date 2013-07-15;
    }

    import ietf-inet-types {
        prefix inet;
        revision-date 2013-07-15;
    }

    import cml-data-types {
        prefix cml-data-types;
        revision-date 2026-05-15;
    }

    import feature-list {
        prefix feature-list;
        revision-date 2026-09-15;
    }

    include ipi-bfd-interface { revision-date 2025-09-04;}
    include ipi-bfd-session { revision-date 2025-02-24;}
    include ipi-mpls-bfd-session { revision-date 2023-01-23;}
    organization
        "IP Infusion Inc.";

    contact
        "Address: 3965 Freedom Circle, Suite 200, Santa Clara, CA 95054
         Phone: +1 408-400-1900
         E-mail: support@ipinfusion.com
         Web: http://www.ipinfusion.com/";

    description
        "Datamodel for Bidirecional Forwarding Detection (BFD)";


    revision "2025-12-12" {
        description "Added hidden-cli to enable or disable bgp vpls fec128 tlv";
        reference " 0.10.2.";
    }

    revision "2025-09-04" {
        description "Removed EVPN_IRB_IF_MODE while configuring IRB interface";
        reference " 0.10.1.";
    }

    revision "2025-08-14" {
        description "Added hidden-cli to enable or disable default vccv capability";
        reference " 0.10.0.";
    }

    revision "2025-02-24" {
        description "Added the grouping micro-bfd-session-state-common for micro-BFD sessions";
        reference " 0.9.9.";
    }

    revision "2025-02-14" {
        description "Removing LDP/RSVP all option in mpls bfd command";
        reference " 0.9.8.";
    }

    revision "2025-02-13" {
        description "Added attribite local-discriminator under micro-bfd-sessions";
        reference " 0.9.7.";
    }

    revision "2025-01-09" {
        description "Added utils-func cml_ipv6_format for the attributes 'local-address' and 'remote address'";
        reference " 0.9.6.";
    }

    revision "2024-12-27" {
        description "Added CML_SKIP_HITLESS_MERGE flag for bfd authentication";
        reference " 0.9.5.";
    }

    revision "2024-12-03" {
        description "Added bfd cli support for MHOP global command";
        reference " 0.9.4.";
    }

    revision "2024-10-14" {
        description "Added bfd cli support for irb if-mode";
        reference " 0.9.3.";
    }

    revision "2024-06-12" {
        description "Inclusion of streaming telemetry yaml file";
        reference " 0.9.2.";
    }

    revision "2024-05-29" {
        description "Added if-feature for when tagi for bfd interface";
        reference " 0.9.1.";
    }

    revision "2024-04-03" {
        description "Added aggregate-id when tag to bfd sessions interface echo interval and authentication container";
        reference " 0.9.0.";
    }

    revision "2024-03-04" {
        description "Slow timer interval update for BFD DUNE devices ";
        reference " 0.8.4.";
    }

    revision "2023-05-25" {
        description "Hidden command added to block or unblock hardware BFD based failover trigger";
        reference " 0.8.3.";
    }

    revision "2023-02-10" {
        description "Added debug for SRV6 OAM feature";
        reference " 0.8.1.";
    }

    revision "2023-02-02" {
        description "Updated missing Description";
        reference " 0.8.0.";
    }

    revision "2023-01-23" {
        description "BFD Single Hop session offloaded options added";
        reference " 0.7.7.";
    }

    revision "2022-11-29" {
        description "Added implicit_delete tag to clear interface configs";
        reference " 0.7.6.";
    }

    revision "2022-09-30" {
        description "Import cml-data-types used by notifications";
        reference " 0.7.5.";
    }

    revision "2022-08-12" {
        description "Changed name of the element in OAMBFD_MPLS_LSP_TYPE_T and MPLS_BFD_ALL_LSP_TYPE_T";
        reference " 0.7.4.";
    }

    revision "2022-08-10" {
        description "Debug hierarchy change";
        reference " 0.8.1.";
    }

    revision "2022-07-31" {
        description "Stop using inet:ipv4-prefix and inet:ipv6-prefix due to Cisco NSO iterop";
        reference " 0.8.0.";
    }

    revision "2022-07-30" {
        description "Updated implicit delete for config container";
        reference " 0.8.0.";
    }

    revision "2022-07-13" {
        description "Implicit delete for peers table";
        reference " 0.7.2.";
    }

    revision "2022-06-20" {
        description "Added interface-name attribute to bfd-session-state-common grouping";
        reference " 0.7.1.";
    }

    revision "2022-06-01" {
        description "Updated the yang file with feature";
        reference " 0.7.0.";
    }

    revision "2022-02-09" {
        description "Added When tag constraints for 'debug' container";
        reference " 0.8.2.";
    }

    revision "2022-01-13" {
        description "Modified sub module";
        reference " 0.6.0.";
    }

    revision "2021-11-19" {
        description "Added interface-index attribute to bfd-session-state-common grouping and updated BFD session state type";
        reference " 0.5.0.";
    }

    revision "2021-09-03" {
        description "Update descriptions of attribute";
        reference " 0.4.2.";
    }

    revision "2021-09-01" {
        description "Updated ipi-bfd-interface submodule when tag as Changed base interface module's switchport attribute name and the datatype from bool to empty";
        reference " 0.4.1.";
    }

    revision "2021-08-17" {
        description "Updated ipi-mpls-bfd-session submodule with MPLS BFD state attributes";
        reference " 0.4.0.";
    }

    revision "2021-01-19" {
        description "Updated ipi-bfd-session submodule with support to micro-bfd session status";
        reference " 0.3.0.";
    }

    revision "2020-12-15" {
        description "Change to have data-types in lower case instead of camel case";
        reference " 0.2.0.";
    }

    revision "2020-11-30" {
        description "Restructured module as per open-config style";
        reference " 0.1.0.";
    }

    grouping bfd-gtsm-config {
        description
            "Structural grouping for Generalized TTL Security Mechanism.";
        leaf generalized-ttl-security-mechanism-enabled  {
            type  boolean;
            default false;
            description "Use this attribute to enable or disable Generalized TTL Security
                        Mechanism.";
        } // END of generalized-ttl-security-mechanism-enabled definition.

        leaf ttl  {
            type  uint8 {
                 range "1..255"  {
                    description "1..255: Supported range 1 - 255";
                 }
            }
            default "255";
            description "Use this attribute to set Time To Live value for Generalized TTL
                        Security Mechanism.";
        } // END of ttl definition.

    } // END of bfd-gtsm-config definition.
    grouping bfd-global-config {
        description
            "Global configuration parameters for BFD.";
        leaf notification-enabled  {
            if-feature feature-list:HAVE_BFD_MONO;
            type  boolean;
            default false;
            description "Use this attribute to enable or disable BFD SNMP notification.";
        } // END of notification-enabled definition.

        leaf echo-mode-enabled  {
            if-feature feature-list:HAVE_BFD_MONO;
            type  empty;
            description "This leaf exists when echo mode is running between the local and
                        remote system. When it does not exist, solely asynchronous mode is
                        active.";
        } // END of echo-mode-enabled definition.

        leaf slow-tx-interval  {
            if-feature feature-list:HAVE_BFD_MONO;
            type  uint32 {
                 range "1000..30000"  {
                    description "1000..30000:Not Feature : HAVE_DUNE  Supported range 1000 -
                            30000Feature : HAVE_DUNE Supported range 1000 - 1703";
                 }
            }
            units "milliseconds";
            default "2000";
            description "Use this command to set a BFD slow timer interval.";
        } // END of slow-tx-interval definition.

    } // END of bfd-global-config definition.
    grouping bfd-global-counters {
        description
            "Global BFD counters parameters";
        container counters {
            config false;
            description
                "Counters parameters for BFD.";
            leaf total-sessions  {
                type  yang:counter32;
                description "Total number of BFD sessions";
            } // END of total-sessions definition.

        } // END of counters-container definition.
    } // END of bfd-global-counters definition.
    grouping bfd-global-state {
        description
            "Global operational state parameters for BFD.";
        leaf start-time  {
            if-feature feature-list:HAVE_BFD_MONO;
            type  yang:timeticks;
            units "seconds";
            description "The date and time at which BFD process started, expressed as the
                        number of seconds since the Unix Epoch (January 1, 1970, 00:00 UTC).";
        } // END of start-time definition.

        leaf administrative-state  {
            if-feature feature-list:HAVE_BFD_MONO;
            type  ipi-bfd-types:oambfd_admin_state_t;
            description "The administrative state of the BFD process on local system.";
        } // END of administrative-state definition.

        leaf image-type  {
            if-feature feature-list:HAVE_BFD_MONO;
            type  ipi-bfd-types:oambfd_image_type_t;
            description "Monolitc or distributed BFD image type.";
        } // END of image-type definition.

        leaf next-session-discriminator  {
            if-feature feature-list:HAVE_BFD_MONO;
            type  string {
                length "1..1965";
                pattern "[^?' =,>|]+";
            }
            description "Local discriminator to be used in the next BFD session.";
        } // END of next-session-discriminator definition.

    } // END of bfd-global-state definition.
    grouping bfd-debug-config {
        description
            "Grouping for debug configuration for BFD";
        leaf options  {
            type  ipi-bfd-types:bfd_debug_t;
            description "Use this attribute to debug the oamd process.";
        } // END of options definition.

        leaf enable-oam-srv6  {
            if-feature feature-list:HAVE_SRV6;
            type  empty;
            description "Use this attribute to debug OAM SRV6";
        } // END of enable-oam-srv6 definition.

    } // END of bfd-debug-config definition.
    grouping bfd-debug-terminal-state {
        description
            "Grouping for terminal debug operational state";
        leaf terminal-debug-status  {
            type  ipi-bfd-types:bfd_debug_t;
            description "Terminal debug option";
        } // END of terminal-debug-status definition.

    } // END of bfd-debug-terminal-state definition.
    grouping oammpls-config {
        description
            "Grouping for oam MPLS configuration for BFD";
        leaf enable-mpls-ping-request  {
            type  empty;
            description "Use this attribute to enable or disable MPLS ping request DSMAP TLV";
        } // END of enable-mpls-ping-request definition.

        leaf mpls-ping-reply  {
            type  empty;
            description "Use this attribute to enable or disable MPLS ping reply TLV";
        } // END of mpls-ping-reply definition.

    } // END of oammpls-config definition.
    grouping oam-global-config {
        description
            "Grouping for oam MPLS configuration for default vccv config";
        leaf disable-default-vccv-capability  {
            type  empty;
            description "Use this attribute to disable default vccv capability.";
        } // END of disable-default-vccv-capability definition.

        leaf l2vpn-ping-use-fec128-tlv  {
            type  empty;
            description "Use this attribute to send fec128 tlv for l2vpn bgp vpls";
        } // END of l2vpn-ping-use-fec128-tlv definition.

    } // END of oam-global-config definition.
    grouping bfd-peer-config {
        description
            "Grouping for BFD peer configuration";
        leaf remote-address  {
            type  inet:ip-address;
            description "The IP address used by the remote system for BFD session.";
        } // END of remote-address definition.

    } // END of bfd-peer-config definition.

    grouping  bfd-grouping {
    description
        "Structural container for Bidirectional Forwarding Detection (BFD).";
    container bfd {
        if-feature feature-list:HAVE_BFD;
        description
            "Structural container for Bidirectional Forwarding Detection (BFD).";
        container global {
            description
                "Global parameters for BFD.";
            container config {
                description
                    "Configuration parameters for BFD.";
                uses bfd-global-config;
            } // END of config-container definition.
            container state {
                config false;
                description
                    "Operational state parameters for BFD.";
                uses bfd-global-config;
                uses bfd-global-state;
                uses bfd-global-counters;
            } // END of state-container definition.
            container multihop-peer-intervals {
                description
                    "BFD multihop peer interval parameters.";

                list multihop-peer-interval {
                    if-feature feature-list:HAVE_BFD_MONO;
                    key "desired-minimum-tx-interval required-minimum-rx-interval detection-multiplier";
                    max-elements 1;
                    description
                        "BFD multihop peer interval parameters.";
                    leaf desired-minimum-tx-interval  {
                        type  leafref {
                            path  "../config/desired-minimum-tx-interval";
                        }
                        description "The minimum interval between transmission of BFD control packets that
                                    the operator desires. This value is advertised to the peer, however
                                    the actual interval used is specified by taking the maximum of
                                    desired-minimum-tx-interval and the        value of the remote
                                    required-min
                                    imum-receive interval value.";
                    } // END of desired-minimum-tx-interval definition.

                    leaf required-minimum-rx-interval  {
                        type  leafref {
                            path  "../config/required-minimum-rx-interval";
                        }
                        description "The minimum interval between received BFD control packets that this
                                    system should support. This value is advertised to the remote peer to
                                    indicate the maximum frequency (i.e., minimum inter-packet interval)
                                    between BFD control packets         that is acceptable to the local
                                    system.";
                    } // END of required-minimum-rx-interval definition.

                    leaf detection-multiplier  {
                        type  leafref {
                            path  "../config/detection-multiplier";
                        }
                        description "The number of packets that must be missed to declare this session as
                                    down. The detection interval for the BFD session is calculated by
                                    multiplying the value of the negotiated transmission interval by this
                                    value.";
                    } // END of detection-multiplier definition.

                    container config {
                        description
                            "BFD multihop peer configuration parameters";
                        uses ipi-bfd-common:bfd-interval-config-common;
                    } // END of config-container definition.
                    container state {
                        config false;
                        description
                            "Operational state parameters for BFD multihop peer";
                        uses ipi-bfd-common:bfd-interval-config-common;
                    } // END of state-container definition.
                } // End of multihop-peer-interval-list
            } // END of multihop-peer-intervals-container definition.
            container intervals {
                description
                    "BFD multihop peer interval parameters.";

                list interval {
                    if-feature feature-list:HAVE_BFD_MONO;
                    key "desired-minimum-tx-interval required-minimum-rx-interval detection-multiplier";
                    max-elements 1;
                    description
                        "BFD multihop peer interval parameters.";
                    leaf desired-minimum-tx-interval  {
                        type  leafref {
                            path  "../config/desired-minimum-tx-interval";
                        }
                        description "The minimum interval between transmission of BFD control packets that
                                    the operator desires. This value is advertised to the peer, however
                                    the actual interval used is specified by taking the maximum of
                                    desired-minimum-tx-interval and the value of the remote
                                    required-minimum-receive interval value.";
                    } // END of desired-minimum-tx-interval definition.

                    leaf required-minimum-rx-interval  {
                        type  leafref {
                            path  "../config/required-minimum-rx-interval";
                        }
                        description "The minimum interval between received BFD control packets that this
                                    system should support. This value is advertised to the remote peer to
                                    indicate the maximum frequency (i.e., minimum inter-packet interval)
                                    between BFD control packets that is acceptable to the local system.";
                    } // END of required-minimum-rx-interval definition.

                    leaf detection-multiplier  {
                        type  leafref {
                            path  "../config/detection-multiplier";
                        }
                        description "The number of packets that must be missed to declare this session as
                                    down. The detection interval for the BFD session is calculated by
                                    multiplying the value of the negotiated transmission interval by this
                                    value.";
                    } // END of detection-multiplier definition.

                    container config {
                        description
                            "BFD multihop peer configuration parameters";
                        uses ipi-bfd-common:bfd-interval-config-common;
                    } // END of config-container definition.
                    container state {
                        config false;
                        description
                            "Operational state parameters for BFD multihop peer";
                        uses ipi-bfd-common:bfd-interval-config-common;
                    } // END of state-container definition.
                } // End of interval-list
            } // END of intervals-container definition.
        } // END of global-container definition.
        container generalized-ttl-security-mechanism {
            if-feature feature-list:HAVE_BFD_MONO;
            if-feature feature-list:NOT_HAVE_BFD_HW_OFFLOAD;
            description
                "Generalized TTL Security Mechanism parameters.";
            container config {
                if-feature feature-list:HAVE_BFD_MONO;
                if-feature feature-list:NOT_HAVE_BFD_HW_OFFLOAD;
                description
                    "Configuration parameters for Generalized TTL Security Mechanism.";
                uses bfd-gtsm-config;
            } // END of config-container definition.
            container state {
                config false;
                description
                    "Operational state parameters for Generalized TTL Security Mechanism.";
                uses bfd-gtsm-config;
            } // END of state-container definition.
        } // END of generalized-ttl-security-mechanism-container definition.
        container peers {
            description
                "BFD multihop peer parameters.";

            list peer {
            // when " ipi-bfd:bfd/peers/peer/intervals/interval/desired-minimum-tx-interval + ipi-bfd:bfd/peers/peer/authentication/config/key-type ";
                key "remote-address";
                description
                    "BFD multihop peer.";
                leaf remote-address  {
                    type  leafref {
                        path  "../config/remote-address";
                    }
                    description "The IP address used by the remote system for BFD session.";
                } // END of remote-address definition.

                container config {
                    description
                        "BFD multihop peer configuration parameters.";
                    uses bfd-peer-config;
                } // END of config-container definition.
                container state {
                    config false;
                    description
                        "Opearational state for BFD multihop peer.";
                    uses bfd-peer-config;
                } // END of state-container definition.
                container intervals {
                    description
                        "BFD multihop peer interval.";

                    list interval {
                        if-feature feature-list:HAVE_BFD_MONO;
                        key "desired-minimum-tx-interval required-minimum-rx-interval detection-multiplier";
                        max-elements 1;
                        description
                            "BFD multihop peer interval parameters.";
                        leaf desired-minimum-tx-interval  {
                            type  leafref {
                                path  "../config/desired-minimum-tx-interval";
                            }
                            description "The minimum interval between transmission of BFD control packets that
                                        the operator desires. This value is advertised to the peer, however
                                        the actual interval used is specified by taking the maximum of
                                        desired-minimum-tx-interval and the value of the remote
                                        required-minimum-receive interval value.";
                        } // END of desired-minimum-tx-interval definition.

                        leaf required-minimum-rx-interval  {
                            type  leafref {
                                path  "../config/required-minimum-rx-interval";
                            }
                            description "The minimum interval between received BFD control packets that this
                                        system should support. This value is advertised to the remote peer to
                                        indicate the maximum frequency (i.e., minimum inter-packet interval)
                                        between BFD control packets that is acceptable to the local system.";
                        } // END of required-minimum-rx-interval definition.

                        leaf detection-multiplier  {
                            type  leafref {
                                path  "../config/detection-multiplier";
                            }
                            description "The number of packets that must be missed to declare this session as
                                        down. The detection interval for the BFD session is calculated by
                                        multiplying the value of the negotiated transmission interval by this
                                        value.";
                        } // END of detection-multiplier definition.

                        container config {
                            description
                                "BFD multihop peer configuration parameters";
                            uses ipi-bfd-common:bfd-interval-config-common;
                        } // END of config-container definition.
                        container state {
                            config false;
                            description
                                "Operational state parameters for BFD multihop peer";
                            uses ipi-bfd-common:bfd-interval-config-common;
                        } // END of state-container definition.
                    } // End of interval-list
                } // END of intervals-container definition.
                uses ipi-bfd-common:bfd-authentication-top;
            } // End of peer-list
        } // END of peers-container definition.
        container debug {
            description
                "Debugging functions";
            container config {
                description
                    "Configuration data";
                uses bfd-debug-config;
            } // END of config-container definition.
            container state {
                config false;
                description
                    "Operational state data";
                uses bfd-debug-config;
                uses bfd-debug-terminal-state;
            } // END of state-container definition.
        } // END of debug-container definition.
        uses interfaces-grouping;
        uses sessions-grouping;
    } // END of bfd-container definition.
    } // END of bfd-grouping definition.

    uses bfd-grouping;

    rpc bfd-snmp-restart {
        if-feature feature-list:HAVE_SNMP;
        if-feature feature-list:HAVE_BFD;
        description "Restart SNMP in Bidirectional Forwarding Detection (BFD)";
    }

    rpc bfd-terminal-debug-on {
        if-feature feature-list:HAVE_BFD;
        description "Enable BFD debug categories";
        input  {
            leaf terminal-debug-options  {
                type ipi-bfd-types:bfd_debug_t;
                mandatory true;
                description "Bitmap representing BFD debug categories";
            }
        }
    }

    rpc bfd-terminal-debug-off {
        if-feature feature-list:HAVE_BFD;
        description "Disable BFD debug categories";
        input  {
            leaf terminal-debug-options  {
                type ipi-bfd-types:bfd_debug_t;
                mandatory true;
                description "Bitmap representing BFD debug categories";
            }
        }
    }

    rpc debug-oam-srv6-on {
        if-feature feature-list:HAVE_SRV6;
        if-feature feature-list:HAVE_BFD;
        description "Enable OAM SRV6 debug";
    }

    rpc debug-oam-srv6-off {
        if-feature feature-list:HAVE_SRV6;
        if-feature feature-list:HAVE_BFD;
        description "Disable OAM SRV6 debug";
    }

    notification bfd-session-state-change {
        if-feature feature-list:HAVE_BFD;

        description "This notification is sent when the BFD Session state changes..";

        leaf severity {
            type cml-data-types:cml_notif_severity_t;
            description "Notification severity level (value: MINOR)";
        }

        leaf eventClass {
            type cml-data-types:cml_notif_class_t;
            description "Notification event class (value: STATE)";
        }

        leaf local-discriminator {
            type  string;
        description
            "A unique identifier used by the local system to identify this BFD
                    session";
        }

        leaf vrf-name {
            type  string;
        description
            "VRF name";
        }

        leaf session-state {
            type ipi-bfd-types:oambfd_session_state_t;
        description
            "The state of the BFD session perceived by the local system";
        }

        leaf session-diagnostics {
            type ipi-bfd-types:oambfd_perform_diag_t;
        description
            "The local BFD diagnostic code indicating the most recent reason for
                    failure of this BFD session";
        }
    }

}
