/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-bfd-interface.yang
*
*/

submodule ipi-bfd-interface {

    yang-version 1.1;

    belongs-to  ipi-bfd { prefix ipi-bfd; }

    import feature-list {
        prefix feature-list;
        revision-date 2026-09-15;
    }

    import ipi-bfd-types {
        prefix ipi-bfd-types;
        revision-date 2025-02-14;
    }

    import ipi-bfd-common {
        prefix ipi-bfd-common;
        revision-date 2025-09-04;
    }

    import ipi-interface {
        prefix ipi-interface;
        revision-date 2026-03-10;
    }

    import ietf-inet-types {
        prefix inet;
        revision-date 2013-07-15;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for Bidirecional Forwarding Detection (BFD) interface
                information";


    revision "2025-09-04" {
        description "Removed EVPN_IRB_IF_MODE while configuring IRB interface";
        reference " 0.7.0.";
    }

    revision "2025-01-09" {
        description "Added utils-func cml_ipv6_format for the attributes 'local-address' and 'remote address'";
        reference " 0.6.5.";
    }

    revision "2024-12-27" {
        description "Added CML_SKIP_HITLESS_MERGE flag for bfd authentication";
        reference " 0.6.4.";
    }

    revision "2024-10-14" {
        description "Added bfd cli support for irb if-mode";
        reference " 0.6.3.";
    }

    revision "2024-06-12" {
        description "Inclusion of streaming telemetry yaml file";
        reference " 0.6.2.";
    }

    revision "2024-05-29" {
        description "Added if-feature for when tag";
        reference " 0.6.1.";
    }

    revision "2024-04-03" {
        description "Added when tag aggregate-id to bfd sessions interval echo interface container";
        reference " 0.6.0.";
    }

    revision "2023-02-02" {
        description "Updated missing Description";
        reference " 0.5.0.";
    }

    revision "2023-01-23" {
        description "BFD Single Hop session on LAG feature added";
        reference " 0.4.4.";
    }

    revision "2022-11-29" {
        description "Added implicit_delete tag to clear interface configs";
        reference " 0.4.3.";
    }

    revision "2022-08-12" {
        description "Changed name of the element in OAMBFD_MPLS_LSP_TYPE_T and MPLS_BFD_ALL_LSP_TYPE_T";
        reference " 0.4.2.";
    }

    revision "2022-06-20" {
        description "Changed name of the element in OAMBFD_MPLS_LSP_TYPE_T";
        reference " 0.4.1.";
    }

    revision "2022-06-01" {
        description "Updated the yang file with feature";
        reference " 0.4.0.";
    }

    revision "2021-09-01" {
        description "Changed base interface module's switchport attribute name and the datatype from bool to empty";
        reference " 0.3.0.";
    }

    revision "2020-12-15" {
        description "Change to have data-types in lower case instead of camel case";
        reference " 0.2.0.";
    }

    revision "2020-11-30" {
        description "Restructured module as per open-config style";
        reference " 0.1.0.";
    }

    grouping bfd-interface-session-config {
        description
            "Grouping for BFD session config";
        leaf local-address  {
            type  inet:ip-address;
            description "BFD ip user intf src related configs";
        } // END of local-address definition.

        leaf remote-address  {
            type  inet:ip-address;
            description "BFD ip user intf dest related configs";
        } // END of remote-address definition.

        leaf session-type  {
            type  ipi-bfd-types:bfd_session_type_t;
            description "BFD session type";
        } // END of session-type definition.

        leaf administrative-down  {
            type  empty;
            description "BFD administrative down session";
        } // END of administrative-down definition.

        leaf demand-mode  {
            if-feature feature-list:NOT_HAVE_BFD_HW_OFFLOAD;
            type  empty;
            description "BFD demand mode session";
        } // END of demand-mode definition.

        leaf non-persistent  {
            type  empty;
            description "BFD non persistent session";
        } // END of non-persistent definition.

    } // END of bfd-interface-session-config definition.
    grouping bfd-interface-sessions-top {
        description
            "Grouping for BFD sessions configuration on interface";
        container sessions {
            description
                "Set BFD sessions on this interface";

            list session {
                key "local-address remote-address session-type";
                description
                    "BFD session table for runtime attrs";
                leaf local-address  {
                    type  leafref {
                        path  "../config/local-address";
                    }
                    description "BFD ip user intf src related configs";
                } // END of local-address definition.

                leaf remote-address  {
                    type  leafref {
                        path  "../config/remote-address";
                    }
                    description "BFD ip user intf dest related configs";
                } // END of remote-address definition.

                leaf session-type  {
                    type  leafref {
                        path  "../config/session-type";
                    }
                    description "BFD session type";
                } // END of session-type definition.

                container config {
                    description
                        "BFD session config";
                    uses bfd-interface-session-config;
                } // END of config-container definition.
                container state {
                    config false;
                    description
                        "BFD session state";
                    uses bfd-interface-session-config;
                } // END of state-container definition.
            } // End of session-list
        } // END of sessions-container definition.
    } // END of bfd-interface-sessions-top definition.
    grouping bfd-interface-config {
        description
            "Grouping for BFD configuration on interface";
        leaf name  {
            type  leafref {
                path  "/ipi-interface:interfaces/ipi-interface:interface/ipi-interface:name";
            }
            description "Interface name for which BFD is being configured";
        } // END of name definition.

        leaf bfd-disabled  {
            type  empty;
            description "Use this attribute to enable or disable all the BFD sessions on this
                        interface.";
        } // END of bfd-disabled definition.

        leaf bfd-session-type  {
            if-feature feature-list:HAVE_BFD_HW_OFFLOAD;
            type  ipi-bfd-types:oambfd_session_type_t;
            description "Use this attribute to offload Single HOP BFD sessions to software or
                        hardware.";
        } // END of bfd-session-type definition.

    } // END of bfd-interface-config definition.
    grouping bfd-interface-state {
        description
            "Grouping for BFD state data on interface";
        leaf interface-index  {
            type  uint32;
            config false;
            description "The internal interface index";
        } // END of interface-index definition.

        leaf interface-state  {
            type  ipi-bfd-types:oambfd_if_state_t;
            config false;
            description "The interface operational state";
        } // END of interface-state definition.

    } // END of bfd-interface-state definition.
    grouping bfd-interval-top {
        description
            "Grouping for generic BFD interval parameters configuration";
        container intervals {
            description
                "BFD intervals configuration";

            list interval {
                if-feature feature-list:HAVE_BFD_MONO;
                key "desired-minimum-tx-interval required-minimum-rx-interval detection-multiplier";
                max-elements 1;
                description
                    "BFD interval parameters.";
                leaf desired-minimum-tx-interval  {
                    type  leafref {
                        path  "../config/desired-minimum-tx-interval";
                    }
                    description "The minimum interval between transmission of BFD control packets that
                                the operator desires. This value is advertised to the peer,
                                however the actual interval used is specified by taking the maximum of
                                desired-minimum-tx-interval and the value of the remote
                                required-minimum-receive
                                interval value.";
                } // END of desired-minimum-tx-interval definition.

                leaf required-minimum-rx-interval  {
                    type  leafref {
                        path  "../config/required-minimum-rx-interval";
                    }
                    description "The minimum interval between received BFD control packets that this
                                system should support. This value is advertised to the
                                remote peer to indicate the maximum frequency (i.e., minimum
                                inter-packet interval) between BFD control packets that is acceptable
                                to the local system.";
                } // END of required-minimum-rx-interval definition.

                leaf detection-multiplier  {
                    type  leafref {
                        path  "../config/detection-multiplier";
                    }
                    description "The number of packets that must be missed to declare this session as
                                down. The detection interval for the BFD session is
                                calculated by multiplying the value of the negotiated transmission
                                interval by this value.";
                } // END of detection-multiplier definition.

                container config {
                    description
                        "BFD intervals configuration parameters";
                    uses ipi-bfd-common:bfd-interval-config-common;
                } // END of config-container definition.
                container state {
                    config false;
                    description
                        "Operational state parameters for BFD intervals";
                    uses ipi-bfd-common:bfd-interval-config-common;
                } // END of state-container definition.
            } // End of interval-list
        } // END of intervals-container definition.
    } // END of bfd-interval-top definition.
    grouping bfd-echo-config {
        description
            "Grouping for BFD echo configuration on interface";
        leaf ipv4-source  {
            type  inet:ipv4-address;
            description "Use this attribute to configure BFD echo packet IPv4 source address";
        } // END of ipv4-source definition.

        leaf required-minimum-tx-interval  {
            type  uint32 {
                 range "50..4294967"  {
                    description "50..4294967: Supported range 50 - 4294967";
                 }
            }
            description "Use this attribute to configure BFD echo packet transmission interval,
                        in milliseconds";
        } // END of required-minimum-tx-interval definition.

    } // END of bfd-echo-config definition.
    grouping bfd-echo-top {
        description
            "Grouping for BFD echo configuration on interface";
        container echo {
            description
                "Set BFD echo parameter";
            container config {
                description
                    "Configuration data";
                uses bfd-echo-config;
            } // END of config-container definition.
            container state {
                config false;
                description
                    "Operational state data";
                uses bfd-echo-config;
            } // END of state-container definition.
        } // END of echo-container definition.
    } // END of bfd-echo-top definition.

    grouping  interfaces-grouping {
    description
        "Configuration data";
    container interfaces {
        if-feature feature-list:HAVE_BFD;
        description
            "Configuration data";

        list interface {
            key "name";
            description
                "BFD interface related operations";
            leaf name  {
                type  leafref {
                    path  "../config/name";
                }
                description "Interface name for which BFD is being configured";
            } // END of name definition.

            container config {
                description
                    "Configuration data";
                uses bfd-interface-config;
            } // END of config-container definition.
            container state {
                config false;
                description
                    "Operational state data";
                uses bfd-interface-config;
                uses bfd-interface-state;
            } // END of state-container definition.
            uses bfd-interval-top;
            uses bfd-echo-top;
            uses ipi-bfd-common:bfd-authentication-top;
            uses bfd-interface-sessions-top;
        } // End of interface-list
    } // END of interfaces-container definition.
    } // END of interfaces-grouping definition.


}
