/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-mpls-bfd-session.yang
*
*/

submodule ipi-mpls-bfd-session {

    yang-version 1.1;

    belongs-to  ipi-bfd { prefix ipi-bfd; }

    import feature-list {
        prefix feature-list;
        revision-date 2026-09-15;
    }

    import ietf-inet-types {
        prefix inet;
        revision-date 2013-07-15;
    }

    import ietf-yang-types {
        prefix yang;
        revision-date 2013-07-15;
    }

    import cml-data-types {
        prefix cml-data-types;
        revision-date 2026-05-15;
    }

    import ipi-bfd-types {
        prefix ipi-bfd-types;
        revision-date 2025-02-14;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for MPLS BFD session attributes";


    revision "2023-01-23" {
        description "BFD Single Hop session on LAG feature added";
        reference " 0.2.2.";
    }

    revision "2022-08-12" {
        description "Changed name of the element in OAMBFD_MPLS_LSP_TYPE_T and MPLS_BFD_ALL_LSP_TYPE_T";
        reference " 0.2.1.";
    }

    revision "2022-07-31" {
        description "Stop using inet:ipv4-prefix and inet:ipv6-prefix due to Cisco NSO iterop";
        reference " 0.2.0.";
    }

    revision "2022-06-20" {
        description "Changed name of the element in OAMBFD_MPLS_LSP_TYPE_T";
        reference " 0.1.3.";
    }

    revision "2022-06-01" {
        description "Updated the yang file with feature";
        reference " 0.1.2.";
    }

    revision "2021-09-03" {
        description "Update descriptions of attribute";
        reference " 0.1.1.";
    }

    revision "2021-08-17" {
        description "Initial Version";
        reference " 0.1.0.";
    }

    grouping mpls-bfd-summary-state {
        description
            "MPLS BFD Summary";
        leaf number-of-sessions  {
            type  uint32;
            description "This attribute provides total number of MPLS BFD sessions";
        } // END of number-of-sessions definition.

        leaf number-of-sessions-up  {
            type  uint32;
            description "This attribute provides number of sessions that are UP";
        } // END of number-of-sessions-up definition.

        leaf number-of-sessions-down  {
            type  uint32;
            description "This attribute provides number of sessions that are DOWN";
        } // END of number-of-sessions-down definition.

        leaf number-of-sessions-admin-down  {
            type  uint32;
            description "This attribute provides number of sessions that have ADMIN-DOWN";
        } // END of number-of-sessions-admin-down definition.

    } // END of mpls-bfd-summary-state definition.
    grouping mpls-bfd-session-common-info-state {
        description
            "Common operational attrs for all MPLS BFD egress sessions";
        leaf fec-address  {
            type  cml-data-types:cml_ipv4_addr_prefix_t;
            description "This attribute provides fec address of the MPLS BFD session";
        } // END of fec-address definition.

        leaf local-discriminator  {
            type  string {
                length "1..1965";
                pattern "[^?' =,>|]+";
            }
            description "This attribute provides local discriminator of the MPLS BFD session";
        } // END of local-discriminator definition.

        leaf remote-discriminator  {
            type  string {
                length "1..1965";
                pattern "[^?' =,>|]+";
            }
            description "This attribute provides remote discriminator of the MPLS BFD session";
        } // END of remote-discriminator definition.

        leaf source-port  {
            type  inet:port-number;
            description "This attribute provides source port of the MPLS BFD session";
        } // END of source-port definition.

        leaf destination-port  {
            type  inet:port-number;
            description "This attribute provides destination port of the MPLS BFD session";
        } // END of destination-port definition.

    } // END of mpls-bfd-session-common-info-state definition.
    grouping mpls-bfd-egress-session-state {
        description
            "MPLS BFD Egress Sessions";
        leaf local-multiplier  {
            type  uint32;
            description "This attribute provides local multiplier of the MPLS BFD session";
        } // END of local-multiplier definition.

    } // END of mpls-bfd-egress-session-state definition.
    grouping mpls-bfd-session-info-state {
        description
            "MPLS BFD session info";
        leaf lsp-type  {
            type  ipi-bfd-types:mpls_bfd_all_lsp_type_t;
            description "This attribute provides lsp type for the MPLS BFD session";
        } // END of lsp-type definition.

        leaf ip-encapsulation  {
            type  empty;
            description "This attribute shows if the session is ip encapsulated";
        } // END of ip-encapsulation definition.

        leaf remote-multiplier  {
            type  uint32;
            description "This attribute provides remote multiplier of the MPLS BFD session";
        } // END of remote-multiplier definition.

    } // END of mpls-bfd-session-info-state definition.
    grouping mpls-bfd-session-runtime-info-state {
        description
            "MPLS BFD session runtime info";
        leaf session-index  {
            type  uint32;
            description "This attribute provides session index of the MPLS BFD session";
        } // END of session-index definition.

        leaf local-state  {
            type  ipi-bfd-types:mpls_bfd_session_state_t;
            description "This attribute provides local state of the MPLS BFD session";
        } // END of local-state definition.

        leaf remote-state  {
            type  ipi-bfd-types:mpls_bfd_session_state_t;
            description "This attribute provides remote state of the MPLS BFD session";
        } // END of remote-state definition.

        leaf local-diagnostic  {
            type  ipi-bfd-types:mpls_bfd_diag_info_t;
            description "This attribute provides local diagnostic of the MPLS BFD session";
        } // END of local-diagnostic definition.

        leaf remote-diagnostic  {
            type  ipi-bfd-types:mpls_bfd_diag_info_t;
            description "This attribute provides remote diagnostic of the MPLS BFD session";
        } // END of remote-diagnostic definition.

        leaf negotiated-tx-interval  {
            type  uint32;
            description "This attribute provides negotiated tx interval of the MPLS BFD session";
        } // END of negotiated-tx-interval definition.

        leaf negotiated-rx-interval  {
            type  uint32;
            description "This attribute provides negotiated rx interval of the MPLS BFD session";
        } // END of negotiated-rx-interval definition.

    } // END of mpls-bfd-session-runtime-info-state definition.
    grouping mpls-bfd-session-stats-info-state {
        description
            "MPLS BFD session stats info";
        leaf create-time  {
            type  yang:timeticks;
            description "This attribute provides time of creation of the MPLS BFD session";
        } // END of create-time definition.

        leaf last-down-time  {
            type  yang:timeticks;
            description "This attribute provides last down time of the MPLS BFD session";
        } // END of last-down-time definition.

        leaf last-up-time  {
            type  yang:timeticks;
            description "This attribute provides last up time of the MPLS BFD session";
        } // END of last-up-time definition.

        leaf down-count  {
            type  yang:counter32;
            description "This attribute provides count of down MPLS BFD sessions";
        } // END of down-count definition.

        leaf admin-down-count  {
            type  yang:counter32;
            description "This attribute provides count of admin down MPLS BFD sessions";
        } // END of admin-down-count definition.

        leaf receive-packet-count  {
            type  yang:counter64;
            description "This attribute provides rx packet counts of MPLS BFD sessions";
        } // END of receive-packet-count definition.

        leaf send-packet-count  {
            type  yang:counter64;
            description "This attribute provides tx packet counts of MPLS BFD sessions";
        } // END of send-packet-count definition.

    } // END of mpls-bfd-session-stats-info-state definition.
    grouping mpls-bfd-lsp-state {
        description
            "MPLS BFD LSP Configs";
        leaf lsp-type  {
            type  ipi-bfd-types:mpls_bfd_lsp_type_t;
            description "This attribute provides lsp type of the MPLS BFD session";
        } // END of lsp-type definition.

        leaf fec-address  {
            type  cml-data-types:cml_ipv4_addr_prefix_t;
            description "This attribute provides fec address of the MPLS BFD session";
        } // END of fec-address definition.

    } // END of mpls-bfd-lsp-state definition.
    grouping mpls-bfd-session-info-top {
        description
            "Top Level Grouping for MPLS BFD Session info";
        container sessions {
            config false;
            description
                "MPLS BFD sessions";

            list session {
                key "lsp-type";
                config false;
                description
                    "MPLS BFD session";
                leaf lsp-type  {
                    type  leafref {
                        path  "../state/lsp-type";
                    }
                    description "This attribute provides lsp type of the MPLS BFD session";
                } // END of lsp-type definition.

                container state {
                    config false;
                    description
                        "Operational container for MPLS BFD LSP";
                    uses mpls-bfd-session-info-state;
                    uses mpls-bfd-session-common-info-state;
                    uses mpls-bfd-session-runtime-info-state;
                } // END of state-container definition.
                container statistics {
                    config false;
                    description
                        "MPLS BFD session statistics";
                    container state {
                        config false;
                        description
                            "Operational container for MPLS BFD LSP";
                        uses mpls-bfd-session-stats-info-state;
                    } // END of state-container definition.
                } // END of statistics-container definition.
            } // End of session-list
        } // END of sessions-container definition.
    } // END of mpls-bfd-session-info-top definition.
    grouping mpls-bfd-all-state {
        description
            "MPLS BFD all Configs";
        leaf lsp-type  {
            type  ipi-bfd-types:mpls_bfd_all_lsp_type_t;
            description "This attribute provides lsp type of the MPLS BFD session";
        } // END of lsp-type definition.

    } // END of mpls-bfd-all-state definition.
    grouping mpls-bfd-te-state {
        description
            "MPLS-TE BFD Configs";
        leaf lsp-type  {
            type  ipi-bfd-types:mpls_bfd_te_type_t;
            description "This attribute provides lsp type of the MPLS BFD session";
        } // END of lsp-type definition.

        leaf tunnel-name  {
            type  string {
                length "1..32";
                pattern "[^?' =,>|]+";
            }
            description "This attribute provides tunnel name of the RSVP BFD session";
        } // END of tunnel-name definition.

    } // END of mpls-bfd-te-state definition.

    grouping  mpls-lsp-grouping {
    description
        "MPLS BFD LSP configurations";
    container mpls-lsp {
        if-feature feature-list:HAVE_CUSTOM1_MPLS_BFD;
        if-feature feature-list:HAVE_BFD;
        config false;
        description
            "MPLS BFD LSP configurations";
        container summary {
            config false;
            description
                "MPLS BFD Summary";
            container state {
                config false;
                description
                    "Operational container for MPLS BFD LSP";
                uses mpls-bfd-summary-state;
            } // END of state-container definition.
        } // END of summary-container definition.
        container egress-sessions {
            config false;
            description
                "MPLS BFD Egress Sessions";

            list egress-session {
                key "local-discriminator";
                config false;
                description
                    "MPLS BFD Egress Sessions";
                leaf local-discriminator  {
                    type  leafref {
                        path  "../state/local-discriminator";
                    }
                    description "This attribute provides local discriminator of the MPLS BFD session";
                } // END of local-discriminator definition.

                container state {
                    config false;
                    description
                        "Operational container for MPLS BFD LSP";
                    uses mpls-bfd-egress-session-state;
                    uses mpls-bfd-session-common-info-state;
                } // END of state-container definition.
            } // End of egress-session-list
        } // END of egress-sessions-container definition.
        container session-groups {
            config false;
            description
                "MPLS BFD LSP Sessions";

            list session-group {
                key "lsp-type fec-address";
                config false;
                description
                    "MPLS BFD LSP Sessions";
                leaf lsp-type  {
                    type  leafref {
                        path  "../state/lsp-type";
                    }
                    description "This attribute provides lsp type of the MPLS BFD session";
                } // END of lsp-type definition.

                leaf fec-address  {
                    type  leafref {
                        path  "../state/fec-address";
                    }
                    description "This attribute provides fec address of the MPLS BFD session";
                } // END of fec-address definition.

                container state {
                    config false;
                    description
                        "Operational container for MPLS BFD LSP";
                    uses mpls-bfd-lsp-state;
                } // END of state-container definition.
                uses mpls-bfd-session-info-top;
            } // End of session-group-list
        } // END of session-groups-container definition.
    } // END of mpls-lsp-container definition.
    } // END of mpls-lsp-grouping definition.

    grouping  mpls-te-grouping {
    description
        "MPLS-TE BFD configurations";
    container mpls-te {
        if-feature feature-list:HAVE_CUSTOM1_MPLS_BFD;
        if-feature feature-list:HAVE_BFD;
        config false;
        description
            "MPLS-TE BFD configurations";
        container summary {
            config false;
            description
                "MPLS BFD Summary";
            container state {
                config false;
                description
                    "Operational container for MPLS BFD TE";
                uses mpls-bfd-summary-state;
            } // END of state-container definition.
        } // END of summary-container definition.
        container egress-sessions {
            config false;
            description
                "MPLS BFD Egress Sessions";

            list egress-session {
                key "fec-address";
                config false;
                description
                    "MPLS BFD Egress Sessions";
                leaf fec-address  {
                    type  leafref {
                        path  "../state/fec-address";
                    }
                    description "This attribute provides fec address of the MPLS BFD session";
                } // END of fec-address definition.

                container state {
                    config false;
                    description
                        "Operational container for MPLS-TE BFD";
                    uses mpls-bfd-egress-session-state;
                    uses mpls-bfd-session-common-info-state;
                } // END of state-container definition.
            } // End of egress-session-list
        } // END of egress-sessions-container definition.
        container mpls-tunnels {
            config false;
            description
                "MPLS BFD TUNNEL configurations";

            list mpls-tunnel {
                key "lsp-type tunnel-name";
                config false;
                description
                    "MPLS BFD TUNNEL configurations";
                leaf lsp-type  {
                    type  leafref {
                        path  "../state/lsp-type";
                    }
                    description "This attribute provides lsp type of the MPLS BFD session";
                } // END of lsp-type definition.

                leaf tunnel-name  {
                    type  leafref {
                        path  "../state/tunnel-name";
                    }
                    description "This attribute provides tunnel-name of the RSVP BFD session";
                } // END of tunnel-name definition.

                container state {
                    config false;
                    description
                        "Operational container for MPLS BFD";
                    uses mpls-bfd-te-state;
                } // END of state-container definition.
                uses mpls-bfd-session-info-top;
            } // End of mpls-tunnel-list
        } // END of mpls-tunnels-container definition.
    } // END of mpls-te-container definition.
    } // END of mpls-te-grouping definition.


}
