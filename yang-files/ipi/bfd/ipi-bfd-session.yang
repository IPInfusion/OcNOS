/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-bfd-session.yang
*
*/

submodule ipi-bfd-session {

    yang-version 1.1;

    belongs-to  ipi-bfd { prefix ipi-bfd; }

    import feature-list {
        prefix feature-list;
        revision-date 2026-09-15;
    }

    import ipi-bfd-types {
        prefix ipi-bfd-types;
        revision-date 2025-02-14;
    }

    import ietf-inet-types {
        prefix inet;
        revision-date 2013-07-15;
    }

    import ipi-interface {
        prefix ipi-interface;
        revision-date 2026-03-10;
    }

    import ietf-yang-types {
        prefix yang;
        revision-date 2013-07-15;
    }

    include ipi-mpls-bfd-session { revision-date 2023-01-23;}
    organization
        "IP Infusion Inc.";

    contact
        "Address: 3965 Freedom Circle, Suite 200, Santa Clara, CA 95054
         Phone: +1 408-400-1900
         E-mail: support@ipinfusion.com
         Web: http://www.ipinfusion.com/";

    description
        "Datamodel for Bidirecional Forwarding Detection (BFD) session
                information";


    revision "2025-02-24" {
        description "Added the grouping micro-bfd-session-state-common for micro-BFD sessions";
        reference " 0.6.3.";
    }

    revision "2025-02-13" {
        description "Added attribite local-discriminator under micro-bfd-sessions";
        reference " 0.6.2.";
    }

    revision "2024-04-22" {
        description "Inclusion of streaming telemetry yaml file";
        reference " 0.6.1.";
    }

    revision "2022-06-20" {
        description "Added interface-name attribute to bfd-session-state-common grouping";
        reference " 0.6.1.";
    }

    revision "2022-06-01" {
        description "Updated the yang file with feature";
        reference " 0.6.0.";
    }

    revision "2021-11-19" {
        description "Added interface-index attribute to bfd-session-state-common grouping";
        reference " 0.5.0.";
    }

    revision "2021-09-03" {
        description "Update descriptions of attribute";
        reference " 0.4.0.";
    }

    revision "2021-01-19" {
        description "Added support to micro-bfd session status";
        reference " 0.3.0.";
    }

    revision "2020-12-15" {
        description "Change to have data-types in lower case instead of camel case";
        reference " 0.2.0.";
    }

    revision "2020-11-30" {
        description "Restructured module as per open-config style";
        reference " 0.1.0.";
    }

    grouping bfd-session-counters-packet-state {
        description
            "Packets counters for BFD session state";
        leaf received  {
            type  yang:counter64;
            description "Number of packets that have been received during this BFD session";
        } // END of received definition.

        leaf transmitted  {
            type  yang:counter64;
            description "Number of packets that have been transmitted during this BFD session";
        } // END of transmitted definition.

        leaf echo-transmitted  {
            type  yang:counter64;
            description "Number of Echo-packets that have been transmitted during this BFD
                        session";
        } // END of echo-transmitted definition.

    } // END of bfd-session-counters-packet-state definition.
    grouping bfd-session-counters-state {
        description
            "Counters for BFD session state";
        leaf up-transitions  {
            type  yang:counter32;
            description "Number of times the BFD session has been up";
        } // END of up-transitions definition.

    } // END of bfd-session-counters-state definition.
    grouping bfd-session-client-state {
        description
            "bfd-session-client-state";
        leaf index  {
            type  uint32;
            description "Internal index of BFD client module";
        } // END of index definition.

        leaf flags  {
            type  ipi-bfd-types:oambfd_client_flags_t;
            description "Flags for internal BFD client module";
        } // END of flags definition.

    } // END of bfd-session-client-state definition.
    grouping bfd-session-client-state-top {
        description
            "Client for BFD session state";

        list client {
            key "index";
            config false;
            description
                "Client for BFD session";
            leaf index  {
                type  leafref {
                    path  "../state/index";
                }
                description "Session index, usually the local discriminator";
            } // END of index definition.

            container state {
                config false;
                description
                    "client for BFD session state";
                uses bfd-session-client-state;
            } // END of state-container definition.
        } // End of client-list
    } // END of bfd-session-client-state-top definition.
    grouping bfd-session-packet-state {
        description
            "Grouping for BFD session packet state";
        leaf packet-version  {
            type  uint32;
            description "Session version number of the remote system";
        } // END of packet-version definition.

        leaf packet-diagnostics  {
            type  ipi-bfd-types:oambfd_perform_diag_t;
            description "The remote BFD diagnostic code indicating the most recent reason for
                        failure of this BFD session";
        } // END of packet-diagnostics definition.

        leaf packet-state  {
            type  ipi-bfd-types:oambfd_session_state_t;
            description "The state of the BFD session perceived by the remote system";
        } // END of packet-state definition.

        leaf demand-enabled  {
            type  empty;
            description "Demand mode enabled";
        } // END of demand-enabled definition.

        leaf poll-sequence-initiated  {
            type  empty;
            description "Poll sequence initiated indication";
        } // END of poll-sequence-initiated definition.

        leaf final-bit  {
            type  boolean;
            description "Poll sequence terminated indication";
        } // END of final-bit definition.

        leaf detection-multiplier  {
            type  uint8;
            description "Detection multiplier";
        } // END of detection-multiplier definition.

        leaf length  {
            type  uint32;
            units "bytes";
            description "BFD packet length";
        } // END of length definition.

        leaf packet-local-discriminator  {
            type  string {
                length "1..1965";
                pattern "[^?' =,>|]+";
            }
            description "Local discriminator";
        } // END of packet-local-discriminator definition.

        leaf packet-remote-discriminator  {
            type  string {
                length "1..1965";
                pattern "[^?' =,>|]+";
            }
            description "Remote discriminator";
        } // END of packet-remote-discriminator definition.

        leaf packet-desired-minimum-tx-interval  {
            type  uint32;
            units "milliseconds";
            description "Minimum echo transmit interval of the remote system";
        } // END of packet-desired-minimum-tx-interval definition.

        leaf packet-required-minimum-rx-interval  {
            type  uint32;
            units "milliseconds";
            description "Minimum receive interval of the remote system";
        } // END of packet-required-minimum-rx-interval definition.

        leaf required-minimum-echo-rx-interval  {
            type  uint32;
            units "milliseconds";
            description "Minimum receive interval capacity of the remote system";
        } // END of required-minimum-echo-rx-interval definition.

    } // END of bfd-session-packet-state definition.
    grouping bfd-session-mpls-state {
        description
            "Grouping for BFD session MPLS state";
        leaf fec-address  {
            type  inet:ipv4-address;
            description "FEC Prefix";
        } // END of fec-address definition.

        leaf lsp-type  {
            type  ipi-bfd-types:oambfd_mpls_lsp_type_t;
            description "LSP Type";
        } // END of lsp-type definition.

        leaf tunnel-name  {
            type  string {
                length "1..1965";
                pattern "[^?' =,>|]+";
            }
            description "Tunnel Name";
        } // END of tunnel-name definition.

        leaf tunnel-label  {
            type  uint32;
            description "FEC/RSVP Tunnel Label";
        } // END of tunnel-label definition.

        leaf ftn-index  {
            type  uint32;
            description "FTN index of the FEC";
        } // END of ftn-index definition.

        leaf lsp-ping-interval  {
            type  uint32;
            units "milliseconds";
            description "Desired LSP Ping Interval";
        } // END of lsp-ping-interval definition.

        leaf minimum-tx  {
            type  uint32;
            units "milliseconds";
            description "Minimum transmit interval";
        } // END of minimum-tx definition.

        leaf minimum-rx  {
            type  uint32;
            units "milliseconds";
            description "Minimum receive interval";
        } // END of minimum-rx definition.

        leaf detection-multiplier  {
            type  uint8;
            description "BFD Detection multiplier value";
        } // END of detection-multiplier definition.

    } // END of bfd-session-mpls-state definition.
    grouping bfd-session-mpls-vccv {
        description
            "Grouping for BFD MPLS Virtual Circuit Connectivity Verification";
        leaf vc-identifier  {
            type  uint32;
            description "Virtual circuit identifier";
        } // END of vc-identifier definition.

        leaf incoming-vc-label  {
            type  uint32;
            description "Incoming VC label";
        } // END of incoming-vc-label definition.

        leaf outgoing-vc-label  {
            type  uint32;
            description "Outgoing VC label";
        } // END of outgoing-vc-label definition.

        leaf control-channel-type  {
            type  ipi-bfd-types:oambfd_mpls_cc_type_t;
            description "CC type";
        } // END of control-channel-type definition.

        leaf connectivity-verification-type  {
            type  ipi-bfd-types:oambfd_mpls_cv_type_t;
            description "CV type";
        } // END of connectivity-verification-type definition.

        leaf attachment-circuit-index  {
            type  uint32;
            description "Access interface index";
        } // END of attachment-circuit-index definition.

        leaf tunnel-label  {
            type  uint32;
            description "MPLS tunnel label";
        } // END of tunnel-label definition.

        leaf peer-address  {
            type  inet:ipv4-address;
            description "Remote peer IPv4 address";
        } // END of peer-address definition.

    } // END of bfd-session-mpls-vccv definition.
    grouping bfd-session-mpls-tp {
        description
            "bfd-session-mpls-tp";
        leaf maintenance-entity-group-name  {
            type  string {
                length "1..1965";
                pattern "[^?' =,>|]+";
            }
            description "Name of maintenance entity group";
        } // END of maintenance-entity-group-name definition.

        leaf maintenance-entity-name  {
            type  string {
                length "1..1965";
                pattern "[^?' =,>|]+";
            }
            description "Name of maintenance entity";
        } // END of maintenance-entity-name definition.

        leaf path-type  {
            type  ipi-bfd-types:oambfd_mpls_path_type_t;
            description "MPLS path type";
        } // END of path-type definition.

    } // END of bfd-session-mpls-tp definition.
    grouping bfd-session-echo-state {
        description
            "Grouping for BFD session echo state";
        leaf local-echo-port  {
            type  inet:port-number;
            description "Echo UDP port number of the transmitting device";
        } // END of local-echo-port definition.

        leaf echo-desired-minimum-tx-interval  {
            type  uint32;
            units "milliseconds";
            description "Minimum echo transmit interval";
        } // END of echo-desired-minimum-tx-interval definition.

        leaf echo-required-minimum-rx-interval  {
            type  uint32;
            units "milliseconds";
            description "Minimum echo receive interval";
        } // END of echo-required-minimum-rx-interval definition.

        leaf negotiated-interval  {
            type  uint32;
            units "milliseconds";
            description "Negotiated echo interval";
        } // END of negotiated-interval definition.

    } // END of bfd-session-echo-state definition.
    grouping bfd-session-state-common {
        description
            "Grouping for common runtime attributes for BFD sessions";
        leaf interface-index  {
            type  uint32;
            description "Interface index associated with this BFD session";
        } // END of interface-index definition.

        leaf interface-name  {
            type  string {
                length "1..1965";
                pattern "[^?' =,>|]+";
            }
            description "Interface name associated with this BFD session";
        } // END of interface-name definition.

        leaf remote-discriminator  {
            type  string {
                length "1..1965";
                pattern "[^?' =,>|]+";
            }
            description "A unique identified used by the remote system to identify this BFD
                        session";
        } // END of remote-discriminator definition.

        leaf local-discriminator  {
            type  string {
                length "1..1965";
                pattern "[^?' =,>|]+";
            }
            description "A unique identifier used by the local system to identify this BFD
                        session";
        } // END of local-discriminator definition.

        leaf session-state  {
            type  ipi-bfd-types:oambfd_session_state_t;
            description "The state of the BFD session perceived by the local system";
        } // END of session-state definition.

        leaf session-type  {
            type  ipi-bfd-types:bfd_session_type_state_t;
            description "Session type configured for this BFD session";
        } // END of session-type definition.

        leaf session-diagnostics  {
            type  ipi-bfd-types:oambfd_perform_diag_t;
            description "The local BFD diagnostic code indicating the most recent reason for
                        failure of this BFD session";
        } // END of session-diagnostics definition.

        leaf negotiated-tx-interval  {
            type  uint32;
            units "milliseconds";
            description "Negotiated transmit interval";
        } // END of negotiated-tx-interval definition.

        leaf negotiated-rx-interval  {
            type  uint32;
            units "milliseconds";
            description "Negotiated receive interval";
        } // END of negotiated-rx-interval definition.

    } // END of bfd-session-state-common definition.
    grouping micro-bfd-session-state-common {
        description
            "Grouping for common runtime attributes for BFD sessions";
        leaf interface-index  {
            type  uint32;
            description "Interface index associated with this BFD session";
        } // END of interface-index definition.

        leaf interface-name  {
            type  string {
                length "1..1965";
                pattern "[^?' =,>|]+";
            }
            description "Interface name associated with this BFD session";
        } // END of interface-name definition.

        leaf remote-discriminator  {
            type  string {
                length "1..1965";
                pattern "[^?' =,>|]+";
            }
            description "A unique identified used by the remote system to identify this BFD
                        session";
        } // END of remote-discriminator definition.

        leaf local-discriminator  {
            type  string {
                length "1..1965";
                pattern "[^?' =,>|]+";
            }
            description "A unique identifier used by the local system to identify this BFD
                        session";
        } // END of local-discriminator definition.

        leaf microbfd-local-discriminator  {
            type  string {
                length "1..1965";
                pattern "[^?' =,>|]+";
            }
            description "A unique identifier used by the local system to identify this BFD
                        session";
        } // END of microbfd-local-discriminator definition.

        leaf session-state  {
            type  ipi-bfd-types:oambfd_session_state_t;
            description "The state of the BFD session perceived by the local system";
        } // END of session-state definition.

        leaf session-type  {
            type  ipi-bfd-types:bfd_session_type_state_t;
            description "Session type configured for this BFD session";
        } // END of session-type definition.

        leaf session-diagnostics  {
            type  ipi-bfd-types:oambfd_perform_diag_t;
            description "The local BFD diagnostic code indicating the most recent reason for
                        failure of this BFD session";
        } // END of session-diagnostics definition.

        leaf negotiated-tx-interval  {
            type  uint32;
            units "milliseconds";
            description "Negotiated transmit interval";
        } // END of negotiated-tx-interval definition.

        leaf negotiated-rx-interval  {
            type  uint32;
            units "milliseconds";
            description "Negotiated receive interval";
        } // END of negotiated-rx-interval definition.

    } // END of micro-bfd-session-state-common definition.
    grouping bfd-session-microbfd-state {
        description
            "Operational state parameters relating to a micro-BFD session on an
                        interface";
        leaf member-interface  {
            type  leafref {
                path  "/ipi-interface:interfaces/ipi-interface:interface/ipi-interface:name";
            }
            description "Reference to a member link of the aggregate interface being described";
        } // END of member-interface definition.

        leaf remote-session-state  {
            type  ipi-bfd-types:oambfd_session_state_t;
            description "The reported state of the BFD session according to the remote system.
                        This state reflects the last state reported in a BFD control packet";
        } // END of remote-session-state definition.

        leaf remote-session-diagnostics  {
            type  ipi-bfd-types:oambfd_perform_diag_t;
            description "The remote BFD diagnostic code indicating the remote system's reason
                        for failure of the BFD session";
        } // END of remote-session-diagnostics definition.

    } // END of bfd-session-microbfd-state definition.
    grouping bfd-session-state {
        description
            "Grouping for BFD session state";
        leaf lower-layer-type  {
            type  ipi-bfd-types:oambfd_sess_lower_layer_t;
            description "The lower layer protocol on which BFD is carried";
        } // END of lower-layer-type definition.

        leaf uptime  {
            type  yang:timeticks;
            units "seconds";
            description "Length of time this BFD session has been up";
        } // END of uptime definition.

        leaf version  {
            type  uint32;
            description "Session version number";
        } // END of version definition.

        leaf local-port  {
            type  inet:port-number;
            description "UDP port number of the transmitting device";
        } // END of local-port definition.

        leaf remote-port  {
            type  inet:port-number;
            description "UDP port number of destination";
        } // END of remote-port definition.

        leaf negotiated-detection-multiplier  {
            type  uint8;
            description "Negotiated detection multiplier";
        } // END of negotiated-detection-multiplier definition.

        leaf forward-hello-timer-hits  {
            type  uint32;
            units "milliseconds";
            description "Hello timer hits";
        } // END of forward-hello-timer-hits definition.

        leaf remote-heard  {
            type  empty;
            description "Indication that a BFD control packet has been received from remote
                        peer";
        } // END of remote-heard definition.

        leaf fate-shared  {
            type  empty;
            description "Indication that a failure in this BFD session cannot be disentangled
                        from other events taking place in the control plane";
        } // END of fate-shared definition.

        leaf remote-administrative-down  {
            type  empty;
            description "This leaf is set to true when the remote system is administratively
                        down";
        } // END of remote-administrative-down definition.

        leaf remote-demand-mode-enabled  {
            type  empty;
            description "This leaf is set to true when the remote system has requested demand
                        mode be run for this session";
        } // END of remote-demand-mode-enabled definition.

        leaf remote-echo-enabled  {
            type  empty;
            description "This leaf is set to true when the remote system is operating in echo
                        mode";
        } // END of remote-echo-enabled definition.

        leaf poll-bit  {
            type  empty;
            description "BFD poll sequence indication";
        } // END of poll-bit definition.

        leaf storage-type  {
            type  ipi-bfd-types:bfd_storage_type_t;
            description "SNMPv2 storage type";
        } // END of storage-type definition.

        leaf downtime  {
            type  yang:timeticks;
            units "seconds";
            description "Amount of time that this BFD session is in down state";
        } // END of downtime definition.

        leaf discontinuity-time  {
            type  yang:timeticks;
            units "seconds";
            description "Time when counters met with discontinuity";
        } // END of discontinuity-time definition.

        leaf authentication-key-id  {
            type  uint32;
            description "identifier number of the authentication key specified for this BFD
                        session";
        } // END of authentication-key-id definition.

        leaf last-up-time  {
            type  yang:timeticks;
            units "seconds";
            description "The time of the last transition of the BFD session to UP state,
                        expressed as the number of seconds since the Unix epoch";
        } // END of last-up-time definition.

        leaf hold-down-timer  {
            type  uint32;
            units "milliseconds";
            description "Time for holding the session before deleting it";
        } // END of hold-down-timer definition.

        leaf hold-down-timer-hits  {
            type  uint32;
            units "milliseconds";
            description "Elapsed time for holding the session before deleting it";
        } // END of hold-down-timer-hits definition.

        leaf session-type-status  {
            type  ipi-bfd-types:oambfd_session_type_status_t;
            description "Detailed session type";
        } // END of session-type-status definition.

        leaf remote-address  {
            type  inet:ip-address;
            description "The IP address used by the remote system for this BFD session";
        } // END of remote-address definition.

        leaf local-address  {
            type  inet:ip-address;
            description "The IP address used by the local system for this BFD session";
        } // END of local-address definition.

        leaf vrf-name  {
            type  string {
                length "1..1965";
                pattern "[^?' =,>|]+";
            }
            description "VRF name";
        } // END of vrf-name definition.

    } // END of bfd-session-state definition.

    grouping  sessions-grouping {
    description
        "BFD sessions on this interface";
    container sessions {
        if-feature feature-list:HAVE_BFD;
        config false;
        description
            "BFD sessions on this interface";

        list session {
            key "local-discriminator vrf-name";
            config false;
            description
                "BFD sessions list";
            leaf local-discriminator  {
                type  leafref {
                    path  "../state/local-discriminator";
                }
                description "A unique identifier used by the local system to identify this BFD
                            session";
            } // END of local-discriminator definition.

            leaf vrf-name  {
                type  leafref {
                    path  "../state/vrf-name";
                }
                description "VRF name";
            } // END of vrf-name definition.

            container state {
                config false;
                description
                    "BFD session state";
                container counters {
                    config false;
                    description
                        "BFD session counters state";
                    container packets {
                        config false;
                        description
                            "BFD session packets counters state";
                        container ipv4 {
                            config false;
                            description
                                "BFD session ipv4 packets counters state";
                            uses bfd-session-counters-packet-state;
                        } // END of ipv4-container definition.
                        container ipv6 {
                            if-feature feature-list:HAVE_IPV6;
                            config false;
                            description
                                "BFD session IPv6 packets counters state";
                            uses bfd-session-counters-packet-state;
                        } // END of ipv6-container definition.
                    } // END of packets-container definition.
                    uses bfd-session-counters-state;
                } // END of counters-container definition.
                uses bfd-session-state;
                uses bfd-session-state-common;
            } // END of state-container definition.
            container micro-bfd-sessions {
                if-feature feature-list:HAVE_BFD_HW_OFFLOAD;
                config false;
                description
                    "Include per-member link BFD only when the type of interface is a link
                            aggregate";

                list interface {
                    if-feature feature-list:HAVE_BFD_HW_OFFLOAD;
                    key "member-interface";
                    config false;
                    description
                        "This list contains configuration and state parameters relating to
                                    micro-BFD session";
                    leaf member-interface  {
                        type  leafref {
                            path  "../state/member-interface";
                        }
                        description "Reference to a member link of the aggregate interface being described";
                    } // END of member-interface definition.

                    container state {
                        config false;
                        description
                            "Operational state parameters for the micro-BFD session";
                        uses bfd-session-microbfd-state;
                        uses micro-bfd-session-state-common;
                    } // END of state-container definition.
                } // End of interface-list
            } // END of micro-bfd-sessions-container definition.
            container echo {
                config false;
                description
                    "BFD session echo";
                container state {
                    config false;
                    description
                        "BFD session echo state";
                    uses bfd-session-echo-state;
                } // END of state-container definition.
            } // END of echo-container definition.
            container mpls {
                if-feature feature-list:HAVE_CUSTOM1_MPLS_BFD;
                config false;
                description
                    "BFD session MPLS";
                container state {
                    if-feature feature-list:HAVE_MPLS_OAM;
                    config false;
                    description
                        "BFD session MPLS state";
                    uses bfd-session-mpls-state;
                } // END of state-container definition.
                container virtual-circuit-connectivity-verification {
                    config false;
                    description
                        "Virtual Circuit Connectivity Verification for BFD MPLS session";
                    container state {
                        if-feature feature-list:HAVE_VCCV;
                        config false;
                        description
                            "Virtual Circuit Connectivity Verification for BFD MPLS session state";
                        uses bfd-session-mpls-vccv;
                    } // END of state-container definition.
                } // END of virtual-circuit-connectivity-verification-container definition.
                container transport-profile {
                    config false;
                    description
                        "Transport profile for BFD MPLS session";
                    container state {
                        if-feature feature-list:HAVE_MPLS_TP;
                        config false;
                        description
                            "Transport profile for BFD MPLS session state";
                        uses bfd-session-mpls-tp;
                    } // END of state-container definition.
                } // END of transport-profile-container definition.
            } // END of mpls-container definition.
            container packet {
                config false;
                description
                    "BFD session packet state";
                container state {
                    if-feature feature-list:NOT_HAVE_BFD_HW_OFFLOAD;
                    config false;
                    description
                        "BFD session MPLS state";
                    uses bfd-session-packet-state;
                } // END of state-container definition.
            } // END of packet-container definition.
            container clients {
                config false;
                description
                    "Clients for BFD session";
                uses bfd-session-client-state-top;
            } // END of clients-container definition.
        } // End of session-list
        uses mpls-lsp-grouping;
        uses mpls-te-grouping;
    } // END of sessions-container definition.
    } // END of sessions-grouping definition.


}
