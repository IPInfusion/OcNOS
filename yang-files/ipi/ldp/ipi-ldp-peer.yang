/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-ldp-peer.yang
*
*/

submodule ipi-ldp-peer {

    yang-version 1.1;

    belongs-to  ipi-ldp { prefix ipi-ldp; }

    import feature-list {
        prefix feature-list;
        revision-date 2026-09-15;
    }

    import cml-data-types {
        prefix cml-data-types;
        revision-date 2026-05-15;
    }

    import ipi-ldp-types {
        prefix ipi-ldp-types;
        revision-date 2026-02-09;
    }

    import ipi-interface {
        prefix ipi-interface;
        revision-date 2026-03-10;
    }

    import ietf-inet-types {
        prefix inet;
        revision-date 2013-07-15;
    }

    include ipi-ldp-l2vpn { revision-date 2026-01-12;}
    organization
        "IP Infusion Inc.";

    contact
        "Address: 3965 Freedom Circle, Suite 200, Santa Clara, CA 95054
         Phone: +1 408-400-1900
         E-mail: support@ipinfusion.com
         Web: http://www.ipinfusion.com/";

    description
        "Datamodel for LDP Peer information";


    revision "2026-01-06" {
        description "Added dependency on transport address for targeted peers top level container";
        reference " 0.9.4.";
    }

    revision "2025-11-28" {
        description "Added dependency on ldp global instance for targeted peers top level container";
        reference " 0.9.3.";
    }

    revision "2025-10-24" {
        description "Added dependency between graceful-restart and targeted peer config";
        reference " 0.9.2.";
    }

    revision "2025-02-21" {
        description "Added new attribute tunnel inside targeted peer objectlist";
        reference " 0.9.1.";
    }

    revision "2025-02-19" {
        description "Added streaming telemetry support";
        reference " 0.9.0.";
    }

    revision "2024-08-07" {
        description "Changed the help string for targeted hello timer config";
        reference " 0.8.2.";
    }

    revision "2023-08-28" {
        description "Removed implicit delete tag for config container of targeted peer objectlist";
        reference " 0.8.1.";
    }

    revision "2023-08-21" {
        description "Added a new attribute local-address under adjacency-list object list";
        reference " 0.8.0.";
    }

    revision "2023-01-17" {
        description "Addressed cli-prependstr not used warnings";
        reference " 0.7.0.";
    }

    revision "2022-07-31" {
        description "Stop using inet:ipv4-prefix and inet:ipv6-prefix due to Cisco NSO iterop";
        reference " 0.6.0.";
    }

    revision "2022-06-01" {
        description "Updated the yang file with feature";
        reference " 0.5.0.";
    }

    revision "2022-01-18" {
        description "Include session-protetection attribute";
        reference " 0.4.0.";
    }

    revision "2021-09-03" {
        description "Update descriptions of attribute";
        reference " 0.3.0.";
    }

    revision "2020-12-15" {
        description "Change to have data-types in lower case instead of camel case";
        reference " 0.2.0.";
    }

    revision "2018-06-21" {
        description "Initial Version";
        reference " 0.1.0.";
    }

    grouping ldp-targeted-global-hello-timers-config {
        description
            "Grouping for global level hello timers for targeted peers";
        leaf targeted-global-hello-interval  {
            type  uint16 {
                 range "1..21845"  {
                    description "1..21845: Supported range 1 - 21845";
                 }
            }
            default "15";
            description "Use this attribute to set the interval for sending unicast hello
                        packets to targeted peers";
        } // END of targeted-global-hello-interval definition.

        leaf targeted-global-hello-holdtime  {
            type  uint16 {
                 range "3..65535"  {
                    description "3..65535: Supported range 3 - 65535";
                 }
            }
            default "45";
            description "Use this attribute to set the time-out value that is the time that the
                        router waits before rejecting an adjacency with targeted peers.";
        } // END of targeted-global-hello-holdtime definition.

    } // END of ldp-targeted-global-hello-timers-config definition.
    grouping ldp-targeted-peer-list {
        description
            "Grouping for Targeted-LDP peers configuration";

        list targeted-peer {
            key "target-address";
            description
                "Object list for Targeted-LDP peers configuration";
            leaf target-address  {
                type  leafref {
                    path  "../config/target-address";
                }
                description "Use this attribute to enter a targeted IPv4 or IPv6 LDP peer mode. A
                            targeted session is an LDP session between non-directly connected
                            LSRs. Set this command to send a targeted hello messages to specific
                            IP addresses. This command is specific to a targeted IPv4 or IPv6 LDP
                            peer.";
            } // END of target-address definition.

            container config {
                description
                    "Configuration data";
                uses ldp-targeted-address-config;
                uses ldp-targeted-hello-timers-config;
            } // END of config-container definition.
            container state {
                config false;
                description
                    "Operational state data";
                uses ldp-targeted-address-config;
                uses ldp-targeted-hello-timers-config;
                uses ldp-counters-state;
            } // END of state-container definition.
        } // End of targeted-peer-list
    } // END of ldp-targeted-peer-list definition.
    grouping ldp-targeted-hello-timers-config {
        description
            "Grouping for LDP capabilities for Hello Timers configurtaion";
        leaf hello-interval  {
            type  uint16 {
                 range "1..21845"  {
                    description "1..21845: Supported range 1 - 21845";
                 }
            }
            units "seconds";
            default "15";
            description "Use this attribute set the hello interval to send the hello messages
                        to peers";
        } // END of hello-interval definition.

        leaf hello-holdtime  {
            type  uint16 {
                 range "3..65535"  {
                    description "3..65535: Supported range 3 - 65535";
                 }
            }
            units "seconds";
            default "45";
            description "Use this attribute set the hello hold time as the time out value that
                        the router waits before rejecting an adjacency";
        } // END of hello-holdtime definition.

    } // END of ldp-targeted-hello-timers-config definition.
    grouping ldp-targeted-address-config {
        description
            "Grouping for Targeted-peer address configuration";
        leaf target-address  {
            type  ipi-ldp-types:ldp_ip_addr_t;
            description "Use this attribute to enter a targeted IPv4 or IPv6 LDP peer mode. A
                        targeted session is an LDP session between non-directly connected
                        LSRs. Set this command to send a targeted hello messages to specific
                        IP addresses. This command is specific to a targeted IPv4 or IPv6 LDP
                        peer.";
        } // END of target-address definition.

        leaf tunnel  {
            type  empty;
            description "Use this attribute to specify tunnel for targeted peer";
        } // END of tunnel definition.

    } // END of ldp-targeted-address-config definition.
    grouping ldp-peer-info-state {
        description
            "State data for peer-session information";
        leaf peer-address  {
            type  inet:ipv4-address;
            description "This attribute acquires LDP peer address";
        } // END of peer-address definition.

        leaf ldp-identifier  {
            type  string {
                length "1..1965";
                pattern "[^?' =,>|]+";
            }
            description "This attribute acquires LDP-ID of peer";
        } // END of ldp-identifier definition.

        leaf label-space  {
            type  uint16;
            description "This attribute acquires label space of peer";
        } // END of label-space definition.

        leaf keepalive-timeout  {
            type  uint32;
            description "This attribute acquires keepalive timeout of peer";
        } // END of keepalive-timeout definition.

        leaf session-up-time  {
            type  string {
                length "1..1965";
                pattern "[^?' =,>|]+";
            }
            description "This attribute acquires LDP session uptime";
        } // END of session-up-time definition.

        leaf session-state  {
            type  ipi-ldp-types:ldp_session_state_t;
            description "This attribute acquires state of LDP Session";
        } // END of session-state definition.

        leaf session-role  {
            type  ipi-ldp-types:ldp_session_role_t;
            description "This attribute acquires role of LDP Session";
        } // END of session-role definition.

        leaf advertisement-mode  {
            type  ipi-ldp-types:ldp_advertise_mode_t;
            description "This attribute acquires advertisement mode of LDP Session";
        } // END of advertisement-mode definition.

        leaf retention-mode  {
            type  ipi-ldp-types:ldp_retention_mode_t;
            description "This attribute acquires retention mode of LDP Session";
        } // END of retention-mode definition.

        leaf tcp-established  {
            type  ipi-ldp-types:ldp_tcp_status_t;
            description "This attribute acquires informatoin for establishment of TCP
                        connection";
        } // END of tcp-established definition.

        leaf ldp-interface-name  {
            type  string {
                length "1..1965";
                pattern "[^?' =,>|]+";
            }
            description "This attribute acquires interface name over which ldp session
                        is established";
        } // END of ldp-interface-name definition.

        leaf discontinuity-time  {
            type  uint32;
            description "The value on the most recent occasion at which any one or more of this
                        session's
                        counters suffered a discontinuity.";
        } // END of discontinuity-time definition.

        leaf unknown-message-type-errors  {
            type  uint32;
            description "This object counts the number of Unknown Message Type Errors detected
                        by this LSR/LER during this session";
        } // END of unknown-message-type-errors definition.

        leaf unknown-tlv-type-errors  {
            type  uint32;
            description "This object counts the number of Unknown TLV Errors detected by this
                        LSR/LER during this session";
        } // END of unknown-tlv-type-errors definition.

        leaf initialization-session-threshold-limit  {
            type  uint32;
            description "This attribute acquires the threshold value of number of Session
                        Initialization
                        messages can be sent.";
        } // END of initialization-session-threshold-limit definition.

        leaf entity-path-vector-limit  {
            type  uint32;
            description "If this object has a value greater than zero, then Loop Dection for
                        Path Vectors is enabled,
                        and the Path Vector Limit is this value.";
        } // END of entity-path-vector-limit definition.

        leaf peer-path-vector-limit  {
            type  uint32;
            description "This object acquires the peer's Path Vector Limit value.";
        } // END of peer-path-vector-limit definition.

        leaf session-protection-status  {
            if-feature feature-list:HAVE_LDP_SESS_PROT;
            type  ipi-ldp-types:ldp_sess_prot_status_t;
            description "LDP Session Protection Status";
        } // END of session-protection-status definition.

    } // END of ldp-peer-info-state definition.
    grouping ldp-graceful-restart-info-state {
        description
            "State data for GR related peer information";
        leaf reconnect-timeout  {
            if-feature feature-list:HAVE_RESTART;
            type  uint32;
            description "This attribute acquires reconnect timeout value for LDP GR";
        } // END of reconnect-timeout definition.

        leaf recovery-time  {
            if-feature feature-list:HAVE_RESTART;
            type  uint32;
            description "This attribute acquires recovery time value for LDP GR";
        } // END of recovery-time definition.

        leaf reconnect-interval  {
            if-feature feature-list:HAVE_RESTART;
            type  int32;
            description "This attribute acquires reconnect interval value for LDP GR";
        } // END of reconnect-interval definition.

        leaf graceful-restart-capability  {
            if-feature feature-list:HAVE_RESTART;
            type  uint8;
            description "This attribute acquires LDP GR capability state";
        } // END of graceful-restart-capability definition.

        leaf graceful-restart-flags  {
            if-feature feature-list:HAVE_RESTART;
            type  uint8;
            description "This attribute acquires LDP GR flag values";
        } // END of graceful-restart-flags definition.

    } // END of ldp-graceful-restart-info-state definition.
    grouping ldp-adjacency-info-state {
        description
            "State data for LDP adjacency with peer";
        leaf adjacency-prefix  {
            type  inet:ipv4-address;
            description "This attribute acquires prefix IP address for adjacency";
        } // END of adjacency-prefix definition.

        leaf is-targeted-peer  {
            type  boolean;
            description "This attribute acquires information if adjacency formed is for
                        targeted session";
        } // END of is-targeted-peer definition.

        leaf name  {
            type  leafref {
                path  "/ipi-interface:interfaces/ipi-interface:interface/ipi-interface:name";
            }
            description "This attribute acquires interface name using which LDP
                        adjacency was formed";
        } // END of name definition.

        leaf local-address  {
            type  inet:ipv4-address;
            description "This attribute is used to specify the local address of ldp adjacency";
        } // END of local-address definition.

    } // END of ldp-adjacency-info-state definition.
    grouping ldp-label-mapping-state {
        description
            "State data for LDP Fec_Label mapping with peer";
        leaf fec-prefix  {
            type  cml-data-types:cml_ipv4_addr_prefix_t;
            description "This attribute acquires FEC (IP-Prefix) for which label mapping is
                        formed";
        } // END of fec-prefix definition.

        leaf label  {
            type  string {
                length "1..1965";
                pattern "[^?' =,>|]+";
            }
            description "This attribute acquires label value for a fec-prefix";
        } // END of label definition.

    } // END of ldp-label-mapping-state definition.

    grouping  targeted-peers-grouping {
    description
        "Configuration data for Targeted LDP";
    container targeted-peers {
        // when " ipi-ldp:ldp/global/config ";
        if-feature feature-list:HAVE_LDPD;
        description
            "Configuration data for Targeted LDP";
        container global-timers {
            // when " ipi-ldp:ldp/global/config ";
            description
                "Configuration data";
            container config {
                description
                    "Configuration data";
                uses ldp-targeted-global-hello-timers-config;
            } // END of config-container definition.
            container state {
                config false;
                description
                    "Operational state data";
                uses ldp-targeted-global-hello-timers-config;
            } // END of state-container definition.
        } // END of global-timers-container definition.
        uses ldp-targeted-peer-list;
    } // END of targeted-peers-container definition.
    } // END of targeted-peers-grouping definition.

    grouping  peers-grouping {
    description
        "LDP peers container";
    container peers {
        if-feature feature-list:HAVE_LDPD;
        config false;
        description
            "LDP peers container";

        list peer {
            key "peer-address";
            config false;
            description
                "State data list for LDP Peers";
            leaf peer-address  {
                type  leafref {
                    path  "../state/peer-address";
                }
                description "This attribute acquires LDP peer address";
            } // END of peer-address definition.


            list adjacency-list {
                key "adjacency-prefix";
                config false;
                description
                    "State data list for LDP adjacencies";
                leaf adjacency-prefix  {
                    type  leafref {
                        path  "../state/adjacency-prefix";
                    }
                    description "This attribute acquires prefix IP address for adjacency";
                } // END of adjacency-prefix definition.

                container state {
                    config false;
                    description
                        "Operational state data";
                    uses ldp-adjacency-info-state;
                } // END of state-container definition.
            } // End of adjacency-list-list

            list received-label-list {
                key "fec-prefix";
                config false;
                description
                    "State labels received from LDP Peers";
                leaf fec-prefix  {
                    type  leafref {
                        path  "../state/fec-prefix";
                    }
                    description "This attribute acquires FEC (IP-Prefix) for which label mapping is
                                formed";
                } // END of fec-prefix definition.

                container state {
                    config false;
                    description
                        "Operational state data";
                    uses ldp-label-mapping-state;
                } // END of state-container definition.
            } // End of received-label-list-list

            list sent-label-list {
                key "fec-prefix";
                config false;
                description
                    "State labels sent to LDP Peers";
                leaf fec-prefix  {
                    type  leafref {
                        path  "../state/fec-prefix";
                    }
                    description "This attribute acquires FEC (IP-Prefix) for which label mapping is
                                formed";
                } // END of fec-prefix definition.

                container state {
                    config false;
                    description
                        "Operational state data";
                    uses ldp-label-mapping-state;
                } // END of state-container definition.
            } // End of sent-label-list-list
            container state {
                config false;
                description
                    "Operational state data";
                uses ldp-peer-info-state;
            } // END of state-container definition.
        } // End of peer-list
    } // END of peers-container definition.
    } // END of peers-grouping definition.


}
