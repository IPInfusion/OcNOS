/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-ldp-l2vpn.yang
*
*/

submodule ipi-ldp-l2vpn {

    yang-version 1.1;

    belongs-to  ipi-ldp { prefix ipi-ldp; }

    import feature-list {
        prefix feature-list;
        revision-date 2026-09-15;
    }

    import ietf-yang-types {
        prefix yang;
        revision-date 2013-07-15;
    }

    import ietf-inet-types {
        prefix inet;
        revision-date 2013-07-15;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for LDP-L2VPN attributes information";


    revision "2026-01-12" {
        description "Updated datatype from LDP_VC_STATE_T to CML_STRING_T for virtual-circuit-state attribute";
        reference " 0.8.0.";
    }

    revision "2024-05-24" {
        description "Added attributes to display Local and Remote Pseudowire Status Capability";
        reference " 0.7.0.";
    }

    revision "2023-09-01" {
        description "Updated if-feature flag for LDP VPLS counters";
        reference " 0.6.1.";
    }

    revision "2023-08-24" {
        description "Added new attributes for LDP VPLS counters";
        reference " 0.6.0.";
    }

    revision "2022-09-08" {
        description "Added HAVE_MPLS_VC and HAVE_VPLS flags to fix compilation issues";
        reference " 0.5.1.";
    }

    revision "2022-08-10" {
        description "Debug hierarchy change";
        reference " 0.5.0.";
    }

    revision "2022-06-01" {
        description "Updated the yang file with feature";
        reference " 0.4.0.";
    }

    revision "2021-09-03" {
        description "Update descriptions of attribute";
        reference " 0.3.0.";
    }

    revision "2020-12-15" {
        description "Change to have data-types in lower case instead of camel case";
        reference " 0.2.0.";
    }

    revision "2018-06-21" {
        description "Initial Version";
        reference " 0.1.0.";
    }

    grouping ldp-hello-timers-config {
        description
            "Grouping for LDP capabilities for Hello Timers configurtaion";
        leaf hello-interval  {
            type  uint16 {
                 range "1..21845"  {
                    description "1..21845: Supported range 1 - 21845";
                 }
            }
            units "seconds";
            default "5";
            description "Use this attribute set the hello interval to send the hello messages
                        to peers";
        } // END of hello-interval definition.

        leaf hello-holdtime  {
            type  uint16 {
                 range "3..65535"  {
                    description "3..65535: Supported range 3 - 65535";
                 }
            }
            units "seconds";
            default "15";
            description "Use this attribute set the hello hold time as the time out value that
                        the router waits before rejecting an adjacency";
        } // END of hello-holdtime definition.

    } // END of ldp-hello-timers-config definition.
    grouping ldp-session-timers-config {
        description
            "Grouping for LDP capabilities for Keepalive Timers configuration";
        leaf keepalive-timeout  {
            type  uint16 {
                 range "3..65535"  {
                    description "3..65535: Supported range 3 - 65535";
                 }
            }
            units "seconds";
            default "30";
            description "Use this attribute to set the time period for which an LSR must wait
                        for successive keep-alive messages from LDP peers";
        } // END of keepalive-timeout definition.

        leaf keepalive-interval  {
            type  uint16 {
                 range "1..21845"  {
                    description "1..21845: Supported range 1 - 21845";
                 }
            }
            units "seconds";
            default "10";
            description "Use this attribute to set the global value for the interval after
                        which keep-alive packets are sent out";
        } // END of keepalive-interval definition.

    } // END of ldp-session-timers-config definition.
    grouping ldp-counters-state {
        description
            "Targeted peer address data grouping";
        container counters {
            config false;
            description
                "Operational state data";
            container packets {
                config false;
                description
                    "LDP Packets data";
                container received {
                    config false;
                    description
                        "LDP Packets Received";
                    uses ldp-packets-state;
                } // END of received-container definition.
                container sent {
                    config false;
                    description
                        "LDP Packets Sent";
                    uses ldp-packets-state;
                } // END of sent-container definition.
            } // END of packets-container definition.
            container events {
                config false;
                description
                    "LDP events data";
                uses ldp-events-state;
            } // END of events-container definition.
        } // END of counters-container definition.
    } // END of ldp-counters-state definition.
    grouping ldp-targeted-peer-address {
        description
            "Targeted peer address data grouping";
        leaf targeted-peer-address  {
            type  string {
                length "1..1965";
                pattern "[^?' =,>|]+";
            }
            config false;
            description "This attribute stores targeted peer address for targeted for targeted
                        LDP session";
        } // END of targeted-peer-address definition.

    } // END of ldp-targeted-peer-address definition.
    grouping ldp-packets-state {
        description
            "State data grouping for LDP Packets";
        leaf notification  {
            type  yang:counter32;
            description "This attribute stores counter for LDP Notification message";
        } // END of notification definition.

        leaf hello  {
            type  yang:counter32;
            description "This attribute stores counter for LDP Hello message";
        } // END of hello definition.

        leaf initialization  {
            type  yang:counter32;
            description "This attribute stores counter for LDP Session Initialization message";
        } // END of initialization definition.

        leaf keepalive  {
            type  yang:counter32;
            description "This attribute stores counter for LDP Session keepalive message";
        } // END of keepalive definition.

        leaf address-message  {
            type  yang:counter32;
            description "This attribute stores counter for LDP Session address message";
        } // END of address-message definition.

        leaf address-withdraw  {
            type  yang:counter32;
            description "This attribute stores counter for LDP Session address withdraw message";
        } // END of address-withdraw definition.

        leaf label-mapping  {
            type  yang:counter32;
            description "This attribute stores counter for LDP Label Mapping message";
        } // END of label-mapping definition.

        leaf label-request  {
            type  yang:counter32;
            description "This attribute stores counter for LDP Label Request message";
        } // END of label-request definition.

        leaf label-withdraw  {
            type  yang:counter32;
            description "This attribute stores counter for LDP Label Withdraw message";
        } // END of label-withdraw definition.

        leaf label-release  {
            type  yang:counter32;
            description "This attribute stores counter for LDP Label Release message";
        } // END of label-release definition.

        leaf request-abort  {
            type  yang:counter32;
            description "This attribute stores counter for LDP Abort message";
        } // END of request-abort definition.

    } // END of ldp-packets-state definition.
    grouping ldp-events-state {
        description
            "State data grouping for LDP Packets";
        leaf ldp-shutdown-notification-received  {
            type  yang:counter32;
            description "This attribute stores counter for LDP shutdown notification received";
        } // END of ldp-shutdown-notification-received definition.

        leaf ldp-shutdown-notification-sent  {
            type  yang:counter32;
            description "This attribute stores counter for LDP shutdown notification sent";
        } // END of ldp-shutdown-notification-sent definition.

        leaf ldp-sessions-attempted  {
            type  yang:counter32;
            description "This attribute stores counter for LDP sessions attempted";
        } // END of ldp-sessions-attempted definition.

        leaf ldp-session-rejected-no-hello-errors  {
            type  yang:counter32;
            description "This attribute stores counter for LDP session rejected due to no hello
                        message";
        } // END of ldp-session-rejected-no-hello-errors definition.

        leaf ldp-session-rejected-advertisement-errors  {
            type  yang:counter32;
            description "This attribute stores counter for LDP session rejected due to
                        advertisement errors";
        } // END of ldp-session-rejected-advertisement-errors definition.

        leaf ldp-session-rejected-maximum-pdu-errors  {
            type  yang:counter32;
            description "This attribute stores counter for LDP session rejected due to maximum
                        pdu errors";
        } // END of ldp-session-rejected-maximum-pdu-errors definition.

        leaf ldp-session-rejected-label-range-errors  {
            type  yang:counter32;
            description "This attribute stores counter for LDP session rejected due to
                        label-range errors";
        } // END of ldp-session-rejected-label-range-errors definition.

        leaf ldp-bad-ldp-identifier-errors  {
            type  yang:counter32;
            description "This attribute stores counter for incorrect LDP-ID error";
        } // END of ldp-bad-ldp-identifier-errors definition.

        leaf ldp-bad-pdu-length-errors  {
            type  yang:counter32;
            description "This attribute stores counter for incorrect PDU length errors";
        } // END of ldp-bad-pdu-length-errors definition.

        leaf ldp-bad-message-length-errors  {
            type  yang:counter32;
            description "This attribute stores counter for incorrect message length errors";
        } // END of ldp-bad-message-length-errors definition.

        leaf ldp-bad-tlv-length-errors  {
            type  yang:counter32;
            description "This attribute stores counter for LDP message incorrect TLV length
                        errors";
        } // END of ldp-bad-tlv-length-errors definition.

        leaf ldp-malformed-tlv-value-errors  {
            type  yang:counter32;
            description "This attribute stores counter for LDP message malformed TLV errors";
        } // END of ldp-malformed-tlv-value-errors definition.

        leaf ldp-keepalive-timer-expired-errors  {
            type  yang:counter32;
            description "This attribute stores counter for LDP keepalive timer exipry";
        } // END of ldp-keepalive-timer-expired-errors definition.

    } // END of ldp-events-state definition.
    grouping ldp-vpls-virtual-circuit-top {
        description
            "Top level grouping for LDP based Virtual-Circuit";

        list virtual-circuit-list {
            key "neighbor-address";
            config false;
            description
                "VC list established by LDP";
            leaf neighbor-address  {
                type  leafref {
                    path  "../state/neighbor-address";
                }
                description "This attribute acquires the virtual circuit peer's address";
            } // END of neighbor-address definition.

            container state {
                config false;
                description
                    "Operational state data";
                uses ldp-virtual-circuit-info-state;
            } // END of state-container definition.
        } // End of virtual-circuit-list-list
    } // END of ldp-vpls-virtual-circuit-top definition.
    grouping ldp-virtual-circuit-top {
        description
            "Top level grouping for LDP based Virtual-Circuit";

        list virtual-circuit-list {
            if-feature feature-list:HAVE_MPLS_VC;
            key "virtual-circuit-identifier";
            config false;
            description
                "VC list established by LDP";
            leaf virtual-circuit-identifier  {
                type  leafref {
                    path  "../state/virtual-circuit-identifier";
                }
                description "This attribute acquires virtual circuit Id of a pseudowire";
            } // END of virtual-circuit-identifier definition.

            container state {
                config false;
                description
                    "Operational state data";
                uses ldp-virtual-circuit-info-state;
            } // END of state-container definition.
        } // End of virtual-circuit-list-list
    } // END of ldp-virtual-circuit-top definition.
    grouping ldp-vpls-counters-state {
        description
            "Grouping for global counters for VPLS";
        leaf total-vpls-instances  {
            type  yang:counter32;
            description "This attribute acquires total VPLS instances";
        } // END of total-vpls-instances definition.

        leaf total-virtual-circuit-instances  {
            type  yang:counter32;
            description "This attribute acquires total VC instances";
        } // END of total-virtual-circuit-instances definition.

        leaf active-virtual-circuit-instances  {
            type  yang:counter32;
            description "This attribute acquires total active VC instances";
        } // END of active-virtual-circuit-instances definition.

        leaf inactive-virtual-circuit-instances  {
            type  yang:counter32;
            description "This attribute acquires total non-active VC instances";
        } // END of inactive-virtual-circuit-instances definition.

    } // END of ldp-vpls-counters-state definition.
    grouping ldp-virtual-circuit-info-state {
        description
            "State data for LDP based Virtual-Circuits";
        leaf virtual-circuit-identifier  {
            type  uint32;
            description "This attribute acquires virtual circuit Id of a pseudowire";
        } // END of virtual-circuit-identifier definition.

        leaf neighbor-address  {
            type  inet:ipv4-address;
            description "This attribute acquires the virtual circuit peer's address";
        } // END of neighbor-address definition.

        leaf virtual-circuit-state  {
            type  string {
                length "1..1965";
                pattern "[^?' =,>|]+";
            }
            description "This attribute acquires the virtual circuit status";
        } // END of virtual-circuit-state definition.

        leaf local-pw-status-capability  {
            type  uint32;
            description "This attribute is used to indicate Local Pseudowire Status Capability";
        } // END of local-pw-status-capability definition.

        leaf remote-pw-status-capability  {
            type  uint32;
            description "This attribute is used to indicate Remote Pseudowire Status Capability";
        } // END of remote-pw-status-capability definition.

        leaf current-pw-status-tlv  {
            type  uint32;
            description "This attribute is used to indicate Current Pseudowire Status
                        Capability";
        } // END of current-pw-status-tlv definition.

        leaf local-pseudowire-status  {
            type  string {
                length "1..1965";
            }
            description "This attribute acquires the virtual circuit's local status, if status
                        capability is configured";
        } // END of local-pseudowire-status definition.

        leaf remote-pseudowire-status  {
            type  string {
                length "1..1965";
            }
            description "This attribute acquires the virtual circuit's remote status, if status
                        capability is configured";
        } // END of remote-pseudowire-status definition.

        leaf virtual-circuit-label-sent  {
            type  uint32;
            description "This attribute acquires the label sent to the neighbor for this
                        virtual circuit";
        } // END of virtual-circuit-label-sent definition.

        leaf virtual-circuit-label-received  {
            type  uint32;
            description "This attribute acquires the label received from the neighbor for this
                        virtual circuit";
        } // END of virtual-circuit-label-received definition.

    } // END of ldp-virtual-circuit-info-state definition.
    grouping ldp-mesh-virtual-circuit-state {
        description
            "State data for LDP based mesh Virtual-Circuits";
        leaf vpls-identifier  {
            type  uint32;
            description "This attribute acquires the VPLS Id";
        } // END of vpls-identifier definition.

        leaf mesh-vc-count  {
            type  uint32;
            description "This attribute acquires the count of virtual-circuits in this VPLS";
        } // END of mesh-vc-count definition.

    } // END of ldp-mesh-virtual-circuit-state definition.

    grouping  l2vpn-grouping {
    description
        "L2vpn related LDP data";
    container l2vpn {
        if-feature feature-list:HAVE_LDPD;
        config false;
        description
            "L2vpn related LDP data";

        list vpls-list {
            if-feature feature-list:HAVE_VPLS;
            key "vpls-identifier";
            config false;
            description
                "Object list for VPLS";
            leaf vpls-identifier  {
                type  leafref {
                    path  "../state/vpls-identifier";
                }
                description "This attribute acquires the VPLS Id";
            } // END of vpls-identifier definition.

            container state {
                config false;
                description
                    "Operational state data";
                uses ldp-mesh-virtual-circuit-state;
            } // END of state-container definition.
            uses ldp-vpls-virtual-circuit-top;
        } // End of vpls-list-list
        container state {
            config false;
            description
                "Operational state data";
            container counters {
                if-feature feature-list:HAVE_VPLS;
                config false;
                description
                    "Operational container for VPLS counters";
                uses ldp-vpls-counters-state;
            } // END of counters-container definition.
        } // END of state-container definition.
        uses ldp-virtual-circuit-top;
    } // END of l2vpn-container definition.
    } // END of l2vpn-grouping definition.


}
