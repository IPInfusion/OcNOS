/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-ldp.yang
*
*/

module ipi-ldp {

    yang-version 1.1;

    namespace   "http://www.ipinfusion.com/yang/ocnos/ipi-ldp";

    prefix "ipi-ldp";

    import ipi-ldp-types {
        prefix ipi-ldp-types;
        revision-date 2026-02-09;
    }

    import ietf-inet-types {
        prefix inet;
        revision-date 2013-07-15;
    }

    import cml-data-types {
        prefix cml-data-types;
        revision-date 2026-05-15;
    }

    import feature-list {
        prefix feature-list;
        revision-date 2026-09-15;
    }

    include ipi-ldp-l2vpn { revision-date 2026-01-12;}
    include ipi-ldp-interface { revision-date 2024-12-20;}
    include ipi-ldp-peer { revision-date 2026-01-06;}
    organization
        "IP Infusion Inc.";

    contact
        "Address: 3965 Freedom Circle, Suite 200, Santa Clara, CA 95054
         Phone: +1 408-400-1900
         E-mail: support@ipinfusion.com
         Web: http://www.ipinfusion.com/";

    description
        "Datamodel for LDP protocol";


    revision "2026-06-16" {
        description "Updated helpstring for attribute ftn-del-timer so that default doesnt get displayed twice";
        reference " 0.13.2.";
    }

    revision "2026-06-08" {
        description "Updated helpstring for attribute ftn-del-timer";
        reference " 0.13.1.";
    }

    revision "2026-06-03" {
        description "Added CLI support to enable delayed FTN deletion with a configurable timer value";
        reference " 0.13.0.";
    }

    revision "2026-02-09" {
        description "Added new debug LDP option";
        reference " 0.12.6.";
    }

    revision "2026-01-12" {
        description "Updated datatype from LDP_VC_STATE_T to CML_STRING_T for virtual-circuit-state attribute";
        reference " 0.12.5.";
    }

    revision "2026-01-06" {
        description "Added dependency on transport address for targeted peers top level container";
        reference " 0.12.4.";
    }

    revision "2025-11-28" {
        description "Added dependency on ldp global instance for top level containers dependent on ldp instance creation before configuring them";
        reference " 0.12.3.";
    }

    revision "2025-10-24" {
        description "Added dependency between graceful-restart and targeted peer config";
        reference " 0.12.2.";
    }

    revision "2025-10-04" {
        description "Added dependency between segment-routing global block and ldp instance config";
        reference " 0.12.1.";
    }

    revision "2025-09-26" {
        description "Moved mldp cli's under flag";
        reference " 0.12.0.";
    }

    revision "2025-04-02" {
        description "Added CML_RESET_INSTANCE flag for password and password type attributes under objectlist authentication-group-password";
        reference " 0.11.5.";
    }

    revision "2025-03-20" {
        description "removed common-label-per-fec attribute";
        reference " 0.11.4.";
    }

    revision "2025-03-14" {
        description "Added CML_RESET_INSTANCE flag for password and password type attributes";
        reference " 0.11.3.";
    }

    revision "2025-02-28" {
        description "Changed default and max value for rlfa-tunnel attribute";
        reference " 0.11.2.";
    }

    revision "2025-02-21" {
        description "Added new attribute tunnel inside targeted peer objectlist";
        reference " 0.11.1.";
    }

    revision "2025-02-19" {
        description "Added streaming telemetry support";
        reference " 0.11.0.";
    }

    revision "2025-02-10" {
        description "Changes ported from ldp scaling solution";
        reference " 0.10.11.";
    }

    revision "2025-02-07" {
        description "Removed ha message option from LDP_DEBUG_T datatype";
        reference " 0.10.10.";
    }

    revision "2025-01-17" {
        description "Added drop element tag for iccp container and attributes to block from netconf";
        reference " 0.10.9.";
    }

    revision "2025-01-13" {
        description "Added initilaized flag for tcp-mss range attribute";
        reference " 0.10.8.";
    }

    revision "2024-12-20" {
        description "Added when tag for interface-retention-mode attribute";
        reference " 0.10.7.";
    }

    revision "2024-12-19" {
        description "Added when tag validation for attribute retention-node";
        reference " 0.10.6.";
    }

    revision "2024-12-17" {
        description "Updated data-type to EMPTY for boolean attributes present inside router ldp";
        reference " 0.10.5.";
    }

    revision "2024-11-26" {
        description "added new attribute for common label allocation per prefix config";
        reference " 0.10.4.";
    }

    revision "2024-11-19" {
        description "Moved grouping peer-authentication-group-pwd outside config container";
        reference " 0.10.5.";
    }

    revision "2024-11-12" {
        description "Added new attribute ignore-mac-withdraw-bad-pdu-length for LDP";
        reference " 0.10.4.";
    }

    revision "2024-11-07" {
        description "Changed the help string for password size limits";
        reference " 0.10.3.";
    }

    revision "2024-08-07" {
        description "Changed the help string for targeted hello timer config";
        reference " 0.10.2.";
    }

    revision "2024-08-06" {
        description "Added state attributes for sget of LOR";
        reference " 0.10.1.";
    }

    revision "2024-05-24" {
        description "Added attributes to display Local and Remote Pseudowire Status Capability";
        reference " 0.10.0.";
    }

    revision "2024-03-19" {
        description "CLI support for LDP over RSVP";
        reference " 0.9.13.";
    }

    revision "2023-12-18" {
        description "when expression added for LBG db-sync issue";
        reference " 0.9.12.";
    }

    revision "2023-10-05" {
        description "Updated help-string for tcp mss attribute";
        reference " 0.9.11.";
    }

    revision "2023-09-01" {
        description "Updated if-feature flag for LDP VPLS counters";
        reference " 0.9.10.";
    }

    revision "2023-08-28" {
        description "Removed implicit delete tag for config container of targeted peer objectlist";
        reference " 0.9.9.";
    }

    revision "2023-08-24" {
        description "Added new attributes for LDP VPLS counters";
        reference " 0.9.8.";
    }

    revision "2023-08-21" {
        description "Added a new attribute local-address under adjacency-list object list";
        reference " 0.9.7.";
    }

    revision "2023-07-25" {
        description "CLI support for LDP TCP MSS";
        reference " 0.9.6.";
    }

    revision "2023-07-24" {
        description "Updated GR message";
        reference " 0.9.5.";
    }

    revision "2023-07-19" {
        description "Disable IPv6 Support";
        reference " 0.9.4.";
    }

    revision "2023-05-22" {
        description "Fix patter for session protection prefix list name";
        reference " 0.9.3.";
    }

    revision "2023-04-28" {
        description "Added proper position to LDP_DEBUG_T datatype";
        reference " 0.9.2.";
    }

    revision "2023-03-23" {
        description "Added when tag for Control mode attribute";
        reference " 0.9.1.";
    }

    revision "2023-03-03" {
        description "Enclosed all config object lists with container for LDP Data Model";
        reference " 0.9.0.";
    }

    revision "2023-03-01" {
        description "Added dependent object tag for the config container of Objectlist transport address";
        reference " 0.8.4.";
    }

    revision "2023-02-17" {
        description "Addressed cli-prependstr not used and not found  warnings";
        reference " 0.8.3.";
    }

    revision "2023-02-07" {
        description "Reverting Fix for enclosed objectlist within the container";
        reference " 0.8.1.";
    }

    revision "2023-02-06" {
        description "Enclosed all config object lists with container for MPLS Data Model";
        reference " 0.8.5.";
    }

    revision "2023-01-23" {
        description "Addressed cli-prependstr not found cmlgen warnings";
        reference " 0.7.18.";
    }

    revision "2023-01-17" {
        description "Addressed cli-prependstr not used warnings";
        reference " 0.8.2.";
    }

    revision "2023-01-16" {
        description "Added When tag for no-debug-all command";
        reference " 0.7.17.";
    }

    revision "2023-01-05" {
        description "Leafref correction for config container in ldp-interface";
        reference " 0.7.16.";
    }

    revision "2022-12-09" {
        description "Enclosed objectlist within the container";
        reference " 0.8.0.";
    }

    revision "2022-12-08" {
        description "Added new attribute rlfa-ilm-optimization for LDP";
        reference " 0.7.15.";
    }

    revision "2022-12-07" {
        description "Added flag in the iccp container";
        reference " 0.7.14.";
    }

    revision "2022-11-11" {
        description "Added new flag for ICCP debug cli.";
        reference " 0.7.13.";
    }

    revision "2022-11-07" {
        description "Hiding the CLI enable-ldp both and ipv6";
        reference " 0.7.12.";
    }

    revision "2022-11-03" {
        description "Updated category in statistics container";
        reference " 0.7.11.";
    }

    revision "2022-09-30" {
        description "Import cml-data-types used by notifications";
        reference " 0.7.10.";
    }

    revision "2022-09-21" {
        description "Fix neighbor password object dependencies";
        reference " 0.7.9.";
    }

    revision "2022-09-16" {
        description "Fix neighbor password exclude when list is empty";
        reference " 0.7.8.";
    }

    revision "2022-09-12" {
        description "Added the session-protection in ldp dependent object list";
        reference " 0.7.7.";
    }

    revision "2022-09-08" {
        description "Added HAVE_MPLS_VC and HAVE_VPLS flags to fix compilation issues";
        reference " 0.7.6.";
    }

    revision "2022-08-29" {
        description "Updated the when expression with feature";
        reference " 0.7.5.";
    }

    revision "2022-08-12" {
        description "Added configurations for LDP MD5 auto-targeted";
        reference " 0.7.4.";
    }

    revision "2022-08-10" {
        description "Debug hierarchy change";
        reference " 0.7.2.";
    }

    revision "2022-07-31" {
        description "Stop using inet:ipv4-prefix and inet:ipv6-prefix due to Cisco NSO iterop";
        reference " 0.7.1.";
    }

    revision "2022-07-30" {
        description "Updated when expressions in yang";
        reference " 0.7.0.";
    }

    revision "2022-06-29" {
        description "Fixes DB cleanup for label-space-identifier";
        reference " 0.6.5.";
    }

    revision "2022-06-08" {
        description "Fixes dependency for LDP transport-address";
        reference " 0.6.4.";
    }

    revision "2022-06-01" {
        description "Updated the yang file with feature";
        reference " 0.6.3.";
    }

    revision "2022-04-21" {
        description "Fixes dependency for LDP Session Protection";
        reference " 0.6.2.";
    }

    revision "2022-04-15" {
        description "Fixes attributes for LDP Session Protection";
        reference " 0.6.1.";
    }

    revision "2022-01-19" {
        description "Added configurations and state attributes for LDP Session Protection";
        reference " 0.6.0.";
    }

    revision "2022-01-07" {
        description "Modified Data Type";
        reference " 0.5.0.";
    }

    revision "2021-10-21" {
        description "Updated datatype of enable-ldp attributes for ldp-interface";
        reference " 0.3.6.";
    }

    revision "2021-09-27" {
        description "Added configurations and state attributes for LFA";
        reference " 0.4.0.";
    }

    revision "2021-09-17" {
        description "Added DC flag check for entropy command";
        reference " 0.3.5.";
    }

    revision "2021-09-14" {
        description "Removed debug ldp dependency on ldp-instance attribute";
        reference " 0.3.4.";
    }

    revision "2021-09-13" {
        description "Updated presence container and mandatory attribute in graceful-restart";
        reference " 0.3.3.";
    }

    revision "2021-09-03" {
        description "Update descriptions of attribute";
        reference " 0.3.2.";
    }

    revision "2021-08-24" {
        description "Removed attribute and RPCs related to debug ldp packet and its support provided in debug ldp";
        reference " 0.3.1.";
    }

    revision "2021-08-06" {
        description "Removed the attribute helper-mode and combined under enable attr";
        reference " 0.3.0.";
    }

    revision "2021-06-01" {
        description "Added dependency constraint between peer authentication password and password-type attrs";
        reference " 0.2.1.";
    }

    revision "2020-12-15" {
        description "Change to have data-types in lower case instead of camel case";
        reference " 0.2.0.";
    }

    revision "2018-06-21" {
        description "Initial Version";
        reference " 0.1.0.";
    }

    grouping peer-authentication-group-pwd-config {
        description
            "Grouping for LDP session group password configuration";
        leaf auth  {
            type  ipi-ldp-types:ldp_auth_group_type_t;
            description "Use this attribute to configure session-group authentication.";
        } // END of auth definition.

        leaf password-type  {
            type  ipi-ldp-types:ldp_md5_encrypt_password_t;
            mandatory true;
            description "Peer authentication group password type.";
        } // END of password-type definition.

        leaf password  {
            type  ipi-ldp-types:ldp_md5_password_t {
                length "1..1965";
            }
            mandatory true;
            description "Peer authentication group password.";
        } // END of password definition.

    } // END of peer-authentication-group-pwd-config definition.
    grouping peer-authentication-group-pwd {
        description
            "Grouping for LDP Session group password";
        container authentication-group-passwords {
            description
                "LDP Session group passwords";

            list authentication-group-password {
                key "auth";
                description
                    "LDP Session group password list";
                leaf auth  {
                    type  leafref {
                        path  "../config/auth";
                    }
                    description "Use this attribute to configure session-group authentication.";
                } // END of auth definition.

                container config {
                    description
                        "LDP Session group password configuration";
                    uses peer-authentication-group-pwd-config;
                } // END of config-container definition.
                container state {
                    config false;
                    description
                        "LDP Session group password state";
                    uses peer-authentication-group-pwd-config;
                } // END of state-container definition.
            } // End of authentication-group-password-list
        } // END of authentication-group-passwords-container definition.
    } // END of peer-authentication-group-pwd definition.
    grouping peer-authentication-group-config {
        description
            "Grouping for LDP Session groups configuration";
        leaf group-name  {
            type  string {
                length "1..1965";
                pattern "[^?' =,>|]+";
            }
            description "LDP Session group name.";
        } // END of group-name definition.

        leaf prefix-list  {
            type  string {
                length "1..1965";
                pattern "[^?' =,>|]+";
            }
            description "Peer authentication group prefix list.";
        } // END of prefix-list definition.

    } // END of peer-authentication-group-config definition.
    grouping peer-authentication-group-top {
        description
            "Grouping for LDP Session groups";
        container authentication-groups {
            when " /ipi-ldp:ldp/ipi-ldp:global/ipi-ldp:config ";
            description
                "LDP Session groups";

            list authentication-group {
                key "group-name";
                description
                    "LDP Session group list";
                leaf group-name  {
                    type  leafref {
                        path  "../config/group-name";
                    }
                    description "LDP Session group name.";
                } // END of group-name definition.

                container config {
                    description
                        "LDP Peer Authentication groups configuration";
                    uses peer-authentication-group-config;
                } // END of config-container definition.
                container state {
                    config false;
                    description
                        "LDP Peer Authentication groups state";
                    uses peer-authentication-group-config;
                } // END of state-container definition.
                uses peer-authentication-group-pwd;
            } // End of authentication-group-list
        } // END of authentication-groups-container definition.
    } // END of peer-authentication-group-top definition.
    grouping peer-authentication-exclusion-config {
        description
            "Grouping for LDP Peer Authentication configuration";
        leaf-list peer-address  {
            type  inet:ipv4-address;
            description "Use this attribute to exclude neighbors of LDP from authentication.";
        } // END of peer-address definition.

    } // END of peer-authentication-exclusion-config definition.
    grouping peer-authentication-exclusion-top {
        description
            "Grouping for LDP Peer Authentication exclusion";
        container authentication-exclusions {
            when " /ipi-ldp:ldp/ipi-ldp:global/ipi-ldp:config ";
            description
                "ldp peer authentication exclusion list";
            container config {
                // when " ipi-ldp:ldp/peer-authentication/authentication-exclusions/config/peer-address ";
                description
                    "LDP Peer Authentication config";
                uses peer-authentication-exclusion-config;
            } // END of config-container definition.
            container state {
                config false;
                description
                    "LDP Peer Authentication state";
                uses peer-authentication-exclusion-config;
            } // END of state-container definition.
        } // END of authentication-exclusions-container definition.
    } // END of peer-authentication-exclusion-top definition.
    grouping session-protection-config {
        description
            "Grouping for LDP Session protection";
        leaf session-protection-enable  {
            type  empty;
            mandatory true;
            description "This attribute is used to activate adjacency session protection.";
        } // END of session-protection-enable definition.

        leaf duration  {
            type  ipi-ldp-types:ldp_sess_prot_duration_t;
            description "Set adjacency session protection duration. Protection is infinite, it
                        is not configured";
        } // END of duration definition.

        leaf session-protection-prefix-list-name  {
            type  ipi-ldp-types:ldp_sess_prot_pfx_lst_t;
            description "This attribute is used to set adjacency prefixes for session
                        protection.";
        } // END of session-protection-prefix-list-name definition.

    } // END of session-protection-config definition.
    grouping session-protection-top {
        description
            "Grouping for LDP Session protection";
        container session-protection {
            when " /ipi-ldp:ldp/ipi-ldp:global/ipi-ldp:config ";
            if-feature feature-list:HAVE_LDP_SESS_PROT;
            description
                "Session protection container";
            container config {
                presence "yes";
                description
                    "Session protection config";
                uses session-protection-config;
            } // END of config-container definition.
            container state {
                config false;
                description
                    "Session protection state";
                uses session-protection-config;
            } // END of state-container definition.
        } // END of session-protection-container definition.
    } // END of session-protection-top definition.
    grouping ldp-lfa-state {
        description
            "Grouping for FEC primary paths";
        container primary-paths {
            config false;
            description
                "State data for FEC primary paths";

            list primary-path {
                key "nexthop-address nexthop-interface-name";
                config false;
                description
                    "State data list for FEC primary paths";
                leaf nexthop-address  {
                    type  leafref {
                        path  "../state/nexthop-address";
                    }
                    description "This attribute returns the next-hop address value of FEC primary path.";
                } // END of nexthop-address definition.

                leaf nexthop-interface-name  {
                    type  leafref {
                        path  "../state/nexthop-interface-name";
                    }
                    description "This attribute returns the interface name of FEC primary path.";
                } // END of nexthop-interface-name definition.

                container state {
                    config false;
                    description
                        "FEC primary path state";
                    leaf nexthop-address  {
                        type  inet:ip-address;
                        description "This attribute returns the nexthop address value.";
                    } // END of nexthop-address definition.

                    leaf nexthop-interface-name  {
                        type  string {
                            length "1..1965";
                            pattern "[^?' =,>|]+";
                        }
                        description "This attribute returns the interface name.";
                    } // END of nexthop-interface-name definition.

                } // END of state-container definition.
                container backup-path {
                    config false;
                    description
                        "Backup path for FEC primary path";
                    container state {
                        config false;
                        description
                            "State data for backup path for FEC primary path";
                        leaf backup-address  {
                            type  inet:ip-address;
                            description "This attribute returns the backup address value.";
                        } // END of backup-address definition.

                        leaf backup-interface-name  {
                            type  string {
                                length "1..1965";
                                pattern "[^?' =,>|]+";
                            }
                            description "This attribute returns the backup interface name.";
                        } // END of backup-interface-name definition.

                    } // END of state-container definition.
                } // END of backup-path-container definition.
            } // End of primary-path-list
        } // END of primary-paths-container definition.
    } // END of ldp-lfa-state definition.
    grouping ldp-lfa-top {
        description
            "Grouping for LDP LFA state";
        container lfa {
            if-feature feature-list:HAVE_LDP_LFA;
            description
                "State data for LDP LFA feature";
            container fecs {
                config false;
                description
                    "State data for FECs";

                list fec {
                    key "prefix-address";
                    config false;
                    description
                        "State data list for FECs";
                    leaf prefix-address  {
                        type  leafref {
                            path  "../state/prefix-address";
                        }
                        description "This attribute returns the prefix address value of FEC.";
                    } // END of prefix-address definition.

                    container state {
                        config false;
                        description
                            "LDP LFA FEC state";
                        leaf prefix-address  {
                            type  inet:ip-address;
                            description "This attribute returns the prefix address value of FEC.";
                        } // END of prefix-address definition.

                    } // END of state-container definition.
                    uses ldp-lfa-state;
                } // End of fec-list
            } // END of fecs-container definition.
        } // END of lfa-container definition.
    } // END of ldp-lfa-top definition.
    grouping ldp-capability-config {
        description
            "Grouping for LDP capabilities configuration";
        leaf ldp-instance  {
            type  ipi-ldp-types:ldp_instance_t;
            mandatory true;
            description "This command is used to enter the LDP specific command-line mode in
                        which global attributes for the LDP process can
                        be set. Without this command, the LSR does not perform any LDP
                        operations, such as sending hello packets.";
        } // END of ldp-instance definition.

        leaf router-identifier  {
            type  inet:ipv4-address;
            description "This attribute sets the router-id to the supplied IP address; the
                        router uses this address to generate the LDP-ID";
        } // END of router-identifier definition.

        leaf pseudowire-status-tlv  {
            if-feature feature-list:HAVE_MPLS_VC;
            type  empty;
            description "This attribute enables the use of the PW Status TLV to signal the
                        pseudowire status";
        } // END of pseudowire-status-tlv definition.

        leaf rlfa-ilm-optimization  {
            type  empty;
            description "This attribute enables the rlfa ilm optimization";
        } // END of rlfa-ilm-optimization definition.

        leaf entropy-label-capability-enable  {
            if-feature feature-list:NOT_HAVE_CUSTOM1_MPLS;
            type  empty;
            description "This attribute enables ELC for the router. An ELC TLV will be inserted
                        in the label mapping message if the router is capable of processing
                        Entropy Label.";
        } // END of entropy-label-capability-enable definition.

        leaf multicast-hello-disable  {
            type  empty;
            description "This attribute enable multicast hello exchange on all interfaces
                        enabled for LDP. This is used for autodiscovery of LDP peers on
                        directly connected networks. This option is enabled by default.";
        } // END of multicast-hello-disable definition.

        leaf advertise-label-for-default-route  {
            type  empty;
            description "Advertise the label for default route.";
        } // END of advertise-label-for-default-route definition.

        leaf import-bgp-routes  {
            type  empty;
            description "This attribute is used to import BGP routes into LDP. BGP routes are
                        not imported into LDP by default. Use the no parameter to flush out
                        all BGP routes currently being used by LDP, and to reject any further
                        BGP specific routing updates from ZebOS-XP.";
        } // END of import-bgp-routes definition.

        leaf ldp-optimization  {
            type  empty;
            description "This command helps optimize the resetting of an LDP session by
                        enabling the two scalability features for LDP. It Resets the session
                        keepalive timer on receipt of a hello message and Resets the hold
                        timer on receipt of any LDP control message.";
        } // END of ldp-optimization definition.

        leaf explicit-null  {
            type  empty;
            description "This attribute is used to configure the router to send explicit-null
                        labels for directly connected FECs instead of implicit-null labels.
                        Implicit-nulls are the default labels.";
        } // END of explicit-null definition.

        leaf global-merge  {
            type  ipi-ldp-types:ldp_merge_capable_t;
            default "merge-capable";
            description "This attribute is used to override the default merge capability
                        setting of all the interfaces for the current LSR. The merge
                        capability aggregates multiple incoming flows with the same
                        destination address into a single outgoing flow.";
        } // END of global-merge definition.

        leaf propagate-release  {
            type  empty;
            description "This attribute is used to propagate the release of labels to
                        downstream routers";
        } // END of propagate-release definition.

        leaf fast-reroute  {
            if-feature feature-list:HAVE_LDP_LFA;
            type  empty;
            description "This attribute is used to enable the use by LDP of the LFA next-hop";
        } // END of fast-reroute definition.

        leaf prefer-tunnel-in-tunnel  {
            if-feature feature-list:HAVE_LDP_TUNNELING;
            type  empty;
            description "Use this attribute to specify TE-tunnel over LDP tunnel for tunneling";
        } // END of prefer-tunnel-in-tunnel definition.

        leaf ignore-mac-withdraw-bad-pdu-length  {
            if-feature feature-list:HAVE_MPLS_VC;
            type  empty;
            description "This attribute is used to ignore the bad pdu length error and send a
                        non-fatal notification (non-RFC compliance)";
        } // END of ignore-mac-withdraw-bad-pdu-length definition.

        leaf rlfa-tunnels  {
            type  uint16 {
                 range "1..500"  {
                    description "1..500: Supported range 1 - 500";
                 }
            }
            default "100";
            description "Use this attribute to specify maximum rlfa tunnels";
        } // END of rlfa-tunnels definition.

        leaf delay-ftn-delete  {
            type  empty;
            description "Use this attribute to delay FTN deletion";
        } // END of delay-ftn-delete definition.

        leaf ftn-del-timer  {
            // when " ../delay-ftn-delete ";
            type  uint8 {
                 range "15..120"  {
                    description "15..120: Supported range 15 - 120";
                 }
            }
            units "seconds";
            default "50";
            description "Use this attribute to configure a timer to delay FTN deletion";
        } // END of ftn-del-timer definition.

    } // END of ldp-capability-config definition.
    grouping ldp-auto-target-session-config {
        description
            "Grouping for LDP auto target session configuration";
        leaf auto-targeted-session  {
            if-feature feature-list:HAVE_LDP_LFA;
            type  empty;
            description "This attribute is used to dynamically create TLDP session for LDP
                        RLFA.";
        } // END of auto-targeted-session definition.

    } // END of ldp-auto-target-session-config definition.
    grouping ldp-label-management-config {
        description
            "Grouping for LDP capabilities for label management configuration";
        leaf control-mode  {
            type  ipi-ldp-types:ldp_controlmode_t;
            description "Use this attribute to override the default merge capability setting of
                        all the interfaces for the current LSR.The merge capability aggregates
                        multiple incoming flows with the same destination address into a
                        single outgoing flow. This reduces the label-space shortage by sharing
                        labels for different flows with the same destination, or the same FEC
                        (Forwarding Equivalence Class).an LSR replies to a request packet from
                        an LSR higher in the chain only after it receives a label from an LSR
                        lower in the chain. Independent processing setthe mode to instant
                        replies.In independent control mode, each LSR might advertise label
                        mappings to its neighbors at any time. In independent
                        downstream-on-demand mode, an LSR might answer requests for label
                        mappings immediately, without waiting for a label mapping from the
                        next hop. In independent downstream unsolicited mode, an LSR might
                        advertise a label mapping for an Forwarding Equivalence Class (FEC) to
                        its neighbors when ever it is prepared to label-switch that FEC.In
                        independent mode, an upstream label can be advertised before a
                        downstream label is received.In ordered control mode, an LSR may
                        initiate the transmission of label mapping only for an FEC for which
                        it has a label mapping for the FEC next hop, or for which the LSR is
                        the egress. For each FEC for which the LSR is not the egress and no
                        mapping exists, the LSR must wait until a label from a downstream LSR
                        is received. An LSR may be an egress for some FECs and a non-egress
                        for others. Changes in control mode only affect labels that were sent
                        or received after the change was made.";
        } // END of control-mode definition.

        leaf retention-mode  {
            type  ipi-ldp-types:ldp_retention_mode_t;
            description "This attribute is used to set the retention mode to be used for all
                        labels exchanged. When an LSR receives a label binding for a
                        particular FEC (Forwarding Equivalence Class) from another LSR that is
                        not its next hop for that FEC, it might keep track of such bindings or
                        discard them. Use the liberal parameter to retain all labels binding
                        to FEC received from label distribution peers, even if the LSR is not
                        the current next-hop. Use the conservative parameter to maintain only
                        the label bindings for valid next-hops in a LSP.";
        } // END of retention-mode definition.

        leaf advertisement-mode  {
            type  ipi-ldp-types:ldp_advertise_mode_t;
            default "downstream-unsolicited";
            description "This attribute is used to set the label advertisement mode for all the
                        interfaces for the current LSR. Specifying downstream-on-demand and
                        downstream-unsolicited mode affects which LSR initiates mapping
                        requests and mapping advertisements. This command is a global command
                        used to set the label advertisement mode for all interfaces for the
                        current LSR.";
        } // END of advertisement-mode definition.

    } // END of ldp-label-management-config definition.
    grouping ldp-debug-config {
        description
            "Grouping for LDP debugging configuration";
        leaf ldp  {
            type  ipi-ldp-types:ldp_debug_t;
            description "Use this attribute to enable the debugging of all LDP events.";
        } // END of ldp definition.

        leaf dev  {
            type  ipi-ldp-types:ldp_debug_option_t;
            description "Use this attribute to enable dev related debugging for LDP";
        } // END of dev definition.

    } // END of ldp-debug-config definition.
    grouping ldp-terminal-debug-state {
        description
            "Grouping for LDP terminal debugging configuration";
        leaf terminal-debug-options  {
            type  ipi-ldp-types:ldp_debug_t;
            description "Use this attribute to enable the debugging of all LDP events.";
        } // END of terminal-debug-options definition.

    } // END of ldp-terminal-debug-state definition.
    grouping ldp-label-request-policy-config {
        description
            "Grouping for LDP policy for label-request message configuration";
        leaf request-retry-timeout  {
            type  uint16 {
                 range "1..65535"  {
                    description "1..65535: Supported range 1 - 65535";
                 }
            }
            default "5";
            description "Use this attribute to set the interval between retries. Before this
                        time is over, a request is re-sent to a peer. This command changes the
                        interval between request messages that are resent to a peer to account
                        for routing changes.";
        } // END of request-retry-timeout definition.

        leaf request-retry  {
            type  empty;
            description "Use this attribute to enable the retry of requests once a request for
                        a label has been rejected for a valid reason. This command enables the
                        LSR to send a maximum of five label requests if a label request is
                        rejected by an LDP peer.";
        } // END of request-retry definition.

        leaf label-request-policy-ipv4  {
            type  string {
                length "1..1965";
                pattern "[^?' =,>|]+";
            }
            description "Use this attribute to send LDP Label Request Message for certain IPv4
                        FEC prefixes.";
        } // END of label-request-policy-ipv4 definition.

    } // END of ldp-label-request-policy-config definition.
    grouping ldp-loop-detection-config {
        description
            "Grouping for LDP loop-detection configuration";
        leaf loop-detection-enable  {
            type  empty;
            mandatory true;
            description "Use this attribute to enable loop detection on the current LSR. This
                        command detects looping LSPs, and prevent Label Request messages from
                        looping because of non-merge capable LSRs. This loop detection
                        mechanism is useful for networks of non time-to-live (non TTL)
                        decrementing devices that can not allocate resources among traffic
                        flows.";
        } // END of loop-detection-enable definition.

        leaf path-vector-limit  {
            type  uint32 {
                 range "1..255"  {
                    description "1..255: Supported range 1 - 255";
                 }
            }
            default "255";
            description "Use this attribute to set the loop detection vec (vector) count, which
                        determines the maximum supported path vectors. This command sets the
                        maximum supported path vectors for loop detection, which specifies the
                        permitted path vector length. An LSR that detects a path vector has
                        reached the maximum length behaves as if the containing message has
                        traversed a loop. This command ensures that a loop is detected while
                        establishing a label switched path before any data is passed over that
                        LSP.";
        } // END of path-vector-limit definition.

        leaf hop-count-limit  {
            type  uint32 {
                 range "1..255"  {
                    description "1..255: Supported range 1 - 255";
                 }
            }
            default "255";
            description "Use this attribute to set the loop detection hop count, which
                        determines the maximum hop-count value.
                        This command sets the maximum hop count value, which specifies the
                        permitted maximum permitted hop-count. An LSR that detects a maximum
                        hop count behaves as if the containing message has traversed a loop.
                        The use of this command ensures that a loop is detected while
                        establishing a label switched path before any data is passed via LSP";
        } // END of hop-count-limit definition.

    } // END of ldp-loop-detection-config definition.
    grouping ldp-transport-address-top {
        description
            "Top-Level Grouping for LDP transport address per label space";
        container transport-addresses {
            when " /ipi-ldp:ldp/ipi-ldp:global/ipi-ldp:config ";
            description
                "container for transport addresses";

            list transport-address {
                key "label-space-identifier";
                description
                    "Object list for transport address per label-space";
                leaf label-space-identifier  {
                    type  leafref {
                        path  "../config/label-space-identifier";
                    }
                    description "This attribute is used to configure Label space for which a transport
                                address is being configured";
                } // END of label-space-identifier definition.

                container config {
                    description
                        "Configuration data";
                    uses ldp-transport-address-config;
                } // END of config-container definition.
                container state {
                    config false;
                    description
                        "Operational state data";
                    uses ldp-transport-address-config;
                } // END of state-container definition.
            } // End of transport-address-list
        } // END of transport-addresses-container definition.
    } // END of ldp-transport-address-top definition.
    grouping ldp-transport-address-config {
        description
            "Grouping for LDP Transport-Address configuration";
        leaf label-space-identifier  {
            type  ipi-ldp-types:ldp_label_space_identifier_t;
            description "This attribute is used to configure Label space for which a transport
                        address is being configured";
        } // END of label-space-identifier definition.

        leaf transport-address-ipv4  {
            type  inet:ipv4-address;
            description "Use this attribute to configure the IPv4 transport address for a label
                        space.The transport address is the address used for the TCP session
                        over which LDP is running. Use this attribute to manually configure
                        the transport address. Transport addresses may either be bound to a
                        loopback interface, or to a physical interface that is bound to the
                        label space in question. A transport address can also be manually
                        configured using the CLI with the loopback address as the transport
                        address.";
        } // END of transport-address-ipv4 definition.

    } // END of ldp-transport-address-config definition.
    grouping peer-authentication-top {
        description
            "Grouping for LDP Peer Authentication";
        container peer-authentication {
            description
                "LDP Peer Authentication container";
            uses ldp-authentication-top;
            uses peer-authentication-exclusion-top;
            uses peer-authentication-group-top;
        } // END of peer-authentication-container definition.
    } // END of peer-authentication-top definition.
    grouping ldp-authentication-top {
        description
            "Top-Level Grouping for LDP authetication";
        container peer-authentication-lists {
            when " /ipi-ldp:ldp/ipi-ldp:global/ipi-ldp:config ";
            description
                "lists for ldp peer authentication information";

            list peer-authentication-list {
                if-feature feature-list:HAVE_TCP_MD5SIG;
                key "peer-address";
                description
                    "list for ldp peer authentication information";
                leaf peer-address  {
                    type  leafref {
                        path  "../config/peer-address";
                    }
                    description "Use this attribute to configure neighbors of LDP for authentication.";
                } // END of peer-address definition.

                container config {
                    description
                        "Configuration data";
                    uses ldp-authentication-config;
                } // END of config-container definition.
                container state {
                    config false;
                    description
                        "Operational state data";
                    uses ldp-authentication-config;
                } // END of state-container definition.
            } // End of peer-authentication-list-list
        } // END of peer-authentication-lists-container definition.
    } // END of ldp-authentication-top definition.
    grouping ldp-authentication-config {
        description
            "Grouping for LDP authetication configuration data";
        leaf peer-address  {
            type  ipi-ldp-types:ldp_auth_neighbor_type_t;
            description "Use this attribute to configure neighbors of LDP for authentication.";
        } // END of peer-address definition.

        leaf password-type  {
            // when " ipi-ldp:ldp/peer-authentication/peer-authentication-lists/peer-authentication-list/config/password ";
            type  ipi-ldp-types:ldp_md5_encrypt_password_t;
            mandatory true;
            description "Use this attribute to configure password type for LDP peer
                        authentication.";
        } // END of password-type definition.

        leaf password  {
            // when " ipi-ldp:ldp/peer-authentication/peer-authentication-lists/peer-authentication-list/config/password-type ";
            type  ipi-ldp-types:ldp_md5_password_t {
                length "1..1965";
            }
            mandatory true;
            description "Use this attribute to configure password of LDP peer for
                        authentication.";
        } // END of password definition.

    } // END of ldp-authentication-config definition.
    grouping ldp-tcp-mss-top {
        description
            "Top-Level Grouping for TCP MSS";
        container tcp-mss-lists {
            when " /ipi-ldp:ldp/ipi-ldp:global/ipi-ldp:config ";
            description
                "lists for TCP MSS of neighbors";

            list tcp-mss-list {
                key "peer-address";
                description
                    "list for TCP MSS of neighbor";
                leaf peer-address  {
                    type  leafref {
                        path  "../config/peer-address";
                    }
                    description "Use this attribute to specify LDP neighbors";
                } // END of peer-address definition.

                container config {
                    description
                        "Configuration data";
                    uses ldp-tcp-mss-config;
                } // END of config-container definition.
                container state {
                    config false;
                    description
                        "Operational state data";
                    uses ldp-tcp-mss-config;
                } // END of state-container definition.
            } // End of tcp-mss-list-list
        } // END of tcp-mss-lists-container definition.
    } // END of ldp-tcp-mss-top definition.
    grouping ldp-tcp-mss-config {
        description
            "Grouping to adjust TCP MSS configuration data";
        leaf peer-address  {
            type  ipi-ldp-types:ldp_neighbor_type_t;
            description "Use this attribute to specify LDP neighbors";
        } // END of peer-address definition.

        leaf tcp-mss-range  {
            type  uint32 {
                 range "560..1440"  {
                    description "560..1440: Supported range 560 - 1440";
                 }
            }
            mandatory true;
            description "Use this attribute to configure TCP MSS for LDP neighbors";
        } // END of tcp-mss-range definition.

    } // END of ldp-tcp-mss-config definition.
    grouping ldp-label-mapping-access-control-top {
        description
            "Top-Level Grouping for LDP label-advertisement-ACL";
        container label-mapping-access-lists {
            when " /ipi-ldp:ldp/ipi-ldp:global/ipi-ldp:config ";
            description
                "lists for ldp peer ACL information";

            list label-mapping-access-list {
                key "peer-access-control-list-name prefix-access-control-list-name";
                description
                    "Object list for ldp ACL information";
                leaf peer-access-control-list-name  {
                    type  leafref {
                        path  "../config/peer-access-control-list-name";
                    }
                    description "Use this command to prevent the distribution of any locally assigned
                                labels";
                } // END of peer-access-control-list-name definition.

                leaf prefix-access-control-list-name  {
                    type  leafref {
                        path  "../config/prefix-access-control-list-name";
                    }
                    description "Use this attribute to prevent the distribution of any locally assigned
                                labels";
                } // END of prefix-access-control-list-name definition.

                container config {
                    description
                        "Configuration data";
                    uses ldp-prefix-list-name-config;
                    uses ldp-peer-list-name-config;
                } // END of config-container definition.
                container state {
                    config false;
                    description
                        "Operational state data";
                    uses ldp-prefix-list-name-config;
                    uses ldp-peer-list-name-config;
                    uses ldp-peer-list-advertise-labels-state;
                } // END of state-container definition.
                container statistics {
                    config false;
                    description
                        "state container for the statistics advertisement labels";
                    container state {
                        config false;
                        description
                            "Operational state data";
                        uses ldp-peer-list-statistics-advertise-labels-state;
                    } // END of state-container definition.
                } // END of statistics-container definition.
            } // End of label-mapping-access-list-list
        } // END of label-mapping-access-lists-container definition.
    } // END of ldp-label-mapping-access-control-top definition.
    grouping ldp-prefix-list-name-config {
        description
            "Grouping for LDP prefix-ACL name configuration";
        leaf prefix-access-control-list-name  {
            type  string {
                length "1..1965";
                pattern "[^?' =,>|]+";
            }
            description "Use this attribute to prevent the distribution of any locally assigned
                        labels";
        } // END of prefix-access-control-list-name definition.

    } // END of ldp-prefix-list-name-config definition.
    grouping ldp-peer-list-name-config {
        description
            "Grouping for LDP label-advertisement-peer list name configuration";
        leaf peer-access-control-list-name  {
            type  string {
                length "1..1965";
                pattern "[^?' =,>|]+";
            }
            description "Use this command to prevent the distribution of any locally assigned
                        labels";
        } // END of peer-access-control-list-name definition.

    } // END of ldp-peer-list-name-config definition.
    grouping ldp-peer-list-advertise-labels-state {
        description
            "Grouping for LDP label-advertisement-peer list state parameters";
        leaf advertisement-type  {
            type  ipi-ldp-types:ldp_advertisement_type_t;
            config false;
            description "This object stores the advertisement-type for Prefix List.";
        } // END of advertisement-type definition.

    } // END of ldp-peer-list-advertise-labels-state definition.
    grouping ldp-peer-list-statistics-advertise-labels-state {
        description
            "Grouping for LDP label-advertisement-peer list static state parameters";
        leaf label-deny-mapping  {
            type  uint32;
            config false;
            description "Use this attribute to store the number of label mappings denied";
        } // END of label-deny-mapping definition.

        leaf label-deny-request  {
            type  uint32;
            config false;
            description "Use this attribute to store the number of label requests denied";
        } // END of label-deny-request definition.

    } // END of ldp-peer-list-statistics-advertise-labels-state definition.
    grouping ldp-received-label-control-top {
        description
            "Top-Level Grouping for LDP to block received labels";
        container received-label-control-lists {
            when " /ipi-ldp:ldp/ipi-ldp:global/ipi-ldp:config ";
            description
                "lists for ldp peer information";

            list received-label-control-list {
                key "peer-control-list-name prefix-control-list-name";
                description
                    "Object list for ldp information";
                leaf peer-control-list-name  {
                    type  leafref {
                        path  "../config/peer-control-list-name";
                    }
                    description "Use this command to prevent processing of received labels";
                } // END of peer-control-list-name definition.

                leaf prefix-control-list-name  {
                    type  leafref {
                        path  "../config/prefix-control-list-name";
                    }
                    description "Use this attribute to prevent processing of received labels";
                } // END of prefix-control-list-name definition.

                container config {
                    description
                        "Configuration data";
                    uses prefix-list-name-config;
                    uses peer-list-name-config;
                } // END of config-container definition.
                container state {
                    config false;
                    description
                        "Operational state data";
                    uses prefix-list-name-config;
                    uses peer-list-name-config;
                } // END of state-container definition.
            } // End of received-label-control-list-list
        } // END of received-label-control-lists-container definition.
    } // END of ldp-received-label-control-top definition.
    grouping prefix-list-name-config {
        description
            "Grouping for LDP prefix-ACL name configuration";
        leaf prefix-control-list-name  {
            type  string {
                length "1..1965";
                pattern "[^?' =,>|]+";
            }
            description "Use this command to prevent processing of received labels";
        } // END of prefix-control-list-name definition.

    } // END of prefix-list-name-config definition.
    grouping peer-list-name-config {
        description
            "Grouping for LDP label-advertisement-peer list name configuration";
        leaf peer-control-list-name  {
            type  string {
                length "1..1965";
                pattern "[^?' =,>|]+";
            }
            description "Use this attribute to prevent processing of received labels";
        } // END of peer-control-list-name definition.

    } // END of peer-list-name-config definition.
    grouping ldp-inter-area-config {
        description
            "Grouping for LDP Inter-Area configuration";
        leaf inter-area-acl-name  {
            if-feature feature-list:HAVE_LDP_INTER_AREA;
            type  string {
                length "1..1965";
                pattern "[^?' =,>|]+";
            }
            description "Use this attribute to enable creation of inter-area LSPs.";
        } // END of inter-area-acl-name definition.

        leaf inter-area-enable  {
            if-feature feature-list:HAVE_LDP_INTER_AREA;
            type  string {
                length "1..1965";
                pattern "[^?' =,>|]+";
            }
            description "Use this attribute to enable creation of inter-area LSPs.";
        } // END of inter-area-enable definition.

    } // END of ldp-inter-area-config definition.
    grouping ldp-graceful-restart-config {
        description
            "Grouping for LDP Graceful restart config";
        leaf enable  {
            type  ipi-ldp-types:ldp_gr_mode_t;
            mandatory true;
            description "Use this attribute with the enable option to enable Graceful Restart
                        capability on a router. This is a global command. LDP decides whether
                        or not to encode FT Session TLV in its initialization message for each
                        session depending on this capability, but the restart capability of
                        each session also depends on support for graceful restart at the peer
                        router";
        } // END of enable definition.

        leaf neighbor-liveness-time  {
            type  uint16 {
                 range "5..300"  {
                    description "5..300: Supported range 5 - 300";
                 }
            }
            units "seconds";
            default "120";
            description "Use this attribute to set the Neighbor-Liveness timer. The amount of
                        time the LSR keeps its stale label-FEC (Forwarding Equivalence Class)
                        bindings is set to the lesser of the Fault Tolerant (FT) Reconnect
                        timeout and Neighbor-Liveness timer. This command sets the
                        Neighbor-Liveness timer";
        } // END of neighbor-liveness-time definition.

        leaf max-recovery-time  {
            type  uint16 {
                 range "15..600"  {
                    description "15..600: Supported range 15 - 600";
                 }
            }
            units "seconds";
            default "120";
            description "Use this attribute to set the maximum recovery time.If the LSR
                        determines that the neighbor was able to preserve its MPLS forwarding
                        state, the LSR should keep the stale label-FEC (Forwarding Equivalence
                        Class) bindings for as long as the lesser of: the recovery time
                        advertised by the neighbor and a local maximum recovery time. This
                        command sets the maximum recovery time";
        } // END of max-recovery-time definition.

    } // END of ldp-graceful-restart-config definition.
    grouping ldp-graceful-restart-state {
        description
            "Grouping for LDP Inter-Area configuration";
        leaf restart-count  {
            type  uint32;
            config false;
            description "This attribute holds the count for restart";
        } // END of restart-count definition.

    } // END of ldp-graceful-restart-state definition.
    grouping ldp-tunnel-info-state {
        description
            "State data of tunnel";
        leaf tunnel-name  {
            type  string {
                length "1..1965";
                pattern "[^?' =,>|]+";
            }
            description "This attribute acquires name of the tunnel";
        } // END of tunnel-name definition.

        leaf cost  {
            type  uint32;
            description "This attribute acquires cost of tunnel";
        } // END of cost definition.

        leaf owner  {
            type  string {
                length "1..1965";
                pattern "[^?' =,>|]+";
            }
            description "This attribute specify owner";
        } // END of owner definition.

        leaf status  {
            type  string {
                length "1..1965";
                pattern "[^?' =,>|]+";
            }
            description "This attribute specify status of tunnel";
        } // END of status definition.

        leaf fec-count  {
            type  uint8;
            description "This attribute specify total fec count tunneled by tunnel";
        } // END of fec-count definition.

    } // END of ldp-tunnel-info-state definition.
    grouping ldp-fec-info-state {
        description
            "State data of fec";
        leaf fec-prefix  {
            type  cml-data-types:cml_ipv4_addr_prefix_t;
            description "This attribute acquires name of the fec";
        } // END of fec-prefix definition.

        leaf upstream-peer  {
            type  inet:ipv4-address;
            description "This attribute acquires address of the upstream peer";
        } // END of upstream-peer definition.

        leaf in-label  {
            type  string {
                length "1..1965";
                pattern "[^?' =,>|]+";
            }
            description "This attribute specify in-label";
        } // END of in-label definition.

        leaf out-label  {
            type  string {
                length "1..1965";
                pattern "[^?' =,>|]+";
            }
            description "This attribute specify out-label";
        } // END of out-label definition.

    } // END of ldp-fec-info-state definition.
    grouping ldp-tunnel-state {
        description
            "State data of tunnel";
        leaf tunnel-endpoint  {
            type  cml-data-types:cml_ipv4_addr_prefix_t;
            description "This attribute acquires address of tunnel end point";
        } // END of tunnel-endpoint definition.

    } // END of ldp-tunnel-state definition.
    grouping ldp-inter-chassis-communication-protocol-config {
        description
            "Grouping for ICCP configuration";
        leaf redundancy-group-identifier  {
            type  uint32 {
                 range "0..65535"  {
                    description "0..65535: Supported range 0 - 65535";
                 }
            }
            mandatory true;
            description "This attribute is used to configure redundancy group id";
        } // END of redundancy-group-identifier definition.

        leaf ldp-peer-member-ip-address  {
            type  inet:ipv4-address;
            description "This attribute is used to configure peer Ip address of group member";
        } // END of ldp-peer-member-ip-address definition.

        leaf iccp-startup-delay-timer  {
            type  uint32 {
                 range "0..180"  {
                    description "0..180: Supported range 0 - 180";
                 }
            }
            description "This attribute is used to configure startup delay timer";
        } // END of iccp-startup-delay-timer definition.

        leaf bfd-source-ip-address  {
            if-feature feature-list:HAVE_BFD;
            type  inet:ipv4-address;
            description "This attribute is used to configure Source IP address for BFD";
        } // END of bfd-source-ip-address definition.

    } // END of ldp-inter-chassis-communication-protocol-config definition.

    grouping  ldp-grouping {
    description
        "LDP global level container";
    container ldp {
        // when " ipi-ldp:ldp/global/config/ldp-instance + ipi-ldp:ldp/debug ";
        if-feature feature-list:HAVE_LDPD;
        description
            "LDP global level container";
        container global {
            description
                "Configuration data for LDP global capability configuration";
            container config {
                presence "Enable LDP";
                description
                    "LDP global structure for Configuration parameters";
                uses ldp-capability-config;
            } // END of config-container definition.
            container state {
                config false;
                description
                    "Operational state data";
                uses ldp-capability-config;
            } // END of state-container definition.
            container auto-target-session {
                when " /ipi-ldp:ldp/ipi-ldp:global/ipi-ldp:config ";
                if-feature feature-list:HAVE_LDP_LFA;
                description
                    "Configuration data for LDP auto targeted session";
                container config {
                    description
                        "Configuration data";
                    uses ldp-auto-target-session-config;
                } // END of config-container definition.
                container state {
                    config false;
                    description
                        "Operational state data";
                    uses ldp-auto-target-session-config;
                } // END of state-container definition.
            } // END of auto-target-session-container definition.
            container label-management {
                when " /ipi-ldp:ldp/ipi-ldp:global/ipi-ldp:config ";
                description
                    "Configuration data for LDP global label management configuration";
                container config {
                    description
                        "Configuration data";
                    uses ldp-label-management-config;
                } // END of config-container definition.
                container state {
                    config false;
                    description
                        "Operational state data";
                    uses ldp-label-management-config;
                } // END of state-container definition.
            } // END of label-management-container definition.
            container timers {
                when " /ipi-ldp:ldp/ipi-ldp:global/ipi-ldp:config ";
                description
                    "Container for LDP timers";
                container config {
                    description
                        "Configuration data for timers";
                    uses ldp-hello-timers-config;
                    uses ldp-session-timers-config;
                } // END of config-container definition.
                container state {
                    config false;
                    description
                        "Operational state data";
                    uses ldp-hello-timers-config;
                    uses ldp-session-timers-config;
                } // END of state-container definition.
            } // END of timers-container definition.
            container label-request-policy {
                when " /ipi-ldp:ldp/ipi-ldp:global/ipi-ldp:config ";
                description
                    "Configuration data for LDP policies for label-request";
                container config {
                    description
                        "Configuration data";
                    uses ldp-label-request-policy-config;
                } // END of config-container definition.
                container state {
                    config false;
                    description
                        "Operational state data";
                    uses ldp-label-request-policy-config;
                } // END of state-container definition.
            } // END of label-request-policy-container definition.
            container loop-detection-policy {
                when " /ipi-ldp:ldp/ipi-ldp:global/ipi-ldp:config ";
                description
                    "Configuration data for LDP policies for loop detection";
                container config {
                    presence "Enable Loop-Detection";
                    description
                        "Ldp structure for loop-detection configurationdata";
                    uses ldp-loop-detection-config;
                } // END of config-container definition.
                container state {
                    config false;
                    description
                        "Operational state data";
                    uses ldp-loop-detection-config;
                } // END of state-container definition.
            } // END of loop-detection-policy-container definition.
            uses session-protection-top;
        } // END of global-container definition.
        container debug {
            description
                "Configuration data for LDP debugging configuration";
            container config {
                description
                    "Configuration data";
                uses ldp-debug-config;
            } // END of config-container definition.
            container state {
                config false;
                description
                    "Operational state data";
                uses ldp-debug-config;
                uses ldp-terminal-debug-state;
            } // END of state-container definition.
        } // END of debug-container definition.
        container graceful-restart {
            when " /ipi-ldp:ldp/ipi-ldp:global/ipi-ldp:config ";
            if-feature feature-list:HAVE_RESTART;
            description
                "Configuration data for LDP graceful-restart feature";
            container config {
                presence "Enable graceful-restart";
                description
                    "Configuration data";
                uses ldp-graceful-restart-config;
            } // END of config-container definition.
            container state {
                config false;
                description
                    "Operational state data";
                uses ldp-graceful-restart-config;
                uses ldp-graceful-restart-state;
            } // END of state-container definition.
        } // END of graceful-restart-container definition.
        container ldp-tunnels {
            if-feature feature-list:HAVE_LDP_TUNNELING;
            config false;
            description
                "LDP tunnels";

            list ldp-tunnel {
                key "tunnel-endpoint";
                config false;
                description
                    "State data list for LDP tunnel";
                leaf tunnel-endpoint  {
                    type  leafref {
                        path  "../state/tunnel-endpoint";
                    }
                    description "This attribute acquires address of tunnel end point";
                } // END of tunnel-endpoint definition.

                container state {
                    config false;
                    description
                        "Operational state data";
                    uses ldp-tunnel-state;
                } // END of state-container definition.
                container tunnel-lists {
                    config false;
                    description
                        "tunnel lists";

                    list tunnel-list {
                        key "tunnel-name";
                        config false;
                        description
                            "State data list for tunnel";
                        leaf tunnel-name  {
                            type  leafref {
                                path  "../state/tunnel-name";
                            }
                            description "This attribute acquires tunnel name";
                        } // END of tunnel-name definition.

                        container state {
                            config false;
                            description
                                "Operational state data";
                            uses ldp-tunnel-info-state;
                        } // END of state-container definition.
                        container fec-lists {
                            config false;
                            description
                                "Fec lists";

                            list fec-list {
                                key "fec-prefix";
                                config false;
                                description
                                    "State data list for fec list";
                                leaf fec-prefix  {
                                    type  leafref {
                                        path  "../state/fec-prefix";
                                    }
                                    description "This attribute acquires fec IP address";
                                } // END of fec-prefix definition.

                                container state {
                                    config false;
                                    description
                                        "Operational state data";
                                    uses ldp-fec-info-state;
                                } // END of state-container definition.
                            } // End of fec-list-list
                        } // END of fec-lists-container definition.
                    } // End of tunnel-list-list
                } // END of tunnel-lists-container definition.
            } // End of ldp-tunnel-list
        } // END of ldp-tunnels-container definition.
        uses ldp-lfa-top;
        uses ldp-transport-address-top;
        uses peer-authentication-top;
        uses ldp-label-mapping-access-control-top;
        uses ldp-tcp-mss-top;
        uses ldp-received-label-control-top;
        uses interfaces-grouping;
        uses l2vpn-grouping;
        uses targeted-peers-grouping;
        uses peers-grouping;
    } // END of ldp-container definition.
    } // END of ldp-grouping definition.

    uses ldp-grouping;

    rpc clear-ldp-statistics {
        if-feature feature-list:HAVE_LDPD;
        description "Use this RPC to clear LDP statistics";
    }

    rpc clear-ldp-statistics-advertise-labels {
        if-feature feature-list:HAVE_LDPD;
        description "Use this RPC to clear ts LDP advertise-labels statistics";
    }

    rpc clear-ldp-statistics-advertise-labels-prefix {
        if-feature feature-list:HAVE_LDPD;
        description "Use this RPC to clear LDP advertise-labels prefix statistics";
        input  {
            leaf prefix  {
                type string;
                mandatory true;
                description "prefix-list that have their labels advertised";
            }
        }
    }

    rpc clear-ldp-statistics-advertise-labels-prefix-peer {
        if-feature feature-list:HAVE_LDPD;
        description "Use this RPC to clear LDP advertise-labels prefix-peer statistics";
        input  {
            leaf prefix  {
                type string;
                mandatory true;
                description "prefix-list that have their labels advertised";
            }
            leaf peer  {
                type string;
                mandatory true;
                description "peer address for the prefix list name";
            }
        }
    }

    rpc clear-ldp-session-all {
        if-feature feature-list:HAVE_LDPD;
        description "Use this RPC to clear all LDP sessions";
    }

    rpc clear-ldp-session-ipv4 {
        if-feature feature-list:HAVE_LDPD;
        description "Use this RPC to clear the particular LDP IPV4 session";
        input  {
            leaf addr  {
                type inet:ipv4-address;
                mandatory true;
                description "LDP session IPV4 address";
            }
        }
    }

    rpc clear-ldp-adjacency-all {
        if-feature feature-list:HAVE_LDPD;
        description "Use this RPC to clear an adjacency with a specified peer, or to clear
                    all adjacencies for the current LSR";
    }

    rpc clear-ldp-adjacency-ipv4 {
        if-feature feature-list:HAVE_LDPD;
        description "Use this RPC to clear an adjacency with a specified IPV4 peer LSR";
        input  {
            leaf addr  {
                type inet:ipv4-address;
                mandatory true;
                description "LDP adjacency IPV4 address";
            }
        }
    }

    rpc snmp-restart-ldp {
        if-feature feature-list:HAVE_SNMP;
        if-feature feature-list:HAVE_LDPD;
        description "Use this RPC to restart SNMP in LDP";
    }

    rpc ldp-terminal-debug-on {
        if-feature feature-list:HAVE_LDPD;
        description "Use this RPC to enable terminal LDP debugs";
        input  {
            leaf terminal-debug-options  {
                type ipi-ldp-types:ldp_debug_t;
                mandatory true;
                description "debug options for the ICCP";
            }
        }
    }

    rpc ldp-terminal-debug-off {
        if-feature feature-list:HAVE_LDPD;
        description "Use this RPC to disable terminal LDP debugs";
        input  {
            leaf terminal-debug-options  {
                type ipi-ldp-types:ldp_debug_t;
                mandatory true;
                description "debug options for the LDP";
            }
        }
    }

    rpc restart-ldp-graceful {
        if-feature feature-list:HAVE_RESTART;
        if-feature feature-list:HAVE_LDPD;
        description "Use this RPC to LDP gracceful restart";
    }

    notification mpls-ldp-session-up {
        if-feature feature-list:HAVE_LDPD;

        description "If this notification is sent when the value of MPLS LDP 'session-state' enters the operational(5) state..";

        leaf severity {
            type cml-data-types:cml_notif_severity_t;
            description "Notification severity level (value: MINOR)";
        }

        leaf eventClass {
            type cml-data-types:cml_notif_class_t;
            description "Notification event class (value: STATE)";
        }

        leaf peer-address {
            type  inet:ipv4-address;
        description
            "This attribute acquires LDP peer address";
        }

        leaf session-state {
            type ipi-ldp-types:ldp_session_state_t;
        description
            "This attribute acquires state of LDP Session";
        }

        leaf discontinuity-time {
            type  uint32;
        description
            "The value on the most recent occasion at which any one or more of this
                    session's
                    counters suffered a discontinuity.";
        }

        leaf unknown-message-type-errors {
            type  uint32;
        description
            "This object counts the number of Unknown Message Type Errors detected
                    by this LSR/LER during this session";
        }

        leaf unknown-tlv-type-errors {
            type  uint32;
        description
            "This object counts the number of Unknown TLV Errors detected by this
                    LSR/LER during this session";
        }
    }

    notification mpls-ldp-session-down {
        if-feature feature-list:HAVE_LDPD;

        description "If this notification is sent when the value of MPLS LDP 'session-state' leaves the operational(5) state..";

        leaf severity {
            type cml-data-types:cml_notif_severity_t;
            description "Notification severity level (value: CRITICAL)";
        }

        leaf eventClass {
            type cml-data-types:cml_notif_class_t;
            description "Notification event class (value: STATE)";
        }

        leaf peer-address {
            type  inet:ipv4-address;
        description
            "This attribute acquires LDP peer address";
        }

        leaf session-state {
            type ipi-ldp-types:ldp_session_state_t;
        description
            "This attribute acquires state of LDP Session";
        }

        leaf discontinuity-time {
            type  uint32;
        description
            "The value on the most recent occasion at which any one or more of this
                    session's
                    counters suffered a discontinuity.";
        }

        leaf unknown-message-type-errors {
            type  uint32;
        description
            "This object counts the number of Unknown Message Type Errors detected
                    by this LSR/LER during this session";
        }

        leaf unknown-tlv-type-errors {
            type  uint32;
        description
            "This object counts the number of Unknown TLV Errors detected by this
                    LSR/LER during this session";
        }
    }

    notification mpls-ldp-init-session-threshold-exceeded {
        if-feature feature-list:HAVE_LDPD;

        description "This notification is generated when the value of the 'initialization-session-threshold-limit' object is not zero, and the number of Session Initialization messages exceeds the value of the 'initialization-session-threshold-limit' object..";

        leaf severity {
            type cml-data-types:cml_notif_severity_t;
            description "Notification severity level (value: MINOR)";
        }

        leaf eventClass {
            type cml-data-types:cml_notif_class_t;
            description "Notification event class (value: STATE)";
        }

        leaf peer-address {
            type  inet:ipv4-address;
        description
            "This attribute acquires LDP peer address";
        }

        leaf initialization-session-threshold-limit {
            type  uint32;
        description
            "This attribute acquires the threshold value of number of Session
                    Initialization
                    messages can be sent.";
        }
    }

    notification mpls-ldp-path-vector-limit-mismatch {
        if-feature feature-list:HAVE_LDPD;

        description "This notification is sent when the 'entity-path-vector-limit' does NOT match the value of the 'peer-path-vector-limit' for a specific Entity..";

        leaf severity {
            type cml-data-types:cml_notif_severity_t;
            description "Notification severity level (value: MINOR)";
        }

        leaf eventClass {
            type cml-data-types:cml_notif_class_t;
            description "Notification event class (value: STATE)";
        }

        leaf peer-address {
            type  inet:ipv4-address;
        description
            "This attribute acquires LDP peer address";
        }

        leaf entity-path-vector-limit {
            type  uint32;
        description
            "If this object has a value greater than zero, then Loop Dection for
                    Path Vectors is enabled,
                    and the Path Vector Limit is this value.";
        }

        leaf peer-path-vector-limit {
            type  uint32;
        description
            "This object acquires the peer's Path Vector Limit value.";
        }
    }

}
