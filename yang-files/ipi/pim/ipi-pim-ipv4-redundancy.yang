/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-pim-ipv4-redundancy.yang
*
*/

submodule ipi-pim-ipv4-redundancy {

    yang-version 1.1;

    belongs-to  ipi-pim { prefix ipi-pim; }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "PIM IPv4 Redundancy";


    revision "2022-06-01" {
        description "Updated the yang file with feature";
        reference " 0.1.1.";
    }

    revision "2022-03-15" {
        description "Restructured module in accordance with OpenConfig style";
        reference " 0.1.0.";
    }

    grouping pim-ipv4-interface-redundancy-vrrp-state {
        description
            "Grouping for PIM IPv4 Redundancy state data";
        leaf selected-dr-priority  {
            type  uint32;
            description "Selected designated router's priority value.";
        } // END of selected-dr-priority definition.

        leaf vrrp-master  {
            type  boolean;
            description "VRRP state master.";
        } // END of vrrp-master definition.

    } // END of pim-ipv4-interface-redundancy-vrrp-state definition.
    grouping pim-ipv4-interface-redundancy-vrrp-config {
        description
            "Grouping for PIM IPv4 Redundancy configuration data";
        leaf virtual-router-id  {
            type  uint8 {
                 range "1..255"  {
                    description "1..255: Supported range 1 - 255";
                 }
            }
            mandatory true;
            description "Use this attribute to set virtual router identifier value.";
        } // END of virtual-router-id definition.

        leaf dr-priority  {
            type  uint32 {
                 range "0..4294967294"  {
                    description "0..4294967294: Supported range 0 - 4294967294";
                 }
            }
            mandatory true;
            description "Use this attribute to set the designated router's priority value.";
        } // END of dr-priority definition.

    } // END of pim-ipv4-interface-redundancy-vrrp-config definition.
    grouping pim-ipv4-interface-redundancy-vrrp-top {
        description
            "Grouping for PIM IPv4 Redundancy VRRP";
        container vrrp {
            if-feature feature-list:HAVE_PIM_SM_VRRP_AWARE;
            description
                "PIM IPv4 Redundancy VRRP";
            container config {
                // when " ipi-pim-ipv4:ipv4/interfaces/interface/config/pim-mode = '2' ";
                presence "yes";
                description
                    "PIM IPV4 Redundancy VRRP configuration data";
                uses pim-ipv4-interface-redundancy-vrrp-config;
            } // END of config-container definition.
            container state {
                config false;
                description
                    "Operational state data for PIM IPV4 Redundancy VRRP";
                uses pim-ipv4-interface-redundancy-vrrp-config;
                uses pim-ipv4-interface-redundancy-vrrp-state;
            } // END of state-container definition.
        } // END of vrrp-container definition.
    } // END of pim-ipv4-interface-redundancy-vrrp-top definition.
    grouping pim-ipv4-interface-redundancy-top {
        description
            "Grouping for PIM IPv4 Redundancy";
        container pim-redundancy {
            description
                "PIM IPv4 Redundancy";
            uses pim-ipv4-interface-redundancy-vrrp-top;
        } // END of pim-redundancy-container definition.
    } // END of pim-ipv4-interface-redundancy-top definition.


}
