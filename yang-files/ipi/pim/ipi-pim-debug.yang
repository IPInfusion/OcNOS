/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-pim-debug.yang
*
*/

submodule ipi-pim-debug {

    yang-version 1.1;

    belongs-to  ipi-pim { prefix ipi-pim; }

    import feature-list {
        prefix feature-list;
        revision-date 2026-09-15;
    }

    import cml-data-types {
        prefix cml-data-types;
        revision-date 2026-05-15;
    }

    organization
        "IP Infusion Inc.";

    contact
        "Address: 3965 Freedom Circle, Suite 200, Santa Clara, CA 95054
         Phone: +1 408-400-1900
         E-mail: support@ipinfusion.com
         Web: http://www.ipinfusion.com/";

    description
        "PIM IPv4 Debug";


    revision "2023-02-28" {
        description "Adding proper flag for objectAction";
        reference " 0.4.0.";
    }

    revision "2023-02-20" {
        description "Added When tag for no-debug-all command";
        reference " 0.3.0.";
    }

    revision "2022-08-10" {
        description "Debug hierarchy change";
        reference " 0.2.0.";
    }

    revision "2022-06-01" {
        description "Updated the yang file with feature";
        reference " 0.1.1.";
    }

    revision "2022-03-15" {
        description "Restructured module in accordance with OpenConfig style";
        reference " 0.1.0.";
    }

    grouping pim-debug-terminal-state {
        description
            "Grouping for PIM debug";
        leaf terminal-debug-status  {
            type  cml-data-types:cml_on_off_t;
            description "Use this attribute to debug the PIM BFD feature.";
        } // END of terminal-debug-status definition.

    } // END of pim-debug-terminal-state definition.
    grouping pim-debug-config {
        description
            "Grouping for PIM debug configuration";
        leaf bfd  {
            type  empty;
            description "Use this attribute to debug the PIM BFD feature.";
        } // END of bfd definition.

    } // END of pim-debug-config definition.
    grouping pim-debug-top {
        description
            "Grouping for PIM debug";
        container debug {
            if-feature feature-list:HAVE_BFD;
            description
                "Container for PIM debugging functions";
            container config {
                description
                    "Configuration data PIM debug";
                uses pim-debug-config;
            } // END of config-container definition.
            container state {
                config false;
                description
                    "Operational state data for PIM debug";
                uses pim-debug-config;
                uses pim-debug-terminal-state;
            } // END of state-container definition.
        } // END of debug-container definition.
    } // END of pim-debug-top definition.


}
