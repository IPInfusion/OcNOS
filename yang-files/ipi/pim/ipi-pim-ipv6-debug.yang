/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-pim-ipv6-debug.yang
*
*/

submodule ipi-pim-ipv6-debug {

    yang-version 1.1;

    belongs-to  ipi-pim { prefix ipi-pim; }

    import ipi-pim-ipv6-types {
        prefix ipi-pim-ipv6-types;
        revision-date 2024-12-23;
    }

    organization
        "IP Infusion Inc.";

    contact
        "Address: 3965 Freedom Circle, Suite 200, Santa Clara, CA 95054
         Phone: +1 408-400-1900
         E-mail: support@ipinfusion.com
         Web: http://www.ipinfusion.com/";

    description
        "PIM IPv6 Debug";


    revision "2023-02-20" {
        description "Added When tag for no-debug-all command pim-ipv6 debug container";
        reference " 0.4.0.";
    }

    revision "2022-08-10" {
        description "Debug hierarchy change";
        reference " 0.3.0.";
    }

    revision "2022-06-01" {
        description "Updated the yang file with feature";
        reference " 0.2.0.";
    }

    revision "2022-03-30" {
        description "Restructured module in accordance with OpenConfig style";
        reference " 0.1.0.";
    }

    grouping pim-ipv6-debug-terminal-top {
        description
            "Grouping for PIM IPv6 debug";
        leaf terminal-debug-status  {
            type  ipi-pim-ipv6-types:pim_ipv6_debug_t;
            description "Use this attribute to debug the PIM IPv6 feature.";
        } // END of terminal-debug-status definition.

    } // END of pim-ipv6-debug-terminal-top definition.
    grouping pim-ipv6-debug-config {
        description
            "Grouping for PIM IPv6 debug configuration";
        leaf options  {
            type  ipi-pim-ipv6-types:pim_ipv6_debug_t;
            description "Use this attribute to debug the PIM IPv6 feature.";
        } // END of options definition.

    } // END of pim-ipv6-debug-config definition.
    grouping pim-ipv6-debug-top {
        description
            "Grouping for PIM IPv6 debug";
        container debug {
            description
                "Container for PIM IPv6 debugging functions";
            container config {
                description
                    "Configuration data PIM IPv6 debug";
                uses pim-ipv6-debug-config;
            } // END of config-container definition.
            container state {
                config false;
                description
                    "Operational state data for PIM IPv6 debug";
                uses pim-ipv6-debug-config;
                uses pim-ipv6-debug-terminal-top;
            } // END of state-container definition.
        } // END of debug-container definition.
    } // END of pim-ipv6-debug-top definition.


}
