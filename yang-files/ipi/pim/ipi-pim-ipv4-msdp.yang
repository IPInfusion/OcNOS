/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-pim-ipv4-msdp.yang
*
*/

submodule ipi-pim-ipv4-msdp {

    yang-version 1.1;

    belongs-to  ipi-pim { prefix ipi-pim; }

    import feature-list {
        prefix feature-list;
        revision-date 2026-09-15;
    }

    import ietf-inet-types {
        prefix inet;
        revision-date 2013-07-15;
    }

    import ietf-yang-types {
        prefix yang;
        revision-date 2013-07-15;
    }

    import ipi-pim-ipv4-types {
        prefix ipi-pim-ipv4-types;
        revision-date 2023-03-17;
    }

    organization
        "IP Infusion Inc.";

    contact
        "Address: 3965 Freedom Circle, Suite 200, Santa Clara, CA 95054
         Phone: +1 408-400-1900
         E-mail: support@ipinfusion.com
         Web: http://www.ipinfusion.com/";

    description
        "PIM IPv4 Multicast Source Discovery Protocol";


    revision "2024-11-04" {
        description "Changed password size limits";
        reference " 0.2.0.";
    }

    revision "2022-06-01" {
        description "Updated the yang file with feature";
        reference " 0.1.1.";
    }

    revision "2022-03-15" {
        description "Restructured module in accordance with OpenConfig style";
        reference " 0.1.0.";
    }

    grouping pim-ipv4-msdp-peer-authentication-config {
        description
            "Grouping for PIM IPv4 MSDP peer authentication configuration data";
        leaf password  {
            if-feature feature-list:HAVE_TCP_MD5SIG;
            type  string {
                length "1..218";
                pattern "[^?' =,>|]+";
            }
            description "Use this command to set an password key used for authenticating a
                        Multicast Source Discovery Protocol (MSDP) peer. By default, no
                        password is enabled.";
        } // END of password definition.

    } // END of pim-ipv4-msdp-peer-authentication-config definition.
    grouping pim-ipv4-msdp-peer-authentication-top {
        description
            "Grouping for PIM IPv4 MSDP peer authentication";
        container authentication {
            description
                "Container for PIM IPv4 MSDP peer authentication";
            container config {
                description
                    "Configuration data for PIM IPv4 MSDP peer authentication";
                uses pim-ipv4-msdp-peer-authentication-config;
            } // END of config-container definition.
            container state {
                config false;
                description
                    "Operational state data for PIM IPv4 MSDP peer authentication";
                uses pim-ipv4-msdp-peer-authentication-config;
            } // END of state-container definition.
        } // END of authentication-container definition.
    } // END of pim-ipv4-msdp-peer-authentication-top definition.
    grouping pim-ipv4-msdp-peer-state {
        description
            "Grouping for PIM IPv4 MSDP peer operational state data";
        leaf peer-state  {
            type  ipi-pim-ipv4-types:pim_ipv4_msdp_peer_state_t;
            description "Specifies the state of the peer.";
        } // END of peer-state definition.

        leaf peer-role  {
            type  ipi-pim-ipv4-types:pim_ipv4_msdp_peer_role_t;
            description "Use this attribute to configure Active/Passive peer role.";
        } // END of peer-role definition.

    } // END of pim-ipv4-msdp-peer-state definition.
    grouping pim-ipv4-msdp-peer-counters-state {
        description
            "Grouping for PIM IPv4 MSDP peer counters operational state data";
        leaf keepalives-sent  {
            type  yang:counter64;
            description "This counter represents the Keepalive messages sent to peer.";
        } // END of keepalives-sent definition.

        leaf keepalives-received  {
            type  yang:counter64;
            description "This counter represents the Keepalive messages received from the peer.";
        } // END of keepalives-received definition.

        leaf connection-retries  {
            type  yang:counter64;
            description "This counter represents the number of connect retries.";
        } // END of connection-retries definition.

    } // END of pim-ipv4-msdp-peer-counters-state definition.
    grouping pim-ipv4-msdp-peer-config {
        description
            "Grouping for PIM IPv4 MSDP peer configuration data";
        leaf address  {
            type  inet:ipv4-address;
            description "Use this attribute to configure an Multicast Source Discovery Protocol
                        (MSDP) peer relationship.";
        } // END of address definition.

        leaf source-address  {
            type  ipi-pim-ipv4-types:pim_ipv4_reg_source_t;
            description "Use this attribute to configure an Multicast Source Discovery Protocol
                        (MSDP) peer relationship.";
        } // END of source-address definition.

        leaf mesh-group  {
            type  string {
                length "1..64";
                pattern "[a-zA-Z0-9]+";
            }
            description "Use this attribute to add a Multicast Source Discovery Protocol (MSDP)
                        peer to a mesh group.You can set up multiple mesh groups on the same
                        device and multiple peers per mesh group.";
        } // END of mesh-group definition.

        leaf default-peer  {
            type  empty;
            description "Use this attribute to set a Multicast Source Discovery Protocol (MSDP)
                        peer from which to accept Source-Active (SA) messages.You can have
                        multiple active default peers: 1. When you enter multiple ip msdp
                        default-peer commands with a prefix-list keyword, all the default
                        peers are used at the same time for different RP prefixes. This form
                        is typically used in a service provider cloud that connects stub site
                        clouds. 2. When you enter multiple ip msdp default-peer commands
                        without a prefix-list keyword, a single active peer accepts all SA
                        messages. If that peer fails, the next configured default peer accepts
                        all SA messages. This form is typically used at a stub site.";
        } // END of default-peer definition.

        leaf prefix-list  {
            // when " ipi-pim-ipv4:ipv4/instances/instance/msdp/peers/peer/config/default-peer ";
            type  ipi-pim-ipv4-types:pim_ipv4_msdp_peer_acl_t;
            description "Use this attribute to set a Multicast Source Discovery Protocol (MSDP)
                        peer from which to accept Source-Active (SA) messages.You can have
                        multiple active default peers: 1. When you enter multiple ip msdp
                        default-peer commands with a prefix-list keyword, all the default
                        peers are used at the same time for different RP prefixes. This form
                        is typically used in a service provider cloud that connects stub site
                        clouds. 2. When you enter multiple ip msdp default-peer commands
                        without a prefix-list keyword, a single active peer accepts all SA
                        messages. If that peer fails, the next configured default peer accepts
                        all SA messages. This form is typically used at a stub site.";
        } // END of prefix-list definition.

    } // END of pim-ipv4-msdp-peer-config definition.
    grouping pim-ipv4-msdp-peer-top {
        description
            "Grouping for PIM IPv4 MSDP peer";
        container peers {
            description
                "Container for PIM IPv4 MSDP peer";

            list peer {
                key "address";
                description
                    "List of PIM IPv4 MSDP peer";
                leaf address  {
                    type  leafref {
                        path  "../config/address";
                    }
                    description "Use this attribute to configure an Multicast Source Discovery Protocol
                                (MSDP) peer relationship.";
                } // END of address definition.

                container config {
                    description
                        "Configuration data for PIM IPv4 MSDP peer";
                    uses pim-ipv4-msdp-peer-config;
                } // END of config-container definition.
                container state {
                    config false;
                    description
                        "Operational state data for PIM IPv4 MSDP peer";
                    container counters {
                        config false;
                        description
                            "Operational state data for PIM IPv4 MSDP peer counters";
                        uses pim-ipv4-msdp-peer-counters-state;
                    } // END of counters-container definition.
                    uses pim-ipv4-msdp-peer-config;
                    uses pim-ipv4-msdp-peer-state;
                } // END of state-container definition.
                uses pim-ipv4-msdp-peer-authentication-top;
            } // End of peer-list
        } // END of peers-container definition.
    } // END of pim-ipv4-msdp-peer-top definition.
    grouping pim-ipv4-msdp-sa-entry-state {
        description
            "Grouping for PIM IPv4 MSDP source active entry operational state data";
        leaf static-configured  {
            type  empty;
            description "Especifies the static entry.";
        } // END of static-configured definition.

        leaf uptime  {
            type  string {
                length "1..1965";
                pattern "((([0-1]?[0-9])|(2[0-3])):[0-5][0-9]:[0-5][0-9])|([0-9]+d(([0-1][0-9])|(2[0-3]))h[0-5][0-9]m)|([0-9]+w[0-9]+d[0-9]+h)";
            }
            description "Especifies as stated.";
        } // END of uptime definition.

        leaf expire-time  {
            type  uint32;
            description "Especifies the time until entry timeout.";
        } // END of expire-time definition.

        leaf stopped  {
            type  empty;
            description "Especifies the entry timer is not running. When there is no
                        expire-time.";
        } // END of stopped definition.

        leaf sa-rp-forward-count  {
            type  yang:counter64;
            description "Specifies the SA reverse path forwarding counter.";
        } // END of sa-rp-forward-count definition.

        leaf reverse-path-forwarding-peer  {
            type  inet:ipv4-address;
            description "Specifies the reverse path forwarding peer counter.";
        } // END of reverse-path-forwarding-peer definition.

    } // END of pim-ipv4-msdp-sa-entry-state definition.
    grouping pim-ipv4-msdp-sa-entry-config {
        description
            "Grouping for PIM IPv4 MSDP source active entry configuration data";
        leaf source-address  {
            type  inet:ipv4-address;
            description "Use this attribute to configure an Multicast Source Discovery Protocol
                        (MSDP) source address.";
        } // END of source-address definition.

        leaf group-address  {
            type  inet:ipv4-address;
            description "Use this attribute to configure an Multicast Source Discovery Protocol
                        (MSDP) remote group.";
        } // END of group-address definition.

        leaf rp-address  {
            type  inet:ipv4-address;
            mandatory true;
            description "Use this attribute to configure an Multicast Source Discovery Protocol
                        (MSDP) remote rp-address.";
        } // END of rp-address definition.

    } // END of pim-ipv4-msdp-sa-entry-config definition.
    grouping pim-ipv4-msdp-sa-entry-top {
        description
            "Grouping for PIM IPv4 MSDP";
        container source-active-entries {
            description
                "Container for PIM IPv4 MSDP source active entries";

            list source-active-entry {
            // when " ipi-pim-ipv4:ipv4/instances/instance/msdp/source-active-entries/source-active-entry/config/rp-address ";
                key "source-address group-address";
                description
                    "List of PIM IPv4 MSDP source active entry";
                leaf source-address  {
                    type  leafref {
                        path  "../config/source-address";
                    }
                    description "Use this attribute to configure an Multicast Source Discovery Protocol
                                (MSDP) source address.";
                } // END of source-address definition.

                leaf group-address  {
                    type  leafref {
                        path  "../config/group-address";
                    }
                    description "Use this attribute to configure an Multicast Source Discovery Protocol
                                (MSDP) remote group.";
                } // END of group-address definition.

                container config {
                    description
                        "Configuration data for PIM IPv4 MSDP source active entry";
                    uses pim-ipv4-msdp-sa-entry-config;
                } // END of config-container definition.
                container state {
                    config false;
                    description
                        "Operational state data for PIM IPv4 MSDP source active entry";
                    uses pim-ipv4-msdp-sa-entry-config;
                    uses pim-ipv4-msdp-sa-entry-state;
                } // END of state-container definition.
            } // End of source-active-entry-list
        } // END of source-active-entries-container definition.
    } // END of pim-ipv4-msdp-sa-entry-top definition.
    grouping pim-ipv4-msdp-state {
        description
            "Grouping for PIM IPv4 MSDP operational state data";
        leaf source-active-entries-entries-count  {
            type  uint32;
            description "PIM IPv4 MSDP source active entries counter.";
        } // END of source-active-entries-entries-count definition.

    } // END of pim-ipv4-msdp-state definition.
    grouping pim-ipv4-msdp-config {
        description
            "Grouping for PIM IPv4 MSDP configuration data";
        leaf originator-id  {
            type  string {
                length "1..33";
                pattern "[^?' =,>|]+";
            }
            description "Use this attribute to allow a Multicast Source Discovery Protocol
                        (MSDP) speaker that originates a Source-Active (SA) message to use the
                        IP address of an interface as a rendezvous point (RP) address in the
                        SA message.";
        } // END of originator-id definition.

    } // END of pim-ipv4-msdp-config definition.
    grouping pim-ipv4-msdp-top {
        description
            "Grouping for PIM IPv4 MSDP";
        container msdp {
            if-feature feature-list:HAVE_PIM_MSDP;
            description
                "Container for PIM IPv4 MSDP";
            container config {
                description
                    "Configuration data for PIM IPv4 MSDP";
                uses pim-ipv4-msdp-config;
            } // END of config-container definition.
            container state {
                config false;
                description
                    "Operational state data for PIM IPv4 MSDP";
                uses pim-ipv4-msdp-config;
                uses pim-ipv4-msdp-state;
            } // END of state-container definition.
            uses pim-ipv4-msdp-sa-entry-top;
            uses pim-ipv4-msdp-peer-top;
        } // END of msdp-container definition.
    } // END of pim-ipv4-msdp-top definition.


}
