/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-pim-ipv6.yang
*
*/

submodule ipi-pim-ipv6 {

    yang-version 1.1;

    belongs-to  ipi-pim { prefix ipi-pim; }

    import feature-list {
        prefix feature-list;
        revision-date 2026-09-15;
    }

    import cml-data-types {
        prefix cml-data-types;
        revision-date 2026-05-15;
    }

    import ietf-inet-types {
        prefix inet;
        revision-date 2013-07-15;
    }

    import ipi-pim-ipv6-types {
        prefix ipi-pim-ipv6-types;
        revision-date 2024-12-23;
    }

    import ipi-network-instance {
        prefix ipi-network-instance;
        revision-date 2026-08-12;
    }

    import ipi-interface {
        prefix ipi-interface;
        revision-date 2026-03-10;
    }

    import ipi-vrf {
        prefix ipi-vrf;
        revision-date 2026-08-12;
    }

    include ipi-pim-ipv6-debug { revision-date 2023-02-20;}
    include ipi-pim-ipv6-interface { revision-date 2024-06-30;}
    include ipi-pim-ipv6-state { revision-date 2024-12-13;}
    organization
        "IP Infusion Inc.";

    contact
        "Address: 3965 Freedom Circle, Suite 200, Santa Clara, CA 95054
         Phone: +1 408-400-1900
         E-mail: support@ipinfusion.com
         Web: http://www.ipinfusion.com/";

    description
        "Protocol Independent Multicast (PIM) IPv6 configurations";


    revision "2023-07-07" {
        description "Removing the misplaced initialized from pim-ipv6-rp-bsr-candidate-config";
        reference " 0.1.0.";
    }

    revision "2023-03-17" {
        description "Pattern validation added for accept-register name, ACL name and ECMP bundle name";
        reference " 0.5.2.";
    }

    revision "2023-02-20" {
        description "Reordering revision history";
        reference " 0.5.1.";
    }

    revision "2023-02-17" {
        description "Fixed prependstr warning";
        reference " 0.5.0.";
    }

    revision "2022-11-13" {
        description "modified SSM range 232/8 to FF3x::/96 for IPv6";
        reference " 0.4.0.";
    }

    revision "2022-08-10" {
        description "Debug hierarchy change";
        reference " 0.3.0.";
    }

    revision "2022-07-06" {
        description "Fixed removal of embed-rp";
        reference " 0.2.5.";
    }

    revision "2022-06-06" {
        description "Removed rp-interface-name and .../upstream-xg/state/keep-alive-timer attributes";
        reference " 0.2.5.";
    }

    revision "2022-06-01" {
        description "Updated the yang file with feature";
        reference " 0.2.4.";
    }

    revision "2022-04-04" {
        description "The module ipi-pim-ipv6-interface was modified";
        reference " 0.2.3.";
    }

    revision "2022-03-30" {
        description "Restructured module in accordance with OpenConfig style";
        reference " 0.2.0.";
    }

    revision "2018-06-21" {
        description "Initial Version";
        reference " 0.1.0.";
    }

    grouping pim-ipv6-anycast-rp-config {
        description
            "Grouping for PIM IPv6 anycast Rendezvous Point configuration data";
        leaf anycast-rp-address  {
            type  inet:ipv6-address;
            description "Use this attribute to set the unicast IPv6 address of the anycast RP
                        set.
                        An anycast RP set is a collection of RPs in the same domain.";
        } // END of anycast-rp-address definition.

        leaf member-rp-address  {
            type  inet:ipv6-address;
            description "Destination IPv6 address where register messages are copied and sent.
                        A Member RP is an individual RP member in the anycast RP set.";
        } // END of member-rp-address definition.

    } // END of pim-ipv6-anycast-rp-config definition.
    grouping pim-ipv6-anycast-rp-top {
        description
            "Grouping for PIM IPv6 anycast Rendezvous Point";
        container anycast-rps {
            if-feature feature-list:HAVE_PIM_SM;
            description
                "Container for PIM IPv6 anycast Rendezvous Point";

            list anycast-rp {
                key "anycast-rp-address member-rp-address";
                description
                    "List of PIM IPv6 anycast Rendezvous Point";
                leaf anycast-rp-address  {
                    type  leafref {
                        path  "../config/anycast-rp-address";
                    }
                    description "Use this attribute to set the unicast IPv6 address of the anycast RP
                                set.
                                An anycast RP set is a collection of RPs in the same domain.";
                } // END of anycast-rp-address definition.

                leaf member-rp-address  {
                    type  leafref {
                        path  "../config/member-rp-address";
                    }
                    description "Destination IPv6 address where register messages are copied and sent.
                                A Member RP is an individual RP member in the anycast RP set.";
                } // END of member-rp-address definition.

                container config {
                    description
                        "Configuration data for PIM IPv6 anycast Rendezvous Point";
                    uses pim-ipv6-anycast-rp-config;
                } // END of config-container definition.
                container state {
                    config false;
                    description
                        "Operational state data for PIM IPv6 anycast Rendezvous Point";
                    uses pim-ipv6-anycast-rp-config;
                } // END of state-container definition.
            } // End of anycast-rp-list
        } // END of anycast-rps-container definition.
    } // END of pim-ipv6-anycast-rp-top definition.
    grouping pim-ipv6-register-packet-config {
        description
            "Grouping for PIM IPv6 register packet configuration data";
        leaf register-reachability-check  {
            type  cml-data-types:cml_enable_disable_t;
            default "enable";
            description "Use this attribute to enable the RP reachability check for PIM
                        Registers at the designated router (DR).";
        } // END of register-reachability-check definition.

        leaf rate-limit  {
            type  uint16 {
                 range "1..65535"  {
                    description "1..65535: Supported range 1 - 65535";
                 }
            }
            units "packets/seconds";
            description "Use this attribute to configure the rate of register packets sent by
                        this designated router (DR).";
        } // END of rate-limit definition.

        leaf suppress-interval  {
            type  uint16 {
                 range "11..65535"  {
                    description "11..65535: Supported range 11 - 65535";
                 }
            }
            units "seconds";
            default "60";
            description "Use this attribute to configure the register suppression time.";
        } // END of suppress-interval definition.

        leaf keep-alive-interval  {
            type  uint16 {
                 range "1..65535"  {
                    description "1..65535: Supported range 1 - 65535";
                 }
            }
            units "seconds";
            default "185";
            description "Use this attribute to configure a Keep alive Timer (KAT) value for
                        (S,G) states at RP to monitor PIM register packets.";
        } // END of keep-alive-interval definition.

        leaf source-address  {
            type  ipi-pim-ipv6-types:pim_ipv6_reg_source_t;
            description "Use this attribute to configure the source address of register packets
                        sent by this designated router (DR).";
        } // END of source-address definition.

        leaf accept-register  {
            type  string {
                length "1..64";
                pattern "[a-zA-Z0-9_-]+";
            }
            description "Use this attribute to configure the ACL of register packets accepted
                        by this designated router (DR).";
        } // END of accept-register definition.

    } // END of pim-ipv6-register-packet-config definition.
    grouping pim-ipv6-register-packet-top {
        description
            "Grouping for PIM IPv6 register packet";
        container register-packet {
            if-feature feature-list:HAVE_PIM_SM;
            description
                "Container for PIM IPv6 register packet";
            container config {
                description
                    "Configuration data for PIM IPv6 register packet";
                uses pim-ipv6-register-packet-config;
            } // END of config-container definition.
            container state {
                config false;
                description
                    "Operational state data for PIM IPv6 register packet";
                uses pim-ipv6-register-packet-config;
                uses pim-ipv6-register-statistics-state;
            } // END of state-container definition.
        } // END of register-packet-container definition.
    } // END of pim-ipv6-register-packet-top definition.
    grouping pim-ipv6-interop-register-packet-config {
        description
            "Grouping for PIM IPv6 register interoperability configuration data";
        leaf cisco-register-checksum-enable  {
            if-feature feature-list:HAVE_PIM_SM;
            type  empty;
            mandatory true;
            description "Use this attribute to configure the option to calculate the register
                        checksum over the whole packet.
                        This is used to inter-operate with older Cisco IOS versions.";
        } // END of cisco-register-checksum-enable definition.

        leaf access-control-list  {
            if-feature feature-list:HAVE_PIM_SM;
            type  string {
                length "1..64";
                pattern "[a-zA-Z0-9_-]+";
            }
            description "Use this attribute to configure the option to calculate the register
                        checksum over the whole packet
                        on multicast groups specified by the access control list.";
        } // END of access-control-list definition.

    } // END of pim-ipv6-interop-register-packet-config definition.
    grouping pim-ipv6-interop-register-packet-top {
        description
            "Grouping for PIM IPv6 register interoperability";
        container register-packet {
            description
                "Container for PIM IPv6 register interoperability";
            container config {
                presence "yes";
                description
                    "Configuration data for PIM IPv6 register interoperability";
                uses pim-ipv6-interop-register-packet-config;
            } // END of config-container definition.
            container state {
                config false;
                description
                    "Operational state data for PIM IPv6 register interoperability";
                uses pim-ipv6-interop-register-packet-config;
            } // END of state-container definition.
        } // END of register-packet-container definition.
    } // END of pim-ipv6-interop-register-packet-top definition.
    grouping pim-ipv6-interop-config {
        description
            "Grouping for PIM IPv6 interoperability configuration data";
        leaf ignore-rp-set-priority  {
            if-feature feature-list:HAVE_PIM_SM;
            type  empty;
            description "Use this attribute to ignore the RP-SET priority value, and use only
                        the hashing mechanism for RP selection.
                        This is used to inter-operate with older Cisco IOS versions.";
        } // END of ignore-rp-set-priority definition.

        leaf cisco-bsr-interop-enable  {
            if-feature feature-list:HAVE_PIM_SM;
            type  empty;
            description "Use this attribute to turn on or turn the Candidate-RP debugging
                        timerworking with Cisco BSR.";
        } // END of cisco-bsr-interop-enable definition.

    } // END of pim-ipv6-interop-config definition.
    grouping pim-ipv6-interop-top {
        description
            "Grouping for PIM IPv6 interoperability";
        container interop {
            description
                "Container for PIM IPv6 interoperability";
            container config {
                description
                    "Configuration data for PIM IPv6 interoperability";
                uses pim-ipv6-interop-config;
            } // END of config-container definition.
            container state {
                config false;
                description
                    "Operational state data for PIM IPv6 interoperability";
                uses pim-ipv6-interop-config;
            } // END of state-container definition.
            uses pim-ipv6-interop-register-packet-top;
        } // END of interop-container definition.
    } // END of pim-ipv6-interop-top definition.
    grouping pim-ipv6-ssm-config {
        description
            "Grouping for PIM IPv6 SSM configuration data";
        leaf range-policy  {
            type  ipi-pim-ipv6-types:pim_ipv6_ssm_range_policy_type_t;
            description "Use this attribute to set Source Specific Multicast (SSM) and define
                        the range of multicast IP addresses.
                        Ranges can be either the default, which defines the SSM range as
                        FF3x::/96, or indicated by the given standard
                        access control list.";
        } // END of range-policy definition.

    } // END of pim-ipv6-ssm-config definition.
    grouping pim-ipv6-ssm-top {
        description
            "Grouping for PIM IPv6 SSM";
        container ssm {
            if-feature feature-list:HAVE_PIM_SSM;
            description
                "Container for PIM IPv6 SSM";
            container config {
                description
                    "Configuration data for PIM IPv6 SSM";
                uses pim-ipv6-ssm-config;
            } // END of config-container definition.
            container state {
                config false;
                description
                    "Operational state data for PIM IPv6 SSM";
                uses pim-ipv6-ssm-config;
            } // END of state-container definition.
        } // END of ssm-container definition.
    } // END of pim-ipv6-ssm-top definition.
    grouping pim-ipv6-spt-switch-config {
        description
            "Grouping for PIM IPv6 SPT Switch configuration data";
        leaf enable  {
            if-feature feature-list:HAVE_PIM_SM;
            type  empty;
            mandatory true;
            description "Use this attribute to enable the ability of the last-hop PIM router to
                        switch to SPT.";
        } // END of enable definition.

        leaf access-control-list  {
            if-feature feature-list:HAVE_PIM_SM;
            type  string {
                length "1..64";
                pattern "[a-zA-Z0-9_-]+";
            }
            description "Use this attribute to to enable the ability of the last-hop PIM router
                        to switch to SPT for multicast group
                        addresses indicated by the given standard access control list.";
        } // END of access-control-list definition.

    } // END of pim-ipv6-spt-switch-config definition.
    grouping pim-ipv6-spt-switch-top {
        description
            "Grouping for PIM IPv6 Shortest-path tree (SPT) Switch";
        container spt-switch {
            description
                "Container for PIM IPv6 SPT Switch";
            container config {
                presence "yes";
                description
                    "Configuration data for PIM IPv6 SPT Switch";
                uses pim-ipv6-spt-switch-config;
            } // END of config-container definition.
            container state {
                config false;
                description
                    "Operational state data for PIM IPv6 SPT Switch";
                uses pim-ipv6-spt-switch-config;
            } // END of state-container definition.
        } // END of spt-switch-container definition.
    } // END of pim-ipv6-spt-switch-top definition.
    grouping pim-ipv6-rp-static-rp-config {
        description
            "Grouping for PIM IPv6 static rendezvous points configuration data";
        leaf rp-address  {
            type  inet:ipv6-address;
            description "Use this attribute to statically configure Rendezvous Point (RP)
                        address for multicast groups.";
        } // END of rp-address definition.

        leaf access-control-list  {
            type  string {
                length "1..64";
                pattern "[a-zA-Z0-9_-]+";
            }
            description "Use this attribute to configure the name of access control list (ACL).";
        } // END of access-control-list definition.

        leaf override-dynamically-learned-rp  {
            type  empty;
            description "Use this attribute do configure the flag to overrides dynamically
                        learned RP mappings.";
        } // END of override-dynamically-learned-rp definition.

    } // END of pim-ipv6-rp-static-rp-config definition.
    grouping pim-ipv6-rp-static-rp-default-top {
        description
            "Grouping for PIM IPv6 static rendezvous point default mode";

        list static-rp-default {
            key "rp-address";
            description
                "List of PIM IPv6 static rendezvous points default mode";
            leaf rp-address  {
                type  leafref {
                    path  "../config/rp-address";
                }
                description "Use this attribute to statically configure Rendezvous Point (RP)
                            address for multicast groups.";
            } // END of rp-address definition.

            container config {
                description
                    "Configuration data for PIM IPv6 static rendezvous point default mode";
                uses pim-ipv6-rp-static-rp-config;
            } // END of config-container definition.
            container state {
                config false;
                description
                    "Operational state data for PIM IPv6 static rendezvous point default
                            mode";
                uses pim-ipv6-rp-static-rp-config;
            } // END of state-container definition.
        } // End of static-rp-default-list
    } // END of pim-ipv6-rp-static-rp-default-top definition.
    grouping pim-ipv6-rp-static-rp-top {
        description
            "Grouping for PIM IPv6 static rendezvous point";
        container static-rps {
            description
                "Container for PIM IPv6 static rendezvous points";
            container static-rps-default {
                description
                    "Container for PIM IPv6 static rendezvous points default mode";
                uses pim-ipv6-rp-static-rp-default-top;
            } // END of static-rps-default-container definition.
        } // END of static-rps-container definition.
    } // END of pim-ipv6-rp-static-rp-top definition.
    grouping pim-ipv6-rp-bsr-candidate-config {
        description
            "Grouping for PIM IPv6 RP Bootstrap (BSR) candidate attributes";
        leaf interface-name  {
            type  leafref {
                path  "/ipi-interface:interfaces/ipi-interface:interface/ipi-interface:name";
            }
            description "Use this attribute to configure the interface for the candidate BSR
                        router.";
        } // END of interface-name definition.

        leaf hash-mask-length  {
            type  uint8 {
                 range "0..32"  {
                    description "0..32: Supported range 0 - 32";
                 }
            }
            description "Use this attribute to configure the mask length used to calculate the
                        group address for RP.";
        } // END of hash-mask-length definition.

        leaf priority  {
            type  uint8 {
                 range "0..255"  {
                    description "0..255: Supported range 0 - 255";
                 }
            }
            description "Use this attribute to configure the priority value for candidate BSR
                        router.";
        } // END of priority definition.

    } // END of pim-ipv6-rp-bsr-candidate-config definition.
    grouping pim-ipv6-rp-bsr-candidate-top {
        description
            "Grouping for PIM IPv6 RP Bootstrap (BSR) candidate";
        container bsr-candidate {
            description
                "Container for PIM IPv6 RP Bootstrap (BSR) candidate";
            container config {
                // when " ipi-pim-ipv6:ipv6/instances/instance/rendezvous-point/bootstrap-router/bsr-candidate/config/interface-name ";
                description
                    "Configuration data for PIM IPv6 RP Bootstrap (BSR) candidate";
                uses pim-ipv6-rp-bsr-candidate-config;
            } // END of config-container definition.
            container state {
                config false;
                description
                    "Operational state data for PIM IPv6 RP Bootstrap (BSR) candidate";
                uses pim-ipv6-rp-bsr-candidate-config;
            } // END of state-container definition.
        } // END of bsr-candidate-container definition.
    } // END of pim-ipv6-rp-bsr-candidate-top definition.
    grouping pim-ipv6-rp-bsr-top {
        description
            "Grouping for PIM IPv6 RP Bootstrap (BSR)";
        container bootstrap-router {
            description
                "Container for PIM IPv6 RP Bootstrap (BSR)";
            uses pim-ipv6-rp-bsr-candidate-top;
        } // END of bootstrap-router-container definition.
    } // END of pim-ipv6-rp-bsr-top definition.
    grouping pim-ipv6-rp-rp-candidate-config {
        description
            "Grouping for PIM IPv6 RP candidate attributes";
        leaf interface-name  {
            type  leafref {
                path  "/ipi-interface:interfaces/ipi-interface:interface/ipi-interface:name";
            }
            description "Use this attribute to configure the interface for the RP candidate BSR
                        router.";
        } // END of interface-name definition.

        leaf access-control-list  {
            type  string {
                length "1..64";
                pattern "[a-zA-Z0-9_-]+";
            }
            description "Use this attribute to configure the name of ACL for the RP candidate.";
        } // END of access-control-list definition.

        leaf advertisement-interval  {
            type  uint16 {
                 range "1..16383"  {
                    description "1..16383: Supported range 1 - 16383";
                 }
            }
            units "seconds";
            description "Use this attribute to configure the advertisement interval in seconds
                        for RP candidate.";
        } // END of advertisement-interval definition.

        leaf priority  {
            type  uint8 {
                 range "0..255"  {
                    description "0..255: Supported range 0 - 255";
                 }
            }
            description "Use this attribute to configure the priority value for RP candidate.";
        } // END of priority definition.

    } // END of pim-ipv6-rp-rp-candidate-config definition.
    grouping pim-ipv6-rp-rp-candidate-top {
        description
            "Grouping for PIM IPv6 RP candidate";
        container rp-candidates {
            description
                "Container for PIM IPv6 RP candidate";

            list rp-candidate {
                key "interface-name";
                description
                    "List of PIM IPv6 RP candidate";
                leaf interface-name  {
                    type  leafref {
                        path  "../config/interface-name";
                    }
                    description "Use this attribute to configure the interface name for RP.";
                } // END of interface-name definition.

                container config {
                    description
                        "Configuration data for PIM IPv6 RP candidate";
                    uses pim-ipv6-rp-rp-candidate-config;
                } // END of config-container definition.
                container state {
                    config false;
                    description
                        "Operational state data for PIM IPv6 RP candidate";
                    uses pim-ipv6-rp-rp-candidate-config;
                } // END of state-container definition.
            } // End of rp-candidate-list
        } // END of rp-candidates-container definition.
    } // END of pim-ipv6-rp-rp-candidate-top definition.
    grouping pim-ipv6-rp-config {
        description
            "Grouping for PIM IPv6 rendezvous point configuration data";
        leaf embed-rp  {
            type  cml-data-types:cml_enable_disable_t;
            default "enable";
            description "Use this attribute to embed the PIM Rendezvous Point";
        } // END of embed-rp definition.

    } // END of pim-ipv6-rp-config definition.
    grouping pim-ipv6-rp-top {
        description
            "Grouping for PIM IPv6 rendezvous point";
        container rendezvous-point {
            description
                "Container for PIM IPv6 rendezvous point";
            container config {
                description
                    "Configuration data for PIM IPv6 rendezvous point";
                uses pim-ipv6-rp-config;
            } // END of config-container definition.
            container state {
                config false;
                description
                    "Operational state data for PIM IPv6 rendezvous point";
                uses pim-ipv6-rp-config;
            } // END of state-container definition.
            uses pim-ipv6-rp-static-rp-top;
            uses pim-ipv6-rp-bsr-top;
            uses pim-ipv6-rp-rp-candidate-top;
        } // END of rendezvous-point-container definition.
    } // END of pim-ipv6-rp-top definition.
    grouping pim-ipv6-instance-config {
        description
            "Grouping for PIM IPv6 instance configuration attributes";
        leaf vrf-name  {
            type  leafref {
                path  "/ipi-network-instance:network-instances/ipi-network-instance:network-instance/ipi-vrf:vrf/ipi-vrf:config/ipi-vrf:vrf-name";
            }
            description "VRF name associated with this instance.";
        } // END of vrf-name definition.

        leaf router-id  {
            if-feature feature-list:HAVE_PIM_SM;
            type  inet:ipv4-address;
            description "Use this attribute to configure PIM router-ID to uniquely identify the
                        router.By default, PIM registers for the NSM router-id service. This
                        attribute will override the router-id received from NSM.";
        } // END of router-id definition.

        leaf join-prune-interval  {
            if-feature feature-list:HAVE_PIM_SM;
            type  uint16 {
                 range "1..65535"  {
                    description "1..65535: Supported range 1 - 65535";
                 }
            }
            description "Use this attribute to set a PIM join/prune timer.";
        } // END of join-prune-interval definition.

        leaf-list ecmp-bundle  {
            if-feature feature-list:HAVE_PIM_ECMP_REDIRECT;
            type  string {
                length "1..50";
                pattern "[a-zA-Z0-9_-]+";
            }
            description "Use this attribute to create an ECMP bundle.";
        } // END of ecmp-bundle definition.

        leaf-list dense-mode-group  {
            if-feature feature-list:HAVE_PIM_SMDM;
            type  inet:ipv6-address;
            description "Use this attribute to force a particular group to always follow dense
                        mode irrespective of whether RP mapping is available or not in SM-DM
                        mode.";
        } // END of dense-mode-group definition.

        leaf enable-bfd-all-interfaces  {
            if-feature feature-list:HAVE_BFD;
            type  empty;
            description "Use this attribute to enable Bidirectional Forwarding Detection (BFD)
                        on all interfaces.";
        } // END of enable-bfd-all-interfaces definition.

    } // END of pim-ipv6-instance-config definition.
    grouping pim-ipv6-instance-top {
        description
            "Grouping for PIM IPv6 instance";
        container instances {
            description
                "Configuration data for PIM IPv6 instance";

            list instance {
                key "vrf-name";
                description
                    "List of PIM IPv6 instances";
                leaf vrf-name  {
                    type  leafref {
                        path  "../config/vrf-name";
                    }
                    description "VRF name associated with this instance";
                } // END of vrf-name definition.

                container config {
                    description
                        "Configuration data for PIM IPv6 instance";
                    uses pim-ipv6-instance-config;
                } // END of config-container definition.
                container state {
                    config false;
                    description
                        "Operational state data for PIM IPv6 instance";
                    uses pim-ipv6-instance-config;
                    uses pim-ipv6-statistics-state;
                    uses pim-ipv6-rp-set-top;
                } // END of state-container definition.
                uses pim-ipv6-route-top;
                uses pim-ipv6-register-packet-top;
                uses pim-ipv6-interop-top;
                uses pim-ipv6-spt-switch-top;
                uses pim-ipv6-ssm-top;
                uses pim-ipv6-anycast-rp-top;
                uses pim-ipv6-rp-top;
                uses pim-ipv6-debug-top;
                uses pim-ipv6-multicast-route-top;
            } // End of instance-list
        } // END of instances-container definition.
    } // END of pim-ipv6-instance-top definition.

    grouping  ipv6-grouping {
    description
        "Container for Protocol Independent Multicast (PIM) IPv6";
    container ipv6 {
        if-feature feature-list:HAVE_PIM_IPV6;
        if-feature feature-list:HAVE_PIMD;
        description
            "Container for Protocol Independent Multicast (PIM) IPv6";
        uses pim-ipv6-instance-top;
        uses pim-ipv6-interface-top;
    } // END of ipv6-container definition.
    } // END of ipv6-grouping definition.


}
