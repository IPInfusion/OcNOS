/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-pim-ipv6-interface.yang
*
*/

submodule ipi-pim-ipv6-interface {

    yang-version 1.1;

    belongs-to  ipi-pim { prefix ipi-pim; }

    import feature-list {
        prefix feature-list;
        revision-date 2026-09-15;
    }

    import cml-data-types {
        prefix cml-data-types;
        revision-date 2026-05-15;
    }

    import ietf-inet-types {
        prefix inet;
        revision-date 2013-07-15;
    }

    import ipi-interface {
        prefix ipi-interface;
        revision-date 2026-03-10;
    }

    import ipi-pim-ipv6-types {
        prefix ipi-pim-ipv6-types;
        revision-date 2024-12-23;
    }

    organization
        "IP Infusion Inc.";

    contact
        "Address: 3965 Freedom Circle, Suite 200, Santa Clara, CA 95054
         Phone: +1 408-400-1900
         E-mail: support@ipinfusion.com
         Web: http://www.ipinfusion.com/";

    description
        "PIM IPv6 Interfaces";


    revision "2024-06-30" {
        description "IPv6-PIM Added Implicit Delete of interface configs for LAG member";
        reference " 0.4.2.";
    }

    revision "2023-03-17" {
        description "Pattern validation added for neighbor access control list name and ECMP bundle name";
        reference " 0.4.1.";
    }

    revision "2023-02-20" {
        description "Reordering revision history";
        reference " 0.4.0.";
    }

    revision "2022-06-01" {
        description "Updated the yang file with feature";
        reference " 0.3.0.";
    }

    revision "2022-04-04" {
        description "Modified the router-id type to ipv4 address";
        reference " 0.2.0.";
    }

    revision "2022-03-30" {
        description "Restructured module in accordance with OpenConfig style";
        reference " 0.1.0.";
    }

    grouping pim-ipv6-interface-neighbor-state {
        description
            "Grouping for PIM IPv6 interface neighbor operational data";
        leaf address  {
            type  inet:ipv6-address;
            description "PIM IPv6 neighbor's address.";
        } // END of address definition.

        leaf designated-router  {
            type  empty;
            description "Neighbor's designated router field value.";
        } // END of designated-router definition.

        leaf neighbor-established  {
            type  string {
                length "1..1965";
                pattern "((([0-1]?[0-9])|(2[0-3])):[0-5][0-9]:[0-5][0-9])|([0-9]+d(([0-1][0-9])|(2[0-3]))h[0-5][0-9]m)|([0-9]+w[0-9]+d[0-9]+h)";
            }
            description "This timestamp indicates the time that the PIM IPv6 neighbor adjacency
                        established.";
        } // END of neighbor-established definition.

        leaf neighbor-expires  {
            type  string {
                length "1..1965";
                pattern "((([0-1]?[0-9])|(2[0-3])):[0-5][0-9]:[0-5][0-9])|([0-9]+d(([0-1][0-9])|(2[0-3]))h[0-5][0-9]m)|([0-9]+w[0-9]+d[0-9]+h)";
            }
            description "This timestamp indicates the time that the PIM IPv6 neighbor adjacency
                        will expire should hello messages fail to arrive from the neighbor.";
        } // END of neighbor-expires definition.

        leaf-list secondary-address  {
            type  inet:ipv6-address;
            description "The secondary addresses advertised by the PIM IPv6 neighbor.";
        } // END of secondary-address definition.

        leaf hello-holdtime  {
            type  uint16;
            units "seconds";
            description "Hello holdtime.";
        } // END of hello-holdtime definition.

        leaf lan-delay  {
            type  uint16;
            units "milliseconds";
            description "Neighbors' LAN-prune-delay timer value.";
        } // END of lan-delay definition.

        leaf override-interval  {
            type  uint32;
            units "milliseconds";
            description "Neighbors' Override-Interval timer value.";
        } // END of override-interval definition.

        leaf dr-priority  {
            if-feature feature-list:HAVE_PIM_SM;
            type  uint32;
            description "Use this attribute to set the Designated Router's priority value.";
        } // END of dr-priority definition.

        leaf generated-id  {
            type  uint32;
            description "PIM IPv6 router-ID that uniquely identifies the neighbor generated ID.";
        } // END of generated-id definition.

        leaf router-id  {
            type  inet:ipv4-address;
            description "PIM IPv4 router-ID that uniquely identifies the neighbor router ID.";
        } // END of router-id definition.

        leaf local-id  {
            type  uint32;
            description "PIM IPv6 local ID.";
        } // END of local-id definition.

        leaf tracking-support  {
            type  empty;
            description "Neighbor's tracking support field value.";
        } // END of tracking-support definition.

        leaf bidir-capable  {
            if-feature feature-list:HAVE_PIM_BIDIR;
            type  empty;
            description "Neighbor's bidirectional value.";
        } // END of bidir-capable definition.

        leaf ecmp-redirect-enabled  {
            if-feature feature-list:HAVE_PIM_ECMP_REDIRECT;
            type  empty;
            description "Neighbor's ECMP configuration value.";
        } // END of ecmp-redirect-enabled definition.

    } // END of pim-ipv6-interface-neighbor-state definition.
    grouping pim-ipv6-interface-neighbor-top {
        description
            "Grouping for PIM IPv6 interface neighbors";
        container neighbors {
            config false;
            description
                "State data for PIM IPv6 interface neighbors";

            list neighbor {
                key "address";
                config false;
                description
                    "List of PIM IPv6 interface neighbor";
                leaf address  {
                    type  leafref {
                        path  "../state/address";
                    }
                    description "PIM IPv6 neighbor's address.";
                } // END of address definition.

                container state {
                    config false;
                    description
                        "Operational state data for PIM IPv6 interface neighbors";
                    uses pim-ipv6-interface-neighbor-state;
                } // END of state-container definition.
            } // End of neighbor-list
        } // END of neighbors-container definition.
    } // END of pim-ipv6-interface-neighbor-top definition.
    grouping pim-ipv6-interface-state {
        description
            "Grouping for PIM IPv6 interface state data";
        leaf next-hello  {
            type  string {
                length "1..1965";
                pattern "((([0-1]?[0-9])|(2[0-3])):[0-5][0-9]:[0-5][0-9])|([0-9]+d(([0-1][0-9])|(2[0-3]))h[0-5][0-9]m)|([0-9]+w[0-9]+d[0-9]+h)";
            }
            units "seconds";
            description "Time for the next hello message.";
        } // END of next-hello definition.

        leaf router-id  {
            type  inet:ipv4-address;
            description "PIM IPv4 router-ID that uniquely identifies the router.";
        } // END of router-id definition.

        leaf local-id  {
            type  uint32;
            description "PIM IPv6 neighbor's local ID.";
        } // END of local-id definition.

        leaf dr-address  {
            type  inet:ipv6-address;
            description "PIM IPv6 Designated Router address.";
        } // END of dr-address definition.

    } // END of pim-ipv6-interface-state definition.
    grouping pim-ipv6-interface-config {
        description
            "Grouping for PIM IPv6 interface configuration data";
        leaf name  {
            type  leafref {
                path  "/ipi-interface:interfaces/ipi-interface:interface/ipi-interface:name";
            }
            description "The interface name to configure PIM IPv6 parameters.";
        } // END of name definition.

        leaf pim-mode  {
            type  ipi-pim-ipv6-types:pim_ipv6_mode_t;
            description "PIM IPv6 mode to use when delivering multicast traffic via this
                        interface.";
        } // END of pim-mode definition.

        leaf bsr-border  {
            if-feature feature-list:HAVE_PIM_SM;
            type  empty;
            description "When set to true the device will not send bootstrap router messages
                        over this interface. By default these are transmitted over all PIM
                        IPv6 sparse mode (PIM-SM) enabled interfaces.";
        } // END of bsr-border definition.

        leaf dr-priority  {
            type  uint32 {
                 range "0..4294967294"  {
                    description "0..4294967294: Supported range 0 - 4294967294";
                 }
            }
            description "The designated router priority of this interface. Larger always
                        preferred.";
        } // END of dr-priority definition.

        leaf hello-interval  {
            type  uint16 {
                 range "1..18724"  {
                    description "1..18724: Supported range 1 - 18724";
                 }
            }
            units "seconds";
            default "30";
            description "Use this attribute to configure a hello interval value other than the
                        default. When a hello-interval is configured and hello-holdtime is not
                        configured, or when the hello-holdtime value configured is less than
                        the new hello-interval value, the holdtime value is modified to (3.5 *
                        hello_interval). Otherwise, the hello-holdtime value is the configured
                        value.";
        } // END of hello-interval definition.

        leaf hello-holdtime  {
            type  uint16 {
                 range "1..65535"  {
                    description "1..65535: Supported range 1 - 65535";
                 }
            }
            units "seconds";
            default "105";
            description "Use this attribute to configure a hello message holdtime other than
                        the default.";
        } // END of hello-holdtime definition.

        leaf passive-enable  {
            // when " ipi-pim-ipv6:ipv6/interfaces/interface/config/pim-mode ";
            type  empty;
            description "PIM IPv6 passive mode.";
        } // END of passive-enable definition.

        leaf exclude-generated-id  {
            if-feature feature-list:HAVE_PIM_SM;
            type  empty;
            description "Exclude Gen-id option from PIM IPv6 Hello packets on this interface.";
        } // END of exclude-generated-id definition.

        leaf unicast-bootstrap-router  {
            if-feature feature-list:HAVE_PIM_SM;
            type  empty;
            description "Use this attribute to enable support for sending and receiving unicast
                        Bootstrap Messages (BSM) on an interface.";
        } // END of unicast-bootstrap-router definition.

        leaf neighbor-access-control-list-filter  {
            type  string {
                length "1..64";
                pattern "[a-zA-Z0-9_-]+";
            }
            description "Use this attribute to enable filtering of neighbors on the interface.
                        When configuring a neighbor filter, PIM IPv6 either not establishes
                        adjacency with neighbor or terminates adjacency with existing
                        neighbors, when denied by filtering access list.";
        } // END of neighbor-access-control-list-filter definition.

        leaf state-refresh-origination-interval  {
            if-feature feature-list:HAVE_PIM_DM;
            type  uint16 {
                 range "1..100"  {
                    description "1..100: Supported range 1 - 100";
                 }
            }
            units "seconds";
            default "60";
            description "Use this attribute to configure a PIM-DM State-Refresh origination
                        interval other than the default value. The origination interval is the
                        number of seconds between PIM-DM State Refresh control messages.";
        } // END of state-refresh-origination-interval definition.

        leaf ecmp-bundle  {
            if-feature feature-list:HAVE_PIM_ECMP_REDIRECT;
            type  string {
                length "1..50";
                pattern "[a-zA-Z0-9_-]+";
            }
            description "Use this attribute to configure an ECMP bundle.";
        } // END of ecmp-bundle definition.

        leaf propagation-delay  {
            type  uint16 {
                 range "0..32767"  {
                    description "0..32767: Supported range 0 - 32767";
                 }
            }
            units "millisec";
            default "1000";
            description "Propagation-delay value.";
        } // END of propagation-delay definition.

        leaf enable-bfd  {
            if-feature feature-list:HAVE_BFD;
            type  cml-data-types:cml_enable_disable_t;
            description "Use this attribute to configure Bidirectional Forwarding Detection.";
        } // END of enable-bfd definition.

    } // END of pim-ipv6-interface-config definition.
    grouping pim-ipv6-interface-top {
        description
            "Grouping for PIM IPv6 Interfaces";
        container interfaces {
            description
                "PIM IPv6 interfaces";

            list interface {
            // when " ipi-interface:interfaces/interface/config/enable-switchport != '1' ";
                key "name";
                description
                    "List of PIM IPv6 interfaces";
                leaf name  {
                    type  leafref {
                        path  "../config/name";
                    }
                    description "The interface name to configure PIM IPv6 parameters.";
                } // END of name definition.

                container config {
                    description
                        "Configuration data for PIM IPv6 interfaces";
                    uses pim-ipv6-interface-config;
                } // END of config-container definition.
                container state {
                    config false;
                    description
                        "Operational state data for PIM IPv6 interfaces";
                    uses pim-ipv6-interface-config;
                    uses pim-ipv6-interface-state;
                } // END of state-container definition.
                uses pim-ipv6-interface-neighbor-top;
            } // End of interface-list
        } // END of interfaces-container definition.
    } // END of pim-ipv6-interface-top definition.


}
