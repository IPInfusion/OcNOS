/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-pim-ipv4.yang
*
*/

submodule ipi-pim-ipv4 {

    yang-version 1.1;

    belongs-to  ipi-pim { prefix ipi-pim; }

    import feature-list {
        prefix feature-list;
        revision-date 2026-09-15;
    }

    import cml-data-types {
        prefix cml-data-types;
        revision-date 2026-05-15;
    }

    import ietf-inet-types {
        prefix inet;
        revision-date 2013-07-15;
    }

    import ietf-yang-types {
        prefix yang;
        revision-date 2013-07-15;
    }

    import ipi-pim-ipv4-types {
        prefix ipi-pim-ipv4-types;
        revision-date 2023-03-17;
    }

    import ipi-network-instance {
        prefix ipi-network-instance;
        revision-date 2026-08-12;
    }

    import ipi-interface {
        prefix ipi-interface;
        revision-date 2026-03-10;
    }

    import ipi-vrf {
        prefix ipi-vrf;
        revision-date 2026-08-12;
    }

    include ipi-pim-ipv4-bidir { revision-date 2023-03-17;}
    include ipi-pim-ipv4-debug { revision-date 2023-02-20;}
    include ipi-pim-ipv4-interface { revision-date 2023-03-17;}
    include ipi-pim-ipv4-msdp { revision-date 2024-11-04;}
    organization
        "IP Infusion Inc.";

    contact
        "Address: 3965 Freedom Circle, Suite 200, Santa Clara, CA 95054
         Phone: +1 408-400-1900
         E-mail: support@ipinfusion.com
         Web: http://www.ipinfusion.com/";

    description
        "Protocol Independent Multicast (PIM) IPv4 configurations";


    revision "2024-12-13" {
        description "Changed multicast-route source and group address type from CML_IPV4_ADDR_PREFIX_T to CML_IPV4_ADDR_T";
        reference " 0.6.1.";
    }

    revision "2024-11-04" {
        description "Changed password size limits";
        reference " 0.6.0.";
    }

    revision "2023-07-07" {
        description "Removing the misplaced initialized from pim-ipv4-rp-bsr-candidate-config";
        reference " 0.5.0.";
    }

    revision "2023-03-17" {
        description "Pattern validation added for accept-register name, ACL name and ECMP-REDIRECT Bundle name";
        reference " 0.4.1.";
    }

    revision "2023-02-17" {
        description "Fixed prependstr warning";
        reference " 0.4.0.";
    }

    revision "2022-08-10" {
        description "Debug hierarchy change";
        reference " 0.3.0.";
    }

    revision "2022-06-06" {
        description "Added if-feature HAVE_PIM_BIDIR for rp-interface-name attribute";
        reference " 0.2.4.";
    }

    revision "2022-06-01" {
        description "Updated the yang file with feature";
        reference " 0.2.3.";
    }

    revision "2022-04-28" {
        description "Removed macro-state attribute from downstream-xxrp-sg-rpt/state container";
        reference " 0.2.2.";
    }

    revision "2022-03-29" {
        description "Fix the range for suppress-interval attribute";
        reference " 0.2.1.";
    }

    revision "2022-03-15" {
        description "Restructured module in accordance with OpenConfig style";
        reference " 0.2.0.";
    }

    revision "2018-06-21" {
        description "Initial Version";
        reference " 0.1.0.";
    }

    grouping pim-ipv4-multicast-route-ds-xxrp-sg-rpt-state {
        description
            "Grouping for PIM IPv4 multicast route table downstream info about
                        routes of type SGRPT and XXRP";
        leaf route-state  {
            type  ipi-pim-ipv4-types:pim_ipv4_multicast_route_downstream_state_t;
            description "This attribute returns the PIM IPv4 downstream route state.";
        } // END of route-state definition.

        leaf rpt-state  {
            type  ipi-pim-ipv4-types:pim_ipv4_multicast_route_downstream_rpt_state_t;
            description "This attribute returns the PIM IPv4 downstream route state.";
        } // END of rpt-state definition.

        leaf expiry-timer  {
            type  uint32;
            units "seconds";
            description "This attribute returns the PIM IPv4 route expiry timer.";
        } // END of expiry-timer definition.

        leaf prune-pending-timer  {
            type  uint32;
            units "seconds";
            description "This attribute returns the PIM IPv4 route prune pending timer.";
        } // END of prune-pending-timer definition.

    } // END of pim-ipv4-multicast-route-ds-xxrp-sg-rpt-state definition.
    grouping pim-ipv4-multicast-route-ds-xg-sg-state {
        description
            "Grouping for PIM IPv4 multicast route table downstream info about
                        routes of type SG, XG and GPREFIX";
        leaf route-state  {
            type  ipi-pim-ipv4-types:pim_ipv4_multicast_route_downstream_state_t;
            description "This attribute returns the PIM IPv4 downstream route state.";
        } // END of route-state definition.

        leaf expiry-timer  {
            type  uint32;
            units "seconds";
            description "This attribute returns the PIM IPv4 route expiry timer.";
        } // END of expiry-timer definition.

        leaf prune-pending-timer  {
            type  uint32;
            units "seconds";
            description "This attribute returns the PIM IPv4 route prune pending timer.";
        } // END of prune-pending-timer definition.

        leaf assert-state  {
            type  ipi-pim-ipv4-types:pim_ipv4_multicast_route_downstream_assert_state_t;
            description "This attribute returns the PIM IPv4 route assert state.";
        } // END of assert-state definition.

        leaf assert-timer  {
            type  uint32;
            description "This attribute returns the PIM IPv4 route assert timer.";
        } // END of assert-timer definition.

        leaf winner-address  {
            type  inet:ipv4-address;
            description "This attribute returns the PIM IPv4 route assert winner IPv4 address.";
        } // END of winner-address definition.

        leaf metric  {
            type  uint32;
            description "This attribute returns the PIM IPv4 route assert metric value.";
        } // END of metric definition.

        leaf preference  {
            type  uint32;
            description "This attribute returns the PIM IPv4 route assert metric preference
                        value.";
        } // END of preference definition.

        leaf rpt-bit  {
            type  empty;
            description "This attribute returns the PIM IPv4 route assert Rendezvous Point Tree
                        bit value.";
        } // END of rpt-bit definition.

        leaf macro-state  {
            type  ipi-pim-ipv4-types:pim_ipv4_multicast_route_downstream_macro_state_t;
            description "This attribute returns the PIM IPv4 route assert macro state.";
        } // END of macro-state definition.

    } // END of pim-ipv4-multicast-route-ds-xg-sg-state definition.
    grouping pim-ipv4-multicast-route-ds-state {
        description
            "Grouping for PIM IPv4 multicast route table downstream info";
        leaf interface-name  {
            type  string {
                length "1..1965";
                pattern "[^?' =,>|]+";
            }
            description "This attribute returns the interface name associated to this route
                        entry.";
        } // END of interface-name definition.

    } // END of pim-ipv4-multicast-route-ds-state definition.
    grouping pim-ipv4-multicast-route-downstream-top {
        description
            "Grouping for PIM IPv4 multicast route table downstream info";
        container downstream-interfaces {
            config false;
            description
                "Multicast route table downstream data";

            list downstream-interface {
                key "interface-name";
                config false;
                description
                    "List of multicast route table downstream data";
                leaf interface-name  {
                    type  leafref {
                        path  "../state/interface-name";
                    }
                    description "This attribute returns the interface name associated to this route
                                entry.";
                } // END of interface-name definition.

                container state {
                    config false;
                    description
                        "Operational state data for PIM IPv4 multicast downstream route table";
                    uses pim-ipv4-multicast-route-ds-state;
                } // END of state-container definition.
                container downstream-xg-sg {
                    config false;
                    description
                        "PIM IPv4 multicast route table downstream info about routes of type
                                (*,G), (S,G) and GPREFIX";
                    container state {
                        config false;
                        description
                            "Operational state data for PIM IPv4 multicast downstream route table
                                    for routes of type (*,G), (S,G) and GPREFIX";
                        uses pim-ipv4-multicast-route-ds-xg-sg-state;
                    } // END of state-container definition.
                } // END of downstream-xg-sg-container definition.
                container downstream-xxrp-sg-rpt {
                    config false;
                    description
                        "PIM IPv4 multicast route table downstream info about routes of type
                                (*,*,RP) and (S,G,rpt)";
                    container state {
                        config false;
                        description
                            "Operational state data for PIM IPv4 multicast downstream route table
                                    for routes of type (*,*,RP) and (S,G,rpt)";
                        uses pim-ipv4-multicast-route-ds-xxrp-sg-rpt-state;
                    } // END of state-container definition.
                } // END of downstream-xxrp-sg-rpt-container definition.
            } // End of downstream-interface-list
        } // END of downstream-interfaces-container definition.
    } // END of pim-ipv4-multicast-route-downstream-top definition.
    grouping pim-ipv4-multicast-route-us-sg-rpt-state {
        description
            "Grouping for PIM IPv4 muticast route table upstream for source, group
                        and Rendezvous Point Tree";
        leaf route-state  {
            type  ipi-pim-ipv4-types:pim_ipv4_multicast_route_upstream_sg_rpt_mode_t;
            description "This attribute returns the PIM multicast route state.";
        } // END of route-state definition.

        leaf override-timer  {
            type  uint32;
            description "This attribute returns the override timer value.";
        } // END of override-timer definition.

    } // END of pim-ipv4-multicast-route-us-sg-rpt-state definition.
    grouping pim-ipv4-multicast-route-us-sg-rpt-top {
        description
            "Grouping for PIM IPv4 multicast route table upstream for source, group
                        and Rendezvous Point Tree";
        container upstream-sg-rpt {
            config false;
            description
                "Multicast route table data upstream for source, group and Rendezvous
                        Point Tree";
            container state {
                config false;
                description
                    "Operational state data for PIM IPv4 multicast route table upstream for
                            PIM IPv4 source, group and Rendezvous Point Tree";
                uses pim-ipv4-multicast-route-us-sg-rpt-state;
            } // END of state-container definition.
        } // END of upstream-sg-rpt-container definition.
    } // END of pim-ipv4-multicast-route-us-sg-rpt-top definition.
    grouping pim-ipv4-multicast-route-us-sg-state {
        description
            "Grouping for PIM IPv4 muticast route table upstream for source and
                        group";
        leaf route-state  {
            type  ipi-pim-ipv4-types:pim_ipv4_multicast_route_upstream_state_t;
            description "This attribute returns the PIM multicast route state.";
        } // END of route-state definition.

        leaf join-prune-timer  {
            type  uint32;
            units "seconds";
            description "This attribute returns the join/prune interval value.";
        } // END of join-prune-timer definition.

        leaf last-rpf-neighbor-address  {
            type  inet:ipv4-address;
            description "This attribute returns the last neighbor address for reverse path
                        forwarding.";
        } // END of last-rpf-neighbor-address definition.

        leaf keep-alive-timer  {
            type  uint32;
            units "seconds";
            description "This attribute returns the keep alive timer value.";
        } // END of keep-alive-timer definition.

        leaf spt-switch  {
            type  empty;
            description "This attribute returns the state of SPT Switch flag.";
        } // END of spt-switch definition.

        leaf macro-state  {
            if-feature feature-list:HAVE_PIM_SM;
            type  ipi-pim-ipv4-types:pim_ipv4_multicast_route_upstream_macro_state_t;
            description "This attribute returns the PIM IPv4 route assert macro state.";
        } // END of macro-state definition.

    } // END of pim-ipv4-multicast-route-us-sg-state definition.
    grouping pim-ipv4-multicast-route-us-sg-top {
        description
            "Grouping for PIM IPv4 multicast route table upstream for source and
                        group";
        container upstream-sg {
            config false;
            description
                "Multicast route table data upstream for source and group";
            container state {
                config false;
                description
                    "Operational state data for PIM IPv4 multicast route table upstream for
                            source and group";
                uses pim-ipv4-multicast-route-us-sg-state;
            } // END of state-container definition.
        } // END of upstream-sg-container definition.
    } // END of pim-ipv4-multicast-route-us-sg-top definition.
    grouping pim-ipv4-multicast-route-us-xg-state {
        description
            "Grouping for PIM IPv4 muticast route table upstream for any source,
                        group route table";
        leaf route-state  {
            type  ipi-pim-ipv4-types:pim_ipv4_multicast_route_upstream_state_t;
            description "This attribute returns the PIM multicast route state.";
        } // END of route-state definition.

        leaf join-prune-timer  {
            type  uint32;
            units "seconds";
            description "This attribute returns the join/prune interval value.";
        } // END of join-prune-timer definition.

        leaf last-rpf-neighbor-address  {
            type  inet:ipv4-address;
            description "This attribute returns the last neighbor address for reverse path
                        forwarding.";
        } // END of last-rpf-neighbor-address definition.

        leaf rp-interface-name  {
            if-feature feature-list:HAVE_PIM_BIDIR;
            type  string {
                length "1..1965";
                pattern "[^?' =,>|]+";
            }
            description "This attribute returns the interface name for RP.";
        } // END of rp-interface-name definition.

        leaf macro-state  {
            if-feature feature-list:HAVE_PIM_SM;
            type  ipi-pim-ipv4-types:pim_ipv4_multicast_route_upstream_macro_state_t;
            description "This attribute returns the PIM IPv4 route assert macro state.";
        } // END of macro-state definition.

    } // END of pim-ipv4-multicast-route-us-xg-state definition.
    grouping pim-ipv4-multicast-route-us-xg-top {
        description
            "Grouping for PIM IPv4 multicast route table for any source, group
                        muticast route upstream";
        container upstream-xg {
            config false;
            description
                "Multicast route table data upstream for any source, group and RP";
            container state {
                config false;
                description
                    "Operational state data for PIM IPv4 multicast route table upstream for
                            any source, group and RP";
                uses pim-ipv4-multicast-route-us-xg-state;
            } // END of state-container definition.
        } // END of upstream-xg-container definition.
    } // END of pim-ipv4-multicast-route-us-xg-top definition.
    grouping pim-ipv4-multicast-route-us-xxrp-state {
        description
            "Grouping for PIM IPv4 multicast route table upstream for any source,
                        any group and RP";
        leaf route-state  {
            type  ipi-pim-ipv4-types:pim_ipv4_multicast_route_upstream_state_t;
            description "This attribute returns the PIM multicast route state.";
        } // END of route-state definition.

        leaf join-prune-timer  {
            type  uint32;
            units "seconds";
            description "This attribute returns the join/prune interval value.";
        } // END of join-prune-timer definition.

        leaf last-rpf-neighbor-address  {
            type  inet:ipv4-address;
            description "This attribute returns the last neighbor address for reverse path
                        forwarding.";
        } // END of last-rpf-neighbor-address definition.

        leaf last-rpf-next-hop-address  {
            type  inet:ipv4-address;
            description "This attribute returns the last next-hop address for reverse path
                        forwarding.";
        } // END of last-rpf-next-hop-address definition.

        leaf macro-state  {
            if-feature feature-list:HAVE_PIM_SM;
            type  ipi-pim-ipv4-types:pim_ipv4_multicast_route_upstream_macro_state_t;
            description "This attribute returns the PIM IPv4 route assert macro state.";
        } // END of macro-state definition.

    } // END of pim-ipv4-multicast-route-us-xxrp-state definition.
    grouping pim-ipv4-multicast-route-us-xxrp-top {
        description
            "Grouping for PIM IPv4 muticast route table for any source, any group
                        and RP";
        container upstream-xxrp {
            config false;
            description
                "Multicast route table data upstream for any source, any group and RP";
            container state {
                config false;
                description
                    "Operational state data for PIM IPv4 multicast route table upstream for
                            any source, any group and RP";
                uses pim-ipv4-multicast-route-us-xxrp-state;
            } // END of state-container definition.
        } // END of upstream-xxrp-container definition.
    } // END of pim-ipv4-multicast-route-us-xxrp-top definition.
    grouping pim-ipv4-multicast-route-fcr-state {
        description
            "Grouping for PIM IPv4 FCR muticast route table FCR state data";
        leaf address  {
            type  inet:ipv4-address;
            description "This attribute returns the FCR address.";
        } // END of address definition.

        leaf keep-alive-timer  {
            type  uint32;
            units "seconds";
            description "This attribute returns the keep alive timer value.";
        } // END of keep-alive-timer definition.

        leaf-list inherited-olist  {
            type  string {
                length "1..1965";
                pattern "[^?' =,>|]+";
            }
            description "This attribute returns the list of inherited interfaces for FCR in the
                        (*,G) state.";
        } // END of inherited-olist definition.

    } // END of pim-ipv4-multicast-route-fcr-state definition.
    grouping pim-ipv4-multicast-route-fcr-top {
        description
            "Grouping for PIM IPv4 muticast route table FCR";
        container forwarding-cache-registers {
            config false;
            description
                "Multicast Route Table FCR state data";

            list forwarding-cache-register {
                key "address";
                config false;
                description
                    "List of PIM IPv4 FCR multicast routes";
                leaf address  {
                    type  leafref {
                        path  "../state/address";
                    }
                    description "This attribute returns the FCR address.";
                } // END of address definition.

                container state {
                    config false;
                    description
                        "Operational state data for PIM IPv4 anycast Rendezvous Point";
                    uses pim-ipv4-multicast-route-fcr-state;
                } // END of state-container definition.
            } // End of forwarding-cache-register-list
        } // END of forwarding-cache-registers-container definition.
    } // END of pim-ipv4-multicast-route-fcr-top definition.
    grouping pim-ipv4-mrouter-table-statistics-state {
        description
            "Grouping for PIM IPv4 muticast route table statistics";
        container counters {
            config false;
            description
                "Counters for PIM IPv4 multicast route table";
            leaf xxrp-entries  {
                type  yang:counter32;
                description "This attribute returns the PIM Source, Group, Rendezvous Point include
                            entries.";
            } // END of xxrp-entries definition.

            leaf g-prefix-entries  {
                type  yang:counter32;
                description "This attribute returns the PIM Group or Prefix include entries.";
            } // END of g-prefix-entries definition.

            leaf xg-entries  {
                type  yang:counter32;
                description "This attribute returns the PIM Group include entries.";
            } // END of xg-entries definition.

            leaf sg-entries  {
                type  yang:counter32;
                description "This attribute returns the PIM Source, Group include entries.";
            } // END of sg-entries definition.

            leaf sg-rpt-entries  {
                type  yang:counter32;
                description "The RPT is the path between the RP and receivers (hosts) in a
                            multicast group. The RPT is built by means of a PIM join message from
                            a receiver's DR. This attribute returnes the PIM RPT include entries.";
            } // END of sg-rpt-entries definition.

            leaf fcr-entries  {
                type  yang:counter32;
                description "This attribute returns the Forwarding Cache Registers include entries.";
            } // END of fcr-entries definition.

        } // END of counters-container definition.
    } // END of pim-ipv4-mrouter-table-statistics-state definition.
    grouping pim-ipv4-multicast-route-state {
        description
            "Grouping for PIM IPv4 muticast route table state data";
        leaf source-address  {
            type  inet:ipv4-address;
            description "This attribute returns the source IP address of multicast.";
        } // END of source-address definition.

        leaf group-address  {
            type  inet:ipv4-address;
            description "This attribute returns the multicast IP address.";
        } // END of group-address definition.

        leaf mode  {
            type  ipi-pim-ipv4-types:pim_ipv4_multicast_route_mode_t;
            description "This attribute returns the PIM mode.";
        } // END of mode definition.

        leaf type  {
            type  ipi-pim-ipv4-types:pim_ipv4_multicast_route_type_t;
            description "This attribute returns the PIM route type.";
        } // END of type definition.

        leaf uptime  {
            type  string {
                length "1..1965";
                pattern "((([0-1]?[0-9])|(2[0-3])):[0-5][0-9]:[0-5][0-9])|([0-9]+d(([0-1][0-9])|(2[0-3]))h[0-5][0-9]m)|([0-9]+w[0-9]+d[0-9]+h)";
            }
            description "This attribute returns the uptime for this multicast route entry.";
        } // END of uptime definition.

        leaf next-hop-address  {
            type  inet:ipv4-address;
            description "This attribute returns the next-hop address for this multicast route
                        entry.";
        } // END of next-hop-address definition.

        leaf next-hop-interface-name  {
            type  string {
                length "1..1965";
                pattern "[^?' =,>|]+";
            }
            description "This attribute returns the interface-name which is being used to reach
                        the next-hop.";
        } // END of next-hop-interface-name definition.

        leaf last-rendezvous-point  {
            type  inet:ipv4-address;
            description "This attribute returns the last Rendezvous Point for this multicast
                        route entry.";
        } // END of last-rendezvous-point definition.

        leaf spt-switch  {
            type  empty;
            description "This attribute returns the state of SPT Switch flag.";
        } // END of spt-switch definition.

        leaf-list local-olist  {
            type  string {
                length "1..1965";
                pattern "[^?' =,>|]+";
            }
            description "This attribute returns the local list of output interfaces.";
        } // END of local-olist definition.

        leaf-list joined-olist  {
            type  string {
                length "1..1965";
                pattern "[^?' =,>|]+";
            }
            description "This attribute returns the list of interfaces which receive join.";
        } // END of joined-olist definition.

        leaf-list inherited-olist  {
            type  string {
                length "1..1965";
                pattern "[^?' =,>|]+";
            }
            description "This attribute returns the list of inherited interfaces used for
                        forwarding.";
        } // END of inherited-olist definition.

        leaf-list pruned-olist  {
            type  string {
                length "1..1965";
                pattern "[^?' =,>|]+";
            }
            description "This attribute returns the list of interfaces which are in downstream
                        (S,G,rpt) states of prune or prune-tmp.";
        } // END of pruned-olist definition.

    } // END of pim-ipv4-multicast-route-state definition.
    grouping pim-ipv4-multicast-route-top {
        description
            "Grouping for PIM IPv4 muticast route table";
        container multicast-route-table {
            config false;
            description
                "Multicast Route Table state data";
            container state {
                config false;
                description
                    "Operational state data for PIM IPv4 anycast Rendezvous Point";
                uses pim-ipv4-mrouter-table-statistics-state;
            } // END of state-container definition.
            container multicast-routes {
                config false;
                description
                    "Multicast Route Table state data";

                list multicast-route {
                    key "source-address group-address type";
                    config false;
                    description
                        "List of PIM IPv4 multicast routes";
                    leaf source-address  {
                        type  leafref {
                            path  "../state/source-address";
                        }
                        description "This attribute returns the source IP address of multicast.";
                    } // END of source-address definition.

                    leaf group-address  {
                        type  leafref {
                            path  "../state/group-address";
                        }
                        description "This attribute returns the multicast IP address.";
                    } // END of group-address definition.

                    leaf type  {
                        type  leafref {
                            path  "../state/type";
                        }
                        description "This attribute returns the PIM route type.";
                    } // END of type definition.

                    container state {
                        config false;
                        description
                            "Operational state data for PIM IPv4 anycast Rendezvous Point";
                        uses pim-ipv4-multicast-route-state;
                    } // END of state-container definition.
                    uses pim-ipv4-multicast-route-us-xxrp-top;
                    uses pim-ipv4-multicast-route-us-xg-top;
                    uses pim-ipv4-multicast-route-us-sg-top;
                    uses pim-ipv4-multicast-route-us-sg-rpt-top;
                    uses pim-ipv4-multicast-route-fcr-top;
                    uses pim-ipv4-multicast-route-downstream-top;
                } // End of multicast-route-list
            } // END of multicast-routes-container definition.
        } // END of multicast-route-table-container definition.
    } // END of pim-ipv4-multicast-route-top definition.
    grouping pim-ipv4-anycast-rp-config {
        description
            "Grouping for PIM IPv4 anycast Rendezvous Point configuration data";
        leaf anycast-rp-address  {
            type  inet:ipv4-address;
            description "Use this attribute to set the unicast IP address of the anycast RP
                        set.
                        An anycast RP set is a collection of RPs in the same domain.";
        } // END of anycast-rp-address definition.

        leaf member-rp-address  {
            type  inet:ipv4-address;
            description "Destination IP address where register messages are copied and sent.
                        A Member RP is an individual RP member in the anycast RP set.";
        } // END of member-rp-address definition.

    } // END of pim-ipv4-anycast-rp-config definition.
    grouping pim-ipv4-anycast-rp-top {
        description
            "Grouping for PIM IPv4 anycast Rendezvous Point";
        container anycast-rps {
            if-feature feature-list:HAVE_PIM_SM;
            description
                "Container for PIM IPv4 anycast Rendezvous Point";

            list anycast-rp {
                key "anycast-rp-address member-rp-address";
                description
                    "List of PIM IPv4 anycast Rendezvous Point";
                leaf anycast-rp-address  {
                    type  leafref {
                        path  "../config/anycast-rp-address";
                    }
                    description "Use this attribute to set the unicast IP address of the anycast RP
                                set.
                                An anycast RP set is a collection of RPs in the same domain.";
                } // END of anycast-rp-address definition.

                leaf member-rp-address  {
                    type  leafref {
                        path  "../config/member-rp-address";
                    }
                    description "Destination IP address where register messages are copied and sent.
                                A Member RP is an individual RP member in the anycast RP set.";
                } // END of member-rp-address definition.

                container config {
                    description
                        "Configuration data for PIM IPv4 anycast Rendezvous Point";
                    uses pim-ipv4-anycast-rp-config;
                } // END of config-container definition.
                container state {
                    config false;
                    description
                        "Operational state data for PIM IPv4 anycast Rendezvous Point";
                    uses pim-ipv4-anycast-rp-config;
                } // END of state-container definition.
            } // End of anycast-rp-list
        } // END of anycast-rps-container definition.
    } // END of pim-ipv4-anycast-rp-top definition.
    grouping pim-ipv4-register-packet-config {
        description
            "Grouping for PIM IPv4 register packet configuration data";
        leaf register-reachability-check  {
            type  cml-data-types:cml_enable_disable_t;
            default "enable";
            description "Use this attribute to enable the RP reachability check for PIM
                        Registers at the designated router (DR).";
        } // END of register-reachability-check definition.

        leaf rate-limit  {
            type  uint16 {
                 range "1..65535"  {
                    description "1..65535: Supported range 1 - 65535";
                 }
            }
            units "packets/seconds";
            description "Use this attribute to configure the rate of register packets sent by
                        this designated router (DR).";
        } // END of rate-limit definition.

        leaf suppress-interval  {
            type  uint16 {
                 range "11..65535"  {
                    description "11..65535: Supported range 11 - 65535";
                 }
            }
            units "seconds";
            default "60";
            description "Use this attribute to configure the register suppression time.";
        } // END of suppress-interval definition.

        leaf keep-alive-interval  {
            type  uint16 {
                 range "1..65535"  {
                    description "1..65535: Supported range 1 - 65535";
                 }
            }
            units "seconds";
            default "185";
            description "Use this attribute to configure a Keep alive Timer (KAT) value for
                        (S,G) states at RP to monitor PIM register packets.";
        } // END of keep-alive-interval definition.

        leaf source-address  {
            type  ipi-pim-ipv4-types:pim_ipv4_reg_source_t;
            description "Use this attribute to configure the source address of register packets
                        sent by this designated router (DR).";
        } // END of source-address definition.

        leaf accept-register  {
            type  string {
                length "1..64";
                pattern "[a-zA-Z0-9_-]+";
            }
            description "Use this attribute to configure the ACL of register packets accepted
                        by this designated router (DR).";
        } // END of accept-register definition.

    } // END of pim-ipv4-register-packet-config definition.
    grouping pim-ipv4-register-statistics-state {
        description
            "Grouping for PIM IPv4 register packet statistics state data";
        container counters {
            config false;
            description
                "Operational state data for PIM IPv4 register packet counters";
            leaf register-packet-received  {
                type  yang:counter64;
                units "packets";
                description "Total Register messages received by this PIM IPv4 instance.";
            } // END of register-packet-received definition.

            leaf register-null-received  {
                type  yang:counter64;
                units "packets";
                description "Total Null-Register messages received by this PIM IPv4 instance.";
            } // END of register-null-received definition.

            leaf register-stop-sent  {
                type  yang:counter64;
                units "packets";
                description "Total Register-Stop messages sent by this PIM IPv4 instance.";
            } // END of register-stop-sent definition.

            leaf register-stop-received  {
                type  yang:counter64;
                units "packets";
                description "Total Register-Stop messages received by this PIM IPv4 instance.";
            } // END of register-stop-received definition.

        } // END of counters-container definition.
    } // END of pim-ipv4-register-statistics-state definition.
    grouping pim-ipv4-register-packet-top {
        description
            "Grouping for PIM IPv4 register packet";
        container register-packet {
            if-feature feature-list:HAVE_PIM_SM;
            description
                "Container for PIM IPv4 register packet";
            container config {
                description
                    "Configuration data for PIM IPv4 register packet";
                uses pim-ipv4-register-packet-config;
            } // END of config-container definition.
            container state {
                config false;
                description
                    "Operational state data for PIM IPv4 register packet";
                uses pim-ipv4-register-packet-config;
                uses pim-ipv4-register-statistics-state;
            } // END of state-container definition.
        } // END of register-packet-container definition.
    } // END of pim-ipv4-register-packet-top definition.
    grouping pim-ipv4-interop-register-packet-config {
        description
            "Grouping for PIM IPv4 register interoperability configuration data";
        leaf cisco-register-checksum-enable  {
            if-feature feature-list:HAVE_PIM_SM;
            type  empty;
            mandatory true;
            description "Use this attribute to configure the option to calculate the register
                        checksum over the whole packet.
                        This is used to inter-operate with older Cisco IOS versions.";
        } // END of cisco-register-checksum-enable definition.

        leaf access-control-list  {
            if-feature feature-list:HAVE_PIM_SM;
            type  string {
                length "1..64";
                pattern "[a-zA-Z0-9_-]+";
            }
            description "Use this attribute to configure the option to calculate the register
                        checksum over the whole packet
                        on multicast groups specified by the access control list.";
        } // END of access-control-list definition.

    } // END of pim-ipv4-interop-register-packet-config definition.
    grouping pim-ipv4-interop-register-packet-top {
        description
            "Grouping for PIM IPv4 register interoperability";
        container register-packet {
            description
                "Container for PIM IPv4 register interoperability";
            container config {
                presence "yes";
                description
                    "Configuration data for PIM IPv4 register interoperability";
                uses pim-ipv4-interop-register-packet-config;
            } // END of config-container definition.
            container state {
                config false;
                description
                    "Operational state data for PIM IPv4 register interoperability";
                uses pim-ipv4-interop-register-packet-config;
            } // END of state-container definition.
        } // END of register-packet-container definition.
    } // END of pim-ipv4-interop-register-packet-top definition.
    grouping pim-ipv4-interop-config {
        description
            "Grouping for PIM IPv4 interoperability configuration data";
        leaf ignore-rp-set-priority  {
            if-feature feature-list:HAVE_PIM_SM;
            type  empty;
            description "Use this attribute to ignore the RP-SET priority value, and use only
                        the hashing mechanism for RP selection.
                        This is used to inter-operate with older Cisco IOS versions.";
        } // END of ignore-rp-set-priority definition.

        leaf cisco-bsr-interop-enable  {
            if-feature feature-list:HAVE_PIM_SM;
            type  empty;
            description "Use this attribute to turn on or turn the Candidate-RP debugging
                        timerworking with Cisco BSR.";
        } // END of cisco-bsr-interop-enable definition.

    } // END of pim-ipv4-interop-config definition.
    grouping pim-ipv4-interop-top {
        description
            "Grouping for PIM IPv4 interoperability";
        container interop {
            description
                "Container for PIM IPv4 interoperability";
            container config {
                description
                    "Configuration data for PIM IPv4 interoperability";
                uses pim-ipv4-interop-config;
            } // END of config-container definition.
            container state {
                config false;
                description
                    "Operational state data for PIM IPv4 interoperability";
                uses pim-ipv4-interop-config;
            } // END of state-container definition.
            uses pim-ipv4-interop-register-packet-top;
        } // END of interop-container definition.
    } // END of pim-ipv4-interop-top definition.
    grouping pim-ipv4-ssm-config {
        description
            "Grouping for PIM IPv4 SSM configuration data";
        leaf range-policy  {
            type  ipi-pim-ipv4-types:pim_ipv4_ssm_range_policy_type_t;
            description "Use this attribute to set Source Specific Multicast (SSM) and define
                        the range of multicast IP addresses.
                        Ranges can be either the default, which defines the SSM range as
                        232/8, or indicated by the given standard
                        access control list.";
        } // END of range-policy definition.

    } // END of pim-ipv4-ssm-config definition.
    grouping pim-ipv4-ssm-top {
        description
            "Grouping for PIM IPv4 SSM";
        container ssm {
            if-feature feature-list:HAVE_PIM_SSM;
            description
                "Container for PIM IPv4 SSM";
            container config {
                description
                    "Configuration data for PIM IPv4 SSM";
                uses pim-ipv4-ssm-config;
            } // END of config-container definition.
            container state {
                config false;
                description
                    "Operational state data for PIM IPv4 SSM";
                uses pim-ipv4-ssm-config;
            } // END of state-container definition.
        } // END of ssm-container definition.
    } // END of pim-ipv4-ssm-top definition.
    grouping pim-ipv4-spt-switch-config {
        description
            "Grouping for PIM IPv4 SPT Switch configuration data";
        leaf enable  {
            if-feature feature-list:HAVE_PIM_SM;
            type  empty;
            mandatory true;
            description "Use this attribute to enable the ability of the last-hop PIM router to
                        switch to SPT.";
        } // END of enable definition.

        leaf access-control-list  {
            if-feature feature-list:HAVE_PIM_SM;
            type  string {
                length "1..64";
                pattern "[a-zA-Z0-9_-]+";
            }
            description "Use this attribute to to enable the ability of the last-hop PIM router
                        to switch to SPT for multicast group
                        addresses indicated by the given standard access control list.";
        } // END of access-control-list definition.

    } // END of pim-ipv4-spt-switch-config definition.
    grouping pim-ipv4-spt-switch-top {
        description
            "Grouping for PIM IPv4 Shortest-path tree (SPT) Switch";
        container spt-switch {
            description
                "Container for PIM IPv4 SPT Switch";
            container config {
                presence "yes";
                description
                    "Configuration data for PIM IPv4 SPT Switch";
                uses pim-ipv4-spt-switch-config;
            } // END of config-container definition.
            container state {
                config false;
                description
                    "Operational state data for PIM IPv4 SPT Switch";
                uses pim-ipv4-spt-switch-config;
            } // END of state-container definition.
        } // END of spt-switch-container definition.
    } // END of pim-ipv4-spt-switch-top definition.
    grouping pim-ipv4-rp-static-rp-config {
        description
            "Grouping for PIM IPv4 static rendezvous points configuration data";
        leaf rp-address  {
            type  inet:ipv4-address;
            description "Use this attribute to statically configure Rendezvous Point (RP)
                        address for multicast groups.";
        } // END of rp-address definition.

        leaf access-control-list  {
            type  string {
                length "1..64";
                pattern "[a-zA-Z0-9_-]+";
            }
            description "Use this attribute to configure the name of access control list (ACL).";
        } // END of access-control-list definition.

        leaf override-dynamically-learned-rp  {
            type  empty;
            description "Use this attribute do configure the flag to overrides dynamically
                        learned RP mappings.";
        } // END of override-dynamically-learned-rp definition.

    } // END of pim-ipv4-rp-static-rp-config definition.
    grouping pim-ipv4-rp-static-rp-default-top {
        description
            "Grouping for PIM IPv4 static rendezvous point default mode";

        list static-rp-default {
            key "rp-address";
            description
                "List of PIM IPv4 static rendezvous points default mode";
            leaf rp-address  {
                type  leafref {
                    path  "../config/rp-address";
                }
                description "Use this attribute to statically configure Rendezvous Point (RP)
                            address for multicast groups.";
            } // END of rp-address definition.

            container config {
                description
                    "Configuration data for PIM IPv4 static rendezvous point default mode";
                uses pim-ipv4-rp-static-rp-config;
            } // END of config-container definition.
            container state {
                config false;
                description
                    "Operational state data for PIM IPv4 static rendezvous point default
                            mode";
                uses pim-ipv4-rp-static-rp-config;
            } // END of state-container definition.
        } // End of static-rp-default-list
    } // END of pim-ipv4-rp-static-rp-default-top definition.
    grouping pim-ipv4-rp-static-rp-top {
        description
            "Grouping for PIM IPv4 static rendezvous point";
        container static-rps {
            description
                "Container for PIM IPv4 static rendezvous points";
            container static-rps-default {
                description
                    "Container for PIM IPv4 static rendezvous points default mode";
                uses pim-ipv4-rp-static-rp-default-top;
            } // END of static-rps-default-container definition.
            container static-rps-bidir {
                if-feature feature-list:HAVE_PIM_BIDIR;
                description
                    "Container for PIM IPv4 static rendezvous points bidirectional mode";
                uses pim-ipv4-rp-static-rp-bidir-top;
            } // END of static-rps-bidir-container definition.
        } // END of static-rps-container definition.
    } // END of pim-ipv4-rp-static-rp-top definition.
    grouping pim-ipv4-rp-bsr-candidate-config {
        description
            "Grouping for PIM IPv4 RP Bootstrap (BSR) candidate attributes";
        leaf interface-name  {
            type  leafref {
                path  "/ipi-interface:interfaces/ipi-interface:interface/ipi-interface:name";
            }
            description "Use this attribute to configure the interface for the candidate BSR
                        router.";
        } // END of interface-name definition.

        leaf hash-mask-length  {
            type  uint8 {
                 range "0..32"  {
                    description "0..32: Supported range 0 - 32";
                 }
            }
            description "Use this attribute to configure the mask length used to calculate the
                        group address for RP.";
        } // END of hash-mask-length definition.

        leaf priority  {
            type  uint8 {
                 range "0..255"  {
                    description "0..255: Supported range 0 - 255";
                 }
            }
            description "Use this attribute to configure the priority value for candidate BSR
                        router.";
        } // END of priority definition.

    } // END of pim-ipv4-rp-bsr-candidate-config definition.
    grouping pim-ipv4-rp-bsr-candidate-top {
        description
            "Grouping for PIM IPv4 RP Bootstrap (BSR) candidate";
        container bsr-candidate {
            description
                "Container for PIM IPv4 RP Bootstrap (BSR) candidate";
            container config {
                // when " ipi-pim-ipv4:ipv4/instances/instance/rendezvous-point/bootstrap-router/bsr-candidate/config/interface-name ";
                description
                    "Configuration data for PIM IPv4 RP Bootstrap (BSR) candidate";
                uses pim-ipv4-rp-bsr-candidate-config;
            } // END of config-container definition.
            container state {
                config false;
                description
                    "Operational state data for PIM IPv4 RP Bootstrap (BSR) candidate";
                uses pim-ipv4-rp-bsr-candidate-config;
            } // END of state-container definition.
        } // END of bsr-candidate-container definition.
    } // END of pim-ipv4-rp-bsr-candidate-top definition.
    grouping pim-ipv4-rp-bsr-top {
        description
            "Grouping for PIM IPv4 RP Bootstrap (BSR)";
        container bootstrap-router {
            description
                "Container for PIM IPv4 RP Bootstrap (BSR)";
            uses pim-ipv4-rp-bsr-candidate-top;
        } // END of bootstrap-router-container definition.
    } // END of pim-ipv4-rp-bsr-top definition.
    grouping pim-ipv4-rp-rp-candidate-config {
        description
            "Grouping for PIM IPv4 RP candidate attributes";
        leaf interface-name  {
            type  leafref {
                path  "/ipi-interface:interfaces/ipi-interface:interface/ipi-interface:name";
            }
            description "Use this attribute to configure the interface for the RP candidate BSR
                        router.";
        } // END of interface-name definition.

        leaf access-control-list  {
            type  string {
                length "1..64";
                pattern "[a-zA-Z0-9_-]+";
            }
            description "Use this attribute to configure the name of ACL for the RP candidate.";
        } // END of access-control-list definition.

        leaf advertisement-interval  {
            type  uint16 {
                 range "1..16383"  {
                    description "1..16383: Supported range 1 - 16383";
                 }
            }
            units "seconds";
            description "Use this attribute to configure the advertisement interval in seconds
                        for RP candidate.";
        } // END of advertisement-interval definition.

        leaf priority  {
            type  uint8 {
                 range "0..255"  {
                    description "0..255: Supported range 0 - 255";
                 }
            }
            description "Use this attribute to configure the priority value for RP candidate.";
        } // END of priority definition.

        leaf enable-bidir  {
            if-feature feature-list:HAVE_PIM_BIDIR;
            type  empty;
            description "Use this attribute to enable Bidirectional PIM for RP Candidate.";
        } // END of enable-bidir definition.

    } // END of pim-ipv4-rp-rp-candidate-config definition.
    grouping pim-ipv4-rp-rp-candidate-top {
        description
            "Grouping for PIM IPv4 RP candidate";
        container rp-candidates {
            description
                "Container for PIM IPv4 RP candidate";

            list rp-candidate {
                key "interface-name";
                description
                    "List of PIM IPv4 RP candidate";
                leaf interface-name  {
                    type  leafref {
                        path  "../config/interface-name";
                    }
                    description "Use this attribute to configure the interface name for RP.";
                } // END of interface-name definition.

                container config {
                    description
                        "Configuration data for PIM IPv4 RP candidate";
                    uses pim-ipv4-rp-rp-candidate-config;
                } // END of config-container definition.
                container state {
                    config false;
                    description
                        "Operational state data for PIM IPv4 RP candidate";
                    uses pim-ipv4-rp-rp-candidate-config;
                } // END of state-container definition.
            } // End of rp-candidate-list
        } // END of rp-candidates-container definition.
    } // END of pim-ipv4-rp-rp-candidate-top definition.
    grouping pim-ipv4-rp-top {
        description
            "Grouping for PIM IPv4 rendezvous point";
        container rendezvous-point {
            description
                "Container for PIM IPv4 rendezvous point";
            uses pim-ipv4-rp-static-rp-top;
            uses pim-ipv4-rp-bsr-top;
            uses pim-ipv4-rp-rp-candidate-top;
        } // END of rendezvous-point-container definition.
    } // END of pim-ipv4-rp-top definition.
    grouping pim-ipv4-rp-set-rp-state {
        description
            "Grouping for PIM IPv4 instance rp state data";
        leaf rp-address  {
            type  inet:ipv4-address;
            description "RP address.";
        } // END of rp-address definition.

        leaf from  {
            type  inet:ipv4-address;
            description "Originating RP information address.";
        } // END of from definition.

        leaf mode  {
            type  ipi-pim-ipv4-types:pim_ipv4_rp_mode_t;
            description "RP PIM mode as defined by MIB.";
        } // END of mode definition.

        leaf type  {
            type  ipi-pim-ipv4-types:pim_ipv4_rp_type_t;
            description "Type of RP instance.";
        } // END of type definition.

        leaf priority  {
            type  uint8;
            description "RP priority, the lower the higher.";
        } // END of priority definition.

        leaf hold-time  {
            type  uint16;
            units "seconds";
            description "RP hold time.";
        } // END of hold-time definition.

        leaf up-time  {
            type  string {
                length "1..1965";
                pattern "((([0-1]?[0-9])|(2[0-3])):[0-5][0-9]:[0-5][0-9])|([0-9]+d(([0-1][0-9])|(2[0-3]))h[0-5][0-9]m)|([0-9]+w[0-9]+d[0-9]+h)";
            }
            description "RP uptime.";
        } // END of up-time definition.

        leaf expiration-time  {
            type  string {
                length "1..1965";
                pattern "((([0-1]?[0-9])|(2[0-3])):[0-5][0-9]:[0-5][0-9])|([0-9]+d(([0-1][0-9])|(2[0-3]))h[0-5][0-9]m)|([0-9]+w[0-9]+d[0-9]+h)";
            }
            description "RP expiration time.";
        } // END of expiration-time definition.

    } // END of pim-ipv4-rp-set-rp-state definition.
    grouping pim-ipv4-rp-set-rp-top {
        description
            "Grouping for PIM IPv4 instance rps data";
        container rps {
            config false;
            description
                "Operational state data for PIM IPv4 rps";

            list rp {
                key "rp-address";
                config false;
                description
                    "List of PIM IPv4 RP instances";
                leaf rp-address  {
                    type  leafref {
                        path  "../state/rp-address";
                    }
                    description "RP address.";
                } // END of rp-address definition.

                container state {
                    config false;
                    description
                        "Operational state data for PIM IPv4 rp";
                    uses pim-ipv4-rp-set-rp-state;
                } // END of state-container definition.
            } // End of rp-list
        } // END of rps-container definition.
    } // END of pim-ipv4-rp-set-rp-top definition.
    grouping pim-ipv4-rp-set-state {
        description
            "Grouping for PIM IPv4 instance rp-set state data";
        leaf group-address  {
            type  cml-data-types:cml_ipv4_addr_prefix_t;
            description "Group address associated with this instance.";
        } // END of group-address definition.

        leaf fragment-tag  {
            type  uint16;
            description "Fragment tag associated with this Rendezvous Point (RP) instance.";
        } // END of fragment-tag definition.

        leaf number-of-rp  {
            type  uint32;
            description "Number of Rendezvous Point (RP) instances.";
        } // END of number-of-rp definition.

        leaf expiration-time  {
            type  string {
                length "1..1965";
                pattern "((([0-1]?[0-9])|(2[0-3])):[0-5][0-9]:[0-5][0-9])|([0-9]+d(([0-1][0-9])|(2[0-3]))h[0-5][0-9]m)|([0-9]+w[0-9]+d[0-9]+h)";
            }
            description "Rendezvous Point (RP) expiration time.";
        } // END of expiration-time definition.

    } // END of pim-ipv4-rp-set-state definition.
    grouping pim-ipv4-rp-set-top {
        description
            "Grouping for PIM IPv4 instance rp-sets data";
        container rp-sets {
            config false;
            description
                "Operational state data for PIM IPv4 rp-sets";

            list rp-set {
                key "group-address";
                config false;
                description
                    "List of PIM IPv4 RP set instances";
                leaf group-address  {
                    type  leafref {
                        path  "../state/group-address";
                    }
                    description "Group address associated with this instance.";
                } // END of group-address definition.

                container state {
                    config false;
                    description
                        "Operational state data for PIM IPv4 rp-set";
                    uses pim-ipv4-rp-set-state;
                } // END of state-container definition.
                uses pim-ipv4-rp-set-rp-top;
            } // End of rp-set-list
        } // END of rp-sets-container definition.
    } // END of pim-ipv4-rp-set-top definition.
    grouping pim-ipv4-statistics-state {
        description
            "Grouping for PIM IPv4 instance statistics state data";
        container counters {
            config false;
            description
                "Operational state data for PIM IPv4 instance packet counters";
            leaf joins-sent  {
                type  yang:counter64;
                units "packets";
                description "Total PIM Join messages sent by this PIM IPv4 instance.";
            } // END of joins-sent definition.

            leaf joins-received  {
                type  yang:counter64;
                units "packets";
                description "Total PIM Join messages received by this PIM IPv4 instance.";
            } // END of joins-received definition.

        } // END of counters-container definition.
    } // END of pim-ipv4-statistics-state definition.
    grouping pim-ipv4-route-next-hop-state {
        description
            "Grouping for PIM IPv4 route next-hop operational state data";
        leaf ipv4-address  {
            type  inet:ipv4-address;
            description "This attribute returns the next-hop ipv4-address parameter.";
        } // END of ipv4-address definition.

        leaf type  {
            type  ipi-pim-ipv4-types:pim_ipv4_next_hop_type_t;
            description "This attribute returns the next-hop type parameter.";
        } // END of type definition.

        leaf recursive-active-next-hop  {
            type  uint8;
            description "This attribute returns the recursive-active-next-hop parameter.";
        } // END of recursive-active-next-hop definition.

        leaf recursive-type  {
            type  ipi-pim-ipv4-types:pim_ipv4_next_hop_type_t;
            description "This attribute returns the recursive-type parameter.";
        } // END of recursive-type definition.

        leaf recursive-interface-id  {
            type  uint8;
            description "This attribute returns the recursive-interface-id parameter.";
        } // END of recursive-interface-id definition.

        leaf interface-index  {
            type  uint16;
            description "This attribute returns the interface-index parameter.";
        } // END of interface-index definition.

        leaf bfd-interface-index  {
            type  uint16;
            description "This attribute returns the bfd-interface-index parameter.";
        } // END of bfd-interface-index definition.

        leaf interface-name  {
            type  string {
                length "1..1965";
                pattern "[^?' =,>|]+";
            }
            description "This attribute returns the interface-name parameter.";
        } // END of interface-name definition.

    } // END of pim-ipv4-route-next-hop-state definition.
    grouping pim-ipv4-route-next-hop-top {
        description
            "Grouping for PIM IPv4 route next-hop";
        container next-hops {
            config false;
            description
                "Operational state data for PIM IPv4 next-hops";

            list next-hop {
                key "ipv4-address";
                config false;
                description
                    "List of PIM IPv4 next-hop";
                leaf ipv4-address  {
                    type  leafref {
                        path  "../state/ipv4-address";
                    }
                    description "This attribute returns the next-hop ipv4-address parameter.";
                } // END of ipv4-address definition.

                container state {
                    config false;
                    description
                        "Operational state data for PIM IPv4 next-hop";
                    uses pim-ipv4-route-next-hop-state;
                } // END of state-container definition.
            } // End of next-hop-list
        } // END of next-hops-container definition.
    } // END of pim-ipv4-route-next-hop-top definition.
    grouping pim-ipv4-route-state {
        description
            "Grouping for PIM IPv4 route next-hop-destinations operational state
                        data";
        leaf destination-address  {
            type  inet:ipv4-address;
            description "This attribute returns the destination-address parameter.";
        } // END of destination-address definition.

        leaf destination-type  {
            type  ipi-pim-ipv4-types:pim_ipv4_next_hop_flags_t;
            description "This attribute returns the destination-type parameter.";
        } // END of destination-type definition.

        leaf next-hop-count  {
            type  uint32;
            description "This attribute returns the next-hop-count parameter.";
        } // END of next-hop-count definition.

        leaf preference  {
            type  uint16;
            description "This attribute returns the preference parameter.";
        } // END of preference definition.

        leaf metric  {
            type  uint32;
            description "This attribute returns the metric parameter.";
        } // END of metric definition.

        leaf reference-count  {
            type  uint32;
            description "This attribute returns the reference-count parameter.";
        } // END of reference-count definition.

        leaf route-type  {
            type  ipi-pim-ipv4-types:pim_ipv4_route_type_t;
            description "This attribute returns the route-type parameter.";
        } // END of route-type definition.

        leaf route-sub-type  {
            type  ipi-pim-ipv4-types:pim_ipv4_route_sub_type_t;
            description "This attribute returns the route-sub-type parameter.";
        } // END of route-sub-type definition.

        leaf subaddress-familiy-identifier  {
            type  uint32;
            description "This attribute returns the subaddress-familiy-identifier parameter.";
        } // END of subaddress-familiy-identifier definition.

        leaf interface-index  {
            type  uint16;
            description "This attribute returns the interface-index parameter.";
        } // END of interface-index definition.

    } // END of pim-ipv4-route-state definition.
    grouping pim-ipv4-route-top {
        description
            "Grouping for PIM IPv4 next-hop-destinations";
        container next-hop-destinations {
            config false;
            description
                "Operational state data for PIM IPv4 next-hop-destinations";

            list next-hop-destination {
                key "destination-address";
                config false;
                description
                    "List of PIM IPv4 next-hop-destination";
                leaf destination-address  {
                    type  leafref {
                        path  "../state/destination-address";
                    }
                    description "This attribute returns the destination-address parameter.";
                } // END of destination-address definition.

                container state {
                    config false;
                    description
                        "Operational state data for PIM IPv4 next-hop-destination";
                    uses pim-ipv4-route-state;
                } // END of state-container definition.
                uses pim-ipv4-route-next-hop-top;
            } // End of next-hop-destination-list
        } // END of next-hop-destinations-container definition.
    } // END of pim-ipv4-route-top definition.
    grouping pim-ipv4-instance-config {
        description
            "Grouping for PIM IPv4 instance configuration attributes";
        leaf vrf-name  {
            type  leafref {
                path  "/ipi-network-instance:network-instances/ipi-network-instance:network-instance/ipi-vrf:vrf/ipi-vrf:config/ipi-vrf:vrf-name";
            }
            description "VRF name associated with this instance.";
        } // END of vrf-name definition.

        leaf router-id  {
            if-feature feature-list:HAVE_PIM_SM;
            type  inet:ipv4-address;
            description "Use this attribute to configure PIM router-ID to uniquely identify the
                        router.By default, PIM registers for the NSM router-id service. This
                        attribute will override the router-id received from NSM.";
        } // END of router-id definition.

        leaf join-prune-interval  {
            if-feature feature-list:HAVE_PIM_SM;
            type  uint16 {
                 range "1..65535"  {
                    description "1..65535: Supported range 1 - 65535";
                 }
            }
            units "seconds";
            description "Use this attribute to set a PIM join/prune timer.";
        } // END of join-prune-interval definition.

        leaf-list ecmp-bundle  {
            if-feature feature-list:HAVE_PIM_ECMP_REDIRECT;
            type  string {
                length "1..50";
                pattern "[a-zA-Z0-9_-]+";
            }
            description "Use this attribute to create an ECMP bundle.";
        } // END of ecmp-bundle definition.

        leaf-list dense-mode-group  {
            if-feature feature-list:HAVE_PIM_SMDM;
            type  inet:ipv4-address;
            description "Use this attribute to force a particular group to always follow dense
                        mode irrespective of whether RP mapping is available or not in SM-DM
                        mode.";
        } // END of dense-mode-group definition.

        leaf enable-bfd-all-interfaces  {
            if-feature feature-list:HAVE_BFD;
            type  empty;
            description "Use this attribute to enable Bidirectional Forwarding Detection (BFD)
                        on all interfaces.";
        } // END of enable-bfd-all-interfaces definition.

    } // END of pim-ipv4-instance-config definition.
    grouping pim-ipv4-instance-top {
        description
            "Grouping for PIM IPv4 instance";
        container instances {
            description
                "Configuration data for PIM IPv4 instance";

            list instance {
                key "vrf-name";
                description
                    "List of PIM IPv4 instances";
                leaf vrf-name  {
                    type  leafref {
                        path  "../config/vrf-name";
                    }
                    description "VRF name associated with this instance.";
                } // END of vrf-name definition.

                container config {
                    description
                        "Configuration data for PIM IPv4 instance";
                    uses pim-ipv4-instance-config;
                } // END of config-container definition.
                container state {
                    config false;
                    description
                        "Operational state data for PIM IPv4 instance";
                    uses pim-ipv4-instance-config;
                    uses pim-ipv4-statistics-state;
                    uses pim-ipv4-rp-set-top;
                } // END of state-container definition.
                uses pim-ipv4-route-top;
                uses pim-ipv4-register-packet-top;
                uses pim-ipv4-interop-top;
                uses pim-ipv4-spt-switch-top;
                uses pim-ipv4-ssm-top;
                uses pim-ipv4-anycast-rp-top;
                uses pim-ipv4-rp-top;
                uses pim-ipv4-msdp-top;
                uses pim-ipv4-bidir-top;
                uses pim-ipv4-debug-top;
                uses pim-ipv4-multicast-route-top;
            } // End of instance-list
        } // END of instances-container definition.
    } // END of pim-ipv4-instance-top definition.

    grouping  ipv4-grouping {
    description
        "Container for Protocol Independent Multicast (PIM) IPv4";
    container ipv4 {
        if-feature feature-list:HAVE_PIM_IPV4;
        if-feature feature-list:HAVE_PIMD;
        description
            "Container for Protocol Independent Multicast (PIM) IPv4";
        uses pim-ipv4-instance-top;
        uses pim-ipv4-interface-top;
    } // END of ipv4-container definition.
    } // END of ipv4-grouping definition.


}
