/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-pim.yang
*
*/

module ipi-pim {

    yang-version 1.1;

    namespace   "http://www.ipinfusion.com/yang/ocnos/ipi-pim";

    prefix "ipi-pim";

    import ietf-inet-types {
        prefix inet;
        revision-date 2013-07-15;
    }

    import ipi-pim-ipv4-types {
        prefix ipi-pim-ipv4-types;
        revision-date 2023-03-17;
    }

    import ipi-pim-ipv6-types {
        prefix ipi-pim-ipv6-types;
        revision-date 2024-12-23;
    }

    import feature-list {
        prefix feature-list;
        revision-date 2026-09-15;
    }

    include ipi-pim-debug { revision-date 2023-02-28;}
    include ipi-pim-ipv4 { revision-date 2024-12-13;}
    include ipi-pim-ipv6 { revision-date 2023-07-07;}
    include ipi-pim-ipv4-bidir { revision-date 2023-03-17;}
    include ipi-pim-ipv4-debug { revision-date 2023-02-20;}
    include ipi-pim-ipv4-interface { revision-date 2023-03-17;}
    include ipi-pim-ipv4-msdp { revision-date 2024-11-04;}
    include ipi-pim-ipv4-redundancy { revision-date 2022-06-01;}
    include ipi-pim-ipv6-state { revision-date 2024-12-13;}
    include ipi-pim-ipv6-interface { revision-date 2024-06-30;}
    include ipi-pim-ipv6-debug { revision-date 2023-02-20;}
    organization
        "IP Infusion Inc.";

    contact
        "Address: 3965 Freedom Circle, Suite 200, Santa Clara, CA 95054
         Phone: +1 408-400-1900
         E-mail: support@ipinfusion.com
         Web: http://www.ipinfusion.com/";

    description
        "Protocol Independent Multicast (PIM) configurations";


    revision "2024-12-23" {
        description "Reverting the values for PIM_IPV6_MULTICAST_ROUTE_UPSTREAM_STATE_T to avoid automation blockers";
        reference " 0.2.3.";
    }

    revision "2024-12-13" {
        description "Changed multicast-route source and group v4 address type from CML_IPV4_ADDR_PREFIX_T to CML_IPV4_ADDR_T and v6 address type from CML_IPV6_PREFIX_T to CML_IPV6_ADDR_T";
        reference " 0.2.2.";
    }

    revision "2024-11-04" {
        description "Changed password size limits";
        reference " 0.2.1.";
    }

    revision "2024-08-20" {
        description "Updated the values for PIM_IPV6_MULTICAST_ROUTE_UPSTREAM_STATE_T to sync with the cli output";
        reference " 0.2.0.";
    }

    revision "2024-06-30" {
        description "IPv6-PIM Added Implicit Delete of interface configs for LAG member";
        reference " 0.1.1.";
    }

    revision "2023-07-07" {
        description "Removing the misplaced initialized from rp-bsr-candidate-config";
        reference " 0.1.0.";
    }

    revision "2023-03-18" {
        description "Pattern validation added for ACL naming, bundle-name, accept-register names for ipv4 and ipv6";
        reference " 0.5.3.";
    }

    revision "2023-02-28" {
        description "Adding proper flag for objectAction";
        reference " 0.5.2.";
    }

    revision "2023-02-20" {
        description "Added When tag for no-debug-all command pim-ipv4, pim-ipv6 debug container";
        reference " 0.5.1.";
    }

    revision "2023-02-17" {
        description "Fixed prependstr warning";
        reference " 0.5.0.";
    }

    revision "2022-11-13" {
        description "modified SSM range 232/8 to FF3x::/96 for IPv6";
        reference " 0.4.0.";
    }

    revision "2022-08-10" {
        description "Debug hierarchy change";
        reference " 0.3.2.";
    }

    revision "2022-07-31" {
        description "Stop using inet:ipv4-prefix and inet:ipv6-prefix due to Cisco NSO iterop";
        reference " 0.3.1.";
    }

    revision "2022-07-30" {
        description "Updated when expressions in yang";
        reference " 0.3.0.";
    }

    revision "2022-07-06" {
        description "Fixed removal of PIMv6 embed-rp";
        reference " 0.2.7.";
    }

    revision "2022-06-06" {
        description "Added if-feature HAVE_PIM_BIDIR for rp-interface-name attribute and removed invalid PIMv6 state attributes";
        reference " 0.2.6.";
    }

    revision "2022-06-01" {
        description "Updated the yang file with feature";
        reference " 0.2.5.";
    }

    revision "2022-04-28" {
        description "Removed macro-state attribute from downstream-xxrp-sg-rpt/state containers";
        reference " 0.2.4.";
    }

    revision "2022-04-04" {
        description "The module ipi-pim-ipv6-interface was modified";
        reference " 0.2.3.";
    }

    revision "2022-03-30" {
        description "Restructured PIM IPv6 module in accordance with OpenConfig style";
        reference " 0.2.2.";
    }

    revision "2022-03-29" {
        description "Fix the range for suppress-interval attribute on PIM-IPv4";
        reference " 0.2.1.";
    }

    revision "2022-03-15" {
        description "Restructured module in accordance with OpenConfig style";
        reference " 0.2.0.";
    }

    revision "2018-06-21" {
        description "Initial Version";
        reference " 0.1.0.";
    }


    grouping  pim-grouping {
    description
        "Configuration data for PIM instances";
    container pim {
        if-feature feature-list:HAVE_PIMD;
        description
            "Configuration data for PIM instances";
        uses pim-debug-top;
        uses ipv4-grouping;
        uses ipv6-grouping;
    } // END of pim-container definition.
    } // END of pim-grouping definition.

    uses pim-grouping;

    rpc pim-snmp-restart {
        if-feature feature-list:HAVE_SNMP;
        if-feature feature-list:HAVE_PIMD;
        if-feature feature-list:HAVE_PIM_IPV4;
        description "Restart SNMP in PIM";
    }

    rpc pim-ipv4-clear-bsr-rendezvous-point {
        if-feature feature-list:HAVE_PIM_IPV4;
        if-feature feature-list:HAVE_PIM_SM;
        if-feature feature-list:HAVE_PIMD;
        description "Clear all rendezvous point (RP) sets learned through the PIMv2
                    Bootstrap Router (BSR)";
        input  {
            leaf vrf-name  {
                type string {
                    length "1..32";
                }
                description "VRF name associated with this instance.";
            }
            leaf pim-mode  {
                type ipi-pim-ipv4-types:pim_ipv4_mode_clear_bsr_rp_t;
                mandatory true;
                description "PIM mode to use for this clear command.";
            }
        }
    }

    rpc pim-ipv4-clear-multicast-route {
        if-feature feature-list:HAVE_PIM_IPV4;
        if-feature feature-list:HAVE_PIMD;
        description "Clear the multicast route entries in the multicast route table";
        input  {
            leaf vrf-name  {
                type string {
                    length "1..32";
                }
                description "VRF name associated with this instance.";
            }
            leaf pim-mode  {
                type ipi-pim-ipv4-types:pim_ipv4_mode_t;
                mandatory true;
                description "PIM mode to use for this clear command.";
            }
        }
    }

    rpc pim-ipv4-clear-multicast-route-source-group {
        if-feature feature-list:HAVE_PIM_IPV4;
        if-feature feature-list:HAVE_PIMD;
        description "Clear the multicast route entries in the multicast route table";
        input  {
            leaf vrf-name  {
                type string {
                    length "1..32";
                }
                description "VRF name associated with this instance.";
            }
            leaf group-address  {
                type inet:ipv4-address;
                mandatory true;
                description "Group address to use with this clear command.";
            }
        }
    }

    rpc pim-ipv4-clear-multicast-route-source-group-mode {
        if-feature feature-list:HAVE_PIM_IPV4;
        if-feature feature-list:HAVE_PIMD;
        description "Clear the multicast route entries in the multicast route table";
        input  {
            leaf vrf-name  {
                type string {
                    length "1..32";
                }
                description "VRF name associated with this instance.";
            }
            leaf group-address  {
                type inet:ipv4-address;
                mandatory true;
                description "Group address to use with this clear command.";
            }
            leaf source-address  {
                type inet:ipv4-address;
                mandatory true;
                description "Source address to use with this clear command.";
            }
            leaf pim-mode  {
                type ipi-pim-ipv4-types:pim_ipv4_mode_t;
                mandatory true;
                description "PIM mode to use with this clear command.";
            }
        }
    }

    rpc pim-ipv4-clear-msdp-peer {
        if-feature feature-list:HAVE_PIM_IPV4;
        if-feature feature-list:HAVE_PIM_MSDP_API;
        if-feature feature-list:HAVE_PIMD;
        description "Clear the TCP connection to a Multicast Source Discovery Protocol
                    (MSDP) peer";
        input  {
            leaf vrf-name  {
                type string {
                    length "1..32";
                }
                description "VRF name associated with this instance.";
            }
            leaf address  {
                type inet:ipv4-address;
                mandatory true;
                description "IP address of MSDP peer to use with this clear command.";
            }
        }
    }

    rpc pim-ipv4-clear-msdp-sa-cache {
        if-feature feature-list:HAVE_PIM_IPV4;
        if-feature feature-list:HAVE_PIM_MSDP_API;
        if-feature feature-list:HAVE_PIMD;
        description "Clear Multicast Source Discovery Protocol (MSDP) Source-Active (SA)
                    cache entries";
        input  {
            leaf vrf-name  {
                type string {
                    length "1..32";
                }
                description "VRF name associated with this instance.";
            }
            leaf group-address  {
                type inet:ipv4-address;
                mandatory true;
                description "Group address to use with this clear command.";
            }
        }
    }

    rpc pim-ipv4-terminal-debug-on {
        if-feature feature-list:HAVE_PIM_IPV4;
        if-feature feature-list:HAVE_PIMD;
        description "Enable PIM IPv4 debugging functions";
        input  {
            leaf vrf-name  {
                type string;
                description "VRF name associated with this instance.";
            }
            leaf terminal-debug-options  {
                type ipi-pim-ipv4-types:pim_ipv4_debug_t;
                mandatory true;
                description "Use this attribute to debug the PIM IPv4 feature.";
            }
        }
    }

    rpc pim-ipv4-terminal-debug-off {
        if-feature feature-list:HAVE_PIM_IPV4;
        if-feature feature-list:HAVE_PIMD;
        description "Disable PIM IPv4 debugging functions";
        input  {
            leaf vrf-name  {
                type string;
                description "VRF name associated with this instance.";
            }
            leaf terminal-debug-options  {
                type ipi-pim-ipv4-types:pim_ipv4_debug_t;
                mandatory true;
                description "Use this attribute to debug the PIM IPv4 feature.";
            }
        }
    }

    rpc pim-ipv4-terminal-debug-all-on {
        if-feature feature-list:HAVE_PIM_IPV4;
        if-feature feature-list:HAVE_PIMD;
        description "Enable all PIM IPv4 debugging functions";
        input  {
            leaf vrf-name  {
                type string;
                default "default";
                description "VPN routing/forwarding Instance name";
            }
        }
    }

    rpc pim-ipv4-terminal-debug-all-off {
        if-feature feature-list:HAVE_PIM_IPV4;
        if-feature feature-list:HAVE_PIMD;
        description "Disable all PIM IPv4 debugging functions";
        input  {
            leaf vrf-name  {
                type string;
                default "default";
                description "VPN routing/forwarding Instance name";
            }
        }
    }

    rpc pim-ipv6-clear-bsr-rendezvous-point {
        if-feature feature-list:HAVE_PIM_IPV6;
        if-feature feature-list:HAVE_PIM_SM;
        if-feature feature-list:HAVE_PIMD;
        description "Clear all rendezvous point (RP) sets learned through the PIMv2
                    Bootstrap Router (BSR)";
        input  {
            leaf vrf-name  {
                type string {
                    length "1..32";
                }
                description "VRF name associated with this instance.";
            }
            leaf pim-mode  {
                type ipi-pim-ipv6-types:pim_ipv6_mode_clear_bsr_rp_t;
                mandatory true;
                description "PIM mode to use with this clear command.";
            }
        }
    }

    rpc pim-ipv6-clear-multicast-route {
        if-feature feature-list:HAVE_PIM_IPV6;
        if-feature feature-list:HAVE_PIMD;
        description "Clear the multicast route entries in the multicast route table";
        input  {
            leaf vrf-name  {
                type string {
                    length "1..32";
                }
                description "VRF name associated with this instance.";
            }
            leaf pim-mode  {
                type ipi-pim-ipv6-types:pim_ipv6_mode_t;
                mandatory true;
                description "PIM mode to use with this clear command.";
            }
        }
    }

    rpc pim-ipv6-clear-multicast-route-source-group {
        if-feature feature-list:HAVE_PIM_IPV6;
        if-feature feature-list:HAVE_PIMD;
        description "Clear the multicast route entries in the multicast route table";
        input  {
            leaf vrf-name  {
                type string {
                    length "1..32";
                }
                description "VRF name associated with this instance.";
            }
            leaf group-address  {
                type inet:ipv6-address;
                mandatory true;
                description "Group address to use with this clear command.";
            }
        }
    }

    rpc pim-ipv6-clear-multicast-route-source-group-mode {
        if-feature feature-list:HAVE_PIM_IPV6;
        if-feature feature-list:HAVE_PIMD;
        description "Clear the multicast route entries in the multicast route table";
        input  {
            leaf vrf-name  {
                type string {
                    length "1..32";
                }
                description "VRF name associated with this instance.";
            }
            leaf group-address  {
                type inet:ipv6-address;
                mandatory true;
                description "Group address to use with this clear command.";
            }
            leaf source-address  {
                type inet:ipv6-address;
                mandatory true;
                description "Source address to use with this clear command.";
            }
            leaf pim-mode  {
                type ipi-pim-ipv6-types:pim_ipv6_mode_t;
                mandatory true;
                description "PIM mode to use with this clear command.";
            }
        }
    }

    rpc pim-terminal-debug-bfd-on {
        if-feature feature-list:HAVE_PIMD;
        if-feature feature-list:HAVE_PIM_IPV4;
        if-feature feature-list:HAVE_PIM_IPV4_OR_HAVE_PIM_IPV6;
        description "Enable PIM BFD debugging functions";
    }

    rpc pim-terminal-debug-bfd-off {
        if-feature feature-list:HAVE_PIMD;
        if-feature feature-list:HAVE_PIM_IPV4;
        if-feature feature-list:HAVE_PIM_IPV4_OR_HAVE_PIM_IPV6;
        description "Disable PIM BFD debugging functions";
    }

    rpc pim-ipv6-terminal-debug-on {
        if-feature feature-list:HAVE_PIM_IPV6;
        if-feature feature-list:HAVE_PIMD;
        description "Enable PIM IPv6 debugging functions";
        input  {
            leaf vrf-name  {
                type string;
                description "VRF name associated with this instance.";
            }
            leaf terminal-debug-options  {
                type ipi-pim-ipv6-types:pim_ipv6_debug_t;
                mandatory true;
                description "Use this attribute to debug the PIM IPv6 feature.";
            }
        }
    }

    rpc pim-ipv6-terminal-debug-off {
        if-feature feature-list:HAVE_PIM_IPV6;
        if-feature feature-list:HAVE_PIMD;
        description "Disable PIM IPv6 debugging functions";
        input  {
            leaf vrf-name  {
                type string;
                description "VRF name associated with this instance";
            }
            leaf terminal-debug-options  {
                type ipi-pim-ipv6-types:pim_ipv6_debug_t;
                mandatory true;
                description "Use this attribute to debug the PIM IPv6 feature.";
            }
        }
    }

    rpc pim-ipv6-terminal-debug-all-on {
        if-feature feature-list:HAVE_PIM_IPV6;
        if-feature feature-list:HAVE_PIMD;
        description "Enable all PIM IPv6 debugging functions";
        input  {
            leaf vrf-name  {
                type string;
                default "default";
                description "VPN routing/forwarding Instance name";
            }
        }
    }

    rpc pim-ipv6-terminal-debug-all-off {
        if-feature feature-list:HAVE_PIM_IPV6;
        if-feature feature-list:HAVE_PIMD;
        description "Disable all PIM IPv6 debugging functions";
        input  {
            leaf vrf-name  {
                type string;
                default "default";
                description "VPN routing/forwarding Instance name";
            }
        }
    }

}
