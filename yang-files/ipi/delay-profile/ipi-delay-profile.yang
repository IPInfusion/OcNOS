/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-delay-profile.yang
*
*/

module ipi-delay-profile {

    yang-version 1.1;

    namespace   "http://www.ipinfusion.com/yang/ocnos/ipi-delay-profile";

    prefix "ipi-delay-profile";

    import ipi-delay-profile-types {
        prefix ipi-delay-profile-types;
        revision-date 2023-03-02;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for configuring the delay measurement profile";


    revision "2025-09-18" {
        description "Adjusted helpstring for burst count";
        reference " 0.9.1.";
    }

    revision "2025-06-20" {
        description "Increased the burst-count attribute range";
        reference " 0.9.0.";
    }

    revision "2025-06-12" {
        description "Adjusted the sender port help string";
        reference " 0.8.1.";
    }

    revision "2025-02-03" {
        description "Added SNMP Traps support for TWAMP";
        reference " 0.8.0.";
    }

    revision "2024-12-12" {
        description "Added drop-yang tag to drop some unnecessary groupings";
        reference " 0.7.0.";
    }

    revision "2023-09-13" {
        description "Added implicit_delete tag for delay-profile-parameters to fix db-sync";
        reference " 0.6.2.";
    }

    revision "2023-07-26" {
        description "Removed interval attribute for delay profile twamp client";
        reference " 0.6.1.";
    }

    revision "2023-05-12" {
        description "Added delay profile measurment parameters for twamp client";
        reference " 0.6.0.";
    }

    revision "2023-03-02" {
        description "Added one way measurement option";
        reference " 0.5.0.";
    }

    revision "2023-01-10" {
        description "Fixed deleting the DB entry of the empty config container for periodic advertisement";
        reference " 0.4.0.";
    }

    revision "2022-10-27" {
        description "Reduced the maximum value of the burst count attribute";
        reference " 0.3.0.";
    }

    revision "2022-06-01" {
        description "Updated the yang file with feature";
        reference " 0.2.0.";
    }

    revision "2021-09-30" {
        description "Initial release";
        reference " 0.1.0.";
    }

    grouping profile-parameters-top {
        description
            "Set the delay profile parameters";
        container profile-parameters {
            description
                "Definition of delay profile parameters";
            container config {
                description
                    "Configuration data";
                uses profile-parameters-config;
                uses interface-client-config;
                uses interface-config;
            } // END of config-container definition.
            container state {
                config false;
                description
                    "Operational state data";
                uses profile-parameters-config;
                uses interface-client-config;
                uses interface-config;
            } // END of state-container definition.
        } // END of profile-parameters-container definition.
    } // END of profile-parameters-top definition.
    grouping profile-periodic-top {
        description
            "Set the delay profile parameters";
        container periodic-advertisement {
            description
                "Definition of delay profile parameters";
            container config {
                description
                    "Configuration data";
                uses profile-periodic-config;
            } // END of config-container definition.
            container state {
                config false;
                description
                    "Operational state data";
                uses profile-periodic-config;
            } // END of state-container definition.
        } // END of periodic-advertisement-container definition.
    } // END of profile-periodic-top definition.
    grouping profile-periodic-config {
        description
            "periodic";
        leaf disable  {
            type  empty;
            description "Disable the periodic advertisement";
        } // END of disable definition.

        leaf threshold  {
            // when " ipi-delay-profile:delay-profiles/delay-profile/periodic-advertisement/config/disable != '1' ";
            type  uint8 {
                 range "1..100"  {
                    description "1..100: Supported range 1 - 100";
                 }
            }
            description "Configure the periodic advertisement threshold";
        } // END of threshold definition.

        leaf minimum-change  {
            // when " ipi-delay-profile:delay-profiles/delay-profile/periodic-advertisement/config/disable != '1' ";
            type  uint16 {
                 range "0..10000"  {
                    description "0..10000: Supported range 0 - 10000";
                 }
            }
            description "Configure the advertisement minimum-change in microseconds
                        (default=1000)";
        } // END of minimum-change definition.

    } // END of profile-periodic-config definition.
    grouping profile-accelerated-top {
        description
            "Set the delay profile parameters";
        container accelerated-advertisement {
            description
                "Definition of delay profile parameters";
            container config {
                presence "accelerated advertisement config";
                description
                    "Configuration data";
                uses profile-accelerated-config;
            } // END of config-container definition.
            container state {
                config false;
                description
                    "Operational state data";
                uses profile-accelerated-config;
            } // END of state-container definition.
        } // END of accelerated-advertisement-container definition.
    } // END of profile-accelerated-top definition.
    grouping profile-notifications-config {
        description
            "notifications";
        leaf enabled  {
            type  empty;
            mandatory true;
            description "Enable the notifications for advertising via NETCONF/SNMP Traps when
                        thresholds are crossed";
        } // END of enabled definition.

        leaf threshold  {
            type  uint8 {
                 range "1..100"  {
                    description "1..100: Supported range 1 - 100";
                 }
            }
            description "Configure the notifications advertisement threshold";
        } // END of threshold definition.

        leaf minimum-change  {
            type  uint16 {
                 range "0..10000"  {
                    description "0..10000: Supported range 0 - 10000";
                 }
            }
            description "Configure the notifications advertisement minimum-change in
                        microseconds (default=1000)";
        } // END of minimum-change definition.

    } // END of profile-notifications-config definition.
    grouping profile-notifications-top {
        description
            "Set the delay profile notifications parameters";
        container notifications {
            if-feature feature-list:HAVE_TE;
            description
                "Definition of delay profile notifications parameters";
            container config {
                presence "delay profile notifications config";
                description
                    "Configuration data";
                uses profile-notifications-config;
            } // END of config-container definition.
            container state {
                config false;
                description
                    "Operational state data";
                uses profile-notifications-config;
            } // END of state-container definition.
        } // END of notifications-container definition.
    } // END of profile-notifications-top definition.
    grouping profile-accelerated-config {
        description
            "accelerated";
        leaf enable  {
            type  empty;
            mandatory true;
            description "Enable the accelerated advertisement";
        } // END of enable definition.

        leaf threshold  {
            type  uint8 {
                 range "1..100"  {
                    description "1..100: Supported range 1 - 100";
                 }
            }
            description "Configure the accelerated advertisement threshold";
        } // END of threshold definition.

        leaf minimum-change  {
            type  uint16 {
                 range "0..10000"  {
                    description "0..10000: Supported range 0 - 10000";
                 }
            }
            description "Configure the advertisement minimum-change in microseconds
                        (default=1000)";
        } // END of minimum-change definition.

    } // END of profile-accelerated-config definition.
    grouping interface-client-config {
        description
            "Parameters to update delay profile interfaces and clients";
        leaf burst-interval  {
            type  uint16 {
                 range "1000..15000"  {
                    description "1000..15000: Supported range 1000 - 15000";
                 }
            }
            description "Configure the burst-interval";
        } // END of burst-interval definition.

        leaf burst-count  {
            type  uint8 {
                 range "1..10"  {
                    description "1..10: Supported range 1 - 10";
                 }
            }
            description "Configure the burst-count";
        } // END of burst-count definition.

    } // END of interface-client-config definition.
    grouping interface-config {
        description
            "Parameters to update delay profile interfaces";
        leaf interval  {
            type  uint16 {
                 range "30..3600"  {
                    description "30..3600: Supported range 30 - 3600";
                 }
            }
            description "Configure the computation interval";
        } // END of interval definition.

    } // END of interface-config definition.
    grouping profile-parameters-config {
        description
            "Set the configuration parameters";
        leaf mode  {
            type  ipi-delay-profile-types:delay_profile_measurement_mode_t;
            description "Set the measurement mode";
        } // END of mode definition.

        leaf sender-port  {
            type  uint16 {
                 range "1025..65535"  {
                    description "1025..65535: Supported range 1025 - 65535";
                 }
            }
            description "Configure the computation interval";
        } // END of sender-port definition.

    } // END of profile-parameters-config definition.
    grouping delay-profile-config {
        description
            "DELAY profile configuration data";
        leaf profile-type  {
            type  ipi-delay-profile-types:delay_profile_type_t;
            description "The profile type for delay";
        } // END of profile-type definition.

    } // END of delay-profile-config definition.
    grouping delay-profile-client {
        description
            "Use this to enable delay profile for client";
        leaf delay-profile-enable  {
            type  empty;
            mandatory true;
            description "Enables TWAMP Client delay profile";
        } // END of delay-profile-enable definition.

    } // END of delay-profile-client definition.
    grouping twamp-client-delay-profile-top {
        description
            "Grouping for TWAMP client delay profile configuration";
        container delay-profile-clients {
            description
                "TWAMP client delay profile Configuration";
            container config {
                presence "yes";
                description
                    "Delay profile configuration data for TWAMP client";
                uses delay-profile-client;
                uses interface-client-config;
            } // END of config-container definition.
            container state {
                config false;
                description
                    "Operational state data for TWAMP Client delay profile status data";
                uses delay-profile-client;
                uses interface-client-config;
            } // END of state-container definition.
        } // END of delay-profile-clients-container definition.
    } // END of twamp-client-delay-profile-top definition.

    grouping  delay-profiles-grouping {
    description
        "Top level container for the DELAY profile configuration and
                operational data";
    container delay-profiles {
        if-feature feature-list:HAVE_TWAMP;
        description
            "Top level container for the DELAY profile configuration and
                    operational data";

        list delay-profile {
            key "profile-type";
            max-elements 1;
            description
                "This defines a YANG data model forcreating a Delay interfaces profile";
            leaf profile-type  {
                type  leafref {
                    path  "../config/profile-type";
                }
                description "The profile type for delay";
            } // END of profile-type definition.

            container config {
                description
                    "configuration data for the DELAY profile";
                uses delay-profile-config;
            } // END of config-container definition.
            container state {
                config false;
                description
                    "Operational state data of the DELAY profile";
                uses delay-profile-config;
            } // END of state-container definition.
            uses profile-parameters-top;
            uses profile-periodic-top;
            uses profile-accelerated-top;
            uses profile-notifications-top;
        } // End of delay-profile-list
        uses twamp-client-delay-profile-top;
    } // END of delay-profiles-container definition.
    } // END of delay-profiles-grouping definition.

    uses delay-profiles-grouping;

}
