/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-mpls.yang
*
*/

module ipi-mpls {

    yang-version 1.1;

    namespace   "http://www.ipinfusion.com/yang/ocnos/ipi-mpls";

    prefix "ipi-mpls";

    import cml-data-types {
        prefix cml-data-types;
        revision-date 2026-05-15;
    }

    import ipi-mpls-types {
        prefix ipi-mpls-types;
        revision-date 2026-02-03;
    }

    import ipi-interface {
        prefix ipi-interface;
        revision-date 2026-03-10;
    }

    import ipi-global-te {
        prefix ipi-global-te;
        revision-date 2024-12-23;
    }

    import ietf-yang-types {
        prefix yang;
        revision-date 2013-07-15;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Data model for MPLS";


    revision "2026-08-27" {
        description "Added dependentObject of hardware-profile filters on mpls l2vpn-stitching";
        reference " 0.12.2.";
    }

    revision "2026-03-25" {
        description "Bandwidth set command help string modified to max supported bandwidth";
        reference " 0.12.1.";
    }

    revision "2026-02-11" {
        description "Added support for enabling/disabling MPLS-Aware RIB feature";
        reference " 0.11.11.";
    }

    revision "2026-02-03" {
        description "Added not-applicable as a possible value for attribute Action-Type in FTN entry";
        reference " 0.11.10.";
    }

    revision "2025-10-31" {
        description "Updated datatype of FTN entry state attribute to RAW STRING";
        reference " 0.11.8.";
    }

    revision "2025-10-27" {
        description "Added new attributes tunnel-name and transport out interface inside grouping mpls-rib-ftn-nhlfe-entry-state ";
        reference " 0.11.7.";
    }

    revision "2025-10-09" {
        description "Added hidden-cli for customer-service-template";
        reference " 0.11.6.";
    }

    revision "2025-09-19" {
        description "Change srlg helpstring";
        reference " 0.11.5.";
    }

    revision "2025-09-17" {
        description "Corrected SRLG-ID minimum value to be 1";
        reference " 0.11.5.";
    }

    revision "2025-08-21" {
        description "Add MPLS ILM table counter";
        reference " 0.11.4.";
    }

    revision "2025-08-14" {
        description "Reverting the changes added hidden-cli to enable or disable default vccv capability";
        reference " 0.11.3.";
    }

    revision "2025-07-28" {
        description "Added new attribute xc-index to mpls-rib-ip-ilm-nhlfe-entry-state group";
        reference " 0.11.2.";
    }

    revision "2025-07-24" {
        description "Added hidden-cli to enable or disable default vccv capability";
        reference " 0.11.1.";
    }

    revision "2025-07-23" {
        description "Added new attribute xc-type to mpls-rib-ipv4-ftn-nhlfe-entry-state group";
        reference " 0.11.0.";
    }

    revision "2025-04-30" {
        description "Fix compilation warnings";
        reference " 0.10.4.";
    }

    revision "2025-04-29" {
        description "New command added to enable or disable l2vpn network traffic statistics for Qumran2 devices";
        reference " 0.10.3.";
    }

    revision "2025-03-07" {
        description "Introduced a new CLI to enable or disable L2VPN stitching";
        reference " 0.10.2.";
    }

    revision "2025-02-20" {
        description "Added unique flag for group id in acces circuit group objectlist";
        reference " 0.10.1.";
    }

    revision "2025-02-19" {
        description "Added streaming telemetry support";
        reference " 0.10.0.";
    }

    revision "2024-12-23" {
        description "Changes to mpls global-te module";
        reference " 0.9.9.";
    }

    revision "2024-12-06" {
        description "Added new attribute to suppress operator logs for services";
        reference " 0.9.8.";
    }

    revision "2024-11-22" {
        description "Added dependentobject tag inside the label-switching container";
        reference " 0.9.7.";
    }

    revision "2024-09-18" {
        description "Added new container for dscp preserve per 6PE service";
        reference " 0.9.6.";
    }

    revision "2024-09-13" {
        description "Removed the dependent object tag from mpls ac-grp";
        reference " 0.9.5.";
    }

    revision "2024-09-10" {
        description "Added a new command for Q2 boards to inherit cos value from exp in case of PHP ILM";
        reference " 0.9.4.";
    }

    revision "2024-09-05" {
        description "Added flags HAVE_VPLS and HAVE_MPLS_VC inside import tag";
        reference " 0.9.3.";
    }

    revision "2024-08-28" {
        description "Made Interface-mode Extended-Admin-Group CLI(s) visible";
        reference " 0.9.2.";
    }

    revision "2024-08-23" {
        description "Added dependent object tag for mpls ac-grp";
        reference " 0.9.1.";
    }

    revision "2024-07-18" {
        description "Updated the dependentobject tag present inside the label-switching container";
        reference " 0.9.0.";
    }

    revision "2024-07-16" {
        description "Enabled mpls lsp-encap-dscp-preserve for Q2 boards";
        reference " 0.8.6.";
    }

    revision "2024-05-18" {
        description "Added Anomaly Extended-Admin-Group";
        reference " 0.8.5.";
    }

    revision "2024-05-15" {
        description "Added SR element to the type MPLS_ECMP_PROTOCOL_T";
        reference " 0.8.4.";
    }

    revision "2024-04-22" {
        description "Added new attribute lsp-encap-dscp-preserve under mpls-global-config grouping";
        reference " 0.8.3.";
    }

    revision "2024-04-11" {
        description "Changed Extended-Admin-Group CLI to hidden";
        reference " 0.8.2.";
    }

    revision "2024-02-21" {
        description "Added missing state container for MPLS interface";
        reference " 0.8.1.";
    }

    revision "2024-02-09" {
        description "Added Extended Administrative Groups for MPLS-TE on Interface";
        reference " 0.8.0.";
    }

    revision "2024-01-29" {
        description "Revert masking of service template commands for Marvell platform";
        reference " 0.7.12.";
    }

    revision "2024-01-15" {
        description "Mask service template commands for Marvell platform";
        reference " 0.7.11.";
    }

    revision "2023-12-18" {
        description "when expression added for LBG db-sync issue";
        reference " 0.7.10.";
    }

    revision "2023-11-29" {
        description "Added a new attribute entropy-label-capability under mpls-global-config grouping";
        reference " 0.7.9.";
    }

    revision "2023-11-13" {
        description "fix for XP sku's build failures in ocnos-sp-master";
        reference " 0.7.8.";
    }

    revision "2023-10-26" {
        description "Added dependentObject tag for label-switching over sub-intf encapsulation";
        reference " 0.7.7.";
    }

    revision "2023-07-14" {
        description "Updated proper help-string for vlan identifiers";
        reference " 0.7.6.";
    }

    revision "2023-07-05" {
        description "added HAVE_6PE flag to enable rsvp compilation for marvell platforms";
        reference " 0.7.5.";
    }

    revision "2023-06-20" {
        description "CLI support for MPLS FTN and ILM ECMP";
        reference " 0.7.4.";
    }

    revision "2023-06-19" {
        description "Reverting Fix for sget changes to enable or disable ldp ecmp";
        reference " 0.7.3.";
    }

    revision "2023-05-11" {
        description "corrected the helpsting for unform";
        reference " 0.7.2.";
    }

    revision "2023-05-04" {
        description "Removed implicit delete tag for the objectlist Customer Service Template";
        reference " 0.7.1.";
    }

    revision "2023-02-12" {
        description "Deprecation of enable mpls on all interfaces global command";
        reference " 0.6.20.";
    }

    revision "2023-02-06" {
        description "Enclosed all config object lists with container for MPLS Data Model";
        reference " 0.7.0.";
    }

    revision "2023-01-23" {
        description "Addressed cli-prependstr not found cmlgen warnings";
        reference " 0.6.19.";
    }

    revision "2023-01-20" {
        description "Added helpstring for tunnel-select-policy";
        reference " 0.6.18.";
    }

    revision "2023-01-16" {
        description "Leafref correction for config container";
        reference " 0.6.17.";
    }

    revision "2022-12-01" {
        description "Updated when expressions";
        reference " 0.6.16.";
    }

    revision "2022-11-11" {
        description "Add support to configure ldp-vc label pool";
        reference " 0.6.15.";
    }

    revision "2022-10-17" {
        description "Added dependency with evpn-mpls global if present in bulk commit";
        reference " 0.6.14.";
    }

    revision "2022-09-23" {
        description "Added attribute to enable or disable ldp ecmp on transit node";
        reference " 0.6.13.";
    }

    revision "2022-09-20" {
        description "Added attribute to display the type of xc";
        reference " 0.6.12.";
    }

    revision "2022-09-08" {
        description "Added HAVE_MPLS_VC and HAVE_VPLS flags to fix compilation issues";
        reference " 0.6.11.";
    }

    revision "2022-08-29" {
        description "Updated the when expression with feature";
        reference " 0.6.10.";
    }

    revision "2022-08-24" {
        description "Revert changes to fix pre-qat failures";
        reference " 0.6.9.";
    }

    revision "2022-08-19" {
        description "Fix for split-horizon group DB cleanup";
        reference " 0.6.8.";
    }

    revision "2022-08-01" {
        description "Fix interface bandwidth deletion";
        reference " 0.6.7.";
    }

    revision "2022-07-30" {
        description "Updated when expressions in yang";
        reference " 0.6.6.";
    }

    revision "2022-07-20" {
        description "Added attribute for ldp ecmp";
        reference " 0.6.5.";
    }

    revision "2022-07-16" {
        description "Global yang model name is changed as Global TE yang model";
        reference " 0.6.4.";
    }

    revision "2022-07-07" {
        description "Fix for MPLS debug deletion";
        reference " 0.6.1.";
    }

    revision "2022-07-01" {
        description "Added pattern check for bandwidth related commands";
        reference " 0.6.2.";
    }

    revision "2022-06-21" {
        description "Changes in the yang model WRT to admin-groups";
        reference " 0.6.1.";
    }

    revision "2022-06-01" {
        description "Updated the yang file with feature";
        reference " 0.6.0.";
    }

    revision "2021-12-08" {
        description "Updated six-pe-tunnel-policy objectlist for single instance";
        reference " 0.5.9.";
    }

    revision "2021-09-01" {
        description "Changed base interface module's switchport attribute name and the datatype from bool to empty";
        reference " 0.5.8.";
    }

    revision "2021-08-17" {
        description "Added runtime attributes for operational state of RSVP and LDP graceful-restart";
        reference " 0.5.7.";
    }

    revision "2021-08-02" {
        description "Added support for multiple inner vlan Range or ID in MPLS service template";
        reference " 0.5.5.";
    }

    revision "2021-07-29" {
        description "Added bandwidth cli for IGP TE";
        reference " 0.5.6.";
    }

    revision "2021-07-12" {
        description "Corrected inner vlan data-type for MPLS service template";
        reference " 0.5.4.";
    }

    revision "2021-06-29" {
        description "Corrected length property for group-name";
        reference " 0.5.3.";
    }

    revision "2021-06-25" {
        description "Removed implicit delete from config container of service-template config as not required ";
        reference " 0.5.2.";
    }

    revision "2021-05-13" {
        description "Corrected dependencies for label-management object lists";
        reference " 0.5.1.";
    }

    revision "2021-03-30" {
        description "Change for Tunnel policy config";
        reference " 0.5.0.";
    }

    revision "2021-03-15" {
        description "Change for restructuring Diffserve-TE";
        reference " 0.4.0.";
    }

    revision "2021-01-27" {
        description "Change for restructuring Label Management and admin group CLIs";
        reference " 0.3.0.";
    }

    revision "2020-12-15" {
        description "Change to have data-types in lower case instead of camel case";
        reference " 0.2.0.";
    }

    revision "2020-11-03" {
        description "Initial Version";
        reference " 0.1.0.";
    }

    grouping mpls-interface-config {
        description
            "MPLS Interface Configurations";
        leaf name  {
            type  leafref {
                path  "/ipi-interface:interfaces/ipi-interface:interface/ipi-interface:name";
            }
            description "The textual name of the interface.";
        } // END of name definition.

    } // END of mpls-interface-config definition.
    grouping mpls-6pe-tunnel-policy {
        description
            "MPLS 6PE tunnel policy Configurations";
        leaf name  {
            type  string {
                length "1..1965";
                pattern "[^?' =,>|]+";
            }
            description "Use this attribute to map Tunnel policy to 6PE";
        } // END of name definition.

    } // END of mpls-6pe-tunnel-policy definition.
    grouping ecmp-mpls-config {
        description
            "Grouping for MPLS ECMP options per protocol";
        leaf ftn-ecmp-protocol  {
            if-feature feature-list:HAVE_MPLS_ECMP;
            type  ipi-mpls-types:mpls_ecmp_protocol_t;
            description "Use this attribute to configure ECMP on forwarder for supported
                        protocol FTNs";
        } // END of ftn-ecmp-protocol definition.

        leaf ilm-ecmp-protocol  {
            if-feature feature-list:HAVE_MPLS_ECMP;
            type  ipi-mpls-types:mpls_ecmp_protocol_t;
            description "Use this attribute to configure ECMP on forwarder for supported
                        protocol ILMs";
        } // END of ilm-ecmp-protocol definition.

    } // END of ecmp-mpls-config definition.
    grouping nsm-client-graceful-restart-state {
        description
            "Operational parameters for rsvp/ldp graceful-restart";
        leaf graceful-restart-state  {
            type  ipi-mpls-types:mpls_graceful_restart_status_t;
            description "State of ldp/rsvp graceful restart";
        } // END of graceful-restart-state definition.

        leaf remaining-restart-time  {
            type  uint32;
            units "seconds";
            description "remaining ldp/rsvp graceful restart time";
        } // END of remaining-restart-time definition.

        leaf disconnected-time  {
            type  yang:date-and-time {
                pattern "\\d{4}-\\d{2}-\\d{2}T\\d{2}:\\d{2}:\\d{2}(\\.\\d+)?(Z|[\\+\\-]\\d{2}:\\d{2})";
                }
                description "ldp/rsvp disconnected time";
            } // END of disconnected-time definition.

    } // END of nsm-client-graceful-restart-state definition.
    grouping mpls-global-config {
        description
            "MPLS global configuration";
        leaf entropy-label-capability  {
            if-feature feature-list:HAVE_MARVELL;
            type  empty;
            description "Use this attribute to enable termination of entropy labeled packets";
        } // END of entropy-label-capability definition.

        leaf local-packet-handling  {
            type  empty;
            description "Use this attribute to enable the labeling of locally generated TCP
                        packets. All other locally generated packets are not looked at by the
                        MPLS Forwarder";
        } // END of local-packet-handling definition.

        leaf lsp-stitching  {
            type  empty;
            description "Use this attribute to enable lsp stitching for ILM and installed FTM";
        } // END of lsp-stitching definition.

        leaf propagate-ttl  {
            type  empty;
            description "Use this attribute to enable TTL propagation. Enabling TTL propagation
                        causes the TTL value in the IP header to be copied onto the TTL field
                        in the shim header, at the LSP ingress";
        } // END of propagate-ttl definition.

        leaf ingress-ttl-value  {
            type  uint8 {
                 range "0..255"  {
                    description "0..255: Supported range 0 - 255";
                 }
            }
            description "Use this attribute to set a Time to Live (TTL) value for LSPs for
                        which this LSR is the ingress.";
        } // END of ingress-ttl-value definition.

        leaf egress-ttl-value  {
            if-feature feature-list:NOT_HAVE_USER_HSL;
            type  uint8 {
                 range "0..255"  {
                    description "0..255: Supported range 0 - 255";
                 }
            }
            description "mpls egress-ttl . Use this attribute to set a custom Time to Live
                        (TTL) value for LSPs for which this LSR is the egress";
        } // END of egress-ttl-value definition.

        leaf lsp-model-uniform  {
            type  empty;
            description "Use this attribute to configure the MPLS LSP model as Uniform.";
        } // END of lsp-model-uniform definition.

        leaf lsp-encap-dscp-preserve  {
            if-feature feature-list:HAVE_DUNE;
            type  empty;
            description "Use this attribute to allow dscp update for IP packets encapsulated
                        into MPLS frame";
        } // END of lsp-encap-dscp-preserve definition.

        leaf propagate-exp-to-cos  {
            if-feature feature-list:HAVE_DNX;
            type  empty;
            description "Use this attribute to enable EXP propagation to exposed header after
                        PHP action. This will further inherit the information to update COS
                        value when network out interface (sub-interface or SVI) adds a vlan
                        header.";
        } // END of propagate-exp-to-cos definition.

        leaf l2vpn-nw-statistics  {
            if-feature feature-list:HAVE_DNX;
            if-feature feature-list:HAVE_MPLS_STATS;
            type  empty;
            description "Use this attribute to allow counting the network side L2VPN traffic
                        statistics at service level instead of counting them under transport.
                        In Qumran2 devices, since a single counting profile is used, L2VPN
                        traffic can be counted either at transport level or at service level
                        but not both. In order to support auto bandwidth feature in RSVP,
                        counting the traffic under transport is important. So, by default,
                        L2VPN traffic is counted under transport. This attribute provisions
                        the user to prefer network traffic statistics at L2VPN service level.";
        } // END of l2vpn-nw-statistics definition.

        leaf six-pe-dscp-preserve  {
            if-feature feature-list:HAVE_6PE;
            if-feature feature-list:HAVE_DUNE;
            type  ipi-mpls-types:mpls_dscp_preserve_state_t;
            description "Use this attribute to configure DSCP preserve enable or disable for
                        6PE services";
        } // END of six-pe-dscp-preserve definition.

        leaf suppress-oper-log-mpls  {
            type  ipi-mpls-types:mpls_services_t;
            description "Use this attribute to suppress oper logs for the MPLS services";
        } // END of suppress-oper-log-mpls definition.

        leaf l2vpn-stitching  {
            if-feature feature-list:HAVE_DUNE;
            if-feature feature-list:HAVE_L2VPN_STITCHING;
            type  empty;
            description "Use this attribute to enable L2VPN stitching";
        } // END of l2vpn-stitching definition.

    } // END of mpls-global-config definition.
    grouping mpls-debug-config {
        description
            "Grouping for MPLS Debug Level Configurations";
        leaf mpls-log-options  {
            type  cml-data-types:cml_nsm_mpls_log_t;
            description "Use this attribute to exercise logging control. This command interacts
                        with the Linux kernel. When using the kernel logging utility - klogd -
                        it needs to be enabled to a logging level that allows for the
                        requested log messages to be printed.";
        } // END of mpls-log-options definition.

    } // END of mpls-debug-config definition.
    grouping mpls-interface-label-switching-config {
        description
            "interface label switching configuration";
        leaf enable  {
            type  empty;
            mandatory true;
            description "Use this attribute to enable label-switching on a TE link";
        } // END of enable definition.

        leaf label-space  {
            type  uint16 {
                 range "0..60000"  {
                    description "0..60000: Supported range 0 - 60000";
                 }
            }
            description "Use this attribute to specify label-space for the interface, at
                        present only label space 0 is supported";
        } // END of label-space definition.

    } // END of mpls-interface-label-switching-config definition.
    grouping mpls-interface-bandwidth-config {
        description
            "MPLS Interface Bandwidth Configurations";
        leaf-list admin-group-name  {
            if-feature feature-list:HAVE_TE;
            type  leafref {
                path  "/ipi-global-te:admin-groups/ipi-global-te:admin-group/ipi-global-te:name";
            }
            description "Use this attribute to create an administrative group to be used for
                        links. Each link can be a member of one or more, or no administrative
                        groups.this attribute adds link between an interface and a group. The
                        name is the name of the group previously configured. There can be
                        multiple groups per interface.";
        } // END of admin-group-name definition.

        leaf-list admin-group-anomaly-name  {
            if-feature feature-list:HAVE_TE;
            type  leafref {
                path  "/ipi-global-te:admin-groups/ipi-global-te:admin-group/ipi-global-te:name";
            }
            description "Use this attribute to create an anomaly administrative group to be
                        advertised when measured link delay is anomalous. Each link can be a
                        member of one or more, or no administrative groups.this attribute adds
                        link between an interface and a group. The name is the name of the
                        group previously configured. There can be multiple groups per
                        interface.";
        } // END of admin-group-anomaly-name definition.

        leaf-list extended-admin-group-name  {
            if-feature feature-list:HAVE_TE;
            type  leafref {
                path  "/ipi-global-te:extended-admin-groups/ipi-global-te:extended-admin-group/ipi-global-te:name";
            }
            description "Use this attribute to create a regular extended administrative group
                        to be used for links. Each link can be a member of one or more, or no
                        extended administrative groups. This attribute adds link between an
                        interface and a group. The name is the name of the group previously
                        configured. There can be multiple groups per interface.";
        } // END of extended-admin-group-name definition.

        leaf-list extended-admin-group-anomaly-name  {
            if-feature feature-list:HAVE_TE;
            type  leafref {
                path  "/ipi-global-te:extended-admin-groups/ipi-global-te:extended-admin-group/ipi-global-te:name";
            }
            description "Use this attribute to create an anomaly extended administrative group
                        to be advertised when measured link delay is anomalous. Each link can
                        be a member of one or more, or no extended administrative groups. This
                        attribute adds link between an interface and a group. The name is the
                        name of the group previously configured. There can be multiple groups
                        per interface.";
        } // END of extended-admin-group-anomaly-name definition.

        leaf bandwidth  {
            if-feature feature-list:HAVE_TE;
            if-feature feature-list:NOT_IF_BANDWIDTH_INFO;
            type  string {
                length "1..1965";
                pattern "(([1-9]{1}[0-9]{0,2}[m|M|k|K]{1})|([1-9]{1}.[0-9]{1}[g|G|m|M|k|K]{1})|([1-9]{1}[0-9]{0,1}[g|G]{1})|(100[g|G]{1}))+";
            }
            description "Use this attribute to specify a discrete, maximum bandwidth value for
                        the interface. The bandwidth attribute takes input ranges from 1 to
                        999 kbps, 1 to 999 mbps and 1 to 999 gbps.";
        } // END of bandwidth definition.

        leaf reservable-bandwidth  {
            // when " not(/ipi-interface:interfaces/ipi-interface:interface/ipi-interface:config/ipi-interface:enable-switchport) ";
            if-feature feature-list:HAVE_TE;
            type  string {
                length "1..1965";
                pattern "(([1-9]{1}[0-9]{0,2}[m|M|k|K]{1})|([1-9]{1}.[0-9]{1}[g|G|m|M|k|K]{1})|([1-9]{1}[0-9]{0,1}[g|G]{1})|(100[g|G]{1}))+";
            }
            description "Use this attribute to specify the maximum reservable bandwidth per
                        interface. This value can be equal or smaller value than
                        max-bandwidth. Attribute takes input from 1 to 999 kbps, 1 to 999 mbps
                        and 1 to 999 gbps";
        } // END of reservable-bandwidth definition.

        leaf-list shared-risk-link-group  {
            if-feature feature-list:HAVE_SRLG;
            type  uint32 {
                 range "1..4294967295"  {
                    description "1..4294967295: Supported range 1 - 4294967295";
                 }
            }
            description "Use this attribute to add the link to a srlg group";
        } // END of shared-risk-link-group definition.

        leaf uni-available-bandwidth  {
            if-feature feature-list:HAVE_TE;
            if-feature feature-list:NOT_IF_BANDWIDTH_INFO;
            type  string {
                length "1..1965";
                pattern "(([0-9]{1,3}[m|M|k|K]{1})|([0-9]{1}.[0-9]{1}[g|G|m|M|k|K]{1})|([0-9]{1,2}[g|G]{1})|(100[g|G]{1}))+";
            }
            description "Use this attribute to specify a unidirectional, available bandwidth
                        value for the interface. The bandwidth attribute takes input in 0-999
                        kbps, 0-999 mbps and 0-100 gbps.";
        } // END of uni-available-bandwidth definition.

        leaf uni-residual-bandwidth  {
            if-feature feature-list:HAVE_TE;
            if-feature feature-list:NOT_IF_BANDWIDTH_INFO;
            type  string {
                length "1..1965";
                pattern "(([0-9]{1,3}[m|M|k|K]{1})|([0-9]{1}.[0-9]{1}[g|G|m|M|k|K]{1})|([0-9]{1,2}[g|G]{1})|(100[g|G]{1}))+";
            }
            description "Use this attribute to specify a unidirectional, residual  bandwidth
                        value for the interface. The bandwidth attribute takes input in 0-999
                        kbps, 0-999 mbps and 0-100 gbps.";
        } // END of uni-residual-bandwidth definition.

        leaf uni-utilized-bandwidth  {
            if-feature feature-list:HAVE_TE;
            if-feature feature-list:NOT_IF_BANDWIDTH_INFO;
            type  string {
                length "1..1965";
                pattern "(([0-9]{1,3}[m|M|k|K]{1})|([0-9]{1}.[0-9]{1}[g|G|m|M|k|K]{1})|([0-9]{1,2}[g|G]{1})|(100[g|G]{1}))+";
            }
            description "Use this attribute to specify a unidirectional, utilised bandwidth
                        value for the interface. The bandwidth attribute takes input in 0 to
                        999 kbps, 0 to 999 mbps and 1 to 100gbps.";
        } // END of uni-utilized-bandwidth definition.

    } // END of mpls-interface-bandwidth-config definition.
    grouping mpls-bandwidth-class-config {
        description
            "MPLS Bandwidth Class Configurations";
        leaf name  {
            type  string {
                length "1..1965";
                pattern "[^?' =,>|]+";
            }
            description "Use this attribute to create a new bandwidth class name. Using this
                        command changes the command mode to Bandwidth-class mode";
        } // END of name definition.

    } // END of mpls-bandwidth-class-config definition.
    grouping mpls-bandwidth-properties-config {
        description
            "MPLS Bandwidth Class without DSTE Configurations";
        leaf max-bandwidth  {
            type  string {
                length "1..1965";
                pattern "[^?' =,>|]+";
            }
            mandatory true;
            description "Use this attribute to specify a discrete, maximum bandwidth value for
                        the interface. The bandwidth attribute takes input ranges from 1 to
                        999 kbps, 1 to 999 mbps and 1 to 999 gbps.";
        } // END of max-bandwidth definition.

        leaf setup-priority  {
            type  uint8 {
                 range "0..7"  {
                    description "0..7: Supported range 0 - 7";
                 }
            }
            mandatory true;
            description "Use this attribute to specify the maximum bandwidth to be used for a
                        bandwidth-class. The bandwidth value is in bits";
        } // END of setup-priority definition.

        leaf hold-priority  {
            type  uint8 {
                 range "0..7"  {
                    description "0..7: Supported range 0 - 7";
                 }
            }
            mandatory true;
            description "Use this attribute to specify the maximum bandwidth to be used for a
                        bandwidth-class. The bandwidth value is in bits";
        } // END of hold-priority definition.

    } // END of mpls-bandwidth-properties-config definition.
    grouping label-space-config {
        description
            "Label space configuration";
        leaf label-space-name  {
            type  uint16 {
                 range "0..60000"  {
                    description "0..60000: Supported range 0 - 60000";
                 }
            }
            description "This attribute identifies the label space";
        } // END of label-space-name definition.

    } // END of label-space-config definition.
    grouping label-range-config {
        description
            "Label Range configuration";
        leaf min-label  {
            type  uint32 {
                 range "16..1048575"  {
                    description "16..1048575: Supported range 16 - 1048575";
                 }
            }
            mandatory true;
            description "Use this attribute to configure a minimum label value for a label
                        space. After setting a minimum label value for a label space, make
                        sure to bind the label space to an interface.";
        } // END of min-label definition.

        leaf max-label  {
            type  uint32 {
                 range "16..1048575"  {
                    description "16..1048575: Supported range 16 - 1048575";
                 }
            }
            mandatory true;
            description "Use this attribute to configure a maximum label value for a label
                        space. After setting a maximum label value for a label space, make
                        sure to bind the label space to an interface";
        } // END of max-label definition.

    } // END of label-range-config definition.
    grouping module-label-range-config {
        description
            "Module Label Range configurations";
        leaf module-name  {
            type  ipi-mpls-types:mpls_module_t;
            description "Use this attribute to specify the protocol module for which label
                        range is specified";
        } // END of module-name definition.

        uses label-range-config;
    } // END of module-label-range-config definition.
    grouping mpls-supported-diffserv-classes-config {
        description
            "Supported MPLS diffServe class configuration";
        leaf supported-class-name  {
            type  string {
                length "1..1965";
                pattern "[^?' =,>|]+";
            }
            description "Use this attribute to configure a DiffServ class.";
        } // END of supported-class-name definition.

    } // END of mpls-supported-diffserv-classes-config definition.
    grouping mpls-class-exp-bit-config {
        description
            "Grouping for MPLS diffServe class to expbit mapping parameters";
        leaf supported-class-name  {
            type  string {
                length "1..1965";
                pattern "[^?' =,>|]+";
            }
            description "Use this attribute to configure a DiffServ class.";
        } // END of supported-class-name definition.

        leaf exp-bit  {
            type  uint8 {
                 range "0..7"  {
                    description "0..7: Supported range 0 - 7";
                 }
            }
            description "EXP bit to map to the supported class.";
        } // END of exp-bit definition.

    } // END of mpls-class-exp-bit-config definition.
    grouping l2vpn-customer-service-map-state {
        description
            "Grouping for Operational attributes for service-template mapping list";
        leaf vpls-name  {
            type  string {
                length "1..1965";
                pattern "[^?' =,>|]+";
            }
            description "Use this attribute to retrieve confgiured VPLS instance details";
        } // END of vpls-name definition.

        leaf error-status  {
            type  ipi-mpls-types:mpls_l2vpn_serv_temp_error_status_t;
            description "Use this attribute to retrieve error status";
        } // END of error-status definition.

        leaf binding-interface-name  {
            type  string {
                length "1..1965";
                pattern "[^?' =,>|]+";
            }
            description "Use this attribute to retrieve binded interface details for a
                        confgiured VPLS instance";
        } // END of binding-interface-name definition.

    } // END of l2vpn-customer-service-map-state definition.
    grouping l2vpn-access-circuit-group-config {
        description
            "Grouping for Configuration attributes for access-circuit-group";
        leaf group-name  {
            type  string {
                length "1..32";
                pattern "[^?' =,>|]+";
            }
            description "Use this attribute to create a new access circuit group for MPLS";
        } // END of group-name definition.

        leaf group-identifier  {
            type  uint32 {
                 range "1..4294967295"  {
                    description "1..4294967295: Supported range 1 - 4294967295";
                 }
            }
            mandatory true;
            description "Specify group identifier for access circuit group";
        } // END of group-identifier definition.

    } // END of l2vpn-access-circuit-group-config definition.
    grouping l2vpn-access-circuit-group-top {
        description
            "Top level Grouping for access-circuit-group";
        container access-circuit-groups {
            description
                "Container for config data for access-circuit-groups";

            list access-circuit-group {
                if-feature feature-list:HAVE_MPLS_VC;
                key "group-name";
                unique "config/group-identifier";
                description
                    "List for config data for access-circuit-group";
                leaf group-name  {
                    type  leafref {
                        path  "../config/group-name";
                    }
                    description "Use this attribute to create a new access circuit group for MPLS";
                } // END of group-name definition.

                container config {
                    description
                        "Configuration container for access circuit group";
                    uses l2vpn-access-circuit-group-config;
                } // END of config-container definition.
                container state {
                    config false;
                    description
                        "Container for Operationa attributes for access circuit group";
                    uses l2vpn-access-circuit-group-config;
                } // END of state-container definition.
            } // End of access-circuit-group-list
        } // END of access-circuit-groups-container definition.
    } // END of l2vpn-access-circuit-group-top definition.
    grouping customer-service-map-top {
        description
            "Grouping for Operational attributes for service-template mapping";

        list map-list {
            if-feature feature-list:HAVE_VPLS;
            key "vpls-name";
            config false;
            description
                "List for Operational data for Customer Service mapping";
            leaf vpls-name  {
                type  leafref {
                    path  "../state/vpls-name";
                }
                description "Use this attribute to retrieve confgiured VPLS instance details";
            } // END of vpls-name definition.

            container state {
                config false;
                description
                    "Operation state data for map-list";
                uses l2vpn-customer-service-map-state;
            } // END of state-container definition.
        } // End of map-list-list
    } // END of customer-service-map-top definition.
    grouping customer-service-template-config {
        description
            "Configuration attributes for customer-service-template";
        leaf name  {
            type  string {
                length "1..32";
                pattern "[a-zA-Z0-9_-]*";
            }
            description "Specify service template name";
        } // END of name definition.

        leaf match-all  {
            // when " !ipi-mpls:mpls/l2vpn/customer-service-templates/customer-service-template/config/match-single-tag-outer-vlan-range + !ipi-mpls:mpls/l2vpn/customer-service-templates/customer-service-template/config/match-untagged + not(/ipi-mpls:mpls/ipi-mpls:l2vpn/ipi-mpls:customer-service-templates/ipi-mpls:customer-service-template/ipi-mpls:double-tags/ipi-mpls:double-tag/ipi-mpls:match-outer-vlan-id) ";
            type  empty;
            description "Use this attribute to specify match criteria as match all";
        } // END of match-all definition.

        leaf-list match-single-tag-outer-vlan-range  {
            // when " !ipi-mpls:mpls/l2vpn/customer-service-templates/customer-service-template/config/match-all ";
            type  string {
                length "1..4094";
                pattern "[^?' =,>]+";
            }
            description "Use this attribute to set match type with outer vlan value";
        } // END of match-single-tag-outer-vlan-range definition.

        leaf match-untagged  {
            // when " !ipi-mpls:mpls/l2vpn/customer-service-templates/customer-service-template/config/match-all ";
            type  empty;
            description "Use this attribute to specify match criteria as match untagged";
        } // END of match-untagged definition.

    } // END of customer-service-template-config definition.
    grouping customer-service-template-double-tag-top {
        description
            "Top level groupig for customer-service-template double-tag attributes";
        container double-tags {
            description
                "Configuration for double-tags configurations";

            list double-tag {
            // when " not(/ipi-mpls:mpls/ipi-mpls:l2vpn/ipi-mpls:customer-service-templates/ipi-mpls:customer-service-template/ipi-mpls:config/ipi-mpls:match-all) ";
                key "match-outer-vlan-id";
                description
                    "Configuration for double-tag configuration";
                leaf match-outer-vlan-id  {
                    type  leafref {
                        path  "../config/match-outer-vlan-id";
                    }
                    description "Specify outer vlan id for match double tag";
                } // END of match-outer-vlan-id definition.

                container config {
                    description
                        "Configuration container for double-tag configurations";
                    uses customer-service-template-double-tag-config;
                } // END of config-container definition.
                container state {
                    config false;
                    description
                        "Container for Operationa attributes for double-tag";
                    uses customer-service-template-double-tag-config;
                } // END of state-container definition.
            } // End of double-tag-list
        } // END of double-tags-container definition.
    } // END of customer-service-template-double-tag-top definition.
    grouping customer-service-template-double-tag-config {
        description
            "Grouping for double-tag attributes";
        leaf match-outer-vlan-id  {
            type  uint16 {
                 range "1..4094"  {
                    description "1..4094: Supported range 1 - 4094";
                 }
            }
            description "Specify outer vlan id for match double tag";
        } // END of match-outer-vlan-id definition.

        leaf-list match-inner-vlan-id  {
            type  string {
                length "1..1965";
                pattern "[^?' =,>]+";
            }
            description "Specify inner vlan VID or range(VLAN ID 1-4094 or range: 2-5) for
                        match double tag";
        } // END of match-inner-vlan-id definition.

    } // END of customer-service-template-double-tag-config definition.
    grouping customer-service-template-action-type-top {
        description
            "Top level groupig for customer-service-template action-type attributes";
        container action-types {
            description
                "Container for action-types configurations";

            list action-type {
                key "vlan-action-type";
                description
                    "Configuration for action-type configuration";
                leaf vlan-action-type  {
                    type  leafref {
                        path  "../config/vlan-action-type";
                    }
                    description "Specify rewrite ingress action type";
                } // END of vlan-action-type definition.

                container config {
                    description
                        "Configuration container for action-type configurations";
                    uses customer-service-template-action-type-config;
                } // END of config-container definition.
                container state {
                    config false;
                    description
                        "Container for Operationa attributes for action-type";
                    uses customer-service-template-action-type-config;
                } // END of state-container definition.
            } // End of action-type-list
        } // END of action-types-container definition.
    } // END of customer-service-template-action-type-top definition.
    grouping customer-service-template-action-type-config {
        description
            "Grouping for action-type attributes";
        leaf vlan-action-type  {
            type  ipi-mpls-types:mpls_l2vpn_vlan_action_type_t;
            description "Specify rewrite ingress action type";
        } // END of vlan-action-type definition.

        leaf outer-vlan-identifier  {
            // when " ipi-mpls:mpls/l2vpn/customer-service-templates/customer-service-template/action-types/action-type/config/vlan-action-type != '1' ";
            type  uint16 {
                 range "1..4094"  {
                    description "1..4094: Supported range 1 - 4094";
                 }
            }
            description "Spefiy vlan identifier for action types push and translate`";
        } // END of outer-vlan-identifier definition.

        leaf tag-protocol-identifier  {
            // when " ipi-mpls:mpls/l2vpn/customer-service-templates/customer-service-template/action-types/action-type/config/vlan-action-type != '2' ";
            type  ipi-mpls-types:mpls_svc_tpid_t;
            default "dot1.q";
            description "Specify tag protocol identofier for action types pop and translate";
        } // END of tag-protocol-identifier definition.

    } // END of customer-service-template-action-type-config definition.
    grouping l2vpn-service-template-top {
        description
            "Top level Grouping for service template";
        container customer-service-templates {
            description
                "Enclosing container for Customer Service Templates";

            list customer-service-template {
                if-feature feature-list:HAVE_VPLS_OR_HAVE_MPLS_VC;
                key "name";
                description
                    "List of Customer Service Templates";
                leaf name  {
                    type  leafref {
                        path  "../config/name";
                    }
                    description "Specify service template name";
                } // END of name definition.

                container config {
                    description
                        "Configuration container for Service-template configurations";
                    uses customer-service-template-config;
                } // END of config-container definition.
                container state {
                    config false;
                    description
                        "Container for Operationa attributes for Service-template";
                    uses customer-service-template-config;
                } // END of state-container definition.
                uses customer-service-template-double-tag-top;
                uses customer-service-template-action-type-top;
                uses customer-service-map-top;
            } // End of customer-service-template-list
        } // END of customer-service-templates-container definition.
    } // END of l2vpn-service-template-top definition.
    grouping mpls-counters-state {
        description
            "Grouping for MPLS counters attributes";
        leaf label-entries  {
            type  yang:counter32;
            config false;
            description "Total MPLS label entries in the ILM table";
        } // END of label-entries definition.

    } // END of mpls-counters-state definition.
    grouping mpls-counters-top {
        description
            "Top grouping for MPLS counters";
        container counters {
            config false;
            description
                "Container for the MPLS counters";
            uses mpls-counters-state;
        } // END of counters-container definition.
    } // END of mpls-counters-top definition.

    grouping  mpls-grouping {
    description
        "Top level container for MPLS, including configuration and state data";
    container mpls {
        if-feature feature-list:HAVE_MPLS;
        description
            "Top level container for MPLS, including configuration and state data";
        container l2vpn {
            description
                "Top Level container for l2vpn objects";
            uses l2vpn-service-template-top;
            uses l2vpn-access-circuit-group-top;
        } // END of l2vpn-container definition.
        container global {
            description
                "MPLS global configuration";
            container config {
                description
                    "MPLS global configuration";
                uses mpls-global-config;
            } // END of config-container definition.
            container state {
                config false;
                description
                    "Global MPLS Operational state data";
                uses mpls-global-config;
                uses mpls-counters-top;
            } // END of state-container definition.
            container graceful-restart {
                if-feature feature-list:HAVE_RESTART;
                config false;
                description
                    "Graceful restart clients";
                container rsvp {
                    config false;
                    description
                        "Name of the graceful-restart client";
                    container state {
                        config false;
                        description
                            "State of the graceful-restart client";
                        uses nsm-client-graceful-restart-state;
                    } // END of state-container definition.
                } // END of rsvp-container definition.
                container ldp {
                    config false;
                    description
                        "Name of the graceful-restart client";
                    container state {
                        config false;
                        description
                            "State of the graceful-restart client";
                        uses nsm-client-graceful-restart-state;
                    } // END of state-container definition.
                } // END of ldp-container definition.
            } // END of graceful-restart-container definition.
        } // END of global-container definition.
        container interfaces {
            description
                "mpls interface level configuration and state data";

            list interface {
                key "name";
                description
                    "List of MPLS enabled interfaces on the device.";
                leaf name  {
                    type  leafref {
                        path  "../config/name";
                    }
                    description "The textual name of the interface.";
                } // END of name definition.

                container config {
                    description
                        "Interface configuration";
                    uses mpls-interface-config;
                } // END of config-container definition.
                container state {
                    config false;
                    description
                        "Operational state data for MPLS interface";
                    uses mpls-interface-config;
                } // END of state-container definition.
                container label-switching {
                    // when " not(/ipi-interface:interfaces/ipi-interface:interface/ipi-interface:config/ipi-interface:enable-switchport) ";
                    description
                        "Label switching configuration";
                    container config {
                        presence "Enable label switching for interface";
                        description
                            "Label switching configuration";
                        uses mpls-interface-label-switching-config;
                    } // END of config-container definition.
                    container state {
                        config false;
                        description
                            "Operational state for Label switching configuration";
                        uses mpls-interface-label-switching-config;
                    } // END of state-container definition.
                } // END of label-switching-container definition.
                container mpls-interface-bandwidth {
                    // when " not(/ipi-interface:interfaces/ipi-interface:interface/ipi-interface:config/ipi-interface:enable-switchport) ";
                    description
                        "MPLS Interface Bandwidth Configurations";
                    container config {
                        description
                            "Configurations for MPLS Interface Bandwidth";
                        uses mpls-interface-bandwidth-config;
                    } // END of config-container definition.
                    container state {
                        config false;
                        description
                            "Operational state for MPLS Interface Bandwidth";
                        uses mpls-interface-bandwidth-config;
                    } // END of state-container definition.
                } // END of mpls-interface-bandwidth-container definition.
            } // End of interface-list
        } // END of interfaces-container definition.
        container label-spaces {
            description
                "MPLS Label-Spaces Configurations";

            list label-space {
                key "label-space-name";
                description
                    "MPLS Label-Space Configurations";
                leaf label-space-name  {
                    type  leafref {
                        path  "../config/label-space-name";
                    }
                    description "This attribute identifies the label space";
                } // END of label-space-name definition.

                container config {
                    description
                        "Config container for MPLS Label Space Configurations";
                    uses label-space-config;
                } // END of config-container definition.
                container state {
                    config false;
                    description
                        "Operational state container for MPLS Label Space";
                    uses label-space-config;
                } // END of state-container definition.
                container global-label-range {
                    description
                        "MPLS Global Label Range Configurations";
                    container config {
                        presence "Global Label Range is configured for the label space";
                        description
                            "Config Container for MPLS Global Label Range Configurations";
                        uses label-range-config;
                    } // END of config-container definition.
                    container state {
                        config false;
                        description
                            "Operational state container for MPLS Global Label Range";
                        uses label-range-config;
                    } // END of state-container definition.
                } // END of global-label-range-container definition.
                container module-label-ranges {
                    description
                        "MPLS Module Labels Range Configurations";

                    list module-label-range {
                        key "module-name";
                        description
                            "MPLS Module Label Range Configurations";
                        leaf module-name  {
                            type  leafref {
                                path  "../config/module-name";
                            }
                            description "Use this attribute to specify the protocol module for which label
                                        range is specified";
                        } // END of module-name definition.

                        container config {
                            description
                                "Config container for MPLS Module Label Range configuration";
                            uses module-label-range-config;
                        } // END of config-container definition.
                        container state {
                            config false;
                            description
                                "Operational state data for MPLS Module Label Range";
                            uses module-label-range-config;
                        } // END of state-container definition.
                    } // End of module-label-range-list
                } // END of module-label-ranges-container definition.
            } // End of label-space-list
        } // END of label-spaces-container definition.
        container debug {
            if-feature feature-list:HAVE_MPLS_FWD;
            description
                "mpls debug level configuration and state data";
            container config {
                description
                    "mpls debug level configuration";
                uses mpls-debug-config;
            } // END of config-container definition.
            container state {
                config false;
                description
                    "Operational state data for MPLS Debug";
                uses mpls-debug-config;
            } // END of state-container definition.
        } // END of debug-container definition.
        container ecmp {
            description
                "Container for FTN and ILM ECMP configuration per protocol";
            container config {
                description
                    "MPLS ECMP configuration";
                uses ecmp-mpls-config;
            } // END of config-container definition.
            container state {
                config false;
                description
                    "Operational state data for MPLS ECMP";
                uses ecmp-mpls-config;
            } // END of state-container definition.
        } // END of ecmp-container definition.
        container six-pe-tunnel-policies {
            if-feature feature-list:HAVE_SERVICE_MAPPING;
            if-feature feature-list:HAVE_6PE;
            description
                "6PE tunnel policy configuration and state data";

            list six-pe-tunnel-policy {
                key "name";
                max-elements 1;
                description
                    "List of tunnel policies";
                leaf name  {
                    type  leafref {
                        path  "../config/name";
                    }
                    description "Name for the tunnel policy";
                } // END of name definition.

                container config {
                    description
                        "configuration for tunnel selection policy";
                    uses mpls-6pe-tunnel-policy;
                } // END of config-container definition.
                container state {
                    config false;
                    description
                        "state data for 6PE tunnel policy";
                    uses mpls-6pe-tunnel-policy;
                } // END of state-container definition.
            } // End of six-pe-tunnel-policy-list
        } // END of six-pe-tunnel-policies-container definition.
        container bandwidth-classes {
            description
                "MPLS Bandwidth Classes Configurations";

            list bandwidth-class {
                if-feature feature-list:HAVE_TE;
                key "name";
                description
                    "MPLS Bandwidth Class Configurations";
                leaf name  {
                    type  leafref {
                        path  "../config/name";
                    }
                    description "Use this attribute to create a new bandwidth class name. Using this
                                command changes the command mode to Bandwidth-class mode";
                } // END of name definition.

                container config {
                    description
                        "Config Container for MPLS Bandwidth Class Configurations";
                    uses mpls-bandwidth-class-config;
                } // END of config-container definition.
                container state {
                    config false;
                    description
                        "State Contatiner for MPLS Bandwidth Class Configurations";
                    uses mpls-bandwidth-class-config;
                } // END of state-container definition.
                container properties {
                    description
                        "Properties for Bandwidth Class with no DSTE";
                    container config {
                        presence "To configure BC without DSTE";
                        description
                            "Config Container for Bandwidth Class without DSTE";
                        uses mpls-bandwidth-properties-config;
                    } // END of config-container definition.
                    container state {
                        config false;
                        description
                            "State Container for MPLS Bandwidth Class Without DSTE Configurations";
                        uses mpls-bandwidth-properties-config;
                    } // END of state-container definition.
                } // END of properties-container definition.
            } // End of bandwidth-class-list
        } // END of bandwidth-classes-container definition.
    } // END of mpls-container definition.
    } // END of mpls-grouping definition.

    uses mpls-grouping;

}
