/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-enhanced-pbr-types.yang
*
*/

module ipi-enhanced-pbr-types {

    yang-version 1.1;

    namespace   "http://www.ipinfusion.com/yang/ocnos/ipi-enhanced-pbr-types";

    prefix "ipi-enhanced-pbr-types";

    organization
        "IP Infusion Inc.";

    contact
        "Address: 3965 Freedom Circle, Suite 200, Santa Clara, CA 95054
         Phone: +1 408-400-1900
         E-mail: support@ipinfusion.com
         Web: http://www.ipinfusion.com/";

    description
        "Enhanced PBR (ePBR)";


    revision "2023-02-28" {
        description "Initial Version";
        reference " 0.1.0.";
    }



    typedef  epbr_class_map_t {
        type enumeration {
            enum traffic {
                value 1;
                description "traffic is ingress class-map";
            }
        }
        description "type definition for EPBR_CLASS_MAP_T";
    }

    typedef  epbr_match_criteria_t {
        type enumeration {
            enum match-all {
                value 1;
                description "match all";
            }
        }
        description "type definition for EPBR_MATCH_CRITERIA_T";
    }

    typedef  epbr_policy_map_t {
        type enumeration {
            enum pbr {
                value 1;
                description "pbr is ingress policy-map";
            }
        }
        description "type definition for EPBR_POLICY_MAP_T";
    }

    typedef  epbr_rate_unit_t {
        type enumeration {
            enum bps {
                value 1;
                description "Specifies the unit in bits per second";
            }
            enum pps {
                value 2;
                description "Specifies the unit in packets per second";
            }
        }
        description "type definition for EPBR_RATE_UNIT_T";
    }

    typedef  epbr_fragment_type_t {
        type enumeration {
            enum df {
                value 1;
                description "Set DF bit";
            }
            enum isf {
                value 2;
                description "Set ISF bit";
            }
            enum ff {
                value 4;
                description "Set FF bit";
            }
            enum lf {
                value 8;
                description "Set LF bit";
            }
            enum lf-ff-isf {
                value 14;
                description "Set LF-FF-ISF bits";
            }
        }
        description "type definition for EPBR_FRAGMENT_TYPE_T";
    }

    typedef  epbr_vrf_rt_t {
        type string {
            pattern ".*:.*";
        }
        description "type definition for EPBR_VRF_RT_T";
    }

    typedef  epbr_hex_dscp_t {
        type enumeration {
            enum 00 {
                value 0;
                description "Set value in hexadecimal";
            }
            enum 01 {
                value 1;
                description "Set value in hexadecimal";
            }
            enum 02 {
                value 2;
                description "Set value in hexadecimal";
            }
            enum 03 {
                value 3;
                description "Set value in hexadecimal";
            }
            enum 04 {
                value 4;
                description "Set value in hexadecimal";
            }
            enum 05 {
                value 5;
                description "Set value in hexadecimal";
            }
            enum 06 {
                value 6;
                description "Set value in hexadecimal";
            }
            enum 07 {
                value 7;
                description "Set value in hexadecimal";
            }
            enum 08 {
                value 8;
                description "Set value in hexadecimal";
            }
            enum 09 {
                value 9;
                description "Set value in hexadecimal";
            }
            enum 0a {
                value 10;
                description "Set value in hexadecimal";
            }
            enum 0b {
                value 11;
                description "Set value in hexadecimal";
            }
            enum 0c {
                value 12;
                description "Set value in hexadecimal";
            }
            enum 0d {
                value 13;
                description "Set value in hexadecimal";
            }
            enum 0e {
                value 14;
                description "Set value in hexadecimal";
            }
            enum 0f {
                value 15;
                description "Set value in hexadecimal";
            }
            enum 10 {
                value 16;
                description "Set value in hexadecimal";
            }
            enum 11 {
                value 17;
                description "Set value in hexadecimal";
            }
            enum 12 {
                value 18;
                description "Set value in hexadecimal";
            }
            enum 13 {
                value 19;
                description "Set value in hexadecimal";
            }
            enum 14 {
                value 20;
                description "Set value in hexadecimal";
            }
            enum 15 {
                value 21;
                description "Set value in hexadecimal";
            }
            enum 16 {
                value 22;
                description "Set value in hexadecimal";
            }
            enum 17 {
                value 23;
                description "Set value in hexadecimal";
            }
            enum 18 {
                value 24;
                description "Set value in hexadecimal";
            }
            enum 19 {
                value 25;
                description "Set value in hexadecimal";
            }
            enum 1a {
                value 26;
                description "Set value in hexadecimal";
            }
            enum 1b {
                value 27;
                description "Set value in hexadecimal";
            }
            enum 1c {
                value 28;
                description "Set value in hexadecimal";
            }
            enum 1d {
                value 29;
                description "Set value in hexadecimal";
            }
            enum 1e {
                value 30;
                description "Set value in hexadecimal";
            }
            enum 1f {
                value 31;
                description "Set value in hexadecimal";
            }
            enum 20 {
                value 32;
                description "Set value in hexadecimal";
            }
            enum 21 {
                value 33;
                description "Set value in hexadecimal";
            }
            enum 22 {
                value 34;
                description "Set value in hexadecimal";
            }
            enum 23 {
                value 35;
                description "Set value in hexadecimal";
            }
            enum 24 {
                value 36;
                description "Set value in hexadecimal";
            }
            enum 25 {
                value 37;
                description "Set value in hexadecimal";
            }
            enum 26 {
                value 38;
                description "Set value in hexadecimal";
            }
            enum 27 {
                value 39;
                description "Set value in hexadecimal";
            }
            enum 28 {
                value 40;
                description "Set value in hexadecimal";
            }
            enum 29 {
                value 41;
                description "Set value in hexadecimal";
            }
            enum 2a {
                value 42;
                description "Set value in hexadecimal";
            }
            enum 2b {
                value 43;
                description "Set value in hexadecimal";
            }
            enum 2c {
                value 44;
                description "Set value in hexadecimal";
            }
            enum 2d {
                value 45;
                description "Set value in hexadecimal";
            }
            enum 2e {
                value 46;
                description "Set value in hexadecimal";
            }
            enum 2f {
                value 47;
                description "Set value in hexadecimal";
            }
            enum 30 {
                value 48;
                description "Set value in hexadecimal";
            }
            enum 31 {
                value 49;
                description "Set value in hexadecimal";
            }
            enum 32 {
                value 50;
                description "Set value in hexadecimal";
            }
            enum 33 {
                value 51;
                description "Set value in hexadecimal";
            }
            enum 34 {
                value 52;
                description "Set value in hexadecimal";
            }
            enum 35 {
                value 53;
                description "Set value in hexadecimal";
            }
            enum 36 {
                value 54;
                description "Set value in hexadecimal";
            }
            enum 37 {
                value 55;
                description "Set value in hexadecimal";
            }
            enum 38 {
                value 56;
                description "Set value in hexadecimal";
            }
            enum 39 {
                value 57;
                description "Set value in hexadecimal";
            }
            enum 3a {
                value 58;
                description "Set value in hexadecimal";
            }
            enum 3b {
                value 59;
                description "Set value in hexadecimal";
            }
            enum 3c {
                value 60;
                description "Set value in hexadecimal";
            }
            enum 3d {
                value 61;
                description "Set value in hexadecimal";
            }
            enum 3e {
                value 62;
                description "Set value in hexadecimal";
            }
            enum 3f {
                value 63;
                description "Set value in hexadecimal";
            }
        }
        description "type definition for EPBR_HEX_DSCP_T";
    }

}
