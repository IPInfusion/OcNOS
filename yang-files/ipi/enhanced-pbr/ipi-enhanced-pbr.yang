/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-enhanced-pbr.yang
*
*/

module ipi-enhanced-pbr {

    yang-version 1.1;

    namespace   "http://www.ipinfusion.com/yang/ocnos/ipi-enhanced-pbr";

    prefix "ipi-enhanced-pbr";

    import cml-data-types {
        prefix cml-data-types;
        revision-date 2026-05-15;
    }

    import ipi-enhanced-pbr-types {
        prefix ipi-enhanced-pbr-types;
        revision-date 2023-02-28;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Enhanced PBR (ePBR)";


    revision "2025-03-03" {
        description "Changed the class-map and policy-map name length from 32 to 64";
        reference " 0.1.6.";
    }

    revision "2024-02-08" {
        description "Updated xpath for enclosing container";
        reference " 0.1.5.";
    }

    revision "2023-11-09" {
        description "fix wrongly generated cli with suppress-cli and drop-attr-name cli flags";
        reference " 0.1.4.";
    }

    revision "2023-03-30" {
        description "remove default rate for police rate";
        reference " 0.1.3.";
    }

    revision "2023-03-12" {
        description "packet-length attribute corrections";
        reference " 0.1.2.";
    }

    revision "2023-03-08" {
        description "db-sync issue corrections";
        reference " 0.1.1.";
    }

    revision "2023-02-28" {
        description "Initial Version";
        reference " 0.1.0.";
    }

    grouping epbr-class-map-default-top {
        description
            "Grouping for EPBR class-map-default";
        container class-maps-default {
            config false;
            description
                "State data for EPBR class-map-default";

            list class-map-default {
                key "name";
                config false;
                description
                    "State data list for EPBR class-map-default";
                leaf name  {
                    type  leafref {
                        path  "../state/name";
                    }
                    description "Use this attribute to show the class-map-default name";
                } // END of name definition.

                container state {
                    config false;
                    description
                        "Operational state data for EPBR class-map-default";
                    uses epbr-class-map-default-state;
                } // END of state-container definition.
            } // End of class-map-default-list
        } // END of class-maps-default-container definition.
    } // END of epbr-class-map-default-top definition.
    grouping epbr-class-map-default-state {
        description
            "Grouping for EPBR class-default match state";
        leaf name  {
            type  string {
                length "1..1965";
                pattern "[^?' =,>|]+";
            }
            description "Use this attribute to show the class-map-default name";
        } // END of name definition.

        leaf type  {
            type  ipi-enhanced-pbr-types:epbr_class_map_t;
            description "Use this attribute to show the class-map-default type.";
        } // END of type definition.

        leaf match-criteria  {
            type  ipi-enhanced-pbr-types:epbr_match_criteria_t;
            description "Use this attribute to show the class-map-default match-criteria.";
        } // END of match-criteria definition.

    } // END of epbr-class-map-default-state definition.
    grouping epbr-class-map-config {
        description
            "Grouping for EPBR class-map config";
        leaf name  {
            type  string {
                length "1..64";
                pattern "[^?' =,>|]+";
            }
            description "Use this attribute to set the class-map name";
        } // END of name definition.

        leaf class-type  {
            type  ipi-enhanced-pbr-types:epbr_class_map_t;
            description "Use this attribute to set the class-map type.";
        } // END of class-type definition.

        leaf match-criteria  {
            type  ipi-enhanced-pbr-types:epbr_match_criteria_t;
            mandatory true;
            description "Use this attribute to set the class-map match-criteria.";
        } // END of match-criteria definition.

        leaf reference-description  {
            type  cml-data-types:cml_line_t {
                length "1..64";
            }
            description "This attribute configures reference description message on class-map
                        profile for QoS type.";
        } // END of reference-description definition.

    } // END of epbr-class-map-config definition.
    grouping epbr-class-map-match-filters-config {
        description
            "Grouping for EPBR class-map match filters config";
        leaf protocol  {
            type  cml-data-types:cml_range_t;
            description "Use this attribute to specify IP protocol";
        } // END of protocol definition.

        leaf port  {
            type  cml-data-types:cml_range_t;
            description "Use this attribute to specify TCP/UDP port number";
        } // END of port definition.

        leaf destination-port  {
            type  cml-data-types:cml_range_t;
            description "Use this attribute to specify TCP/UDP destination port number";
        } // END of destination-port definition.

        leaf source-port  {
            type  cml-data-types:cml_range_t;
            description "Use this attribute to specify TCP/UDP source port number";
        } // END of source-port definition.

        leaf packet-length  {
            type  cml-data-types:cml_range_t;
            description "Use this attribute to specify packet-length value";
        } // END of packet-length definition.

        leaf fragment-type  {
            type  ipi-enhanced-pbr-types:epbr_fragment_type_t;
            description "Use this attribute to specify fragment type value";
        } // END of fragment-type definition.

    } // END of epbr-class-map-match-filters-config definition.
    grouping epbr-class-map-match-filters-ipv4-config {
        description
            "Grouping for EPBR class-map match filters ipv4 config";
        leaf destination-prefix  {
            type  cml-data-types:cml_ipv4_addr_prefix_t;
            description "Use this attribute to specify IPv4 prefix";
        } // END of destination-prefix definition.

        leaf source-prefix  {
            type  cml-data-types:cml_ipv4_addr_prefix_t;
            description "Use this attribute to specify IPv4 prefix";
        } // END of source-prefix definition.

    } // END of epbr-class-map-match-filters-ipv4-config definition.
    grouping epbr-class-map-match-filters-ipv4-icmp-config {
        description
            "Grouping for EPBR class-map match filters ipv4 config";
        leaf icmp-type  {
            type  cml-data-types:cml_range_t;
            description "Use this attribute to specify ICMP type";
        } // END of icmp-type definition.

        leaf icmp-code  {
            type  cml-data-types:cml_range_t;
            description "Use this attribute to specify ICMP code";
        } // END of icmp-code definition.

    } // END of epbr-class-map-match-filters-ipv4-icmp-config definition.
    grouping epbr-class-map-match-filters-tcp-flag-config {
        description
            "Grouping for EPBR class-map match filters TCP flag config";
        leaf value  {
            type  string {
                length "1..1965";
                pattern "[^?' =,>|]+";
            }
            description "Match value for TCP flag";
        } // END of value definition.

        leaf bit-mask  {
            type  string {
                length "1..1965";
                pattern "[^?' =,>|]+";
            }
            description "Use this attribute to specify bit-mask for TCP flag";
        } // END of bit-mask definition.

    } // END of epbr-class-map-match-filters-tcp-flag-config definition.
    grouping epbr-class-map-match-filters-match-dscp-value-config {
        description
            "Grouping for EPBR class-map match filters TCP flag config";
        leaf match-dscp-value  {
            type  cml-data-types:cml_range_t {
                length "1..1965";
            }
            description "Use this attribute to specify dscp value";
        } // END of match-dscp-value definition.

    } // END of epbr-class-map-match-filters-match-dscp-value-config definition.
    grouping epbr-policy-map-policy-actions-config {
        description
            "Grouping for EPBR policy-map policy-actions configuration";
        leaf drop-traffic  {
            type  empty;
            description "Use this attribute to specify drop action";
        } // END of drop-traffic definition.

        leaf dscp-set-value  {
            type  ipi-enhanced-pbr-types:epbr_hex_dscp_t;
            description "Use this attribute to specify DSCP value";
        } // END of dscp-set-value definition.

    } // END of epbr-policy-map-policy-actions-config definition.
    grouping epbr-policy-map-policy-actions-police-config {
        description
            "Grouping for EPBR policy-map policy-actions police configuration";
        leaf rate  {
            type  uint64 {
                 range "1..1000000000"  {
                    description "1..1000000000: Supported range 1 - 1000000000";
                 }
            }
            description "Use this attribute to set a rate policing.";
        } // END of rate definition.

        leaf rate-unit  {
            type  ipi-enhanced-pbr-types:epbr_rate_unit_t;
            default "bps";
            description "Use this attribute to set a rate unit.";
        } // END of rate-unit definition.

    } // END of epbr-policy-map-policy-actions-police-config definition.
    grouping epbr-policy-map-policy-actions-redirect-config {
        description
            "Grouping for EPBR policy-map policy-actions redirect configuration";
        leaf route-target  {
            type  ipi-enhanced-pbr-types:epbr_vrf_rt_t {
                length "1..1965";
            }
            description "Use this attribute to specify route target for rt redirect action";
        } // END of route-target definition.

    } // END of epbr-policy-map-policy-actions-redirect-config definition.
    grouping epbr-class-map-top {
        description
            "Grouping for EPBR class-map";
        container class-maps {
            description
                "Configuration data for EPBR class-map";

            list class-map {
                key "name class-type";
                description
                    "Configuration data list for EPBR class-map";
                leaf name  {
                    type  leafref {
                        path  "../config/name";
                    }
                    description "Use this attribute to set the class-map name";
                } // END of name definition.

                leaf class-type  {
                    type  leafref {
                        path  "../config/class-type";
                    }
                    description "Use this attribute to set the class-map type.";
                } // END of class-type definition.

                container config {
                    description
                        "class-map data confifiguration  for EPBR";
                    uses epbr-class-map-config;
                } // END of config-container definition.
                container state {
                    config false;
                    description
                        "Operational state data for EPBR class-map config";
                    uses epbr-class-map-config;
                } // END of state-container definition.
                container match-filters {
                    description
                        "Configure match data for EPBR class-map";
                    container config {
                        description
                            "Configure match data";
                        uses epbr-class-map-match-filters-config;
                    } // END of config-container definition.
                    container state {
                        config false;
                        description
                            "Operational state data for EPBR class-map match-fliters config";
                        uses epbr-class-map-match-filters-config;
                    } // END of state-container definition.
                    container ipv4 {
                        description
                            "Configure match data for ipv4";
                        container config {
                            description
                                "Configure match data for ipv4";
                            uses epbr-class-map-match-filters-ipv4-config;
                        } // END of config-container definition.
                        container state {
                            config false;
                            description
                                "Operational state data for EPBR class-map match-fliters ipv4 config";
                            uses epbr-class-map-match-filters-ipv4-config;
                        } // END of state-container definition.
                        container icmp {
                            description
                                "Configure match data for icmp";
                            container config {
                                description
                                    "Configure match data for ipv4";
                                uses epbr-class-map-match-filters-ipv4-icmp-config;
                            } // END of config-container definition.
                            container state {
                                config false;
                                description
                                    "Operational state data for EPBR class-map match-filters ipv4 icmp
                                            config";
                                uses epbr-class-map-match-filters-ipv4-icmp-config;
                            } // END of state-container definition.
                        } // END of icmp-container definition.
                    } // END of ipv4-container definition.
                    container tcp-flag {
                        description
                            "Configure match data for TCP-flag";
                        container config {
                            description
                                "Configure match data for TCP-flag";
                            uses epbr-class-map-match-filters-tcp-flag-config;
                        } // END of config-container definition.
                        container state {
                            config false;
                            description
                                "Operational state data for EPBR class-map match-filters TCP-flag
                                        config";
                            uses epbr-class-map-match-filters-tcp-flag-config;
                        } // END of state-container definition.
                    } // END of tcp-flag-container definition.
                    container dscp {
                        description
                            "Configure match data for dscp";
                        container config {
                            description
                                "Configure match data for dscp";
                            uses epbr-class-map-match-filters-match-dscp-value-config;
                        } // END of config-container definition.
                        container state {
                            config false;
                            description
                                "Operational state data for EPBR class-map match-filters dscp config";
                            uses epbr-class-map-match-filters-match-dscp-value-config;
                        } // END of state-container definition.
                    } // END of dscp-container definition.
                } // END of match-filters-container definition.
            } // End of class-map-list
        } // END of class-maps-container definition.
    } // END of epbr-class-map-top definition.
    grouping epbr-policy-map-config {
        description
            "Grouping for EPBR policy-map configuration";
        leaf policy-map-name  {
            type  string {
                length "1..64";
                pattern "[^?' =,>|]+";
            }
            description "Use this attribute to set the policy-map name";
        } // END of policy-map-name definition.

        leaf type  {
            type  ipi-enhanced-pbr-types:epbr_policy_map_t;
            description "Use this attribute to set the policy-map type. Default value is 1.";
        } // END of type definition.

        leaf reference-description  {
            type  cml-data-types:cml_line_t {
                length "1..64";
            }
            description "This attribute configures reference description message on policy-map
                        profile";
        } // END of reference-description definition.

    } // END of epbr-policy-map-config definition.
    grouping epbr-policy-map-class-config {
        description
            "Grouping for EPBR policy-map class configuration";
        leaf class-map-name  {
            type  string {
                length "1..1965";
                pattern "[^?' =,>|]+";
            }
            description "Use this attribute to attach a class-map of type pbr or queue to the
                        policy-map";
        } // END of class-map-name definition.

        leaf class-type  {
            type  ipi-enhanced-pbr-types:epbr_class_map_t;
            description "Use this attribute to set the class-map type.";
        } // END of class-type definition.

    } // END of epbr-policy-map-class-config definition.
    grouping epbr-policy-map-top {
        description
            "Grouping for EPBR policy-map";
        container policy-maps {
            description
                "Configuration data for EPBR policy-map";

            list policy-map {
                key "policy-map-name type";
                description
                    "Configure EPBR policy-map";
                leaf policy-map-name  {
                    type  leafref {
                        path  "../config/policy-map-name";
                    }
                    description "Use this attribute to set the policy-map name";
                } // END of policy-map-name definition.

                leaf type  {
                    type  leafref {
                        path  "../config/type";
                    }
                    description "Use this attribute to set the policy-map type.";
                } // END of type definition.

                container config {
                    description
                        "policy-map configuration for EPBR";
                    uses epbr-policy-map-config;
                } // END of config-container definition.
                container state {
                    config false;
                    description
                        "Operational state data for EPBR policy-map";
                    uses epbr-policy-map-config;
                } // END of state-container definition.
                container classes {
                    description
                        "Configuration data for EPBR policy-map class configuration";

                    list class {
                        key "class-map-name class-type";
                        description
                            "Configuration data list for EPBR policy-map class configuration";
                        leaf class-map-name  {
                            type  leafref {
                                path  "../config/class-map-name";
                            }
                            description "Use this attribute to attach a class-map of type flowspec or queue to
                                        the policy-map";
                        } // END of class-map-name definition.

                        leaf class-type  {
                            type  leafref {
                                path  "../config/class-type";
                            }
                            description "Use this attribute to setthe class-map type.";
                        } // END of class-type definition.

                        container config {
                            description
                                "Configuration data for EPBR policy-map class configuration";
                            uses epbr-policy-map-class-config;
                        } // END of config-container definition.
                        container state {
                            config false;
                            description
                                "Operational state data for class for EPBR policy-map";
                            uses epbr-policy-map-class-config;
                        } // END of state-container definition.
                        container policy-actions {
                            description
                                "Configure EPBR policy actions";
                            container config {
                                description
                                    "Configure EPBR policy actions";
                                uses epbr-policy-map-policy-actions-config;
                            } // END of config-container definition.
                            container state {
                                config false;
                                description
                                    "Operational state data for class for EPBR policy-map";
                                uses epbr-policy-map-policy-actions-config;
                            } // END of state-container definition.
                            container police {
                                description
                                    "Configure police for EPBR policy-map";
                                container config {
                                    description
                                        "Configure EPBR policy actions";
                                    uses epbr-policy-map-policy-actions-police-config;
                                } // END of config-container definition.
                                container state {
                                    config false;
                                    description
                                        "Operational state data for class for EPBR policy-map";
                                    uses epbr-policy-map-policy-actions-police-config;
                                } // END of state-container definition.
                            } // END of police-container definition.
                            container redirect {
                                description
                                    "Configure rt redirect for EPBR policy-map";
                                container ipv4 {
                                    description
                                        "ipv4 rt redirect for EPBR policy-map";
                                    container extcommunity {
                                        description
                                            "ext community for rt  redirect";
                                        container config {
                                            description
                                                "Configure redirect for EPBR policy action";
                                            uses epbr-policy-map-policy-actions-redirect-config;
                                        } // END of config-container definition.
                                        container state {
                                            config false;
                                            description
                                                "Operational state data for class for EPBR policy-map";
                                            uses epbr-policy-map-policy-actions-redirect-config;
                                        } // END of state-container definition.
                                    } // END of extcommunity-container definition.
                                } // END of ipv4-container definition.
                            } // END of redirect-container definition.
                        } // END of policy-actions-container definition.
                    } // End of class-list
                } // END of classes-container definition.
            } // End of policy-map-list
        } // END of policy-maps-container definition.
    } // END of epbr-policy-map-top definition.

    grouping  enhanced-pbr-grouping {
    description
        "Configuration data for Enhanced PBR";
    container enhanced-pbr {
        if-feature feature-list:HAVE_BGP_FLOWSPEC;
        description
            "Configuration data for Enhanced PBR";
        uses epbr-class-map-default-top;
        uses epbr-class-map-top;
        uses epbr-policy-map-top;
    } // END of enhanced-pbr-container definition.
    } // END of enhanced-pbr-grouping definition.

    uses enhanced-pbr-grouping;

}
