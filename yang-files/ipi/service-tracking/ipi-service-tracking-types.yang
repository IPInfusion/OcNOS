/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-service-tracking-types.yang
*
*/

module ipi-service-tracking-types {

    yang-version 1.1;

    namespace   "http://www.ipinfusion.com/yang/ocnos/ipi-service-tracking-types";

    prefix "ipi-service-tracking-types";

    organization
        "IP Infusion Inc.";

    contact
        "Address: 3965 Freedom Circle, Suite 200, Santa Clara, CA 95054
         Phone: +1 408-400-1900
         E-mail: support@ipinfusion.com
         Web: http://www.ipinfusion.com/";

    description
        "Service tracking data types";


    revision "2025-08-22" {
        description "The if-feature is modified to HAVE_ALL_PHOTONICS_CUSTOM";
        reference " 0.2.0.";
    }

    revision "2023-11-07" {
        description "Initial version";
        reference " 0.1.0.";
    }



    typedef  service_tracking_service_type_t {
        type enumeration {
            enum VXLAN {
                value 0;
                description "VxLAN service tracking type";
            }
            enum EBGP {
                value 1;
                description "BGP service tracking type";
            }
            enum OSPF {
                value 2;
                description "OSPF service tracking type";
            }
            enum ISIS {
                value 3;
                description "ISIS service tracking type";
            }
            enum IF {
                value 4;
                description "Interface service tracking type";
            }
        }
        description "type definition for SERVICE_TRACKING_SERVICE_TYPE_T";
    }

    typedef  cml_service_tracking_status_check_t {
        type enumeration {
            enum UP {
                value 0;
                description "Type of service tracking check is UP";
            }
            enum DOWN {
                value 1;
                description "Type of service tracking check is DOWN";
            }
        }
        description "type definition for CML_SERVICE_TRACKING_STATUS_CHECK_T";
    }

    typedef  cml_service_tracking_status_t {
        type enumeration {
            enum SUCCESS {
                value 0;
                description "The final status of service tracking is Success";
            }
            enum FAILURE {
                value 1;
                description "The final status of service tracking is Failure";
            }
            enum IN-PROGRESS {
                value 2;
                description "The status to be showed when service tracking is in progress";
            }
        }
        description "type definition for CML_SERVICE_TRACKING_STATUS_T";
    }

}
