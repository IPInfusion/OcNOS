/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-service-tracking.yang
*
*/

module ipi-service-tracking {

    yang-version 1.1;

    namespace   "http://www.ipinfusion.com/yang/ocnos/ipi-service-tracking";

    prefix "ipi-service-tracking";

    import cml-data-types {
        prefix cml-data-types;
        revision-date 2026-05-15;
    }

    import ipi-service-tracking-types {
        prefix ipi-service-tracking-types;
        revision-date 2025-08-22;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for service tracking";


    revision "2025-08-22" {
        description "The if-feature is modified to HAVE_ALL_PHOTONICS_CUSTOM";
        reference " 0.2.0.";
    }

    revision "2025-04-14" {
        description "Fix compilation warnings";
        reference " 0.1.1.";
    }

    revision "2023-11-07" {
        description "Initial version";
        reference " 0.1.0.";
    }

    grouping service-tracking-state {
        description
            "Grouping for service tracking operational data";
        leaf service-type  {
            type  ipi-service-tracking-types:service_tracking_service_type_t;
            description "Use this attribute to identify the type of the service to be tracked";
        } // END of service-type definition.

        leaf operational-status-check  {
            type  ipi-service-tracking-types:cml_service_tracking_status_check_t;
            description "Use this attribute to inform service tracking what kind of
                        verification must be done. To check if service is going UP or DOWN.";
        } // END of operational-status-check definition.

        leaf status  {
            type  ipi-service-tracking-types:cml_service_tracking_status_t;
            description "Use this attribute to identify the status of service tracking.";
        } // END of status definition.

    } // END of service-tracking-state definition.
    grouping service-tracking-top {
        description
            "Grouping for service tracking operational data";

        list service-tracking {
            key "service-type";
            config false;
            description
                "List of operational data for services-tracking";
            leaf service-type  {
                type  leafref {
                    path  "../state/service-type";
                }
                description "Use this attribute to identify the type of the service to be tracked";
            } // END of service-type definition.

            container state {
                config false;
                description
                    "Container operational data";
                uses service-tracking-state;
            } // END of state-container definition.
        } // End of service-tracking-list
    } // END of service-tracking-top definition.

    grouping  services-tracking-grouping {
    description
        "Container for services-tracking";
    container services-tracking {
        if-feature feature-list:HAVE_ALL_PHOTONICS_CUSTOM;
        description
            "Container for services-tracking";
        uses service-tracking-top;
    } // END of services-tracking-container definition.
    } // END of services-tracking-grouping definition.

    uses services-tracking-grouping;

    rpc start-service-tracking {
        if-feature feature-list:HAVE_ALL_PHOTONICS_CUSTOM;
        description "Use this RPC to start the tracking of service down or up";
        input  {
            leaf service-type  {
                type ipi-service-tracking-types:service_tracking_service_type_t;
                mandatory true;
                description "Use this attribute to identify the type of the service to be tracked";
            }
            leaf operational-status-check  {
                type ipi-service-tracking-types:cml_service_tracking_status_check_t;
                mandatory true;
                description "Use this attribute to inform service tracking what kind of
                            verification must be done. To check if service is going UP or DOWN.";
            }
            leaf service-timeout  {
                type uint16 {
                    range "20..600";
                }
                mandatory true;
                description "How long the service tracking will run until there is a timeout
                            failure.";
            }
        }
    }

    notification service-tracking-status {
        if-feature feature-list:HAVE_ALL_PHOTONICS_CUSTOM;

        description "Notification to inform the final status of service tracking. If success or failure..";

        leaf severity {
            type cml-data-types:cml_notif_severity_t;
            description "Notification severity level";
        }

        leaf eventClass {
            type cml-data-types:cml_notif_class_t;
            description "Notification event class (value: STATE)";
        }

        leaf service-type {
            type ipi-service-tracking-types:service_tracking_service_type_t;
        description
            "Use this attribute to identify the type of the service to be tracked";
        }

        leaf operational-status-check {
            type ipi-service-tracking-types:cml_service_tracking_status_check_t;
        description
            "Use this attribute to inform service tracking what kind of
                    verification must be done. To check if service is going UP or DOWN.";
        }

        leaf status {
            type ipi-service-tracking-types:cml_service_tracking_status_t;
        description
            "Use this attribute to identify the status of service tracking.";
        }
    }

}
