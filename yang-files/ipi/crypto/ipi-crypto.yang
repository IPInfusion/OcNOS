/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-crypto.yang
*
*/

module ipi-crypto {

    yang-version 1.1;

    namespace   "http://www.ipinfusion.com/yang/ocnos/ipi-crypto";

    prefix "ipi-crypto";

    import ietf-inet-types {
        prefix inet;
        revision-date 2013-07-15;
    }

    import ipi-crypto-types {
        prefix ipi-crypto-types;
        revision-date 2024-11-23;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "This module defines configurations related to cryptographic
                certificate generation and management and system encryption management
                global configuration";


    revision "2025-08-25" {
        description "Added exec CLI/NETCONF RPC to copy certificate on OcNOS";
        reference " 0.4.0.";
    }

    revision "2024-11-23" {
        description "Changed CRYPTO_CIPHER_TYPES_T enum names";
        reference " 0.3.1.";
    }

    revision "2024-08-01" {
        description "Add system encryption management global configuration";
        reference " 0.3.0.";
    }

    revision "2022-06-01" {
        description "Updated the yang file with feature";
        reference " 0.2.0.";
    }

    revision "2021-07-30" {
        description "Initial Version";
        reference "Initial Version";
    }

    grouping crypto-global-config {
        description
            "System encryption management global configuration";
        leaf key-encryption  {
            type  ipi-crypto-types:crypto_cipher_types_t;
            description "Use this attribute to set the system global encryption algorithm";
        } // END of key-encryption definition.

    } // END of crypto-global-config definition.

    grouping  crypto-grouping {
    description
        "Top level container for system encryption configuration";
    container crypto {
        if-feature feature-list:HAVE_HOSTPD;
        description
            "Top level container for system encryption configuration";
        container global {
            description
                "System encryption global configuration";
            container config {
                description
                    "System encryption management configuration";
                uses crypto-global-config;
            } // END of config-container definition.
            container state {
                config false;
                description
                    "System encryption management operational state data";
                uses crypto-global-config;
            } // END of state-container definition.
        } // END of global-container definition.
    } // END of crypto-container definition.
    } // END of crypto-grouping definition.

    uses crypto-grouping;

    rpc crypto-rsa-key-gen {
        if-feature feature-list:HAVE_HOSTPD;
        description "Use this RPC to generate private key and certificate signing request";
        input  {
            leaf ipv4-addr  {
                type inet:ipv4-address;
                mandatory true;
                description "IP address for CSR common-name field";
            }
        }
    }

    rpc crypto-rsa-load-cert {
        if-feature feature-list:HAVE_HOSTPD;
        description "Use this RPC to download public key and ca certificate";
        input  {
            leaf source-interface  {
                type string {
                    length "1..49";
                }
                mandatory true;
                description "Source interface name to be used to reach url";
            }
            leaf url  {
                type inet:uri;
                mandatory true;
                description "The URL to be reached to get OcNOS certificate";
            }
        }
    }

}
