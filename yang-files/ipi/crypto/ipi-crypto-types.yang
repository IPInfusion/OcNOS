/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-crypto-types.yang
*
*/

module ipi-crypto-types {

    yang-version 1.1;

    namespace   "http://www.ipinfusion.com/yang/ocnos/ipi-crypto-types";

    prefix "ipi-crypto-types";

    organization
        "IP Infusion Inc.";

    contact
        "Address: 3965 Freedom Circle, Suite 200, Santa Clara, CA 95054
         Phone: +1 408-400-1900
         E-mail: support@ipinfusion.com
         Web: http://www.ipinfusion.com/";

    description
        "System encryption management data types";


    revision "2024-11-23" {
        description "Changed CRYPTO_CIPHER_TYPES_T enum names";
        reference " 0.1.1.";
    }

    revision "2024-08-01" {
        description "Initial Version";
        reference " 0.1.0.";
    }



    typedef  crypto_cipher_types_t {
        type enumeration {
            enum 3des {
                value 0;
                description "Set 3DES as system global encryption algorithm";
            }
            enum aes {
                value 1;
                description "Set AES as system global encryption algorithm";
            }
        }
        description "type definition for CRYPTO_CIPHER_TYPES_T";
    }

}
