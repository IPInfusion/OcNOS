/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-tacacs.yang
*
*/

module ipi-tacacs {

    yang-version 1.1;

    namespace   "http://www.ipinfusion.com/yang/ocnos/ipi-tacacs";

    prefix "ipi-tacacs";

    import cml-data-types {
        prefix cml-data-types;
        revision-date 2026-05-15;
    }

    import ipi-tacacs-types {
        prefix ipi-tacacs-types;
        revision-date 2022-06-01;
    }

    import ipi-vrf {
        prefix ipi-vrf;
        revision-date 2026-08-12;
    }

    import ipi-network-instance {
        prefix ipi-network-instance;
        revision-date 2026-08-12;
    }

    import ietf-yang-types {
        prefix yang;
        revision-date 2013-07-15;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Layer-3 tacacs configurations";


    revision "2026-01-09" {
        description "Added when tag to handle validation during commit dry run";
        reference " 0.14.0.";
    }

    revision "2025-11-21" {
        description "Updated TACACS cli to use set/unset operations for key string uncofnig.";
        reference " 0.13.1.";
    }

    revision "2025-08-10" {
        description "Replaced 'include-input-for-unset' with 'suppress-input-for-unset' for TACACS secret key attributes";
        reference " 0.13.0.";
    }

    revision "2024-06-19" {
        description "Update to support user-defined VRF";
        reference " 0.12.0.";
    }

    revision "2024-06-17" {
        description "Changed the datatype of the tacacs key";
        reference " 0.11.0.";
    }

    revision "2023-05-29" {
        description "Added When tag for no-debug-all command";
        reference " 0.10.0.";
    }

    revision "2022-11-22" {
        description "Modified Tacacs data model to add a new container";
        reference " 0.9.1.";
    }

    revision "2022-11-16" {
        description "Updated missing cliprependstr tags";
        reference " 0.9.0.";
    }

    revision "2022-09-14" {
        description "Tacacs global configs CLI generation change";
        reference " 0.8.0.";
    }

    revision "2022-08-10" {
        description "Debug hierarchy change";
        reference " 0.7.0.";
    }

    revision "2022-06-29" {
        description "Updated timeout option with default value";
        reference " 0.6.0.";
    }

    revision "2022-06-01" {
        description "Updated the yang file with feature";
        reference " 0.5.0.";
    }

    revision "2022-05-30" {
        description "Added runtime attr for terminal debug status";
        reference " 0.4.1.";
    }

    revision "2022-04-27" {
        description "Added Netconf Get support for per-server counters";
        reference " 0.4.0.";
    }

    revision "2022-02-16" {
        description "Added changes to make feature enable attribute mandatory";
        reference " 0.3.0.";
    }

    revision "2021-09-03" {
        description "Update descriptions of attribute";
        reference " 0.2.4.";
    }

    revision "2021-05-10" {
        description "Added dependecy on key type for secret key string attribute";
        reference " 0.2.3.";
    }

    revision "2021-04-29" {
        description "Specified CLI input to RDN host address and updated descriptions";
        reference " 0.2.2.";
    }

    revision "2021-04-27" {
        description "Added dependency on sequence number for remote server object list";
        reference " 0.2.1.";
    }

    revision "2021-02-05" {
        description "Restructured module as per open-config style";
        reference " 0.2.0.";
    }

    revision "2018-06-21" {
        description "Initial Version";
        reference " 0.1.0.";
    }

    grouping tacacs-global-key-config {
        description
            "TACACS Configuration items for KEYS";
        leaf key-type  {
            type  ipi-tacacs-types:tacacs_hostp_key_type_t;
            description "Authentication key value";
        } // END of key-type definition.

        leaf secret-key-string  {
            // when " ipi-tacacs:tacacs/vrfs/vrf/config/key-type ";
            type  string {
                length "1..1965";
                pattern "[^?]+";
            }
            description "Shared key used between the authentication-server and the device";
        } // END of secret-key-string definition.

    } // END of tacacs-global-key-config definition.
    grouping tacacs-server-state {
        description
            "Operational data for each TACACS server";
        leaf last-successful-authentication-time  {
            type  yang:date-and-time {
                pattern "\\d{4}-\\d{2}-\\d{2}T\\d{2}:\\d{2}:\\d{2}(\\.\\d+)?(Z|[\\+\\-]\\d{2}:\\d{2})";
                }
                description "Timestamp for the last successful authentication to this TACACS+
                            Server";
            } // END of last-successful-authentication-time definition.

        container counters {
            config false;
            description
                "TACACS+ Server counters";
            leaf successful-authentications  {
                type  yang:counter64;
                description "Number of successful authentications to the TACACS+ Server";
            } // END of successful-authentications definition.

            leaf authentication-failures  {
                type  yang:counter64;
                description "Number of authentication failures to the TACACS+ Server";
            } // END of authentication-failures definition.

            leaf connection-failures  {
                type  yang:counter64;
                description "Number of connection failures to the TACACS+ Server";
            } // END of connection-failures definition.

        } // END of counters-container definition.
    } // END of tacacs-server-state definition.
    grouping tacacs-global-config {
        description
            "TACACS Global Configuration items";
        leaf vrf-name  {
            type  leafref {
                path  "/ipi-network-instance:network-instances/ipi-network-instance:network-instance/ipi-vrf:vrf/ipi-vrf:config/ipi-vrf:vrf-name";
            }
            description "VRF Name associated with this instance";
        } // END of vrf-name definition.

        leaf feature-enable  {
            type  empty;
            mandatory true;
            description "Use this attribute to enable the TACACS+ feature";
        } // END of feature-enable definition.

        leaf timeout  {
            type  uint8 {
                 range "1..60"  {
                    description "1..60: Supported range 1 - 60";
                 }
            }
            default "5";
            description "Use this attribute to set the period to wait for a response from the
                        server before the client declares a
                        timeout failure. The default timeout value is 5 seconds.";
        } // END of timeout definition.

    } // END of tacacs-global-config definition.
    grouping tacacs-server-key-config {
        description
            "TACACS Configuration items for KEYS in Servers";
        leaf key-type  {
            type  ipi-tacacs-types:tacacs_hostp_key_type_t;
            description "Authentication key value";
        } // END of key-type definition.

        leaf secret-key-string  {
            // when " ipi-tacacs:tacacs/vrfs/vrf/remote-servers/server/config/key-type ";
            type  string {
                length "1..1965";
                pattern "[^?]+";
            }
            description "Shared key used between the authentication-server and the device";
        } // END of secret-key-string definition.

    } // END of tacacs-server-key-config definition.
    grouping tacacs-server-config {
        description
            "TACACS Server Configuration items";
        leaf host-address  {
            type  cml-data-types:cml_hostname_t;
            description "Use this attribute to set the TACACS+ server host name or IP address.";
        } // END of host-address definition.

        leaf sequence-number  {
            type  uint8 {
                 range "1..8"  {
                    description "1..8: Supported range 1 - 8";
                 }
            }
            mandatory true;
            description "Use this attribute to set the sequence-number/priority index for the
                        TACACS+ server";
        } // END of sequence-number definition.

        leaf port  {
            type  uint32 {
                 range "1025..65535"  {
                    description "1025..65535: Supported range 1025 - 65535";
                 }
            }
            description "Port number used for TACACS+ Server Connection";
        } // END of port definition.

        leaf timeout  {
            type  uint32 {
                 range "1..60"  {
                    description "1..60: Supported range 1 - 60";
                 }
            }
            default "5";
            description "To represent the timeout configured by the user";
        } // END of timeout definition.

    } // END of tacacs-server-config definition.
    grouping tacacs-debug-config {
        description
            "Configuration data related to debugging";
        leaf enable  {
            type  empty;
            description "This attribute is to enable/disable TACACS+ debug logging";
        } // END of enable definition.

    } // END of tacacs-debug-config definition.
    grouping tacacs-debug-state {
        description
            "State data related to TACACS debugging status";
        leaf terminal-debug-status  {
            type  cml-data-types:cml_on_off_t;
            description "Use this attribute to display the current terminal debugging status
                        for TACACS module";
        } // END of terminal-debug-status definition.

    } // END of tacacs-debug-state definition.

    grouping  tacacs-grouping {
    description
        "TACACS related operation";
    container tacacs {
        if-feature feature-list:HAVE_HOSTPD;
        description
            "TACACS related operation";
        container vrfs {
            description
                "This container defines TACACS vrf informations";

            list vrf {
                if-feature feature-list:HAVE_HOSTPD;
                if-feature feature-list:HAVE_AAA;
                if-feature feature-list:HAVE_TACACS_CLIENT;
                key "vrf-name";
                description
                    "Global TACACS Server Configuration";
                leaf vrf-name  {
                    type  leafref {
                        path  "../config/vrf-name";
                    }
                    description "VRF Name associated with this instance";
                } // END of vrf-name definition.

                container config {
                    description
                        "tacacs related operation";
                    uses tacacs-global-config;
                    uses tacacs-global-key-config;
                } // END of config-container definition.
                container state {
                    config false;
                    description
                        "This container defines the TACACS Global states.";
                    uses tacacs-global-config;
                    uses tacacs-global-key-config;
                } // END of state-container definition.
                container remote-servers {
                    description
                        "This container defines tacacs server informations";

                    list server {
                    when " /ipi-tacacs:tacacs/ipi-tacacs:vrfs/ipi-tacacs:vrf/ipi-tacacs:config/ipi-tacacs:feature-enable ";
                    // when " ipi-tacacs:tacacs/vrfs/vrf/remote-servers/server/config/sequence-number ";
                        if-feature feature-list:HAVE_HOSTPD;
                        if-feature feature-list:HAVE_AAA;
                        if-feature feature-list:HAVE_TACACS_CLIENT;
                        key "host-address";
                        description
                            "This objectlist defines the TACACS server list";
                        leaf host-address  {
                            type  leafref {
                                path  "../config/host-address";
                            }
                            description "Use this attribute to set the TACACS+ server host name or IP address";
                        } // END of host-address definition.

                        container config {
                            description
                                "This container defines TACACS server operation";
                            uses tacacs-server-config;
                            uses tacacs-server-key-config;
                        } // END of config-container definition.
                        container state {
                            config false;
                            description
                                "This container defines TACACS Server state intormation.";
                            uses tacacs-server-config;
                            uses tacacs-server-key-config;
                            uses tacacs-server-state;
                        } // END of state-container definition.
                    } // End of server-list
                } // END of remote-servers-container definition.
            } // End of vrf-list
        } // END of vrfs-container definition.
        container debug {
            description
                "TACACS debug";
            container config {
                description
                    "This container defines TACACS Debug Configuration";
                uses tacacs-debug-config;
            } // END of config-container definition.
            container state {
                config false;
                description
                    "This container defines TACACS Debug state";
                uses tacacs-debug-config;
                uses tacacs-debug-state;
            } // END of state-container definition.
        } // END of debug-container definition.
    } // END of tacacs-container definition.
    } // END of tacacs-grouping definition.

    uses tacacs-grouping;

    rpc clear-all-tacacs-server-counters {
        if-feature feature-list:HAVE_HOSTPD;
        description "Use this RPC to clear all tacacs-server counters";
        input  {
            leaf vrf-name  {
                type string;
                mandatory true;
                description "VRF Name associated with this instance";
            }
        }
    }

    rpc clear-tacacs-server-host-counters {
        if-feature feature-list:HAVE_HOSTPD;
        description "Use this RPC to clear counters for a TACACS server by hostname or IP
                    address";
        input  {
            leaf hostname  {
                type cml-data-types:cml_hostpname_t;
                mandatory true;
                description "Use this attribute to set the TACACS+ server host name or IP address";
            }
            leaf vrf-name  {
                type string;
                mandatory true;
                description "VRF Name associated with this instance";
            }
        }
    }

    rpc tacacs-terminal-debug-on {
        if-feature feature-list:HAVE_HOSTPD;
        description "Use this RPC to turn on TACACS terminal debug logs";
    }

    rpc tacacs-terminal-debug-off {
        if-feature feature-list:HAVE_HOSTPD;
        description "Use this RPC to turn off TACACS terminal debug logs";
    }

}
