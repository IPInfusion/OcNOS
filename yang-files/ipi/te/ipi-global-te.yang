/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-global-te.yang
*
*/

module ipi-global-te {

    yang-version 1.1;

    namespace   "http://www.ipinfusion.com/yang/ocnos/ipi-global-te";

    prefix "ipi-global-te";

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Data model for Global Te";


    revision "2024-12-23" {
        description "Add function to validate the admin-group name";
        reference " 0.4.1.";
    }

    revision "2024-08-10" {
        description "Commented out EAG-mapping-Range and SRLG-Mapping-Range for OcNOS-6.6";
        reference " 0.4.0.";
    }

    revision "2024-04-20" {
        description "Added SRLG name-to-ID mapping CLI";
        reference " 0.3.2.";
    }

    revision "2024-04-11" {
        description "Changed Extended Administrative Group CLI to hidden";
        reference " 0.3.1.";
    }

    revision "2022-09-30" {
        description "Added data model for Extended Administrative Groups(EAG)";
        reference " 0.3.0.";
    }

    revision "2022-07-11" {
        description "Updated data model name";
        reference " 0.2.0.";
    }

    revision "2022-06-21" {
        description "Initial Version";
        reference " 0.1.0.";
    }

    grouping admin-group-config {
        description
            "Administrative Group Configurations";
        leaf name  {
            type  string {
                length "1..1965";
                pattern "[^?' =,>|]+";
            }
            description "Use this attribute to create a name-to-value binding for an
                        administrative group";
        } // END of name definition.

        leaf id  {
            type  uint8 {
                 range "0..31"  {
                    description "0..31: Supported range 0 - 31";
                 }
            }
            description "identifier value for the administrative group";
        } // END of id definition.

    } // END of admin-group-config definition.
    grouping extended-admin-group-config {
        description
            "Extended Administrative Group (EAG) Configurations";
        leaf name  {
            type  string {
                length "1..1965";
                pattern "[^?' =,>|]+";
            }
            description "Use this attribute to create a name-to-value binding for an extended
                        administrative group";
        } // END of name definition.

        leaf id  {
            type  uint32 {
                 range "32..95"  {
                    description "32..95: Supported range 32 - 95";
                 }
            }
            description "identifier value for the extended administrative group";
        } // END of id definition.

    } // END of extended-admin-group-config definition.
    grouping srlg-map-config {
        description
            "SRLG map configurations";
        leaf name  {
            type  string {
                length "1..1965";
                pattern "[^?' =,>|]+";
            }
            description "Use this attribute to create a name-to-value binding for an SRLG map";
        } // END of name definition.

        leaf id  {
            type  uint32 {
                 range "1..65535"  {
                    description "1..65535: Supported range 1 - 65535";
                 }
            }
            description "identifier value for the SRLG map";
        } // END of id definition.

    } // END of srlg-map-config definition.

    grouping  admin-groups-grouping {
    description
        "This defines a YANG data model for admin group config for  MPLS and TE
                configuration and operation.";
    container admin-groups {
        if-feature feature-list:HAVE_MPLS_OR_HAVE_SRV6;
        description
            "This defines a YANG data model for admin group config for  MPLS and TE
                    configuration and operation.";

        list admin-group {
            key "name id";
            description
                "Administrative Group Configurations";
            leaf name  {
                type  leafref {
                    path  "../config/name";
                }
                description "Use this attribute to create a name-to-value binding for an
                            administrative group";
            } // END of name definition.

            leaf id  {
                type  leafref {
                    path  "../config/id";
                }
                description "identifier value for the administrative group";
            } // END of id definition.

            container config {
                description
                    "Config Container for Administrative Groups";
                uses admin-group-config;
            } // END of config-container definition.
            container state {
                config false;
                description
                    "State Contatiner for Administrative Groups";
                uses admin-group-config;
            } // END of state-container definition.
        } // End of admin-group-list
    } // END of admin-groups-container definition.
    } // END of admin-groups-grouping definition.

    grouping  extended-admin-groups-grouping {
    description
        "This defines a YANG data model for Extended Admin Group config for
                MPLS and TE configuration and operation.";
    container extended-admin-groups {
        if-feature feature-list:HAVE_MPLS_OR_HAVE_SRV6;
        description
            "This defines a YANG data model for Extended Admin Group config for
                    MPLS and TE configuration and operation.";

        list extended-admin-group {
            key "name id";
            description
                "Extended Administrative Group (EAG) Configurations";
            leaf name  {
                type  leafref {
                    path  "../config/name";
                }
                description "Use this attribute to create a name-to-value binding for an extended
                            administrative group";
            } // END of name definition.

            leaf id  {
                type  leafref {
                    path  "../config/id";
                }
                description "identifier value for the extended administrative group";
            } // END of id definition.

            container config {
                description
                    "Config Container for Extended Administrative Groups (EAG)";
                uses extended-admin-group-config;
            } // END of config-container definition.
            container state {
                config false;
                description
                    "State Contatiner for Extended Administrative Groups (EAG)";
                uses extended-admin-group-config;
            } // END of state-container definition.
        } // End of extended-admin-group-list
    } // END of extended-admin-groups-container definition.
    } // END of extended-admin-groups-grouping definition.

    grouping  srlg-maps-grouping {
    description
        "This defines a YANG data model for SRLG map config for MPLS and TE
                configuration and operation.";
    container srlg-maps {
        if-feature feature-list:HAVE_MPLS_OR_HAVE_SRV6;
        description
            "This defines a YANG data model for SRLG map config for MPLS and TE
                    configuration and operation.";

        list srlg-map {
            key "name id";
            description
                "SRLG map configurations";
            leaf name  {
                type  leafref {
                    path  "../config/name";
                }
                description "Use this attribute to create a name-to-value binding for an SRLG map";
            } // END of name definition.

            leaf id  {
                type  leafref {
                    path  "../config/id";
                }
                description "identifier value for the SRLG map";
            } // END of id definition.

            container config {
                description
                    "Config Container for SRLG maps";
                uses srlg-map-config;
            } // END of config-container definition.
            container state {
                config false;
                description
                    "State Contatiner for SRLG maps";
                uses srlg-map-config;
            } // END of state-container definition.
        } // End of srlg-map-list
    } // END of srlg-maps-container definition.
    } // END of srlg-maps-grouping definition.

    uses admin-groups-grouping;
    uses extended-admin-groups-grouping;
    uses srlg-maps-grouping;

}
