/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-ping.yang
*
*/

module ipi-ping {

    yang-version 1.1;

    namespace   "http://www.ipinfusion.com/yang/ocnos/ipi-ping";

    prefix "ipi-ping";

    import cml-data-types {
        prefix cml-data-types;
        revision-date 2026-05-15;
    }

    import ietf-yang-types {
        prefix yang;
        revision-date 2013-07-15;
    }

    import ipi-ping-types {
        prefix ipi-ping-types;
        revision-date 2022-06-01;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "IPI Ping";


    revision "2022-09-30" {
        description "Import cml-data-types used by notifications";
        reference " 0.4.0.";
    }

    revision "2022-06-01" {
        description "Updated the yang file with feature";
        reference " 0.3.0.";
    }

    revision "2021-01-27" {
        description "Updated default values for timeout and deadline";
        reference " 0.2.0.";
    }

    revision "2020-12-01" {
        description "Initial version";
        reference " 0.1.0.";
    }

    grouping ping-test-results {
        description
            "Ping Test Results";
        leaf test-name  {
            type  string {
                length "1..1965";
                pattern "[^?' =,>|]+";
            }
            description "This attribute uniquely identifies the ping test instance.
                        Since the ping test is executed in asynchronous mode, this attribute
                        is used
                        to associate the ping test command with test results and to stop
                        ongoing test";
        } // END of test-name definition.

        leaf test-status  {
            type  ipi-ping-types:ping_test_status_t;
            description "Ping Test Status";
        } // END of test-status definition.

        leaf start-time  {
            type  yang:date-and-time {
                pattern "\\d{4}-\\d{2}-\\d{2}T\\d{2}:\\d{2}:\\d{2}(\\.\\d+)?(Z|[\\+\\-]\\d{2}:\\d{2})";
                }
                description "Start time of the test";
            } // END of start-time definition.

            leaf end-time  {
                type  yang:date-and-time {
                    pattern "\\d{4}-\\d{2}-\\d{2}T\\d{2}:\\d{2}:\\d{2}(\\.\\d+)?(Z|[\\+\\-]\\d{2}:\\d{2})";
                    }
                    description "End time of the test";
                } // END of end-time definition.

    } // END of ping-test-results definition.
    grouping ping-test-parameters {
        description
            "Ping Test Parameters";
        leaf destination  {
            type  string {
                length "1..1965";
                pattern "[^?' =,>|]+";
            }
            description "Destination IP/IPv6 address or host name specified in the ping test";
        } // END of destination definition.

        leaf protocol  {
            type  ipi-ping-types:ping_ip_protocol_t;
            description "Ping protocol to use used";
        } // END of protocol definition.

        leaf vrf-name  {
            type  string {
                length "1..1965";
                pattern "[^?' =,>|]+";
            }
            description "VRF Name";
        } // END of vrf-name definition.

        leaf repeat-count  {
            type  uint32;
            description "Repeat count which was specified in the ping test";
        } // END of repeat-count definition.

        leaf interval  {
            type  uint16;
            description "Time Interval in sec which was specified in the ping test";
        } // END of interval definition.

        leaf time-to-live  {
            type  uint8;
            description "Time to live value used for the ping test";
        } // END of time-to-live definition.

        leaf datagram-size  {
            type  uint32;
            description "Datagram Size used for the ping test";
        } // END of datagram-size definition.

        leaf timeout  {
            type  uint32;
            description "Timeout value used for the ping test. The timeout value specifies the
                        time to wait for a ping packet response, in seconds";
        } // END of timeout definition.

        leaf deadline  {
            type  uint32;
            description "Deadline value used for the ping test. The deadline value specifies a
                        timeout, in seconds, before ping test exits regardless of how many
                        packets have been sent or received";
        } // END of deadline definition.

    } // END of ping-test-parameters definition.
    grouping ping-summary-info {
        description
            "Ping Summary Info";
        leaf packets-transmitted  {
            type  uint32;
            description "Total ping packets transmitted";
        } // END of packets-transmitted definition.

        leaf packets-received  {
            type  uint32;
            description "Total ping packets received";
        } // END of packets-received definition.

        leaf success-rate  {
            type  uint8 {
                 range "0..100"  {
                    description "0..100: Supported range 0 - 100";
                 }
            }
            description "Success Rate";
        } // END of success-rate definition.

        leaf loss-rate  {
            type  uint8 {
                 range "0..100"  {
                    description "0..100: Supported range 0 - 100";
                 }
            }
            description "Loss Rate";
        } // END of loss-rate definition.

        leaf min-rtt  {
            type  decimal64 {
                 fraction-digits 6;            }
            description "Minimum Round trip Time";
        } // END of min-rtt definition.

        leaf rtt-avg  {
            type  decimal64 {
                 fraction-digits 6;            }
            description "Average Round trip Time";
        } // END of rtt-avg definition.

        leaf max-rtt  {
            type  decimal64 {
                 fraction-digits 6;            }
            description "Maximum Round trip Time";
        } // END of max-rtt definition.

    } // END of ping-summary-info definition.
    grouping ping-replies {
        description
            "Ping Replies";
        leaf sequence-number  {
            type  uint32;
            description "Sequence number of the ICMP echo response packet";
        } // END of sequence-number definition.

        leaf ttl-or-hop-limit  {
            type  uint8;
            description "TTL or Hop Limit in received ICMP echo response";
        } // END of ttl-or-hop-limit definition.

        leaf round-trip-time  {
            type  decimal64 {
                 fraction-digits 6;            }
            description "Round Trip Time";
        } // END of round-trip-time definition.

        leaf result  {
            type  ipi-ping-types:ping_packet_result_t;
            description "Ping Result";
        } // END of result definition.

    } // END of ping-replies definition.

    grouping  ping-grouping {
    description
        "Top level container for ping data model";
    container ping {
        if-feature feature-list:HAVE_HOSTPD;
        description
            "Top level container for ping data model";

        list test-result {
            key "test-name";
            config false;
            description
                "Ping Test Results";
            leaf test-name  {
                type  leafref {
                    path  "../state/test-name";
                }
                description "This attribute uniquely identifies the ping test instance.
                            Since the ping test is executed in asynchronous mode, this attribute
                            is used
                            to associate the ping test command with test results and to stop
                            ongoing test";
            } // END of test-name definition.


            list replies {
                key "sequence-number";
                config false;
                description
                    "Ping Replies of the Ping Test conducted";
                leaf sequence-number  {
                    type  leafref {
                        path  "../state/sequence-number";
                    }
                    description "Sequence number of the ICMP echo response packet";
                } // END of sequence-number definition.

                container state {
                    config false;
                    description
                        "State container to display the ping replies";
                    uses ping-replies;
                } // END of state-container definition.
            } // End of replies-list
            container state {
                config false;
                description
                    "State container to display the ping test results";
                uses ping-test-results;
            } // END of state-container definition.
            container test-parameters {
                config false;
                description
                    "Ping Test Parameters which were specified in ping test RPC";
                container state {
                    config false;
                    description
                        "State container to display the ping test parameters";
                    uses ping-test-parameters;
                } // END of state-container definition.
            } // END of test-parameters-container definition.
            container summary-info {
                config false;
                description
                    "Summary of the Ping Test conducted";
                container state {
                    config false;
                    description
                        "State container to display the ping summary info";
                    uses ping-summary-info;
                } // END of state-container definition.
            } // END of summary-info-container definition.
        } // End of test-result-list
    } // END of ping-container definition.
    } // END of ping-grouping definition.

    uses ping-grouping;

    rpc ping-start-test {
        if-feature feature-list:HAVE_HOSTPD;
        description "Use this RPC to run a ping test for a given host";
        input  {
            leaf test-name  {
                type string;
                mandatory true;
                description "This attribute uniquely identifies the ping test instance.
                            Since the ping test is executed in asynchronous mode, this attribute
                            is used
                            to associate the ping test command with test results and to stop
                            ongoing test";
            }
            leaf destination  {
                type string;
                mandatory true;
                description "Destination IP/IPv6 address or host name specified in the ping test";
            }
            leaf protocol  {
                type ipi-ping-types:ping_ip_protocol_t;
                mandatory true;
                description "Ping protocol to use used";
            }
            leaf vrf-name  {
                type string;
                description "VRF Name";
            }
            leaf repeat-count  {
                type uint32 {
                    range "1..2147483647";
                }
                default "5";
                description "Repeat Count";
            }
            leaf interval  {
                type uint16 {
                    range "1..3600";
                }
                default "1";
                description "Time Interval in sec";
            }
            leaf time-to-live  {
                type uint8 {
                    range "1..255";
                }
                default "64";
                description "Time to live";
            }
            leaf datagram-size  {
                type uint32 {
                    range "36..18024";
                }
                default "100";
                description "Datagram Size";
            }
            leaf timeout  {
                type uint32 {
                    range "0..2147";
                }
                default "2";
                description "This attribute specifies the time to wait for a ping packet response,
                            in seconds";
            }
            leaf deadline  {
                type uint32 {
                    range "0..3600";
                }
                default "0";
                description "Specify a timeout, in seconds, before ping test exits regardless of
                            how many packets have been sent or received";
            }
        }
    }

    rpc ping-stop {
        if-feature feature-list:HAVE_HOSTPD;
        description "Use this RPC to stop an ongoing ping test";
        input  {
            leaf test-name  {
                type string;
                mandatory true;
                description "Ping Test Name";
            }
        }
    }

    notification ping-test-completed {
        if-feature feature-list:HAVE_HOSTPD;

        description "This notification is sent when a ping test test is completed.";

        leaf severity {
            type cml-data-types:cml_notif_severity_t;
            description "Notification severity level (value: INFO)";
        }

        leaf eventClass {
            type cml-data-types:cml_notif_class_t;
            description "Notification event class (value: STATE)";
        }

        leaf test-name {
            type  string;
        description
            "This attribute uniquely identifies the ping test instance.
                    Since the ping test is executed in asynchronous mode, this attribute
                    is used
                    to associate the ping test command with test results and to stop
                    ongoing test";
        }

        leaf test-status {
            type ipi-ping-types:ping_test_status_t;
        description
            "Ping Test Status";
        }

        leaf destination {
            type  string;
        description
            "Destination IP/IPv6 address or host name specified in the ping test";
        }
    }

}
