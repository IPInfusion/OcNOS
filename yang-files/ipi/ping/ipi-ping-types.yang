/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-ping-types.yang
*
*/

module ipi-ping-types {

    yang-version 1.1;

    namespace   "http://www.ipinfusion.com/yang/ocnos/ipi-ping-types";

    prefix "ipi-ping-types";

    organization
        "IP Infusion Inc.";

    contact
        "Address: 3965 Freedom Circle, Suite 200, Santa Clara, CA 95054
         Phone: +1 408-400-1900
         E-mail: support@ipinfusion.com
         Web: http://www.ipinfusion.com/";

    description
        "YANG version of the ipi-ping-types";


    revision "2022-06-01" {
        description "Updated the yang file with feature";
        reference " 0.2.0.";
    }

    revision "2020-12-01" {
        description "Initial Version";
        reference "Initial Version";
    }



    typedef  ping_ip_protocol_t {
        type enumeration {
            enum ipv4 {
                value 1;
                description "IPV4 Address";
            }
            enum ipv6 {
                value 2;
                description "IPv6 Address";
            }
        }
        description "type definition for PING_IP_PROTOCOL_T";
    }

    typedef  ping_packet_result_t {
        type enumeration {
            enum Success {
                value 1;
                description "Success";
            }
            enum Destination-Net-Unreachable {
                value 2;
                description "Destination Net Unreachable";
            }
            enum Destination-Host-Unreachable {
                value 3;
                description "Destination Host Unreachable";
            }
            enum Destination-Protocol-Unreachable {
                value 4;
                description "Destination Protocol Unreachable";
            }
            enum Destination-Port-Unreachable {
                value 5;
                description "Destination Port Unreachable";
            }
            enum Frag-needed-and-DF-set {
                value 6;
                description "Frag needed and DF set";
            }
            enum Source-Route-Failed {
                value 7;
                description "Source Route Failed";
            }
            enum Destination-Net-Unknown {
                value 8;
                description "Destination Net Unknown";
            }
            enum Destination-Host-Unknown {
                value 9;
                description "Destination Host Unknown";
            }
            enum Source-Host-Isolated {
                value 10;
                description "Source Host Isolated";
            }
            enum Destination-Net-Prohibited {
                value 11;
                description "Destination Net Prohibited";
            }
            enum Destination-Host-Prohibited {
                value 12;
                description "Destination Host Prohibited";
            }
            enum Destination-Net-Unreachable-for-Type-of-Service {
                value 13;
                description "Destination Net Unreachable for Type of Service";
            }
            enum Destination-Host-Unreachable-for-Type-of-Service {
                value 14;
                description "Destination Host Unreachable for Type of Service";
            }
            enum Packet-filtered {
                value 15;
                description "Packet filtered";
            }
            enum Precedence-Violation {
                value 16;
                description "Precedence Violation";
            }
            enum Precedence-Cutoff {
                value 17;
                description "Precedence Cutoff";
            }
            enum Time-to-live-exceeded {
                value 18;
                description "Time to live exceeded";
            }
            enum Frag-reassembly-time-exceeded {
                value 19;
                description "Frag reassembly time exceeded";
            }
            enum Unknown-Error {
                value 20;
                description "Unknown Error";
            }
        }
        description "type definition for PING_PACKET_RESULT_T";
    }

    typedef  ping_test_status_t {
        type enumeration {
            enum In-Progress {
                value 0;
                description "In Progress";
            }
            enum Completed {
                value 1;
                description "Completed";
            }
            enum Cancelled {
                value 2;
                description "Cancelled";
            }
            enum Temporary-failure-in-name-resolution {
                value 3;
                description "Temporary failure in name resolution";
            }
            enum Unknown-Host {
                value 4;
                description "Unknown Host";
            }
            enum Address-family-for-hostname-not-supported {
                value 5;
                description "Address family for hostname not supported";
            }
        }
        description "type definition for PING_TEST_STATUS_T";
    }

}
