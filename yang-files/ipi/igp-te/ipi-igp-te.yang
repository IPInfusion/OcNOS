/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-igp-te.yang
*
*/

module ipi-igp-te {

    yang-version 1.1;

    namespace   "http://www.ipinfusion.com/yang/ocnos/ipi-igp-te";

    prefix "ipi-igp-te";

    import ipi-interface {
        prefix ipi-interface;
        revision-date 2026-03-10;
    }

    import ipi-twamp {
        prefix ipi-twamp;
        revision-date 2025-11-10;
    }

    import ietf-yang-types {
        prefix yang;
        revision-date 2013-07-15;
    }

    import cml-data-types {
        prefix cml-data-types;
        revision-date 2026-05-15;
    }

    import ipi-twamp-types {
        prefix ipi-twamp-types;
        revision-date 2025-10-20;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for IGP-TE";


    revision "2025-11-24" {
        description "Added when tag in irb-twamp-session-parameter objectlist";
        reference " 0.6.4.";
    }

    revision "2025-10-20" {
        description "Improved CLI validation for twamp session sender-ip and reflector-ip to accept all valid input formats";
        reference " 0.6.3.";
    }

    revision "2025-09-17" {
        description "Added validation for hostname and IPv4 address formats to the TWAMP_HOSTPNAME_T data type";
        reference " 0.6.2.";
    }

    revision "2025-09-08" {
        description "Ignored SNMP generation for uni-link config/state and delay, delay-variation, loss-percentage attributes";
        reference " 0.6.1.";
    }

    revision "2025-09-04" {
        description "Removed EVPN_IRB_IF_MODE while configuring IRB interface";
        reference " 0.6.0.";
    }

    revision "2025-05-01" {
        description "Modified the TWAMP ports to include the default value 862 in the configguration range";
        reference " 0.5.2.";
    }

    revision "2025-02-19" {
        description "Removed empty attr as key from twamp session list and added streaming telemetry support";
        reference " 0.5.1.";
    }

    revision "2025-02-03" {
        description "Added SNMP Traps support for TWAMP";
        reference " 0.5.0.";
    }

    revision "2024-12-12" {
        description "Added ignore snmp generation tag";
        reference " 0.4.2.";
    }

    revision "2024-11-24" {
        description "Fixed the sender port default value";
        reference " 0.4.1.";
    }

    revision "2024-06-13" {
        description "Added dependency with control admin state in the twamp datamodel";
        reference " 0.4.0.";
    }

    revision "2023-03-10" {
        description "Added 'autoPopulate' tag 'igp-te/interfaces/interface/config' container";
        reference " 0.3.2.";
    }

    revision "2023-03-01" {
        description "Fixed the unset of delay-measurement command under IRB interfaces";
        reference " 0.3.1.";
    }

    revision "2023-01-26" {
        description "Added delay-measurement and loss-measurement commands under IRB interfaces";
        reference " 0.3.0.";
    }

    revision "2023-01-05" {
        description "Leafref correction for config container";
        reference " 0.2.1.";
    }

    revision "2022-07-30" {
        description "Updated when expressions in yang";
        reference " 0.2.0.";
    }

    revision "2022-07-19" {
        description "Update if-feature for Notification";
        reference " 0.1.8.";
    }

    revision "2022-07-09" {
        description "Added state parameters for twamp delay-measurement";
        reference " 0.1.7.";
    }

    revision "2022-06-01" {
        description "Updated the yang file with feature";
        reference " 0.1.6.";
    }

    revision "2022-04-07" {
        description "Added sender-port parameter to the TWAMP configuration";
        reference " 0.1.5.";
    }

    revision "2021-10-21" {
        description "Added IGP-TE dynamic cli with TWAMP configuration";
        reference " 0.1.4.";
    }

    revision "2021-09-01" {
        description "Changed base interface module's switchport attribute name and the datatype from bool to empty";
        reference " 0.1.3.";
    }

    revision "2021-08-08" {
        description "Fix for IGP-TE feature data model hierarchy changes";
        reference " 0.1.2.";
    }

    revision "2021-08-06" {
        description "Fix for IGP-TE feature Netconf issues";
        reference " 0.1.1.";
    }

    revision "2021-07-26" {
        description "IGP-TE feature support";
        reference " 0.1.0.";
    }

    grouping igp-te-config {
        description
            "Grouping for IGP TE configuration on interface";
        leaf delay  {
            type  uint32 {
                 range "1..16777215"  {
                    description "1..16777215: Supported range 1 - 16777215";
                 }
            }
            units "microseconds";
            description "Use this attribute to specify a unidirectional, link delay value for
                        the interface";
        } // END of delay definition.

        leaf delay-variation  {
            type  uint32 {
                 range "0..16777215"  {
                    description "0..16777215: Supported range 0 - 16777215";
                 }
            }
            units "microseconds";
            description "Use this attribute to specify a unidirectional, link delay variation
                        value for the interface";
        } // END of delay-variation definition.

        leaf loss-percentage  {
            type  decimal64 {
                 fraction-digits 6;            }
            description "Use this attribute to specify a unidirectional, link loss value for
                        the interface";
        } // END of loss-percentage definition.

    } // END of igp-te-config definition.
    grouping loss-dynamic-config {
        description
            "loss-dynamic-config";
        leaf loss-dynamic  {
            when " /ipi-igp-te:igp-te/ipi-igp-te:interfaces/ipi-igp-te:interface/ipi-igp-te:uni-link/ipi-igp-te:twamp-session-parameters/ipi-igp-te:twamp-session-parameter/ipi-igp-te:config/ipi-igp-te:reflector-ip ";
            type  empty;
            description "Use this attribute to specify a loss percentage value dynamically for
                        the interface";
        } // END of loss-dynamic definition.

    } // END of loss-dynamic-config definition.
    grouping irb-loss-dynamic-config {
        description
            "irb-loss-dynamic-config";
        leaf loss-dynamic  {
            when " /ipi-igp-te:igp-te/ipi-igp-te:interfaces/ipi-igp-te:interface/ipi-igp-te:uni-link/ipi-igp-te:twamp-session-parameters/ipi-igp-te:irb-twamp-session-parameter/ipi-igp-te:config/ipi-igp-te:reflector-ip ";
            type  empty;
            description "Use this attribute to specify a loss percentage value dynamically for
                        the interface";
        } // END of loss-dynamic definition.

    } // END of irb-loss-dynamic-config definition.
    grouping twamp-session-parameters-state {
        description
            "TWAMP session state";
        container state {
            config false;
            description
                "Operational state data";
            leaf last-advertised-calculation-time  {
                type  yang:date-and-time {
                    pattern "\\d{4}-\\d{2}-\\d{2}T\\d{2}:\\d{2}:\\d{2}(\\.\\d+)?(Z|[\\+\\-]\\d{2}:\\d{2})";
                    }
                    description "This attribute represents the time at which a calculation was made";
                } // END of last-advertised-calculation-time definition.

                leaf last-advertised-minimum-delay  {
                    type  uint64;
                    units "microseconds";
                    description "This attribute represents the minimum delay value";
                } // END of last-advertised-minimum-delay definition.

                leaf last-advertised-maximum-delay  {
                    type  uint64;
                    units "microseconds";
                    description "This attribute represents the maximum delay value";
                } // END of last-advertised-maximum-delay definition.

                leaf last-advertised-average-delay  {
                    type  uint64;
                    units "microseconds";
                    description "This attribute represents the average delay value";
                } // END of last-advertised-average-delay definition.

                leaf last-advertised-minimum-delay-variation  {
                    type  uint64;
                    units "microseconds";
                    description "This attribute represents the minimum delay variation value";
                } // END of last-advertised-minimum-delay-variation definition.

                leaf last-advertised-maximum-delay-variation  {
                    type  uint64;
                    units "microseconds";
                    description "This attribute represents the maximum delay variation value";
                } // END of last-advertised-maximum-delay-variation definition.

                leaf last-advertised-average-delay-variation  {
                    type  uint64;
                    units "microseconds";
                    description "This attribute represents the average delay variation value";
                } // END of last-advertised-average-delay-variation definition.

                leaf last-advertised-packets-sent  {
                    type  yang:counter64;
                    description "This attribute represents the amount of sent packets in a measurement
                                interval";
                } // END of last-advertised-packets-sent definition.

                leaf last-advertised-packets-received  {
                    type  yang:counter64;
                    description "This attribute represents the amount of received packets in a
                                measurement interval";
                } // END of last-advertised-packets-received definition.

                leaf last-advertised-packets-timeout  {
                    type  yang:counter64;
                    description "This attribute represents the amount of lost packets in a measurement
                                interval";
                } // END of last-advertised-packets-timeout definition.

                leaf last-advertised-packet-loss  {
                    type  decimal64 {
                         fraction-digits 4;                    }
                    description "This attribute represents the percentage of lost packets in a
                                measurement interval";
                } // END of last-advertised-packet-loss definition.

                leaf last-calculated-calculation-time  {
                    type  yang:date-and-time {
                        pattern "\\d{4}-\\d{2}-\\d{2}T\\d{2}:\\d{2}:\\d{2}(\\.\\d+)?(Z|[\\+\\-]\\d{2}:\\d{2})";
                        }
                        description "This attribute represents the time at which a calculation was made";
                    } // END of last-calculated-calculation-time definition.

                    leaf last-calculated-minimum-delay  {
                        type  uint64;
                        units "microseconds";
                        description "This attribute represents the minimum delay value";
                    } // END of last-calculated-minimum-delay definition.

                    leaf last-calculated-maximum-delay  {
                        type  uint64;
                        units "microseconds";
                        description "This attribute represents the maximum delay value";
                    } // END of last-calculated-maximum-delay definition.

                    leaf last-calculated-average-delay  {
                        type  uint64;
                        units "microseconds";
                        description "This attribute represents the average delay value";
                    } // END of last-calculated-average-delay definition.

                    leaf last-calculated-minimum-delay-variation  {
                        type  uint64;
                        units "microseconds";
                        description "This attribute represents the minimum delay variation value";
                    } // END of last-calculated-minimum-delay-variation definition.

                    leaf last-calculated-maximum-delay-variation  {
                        type  uint64;
                        units "microseconds";
                        description "This attribute represents the maximum delay variation value";
                    } // END of last-calculated-maximum-delay-variation definition.

                    leaf last-calculated-average-delay-variation  {
                        type  uint64;
                        units "microseconds";
                        description "This attribute represents the average delay variation value";
                    } // END of last-calculated-average-delay-variation definition.

                    leaf last-calculated-packets-sent  {
                        type  yang:counter64;
                        description "This attribute represents the amount of sent packets in a measurement
                                    interval";
                    } // END of last-calculated-packets-sent definition.

                    leaf last-calculated-packets-received  {
                        type  yang:counter64;
                        description "This attribute represents the amount of received packets in a
                                    measurement interval";
                    } // END of last-calculated-packets-received definition.

                    leaf last-calculated-packets-timeout  {
                        type  yang:counter64;
                        description "This attribute represents the amount of lost packets in a measurement
                                    interval";
                    } // END of last-calculated-packets-timeout definition.

                    leaf last-calculated-packet-loss  {
                        type  decimal64 {
                             fraction-digits 4;                        }
                        description "This attribute represents the percentage of lost packets in a
                                    measurement interval";
                    } // END of last-calculated-packet-loss definition.

        } // END of state-container definition.
    } // END of twamp-session-parameters-state definition.
    grouping twamp-session-parameters-config {
        description
            "TWAMP session parameters";
        leaf reflector-ip  {
            type  cml-data-types:cml_hostpname_t;
            description "Use this attribute to set the reflector IP.";
        } // END of reflector-ip definition.

        leaf reflector-port  {
            type  ipi-twamp-types:twamp_udp_port_t;
            description "Use this attribute to set the reflector port.";
        } // END of reflector-port definition.

        leaf sender-ip  {
            type  cml-data-types:cml_hostpname_t;
            description "Use this attribute to set the sender IP.";
        } // END of sender-ip definition.

        leaf sender-port  {
            type  ipi-twamp-types:twamp_udp_port_t;
            description "Use this attribute to set the sender port.";
        } // END of sender-port definition.

        leaf dscp  {
            type  string {
                length "1..8";
                pattern "[^?' =,>|]+";
            }
            description "Use this attribute to classify traffic based on the Differentiated
                        Services Code Point (DSCP) value. The DSCP value range is
                        0-63.Warning: In CLI show running, DSCP values with well-known names
                        (ex.: af11, cs0) will be displayed as such.On Netconf, DSCP values
                        will always be numeric. The string type allow up to 8 characters on
                        well-known name.";
        } // END of dscp definition.

    } // END of twamp-session-parameters-config definition.
    grouping uni-link-loss-a-bit-config {
        description
            "Grouping for uni-link-loss a-bit configuration on interface";
        leaf loss-a-bit-min  {
            type  decimal64 {
                 fraction-digits 6;            }
            description "Unidirectional link loss a-bit";
        } // END of loss-a-bit-min definition.

        leaf loss-a-bit-max  {
            type  decimal64 {
                 fraction-digits 6;            }
            description "";
        } // END of loss-a-bit-max definition.

    } // END of uni-link-loss-a-bit-config definition.
    grouping uni-link-delay-a-bit-config {
        description
            "Configuration items for uni-link delay threshold";
        leaf a-bit-min  {
            type  uint32 {
                 range "1..16777215"  {
                    description "1..16777215: Supported range 1 - 16777215";
                 }
            }
            description "Unidirectional link delay a-bit minimum";
        } // END of a-bit-min definition.

        leaf a-bit-max  {
            type  uint32 {
                 range "1..16777215"  {
                    description "1..16777215: Supported range 1 - 16777215";
                 }
            }
            units "microseconds";
            description "";
        } // END of a-bit-max definition.

    } // END of uni-link-delay-a-bit-config definition.
    grouping min-max-uni-link-delay-config {
        description
            "Configuration items for min/max delay";
        leaf min-value  {
            type  uint32 {
                 range "1..16777215"  {
                    description "1..16777215: Supported range 1 - 16777215";
                 }
            }
            units "microseconds";
            description "Min max Unidirectional link delay";
        } // END of min-value definition.

        leaf max-value  {
            type  uint32 {
                 range "1..16777215"  {
                    description "1..16777215: Supported range 1 - 16777215";
                 }
            }
            units "microseconds";
            description "";
        } // END of max-value definition.

    } // END of min-max-uni-link-delay-config definition.
    grouping min-max-uni-link-delay-a-bit-config {
        description
            "Configuration items for min/max delay threshold";
        leaf a-bit-min-range-minimum  {
            type  uint32 {
                 range "1..16777215"  {
                    description "1..16777215: Supported range 1 - 16777215";
                 }
            }
            units "microseconds";
            description "Min/Max Unidirectional link delay a-bit";
        } // END of a-bit-min-range-minimum definition.

        leaf a-bit-min-range-maximum  {
            type  uint32 {
                 range "1..16777215"  {
                    description "1..16777215: Supported range 1 - 16777215";
                 }
            }
            units "microseconds";
            description "";
        } // END of a-bit-min-range-maximum definition.

        leaf a-bit-max-range-minimum  {
            type  uint32 {
                 range "1..16777215"  {
                    description "1..16777215: Supported range 1 - 16777215";
                 }
            }
            units "microseconds";
            description "";
        } // END of a-bit-max-range-minimum definition.

        leaf a-bit-max-range-maximum  {
            type  uint32 {
                 range "1..16777215"  {
                    description "1..16777215: Supported range 1 - 16777215";
                 }
            }
            units "microseconds";
            description "";
        } // END of a-bit-max-range-maximum definition.

    } // END of min-max-uni-link-delay-a-bit-config definition.
    grouping igp-te-params-config {
        description
            "Grouping for IGP TE Paramaters";
        container uni-link {
            description
                "Set IGP TE uni-link parameters";
            container config {
                description
                    "Configuration data for IGP-TE parameters";
                uses igp-te-config;
            } // END of config-container definition.
            container state {
                config false;
                description
                    "Operational state data";
                uses igp-te-config;
            } // END of state-container definition.
            container twamp-loss-parameter {
                if-feature feature-list:HAVE_TWAMP;
                description
                    "TWAMP loss parameter";
                container config {
                    description
                        "Configuration data";
                    uses loss-dynamic-config;
                } // END of config-container definition.
                container state {
                    config false;
                    description
                        "Operational state data";
                    uses loss-dynamic-config;
                } // END of state-container definition.
            } // END of twamp-loss-parameter-container definition.
            container irb-twamp-loss-parameter {
                if-feature feature-list:HAVE_TWAMP;
                description
                    "TWAMP loss parameter for IRB interfaces";
                container config {
                    description
                        "Configuration data";
                    uses irb-loss-dynamic-config;
                } // END of config-container definition.
                container state {
                    config false;
                    description
                        "Operational state data";
                    uses irb-loss-dynamic-config;
                } // END of state-container definition.
            } // END of irb-twamp-loss-parameter-container definition.
            container twamp-session-parameters {
                if-feature feature-list:HAVE_TWAMP;
                description
                    "TWAMP session parameters";

                list twamp-session-parameter {
                when " /ipi-twamp:twamp/ipi-twamp:light/ipi-twamp:control/ipi-twamp:config/ipi-twamp:administrative-state ";
                    key "reflector-ip";
                    max-elements 1;
                    description
                        "TWAMP session parameter list";
                    leaf reflector-ip  {
                        type  leafref {
                            path  "../config/reflector-ip";
                        }
                        description "Use this attribute to set the reflector IP and start TWAMP delay
                                    measurement for the interface";
                    } // END of reflector-ip definition.

                    container config {
                        description
                            "Configuration data";
                        uses twamp-session-parameters-config;
                    } // END of config-container definition.
                    container state {
                        config false;
                        description
                            "Operational state data";
                        uses twamp-session-parameters-config;
                    } // END of state-container definition.
                    container statistics {
                        config false;
                        description
                            "Operational state data";
                        uses twamp-session-parameters-state;
                    } // END of statistics-container definition.
                } // End of twamp-session-parameter-list

                list irb-twamp-session-parameter {
                when " /ipi-twamp:twamp/ipi-twamp:light/ipi-twamp:control/ipi-twamp:config/ipi-twamp:administrative-state ";
                    key "reflector-ip";
                    max-elements 1;
                    description
                        "TWAMP session parameter list for IRB interfaces";
                    leaf reflector-ip  {
                        type  leafref {
                            path  "../config/reflector-ip";
                        }
                        description "Use this attribute to set the reflector IP and start TWAMP delay
                                    measurement for the interface";
                    } // END of reflector-ip definition.

                    container config {
                        description
                            "Configuration data";
                        uses twamp-session-parameters-config;
                    } // END of config-container definition.
                    container state {
                        config false;
                        description
                            "Operational state data";
                        uses twamp-session-parameters-config;
                    } // END of state-container definition.
                    container statistics {
                        config false;
                        description
                            "Operational state data";
                        uses twamp-session-parameters-state;
                    } // END of statistics-container definition.
                } // End of irb-twamp-session-parameter-list
            } // END of twamp-session-parameters-container definition.
            container delay-threshold {
                description
                    "This container defines the min and max values for uni-link-delay";

                list a-bit {
                    key "a-bit-min a-bit-max";
                    max-elements 1;
                    description
                        "This objectlist defines the min and max threshold values";
                    leaf a-bit-min  {
                        type  leafref {
                            path  "../config/a-bit-min";
                        }
                        description "Unidirectional link delay a-bit minimum";
                    } // END of a-bit-min definition.

                    leaf a-bit-max  {
                        type  leafref {
                            path  "../config/a-bit-max";
                        }
                        description "";
                    } // END of a-bit-max definition.

                    container config {
                        description
                            "This container defines uni-link-delay threshold configurations.";
                        uses uni-link-delay-a-bit-config;
                    } // END of config-container definition.
                    container state {
                        config false;
                        description
                            "This container defines uni-link-delay threshold Operational
                                    parameters.";
                        uses uni-link-delay-a-bit-config;
                    } // END of state-container definition.
                } // End of a-bit-list
            } // END of delay-threshold-container definition.
            container min-max-delay {
                description
                    "This container defines the min and max values of delay";

                list delay {
                    key "min-value max-value";
                    max-elements 1;
                    description
                        "This objectlist defines the min and max values";
                    leaf min-value  {
                        type  leafref {
                            path  "../config/min-value";
                        }
                        description "Min max Unidirectional link delay";
                    } // END of min-value definition.

                    leaf max-value  {
                        type  leafref {
                            path  "../config/max-value";
                        }
                        description "";
                    } // END of max-value definition.

                    container config {
                        description
                            "This container defines the min/max static configurations.";
                        uses min-max-uni-link-delay-config;
                    } // END of config-container definition.
                    container state {
                        config false;
                        description
                            "This container defines the min/max static Operational parameters.";
                        uses min-max-uni-link-delay-config;
                    } // END of state-container definition.
                } // End of delay-list
            } // END of min-max-delay-container definition.
            container loss {
                description
                    "This container defines the min and max values for uni-link-loss";

                list threshold {
                    key "loss-a-bit-min loss-a-bit-max";
                    max-elements 1;
                    description
                        "This objectlist defines the min and max values for uni-link-loss";
                    leaf loss-a-bit-min  {
                        type  leafref {
                            path  "../config/loss-a-bit-min";
                        }
                        description "Unidirectional link loss a-bit";
                    } // END of loss-a-bit-min definition.

                    leaf loss-a-bit-max  {
                        type  leafref {
                            path  "../config/loss-a-bit-max";
                        }
                        description "";
                    } // END of loss-a-bit-max definition.

                    container config {
                        description
                            "This container defines the min/max static configurations.";
                        uses uni-link-loss-a-bit-config;
                    } // END of config-container definition.
                    container state {
                        config false;
                        description
                            "This container defines the min/max static Operational parameters.";
                        uses uni-link-loss-a-bit-config;
                    } // END of state-container definition.
                } // End of threshold-list
            } // END of loss-container definition.
            container min-max-delay-threshold {
                description
                    "This container defines  the min and max values for
                            min-max-uni-link-delay";

                list a-bit {
                    key "a-bit-min-range-minimum a-bit-min-range-maximum a-bit-max-range-minimum a-bit-max-range-maximum";
                    max-elements 1;
                    description
                        "This objectlist defines the min and max threshold values";
                    leaf a-bit-min-range-minimum  {
                        type  leafref {
                            path  "../config/a-bit-min-range-minimum";
                        }
                        description "Min/Max Unidirectional link delay a-bit";
                    } // END of a-bit-min-range-minimum definition.

                    leaf a-bit-min-range-maximum  {
                        type  leafref {
                            path  "../config/a-bit-min-range-maximum";
                        }
                        description "";
                    } // END of a-bit-min-range-maximum definition.

                    leaf a-bit-max-range-minimum  {
                        type  leafref {
                            path  "../config/a-bit-max-range-minimum";
                        }
                        description "";
                    } // END of a-bit-max-range-minimum definition.

                    leaf a-bit-max-range-maximum  {
                        type  leafref {
                            path  "../config/a-bit-max-range-maximum";
                        }
                        description "";
                    } // END of a-bit-max-range-maximum definition.

                    container config {
                        description
                            "This container defines the min/max static configurations.";
                        uses min-max-uni-link-delay-a-bit-config;
                    } // END of config-container definition.
                    container state {
                        config false;
                        description
                            "This container defines the min/max static Operational parameters.";
                        uses min-max-uni-link-delay-a-bit-config;
                    } // END of state-container definition.
                } // End of a-bit-list
            } // END of min-max-delay-threshold-container definition.
        } // END of uni-link-container definition.
    } // END of igp-te-params-config definition.
    grouping igp-interface-config {
        description
            "Grouping for IGP TE interface Paramaters";
        leaf name  {
            type  leafref {
                path  "/ipi-interface:interfaces/ipi-interface:interface/ipi-interface:name";
            }
            description "Interface name for which igp-te params are being configured";
        } // END of name definition.

    } // END of igp-interface-config definition.

    grouping  igp-te-grouping {
    description
        "Configuration data for igp-te";
    container igp-te {
        if-feature feature-list:HAVE_TE;
        description
            "Configuration data for igp-te";
        container interfaces {
            description
                "Top level container for interfaces, including configuration and state
                        data";

            list interface {
                key "name";
                description
                    "IGP TE interfaces";
                leaf name  {
                    type  leafref {
                        path  "../config/name";
                    }
                    description "Interface name for which igp-te params are being configured";
                } // END of name definition.

                container config {
                    description
                        "Configuration data for IGP-TE interface parameters";
                    uses igp-interface-config;
                } // END of config-container definition.
                container state {
                    config false;
                    description
                        "Operational state data";
                    uses igp-interface-config;
                } // END of state-container definition.
                uses igp-te-params-config;
            } // End of interface-list
        } // END of interfaces-container definition.
    } // END of igp-te-container definition.
    } // END of igp-te-grouping definition.

    uses igp-te-grouping;

    rpc twamp-clear-measurement-intf {
        if-feature feature-list:HAVE_TWAMP;
        if-feature feature-list:HAVE_TE;
        description "Clear and restart the twamp measurement on an interface";
        input  {
            leaf interface-name  {
                type string {
                    length "1..128";
                }
                mandatory true;
                description "Interface name";
            }
        }
    }

    rpc twamp-clear-measurement-all {
        if-feature feature-list:HAVE_TWAMP;
        if-feature feature-list:HAVE_TE;
        description "Clear and restart the twamp measurement on all interfaces";
    }

    notification delay-measurement-status {
        if-feature feature-list:HAVE_TE;
        if-feature feature-list:HAVE_TWAMP;

        description "This event is generated when the interface delay-measurement status changes.";

        leaf severity {
            type cml-data-types:cml_notif_severity_t;
            description "Notification severity level (value: CRITICAL)";
        }

        leaf eventClass {
            type cml-data-types:cml_notif_class_t;
            description "Notification event class (value: MESSAGE)";
        }

        leaf message {
            type string;
            description " alarm message notification";
        }
    }

    notification twamp-delay-measurement-threshold-crossed {
        if-feature feature-list:HAVE_TE;
        if-feature feature-list:HAVE_TWAMP;

        description "Indicates that the TWAMP Delay Measurement has crossed the configured threshold.";

        leaf severity {
            type cml-data-types:cml_notif_severity_t;
            description "Notification severity level (value: MINOR)";
        }

        leaf eventClass {
            type cml-data-types:cml_notif_class_t;
            description "Notification event class (value: STATE)";
        }

        leaf reflector-ip {
            type cml-data-types:cml_hostpname_t;
        description
            "Use this attribute to set the reflector IP and start TWAMP delay
                    measurement for the interface";
        }

        leaf name {
            type  string;
        description
            "Interface name for which igp-te params are being configured";
        }

        leaf last-calculated-average-delay {
            type  uint64;
        description
            "This attribute represents the average delay value";
        }
    }

    notification twamp-delay-measurement-loss-changed {
        if-feature feature-list:HAVE_TE;
        if-feature feature-list:HAVE_TWAMP;

        description "Indicates that the TWAMP Delay Measurement loss has changed.";

        leaf severity {
            type cml-data-types:cml_notif_severity_t;
            description "Notification severity level (value: MINOR)";
        }

        leaf eventClass {
            type cml-data-types:cml_notif_class_t;
            description "Notification event class (value: STATE)";
        }

        leaf reflector-ip {
            type cml-data-types:cml_hostpname_t;
        description
            "Use this attribute to set the reflector IP and start TWAMP delay
                    measurement for the interface";
        }

        leaf name {
            type  string;
        description
            "Interface name for which igp-te params are being configured";
        }

        leaf last-advertised-packet-loss {
            type  decimal64 {
                 fraction-digits 4;            }
        description
            "This attribute represents the percentage of lost packets in a
                    measurement interval";
        }
    }

}
