/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-g8031-elps.yang
*
*/

submodule ipi-g8031-elps {

    yang-version 1.1;

    belongs-to  ipi-g8031 { prefix ipi-g8031; }

    import feature-list {
        prefix feature-list;
        revision-date 2026-09-15;
    }

    import ipi-g8031-elps-types {
        prefix ipi-g8031-elps-types;
        revision-date 2023-12-20;
    }

    import ietf-yang-types {
        prefix yang;
        revision-date 2013-07-15;
    }

    import ipi-interface {
        prefix ipi-interface;
        revision-date 2026-03-10;
    }

    import cml-data-types {
        prefix cml-data-types;
        revision-date 2026-05-15;
    }

    organization
        "IP Infusion Inc.";

    contact
        "Address: 3965 Freedom Circle, Suite 200, Santa Clara, CA 95054
         Phone: +1 408-400-1900
         E-mail: support@ipinfusion.com
         Web: http://www.ipinfusion.com/";

    description
        "Ethernet Linear Protection Switching";


    revision "2025-09-17" {
        description "Blocking Bridge-domain and cross-connect for all XGS (DC) platforms";
        reference " 1.0.3.";
    }

    revision "2025-02-09" {
        description "Added CML_UNIQUE for the protection group";
        reference " 1.0.2.";
    }

    revision "2024-08-22" {
        description "Changed max value for g8031 instance profile and group names";
        reference " 1.0.1.";
    }

    revision "2024-08-12" {
        description "Added notification for g8031 active path notify";
        reference " 1.0.0.";
    }

    revision "2024-08-01" {
        description "commented the rpc of clear g8031 eps-instance";
        reference " 0.9.3.";
    }

    revision "2024-07-17" {
        description "Getapi support for show g8031 eps-instance INSTANCE_NAME";
        reference " 0.9.2.";
    }

    revision "2024-07-05" {
        description "Added all option for clear g8031 eps-instance";
        reference " 0.9.1.";
    }

    revision "2024-06-28" {
        description "Added Length and corrected spelling of some attributes";
        reference " 0.9.0.";
    }

    revision "2024-06-06" {
        description "Renamed few attributes names and description";
        reference " 0.8.1.";
    }

    revision "2023-11-24" {
        description "Renamed few attributes with repeated parent node name";
        reference " 0.8.0.";
    }

    revision "2023-11-15" {
        description "New ELPS CLI Restructuring Support";
        reference " 0.7.0.";
    }

    revision "2023-09-19" {
        description "Added implicit_delete tag under timer container";
        reference " 0.6.0.";
    }

    revision "2023-03-06" {
        description "Added When tag for no-debug-all command";
        reference " 0.5.0.";
    }

    revision "2022-08-18" {
        description "Updated G.8031 RPCs parameter name for bridge instance";
        reference " 0.4.1.";
    }

    revision "2022-08-10" {
        description "Debug hierarchy change";
        reference " 0.4.0.";
    }

    revision "2022-07-30" {
        description "Fixing db-sync issue on debug container";
        reference " 0.3.5.";
    }

    revision "2022-07-06" {
        description "Removed implicit delete tag on debug config container";
        reference " 0.3.4.";
    }

    revision "2022-06-01" {
        description "Updated the yang file with feature";
        reference " 0.3.3.";
    }

    revision "2022-04-27" {
        description "Added debug support for g8031";
        reference " 0.3.2.";
    }

    revision "2022-04-06" {
        description "Added dependency between protection-type and elps-instance-id";
        reference " 0.3.1.";
    }

    revision "2022-03-17" {
        description "Restructured module as per open-config";
        reference " 0.3.0.";
    }

    revision "2021-12-09" {
        description "Updated dependentObject tag where CFM XPath is used";
        reference " 0.2.0.";
    }

    revision "2021-09-25" {
        description "Admin-cmds changed to RPC due to DB-Sync issues";
        reference " 0.1.2.";
    }

    revision "2021-09-20" {
        description "Block local-lockout configuration";
        reference " 0.1.1.";
    }

    revision "2021-05-14" {
        description "Initial Version";
        reference " 0.1.0.";
    }

    grouping g8031-debug-terminal-state {
        description
            "Bridge Ethernet Linear Protection Switching debug state attributes";
        leaf terminal-debug-status  {
            type  ipi-g8031-elps-types:g8031_debug_t;
            description "Displays terminal debug options enabled for G.8031";
        } // END of terminal-debug-status definition.

    } // END of g8031-debug-terminal-state definition.
    grouping g8031-debug-config {
        description
            "Bridge Ethernet Linear Protection Switching debug configuration
                        attributes";
        leaf options  {
            type  ipi-g8031-elps-types:g8031_debug_t;
            description "Supported debug options for g8031";
        } // END of options definition.

    } // END of g8031-debug-config definition.
    grouping elps-traffic-switch-config {
        description
            "Grouping for Ethernet Linear Protection Switching traffic switching
                        commands";
        leaf local-freeze  {
            // when " ipi-g8031-elps:elps/config/protection-type ";
            type  empty;
            description "Freezes the state of the protection group.";
        } // END of local-freeze definition.

    } // END of elps-traffic-switch-config definition.
    grouping elps-timers-config {
        description
            "Ethernet Linear Protection Switching configuration attributes for
                        restoration and swicthing timers";
        leaf wait-to-restore  {
            // when " ipi-g8031-elps:elps/config/protection-type + ipi-g8031-elps:elps/config/enable-revertive-mode ";
            type  uint16 {
                 range "300..720"  {
                    description "300..720: Supported range 300 - 720";
                 }
            }
            units "seconds";
            description "EPS wait-to-restore timer";
        } // END of wait-to-restore definition.

        leaf hold-off  {
            // when " ipi-g8031-elps:elps/config/protection-type ";
            type  uint8 {
                 range "0..10"  {
                    description "0..10: Supported range 0 - 10";
                 }
            }
            units "seconds";
            description "EPS hold-off timer";
        } // END of hold-off definition.

    } // END of elps-timers-config definition.
    grouping elps-state {
        description
            "Bridge Ethernet Linear Protection switching state data";
        leaf direction  {
            type  ipi-g8031-elps-types:g8031_direction_type_t;
            description "Direction of ELPS";
        } // END of direction definition.

        leaf active-path  {
            type  ipi-g8031-elps-types:g8031_active_path_type_t;
            description "Indicates the path currently active";
        } // END of active-path definition.

        leaf request-signal  {
            type  ipi-g8031-elps-types:g8031_request_signal_type_t;
            description "Request signal operation state";
        } // END of request-signal definition.

        leaf current-state  {
            type  ipi-g8031-elps-types:g8031_current_state_type_t;
            description "Current state of ELPS";
        } // END of current-state definition.

        leaf failure-of-protocol-state  {
            type  ipi-g8031-elps-types:g8031_failure_of_protocol_state_type_t;
            description "Indicates the status of failure in ELPS protocol";
        } // END of failure-of-protocol-state definition.

        leaf rx-lps-frame-count  {
            type  yang:counter32;
            description "LPS PDU Rx count";
        } // END of rx-lps-frame-count definition.

        leaf tx-lps-frame-count  {
            type  yang:counter32;
            description "LPS PDU Tx count";
        } // END of tx-lps-frame-count definition.

    } // END of elps-state definition.
    grouping elps-config {
        description
            "Ethernet Linear Protection Switching configuration attributes";
        leaf protection-type  {
            // when " ipi-g8031:g8031/instances/instance/config/elps-instance-id ";
            type  ipi-g8031-elps-types:g8031_elps_protection_type_t;
            description "protection bridge mode";
        } // END of protection-type definition.

        leaf enable-revertive-mode  {
            // when " ipi-g8031-elps:elps/config/protection-type ";
            type  empty;
            description "protection restoration mode";
        } // END of enable-revertive-mode definition.

        leaf level-identifier  {
            // when " ipi-g8031-elps:elps/config/protection-type ";
            type  uint8 {
                 range "0..7"  {
                    description "0..7: Supported range 0 - 7";
                 }
            }
            description "Ethernet Linear Protection switching level";
        } // END of level-identifier definition.

    } // END of elps-config definition.
    grouping elps-timers-top {
        description
            "Ethernet Linear Protection Switching configuration attributes for
                        restoration and swicthing timers";
        container timers {
            description
                "Top level configuration container for Ethernet Linear Protection
                        Switching restoration and switching timers";
            container config {
                description
                    "Configuration container for Ethernet Linear Protection Switching
                            restoration and switching timers";
                uses elps-timers-config;
            } // END of config-container definition.
            container state {
                config false;
                description
                    "Top level state container for Ethernet Linear Protection Switching";
                uses elps-timers-config;
            } // END of state-container definition.
        } // END of timers-container definition.
    } // END of elps-timers-top definition.
    grouping elps-traffic-switch-top {
        description
            "Top level grouping for Ethernet Linear Protection Switching traffic
                        switching commands";
        container traffic-switch {
            description
                "Top level configuration data for Ethernet Linear Protection Switching
                        traffic switching commands";
            container config {
                description
                    "Configuration data for Ethernet Linear Protection Switching traffic
                            switching commands";
                uses elps-traffic-switch-config;
            } // END of config-container definition.
            container state {
                config false;
                description
                    "Top level state container for Ethernet Linear Protection Switching";
                uses elps-traffic-switch-config;
            } // END of state-container definition.
        } // END of traffic-switch-container definition.
    } // END of elps-traffic-switch-top definition.
    grouping elps-top {
        description
            "Ethernet Linear Protection Switching configuration attributes for
                        restoration and swicthing type";
        container config {
            description
                "Top level configuration container for Ethernet Linear Protection
                        Switching";
            uses elps-config;
        } // END of config-container definition.
        container state {
            config false;
            description
                "Top level state container for Ethernet Linear Protection Switching";
            uses elps-config;
            uses elps-state;
        } // END of state-container definition.
        uses elps-timers-top;
        uses elps-traffic-switch-top;
    } // END of elps-top definition.
    grouping g8031-control-vlan-config {
        description
            "Grouping for ELPS control VLAN configuration data";
        leaf vlan-id  {
            // when " ipi-g8031-elps:g8031-elps/eps-instances/eps-instance/config/eps-protection-group ";
            type  uint16 {
                 range "2..4094"  {
                    description "2..4094: Supported range 2 - 4094";
                 }
            }
            description "Control VLAN-ID used by ELPS instance to send and receive the RAPS
                        messages";
        } // END of vlan-id definition.

        leaf inner-vlan-id  {
            // when " ipi-g8031-elps:g8031-elps/eps-instances/eps-instance/config/eps-protection-group ";
            type  uint16 {
                 range "2..4094"  {
                    description "2..4094: Supported range 2 - 4094";
                 }
            }
            description "Control inner VLAN-ID used by ELPS instance to send and receive the
                        RAPS messages";
        } // END of inner-vlan-id definition.

    } // END of g8031-control-vlan-config definition.
    grouping g8031-control-vlan-top {
        description
            "Grouping for ELPS  channel VLAN";
        container control-vlans {
            description
                "Container for ELPS channel VLAN";

            list control-vlan {
            // when " ipi-g8031-elps:g8031-elps/eps-instances/eps-instance/config/eps-protection-group ";
                key "vlan-id";
                max-elements 1;
                description
                    "List of ELPS control VLANs";
                leaf vlan-id  {
                    type  leafref {
                        path  "../config/vlan-id";
                    }
                    description "Control vlan-id used by ELPS instance to send and receive the RAPS
                                messages";
                } // END of vlan-id definition.

                container config {
                    description
                        "Configuration data for ELPS control VLAN";
                    uses g8031-control-vlan-config;
                } // END of config-container definition.
                container state {
                    config false;
                    description
                        "Operational state data for ELPS control VLAN";
                    uses g8031-control-vlan-config;
                } // END of state-container definition.
            } // End of control-vlan-list
        } // END of control-vlans-container definition.
    } // END of g8031-control-vlan-top definition.
    grouping g8031-aps-channel-config {
        description
            "Grouping for ELPS APS channel configuration data";
        leaf level  {
            type  uint8 {
                 range "0..7"  {
                    description "0..7: Supported range 0 - 7";
                 }
            }
            description "APS level value.";
        } // END of level definition.

    } // END of g8031-aps-channel-config definition.
    grouping g8031-aps-channel-top {
        description
            "Grouping for ELPS APS channel";
        container aps-channel {
            description
                "Container for ELPS APS channel";
            container config {
                description
                    "Configuration data for ELPS APS channel";
                uses g8031-aps-channel-config;
            } // END of config-container definition.
            container state {
                config false;
                description
                    "Operational state data for ELPS APS channel";
                uses g8031-aps-channel-config;
            } // END of state-container definition.
        } // END of aps-channel-container definition.
    } // END of g8031-aps-channel-top definition.
    grouping g8031-data-vlan-config {
        description
            "Grouping for ELPS data VLAN configuration data grouping";
        leaf data-vlan  {
            type  cml-data-types:cml_range_t;
            description "List of VLAN-IDs, protected by ring instance. For
                        example '2, 3-7, 9, 10-100'
                        VLAN-IDs MUST not overlap with VLAN-IDs of any other
                        instance of the same ring.";
        } // END of data-vlan definition.

    } // END of g8031-data-vlan-config definition.
    grouping g8031-data-vlan-top {
        description
            "Grouping for ELPS data VLAN";
        container data {
            // when " ipi-g8031-elps:g8031-elps/eps-instances/eps-instance/config/eps-protection-group ";
            description
                "Container for ELPS data VLAN";
            container config {
                description
                    "Configuration data for ELPS data VLAN";
                uses g8031-data-vlan-config;
            } // END of config-container definition.
            container state {
                config false;
                description
                    "Operational state data for ELPS data VLAN";
                uses g8031-data-vlan-config;
            } // END of state-container definition.
        } // END of data-container definition.
    } // END of g8031-data-vlan-top definition.
    grouping eps-instance-state {
        description
            "Eps instance state data";
        leaf eps-id  {
            type  uint8;
            description "use this attribute to set the eps id for eps instance";
        } // END of eps-id definition.

        leaf bridge  {
            type  string {
                length "1..1965";
                pattern "[^?' =,>|]+";
            }
            description "Use this attribute to set the bridge";
        } // END of bridge definition.

        leaf direction  {
            type  string {
                length "1..1965";
                pattern "[^?' =,>|]+";
            }
            description "Use this attribute to set the direction for eps instance";
        } // END of direction definition.

        leaf revertive  {
            type  string {
                length "1..1965";
                pattern "[^?' =,>|]+";
            }
            description "Use this attribute to set the revertive for eps instance";
        } // END of revertive definition.

        leaf working-port  {
            type  string {
                length "1..1965";
                pattern "[^?' =,>|]+";
            }
            description "Use this attribute to set the working port for eps instance";
        } // END of working-port definition.

        leaf working-port-ifindex  {
            type  uint32;
            description "Use this attribute to set the working port ifindex";
        } // END of working-port-ifindex definition.

        leaf wp-status  {
            type  string {
                length "1..1965";
                pattern "[^?' =,>|]+";
            }
            description "Use this attribute to set the working port status";
        } // END of wp-status definition.

        leaf protection-port  {
            type  string {
                length "1..1965";
                pattern "[^?' =,>|]+";
            }
            description "Use this attribute to set the protection port";
        } // END of protection-port definition.

        leaf protection-port-ifindex  {
            type  uint32;
            description "Use this attribute to set the protection port ifindex";
        } // END of protection-port-ifindex definition.

        leaf pp-status  {
            type  string {
                length "1..1965";
                pattern "[^?' =,>|]+";
            }
            description "Use this attribute to set the protection port status";
        } // END of pp-status definition.

        leaf current-state  {
            type  string {
                length "1..1965";
            }
            description "USe this attribute to set the current state";
        } // END of current-state definition.

        leaf request-signal  {
            type  string {
                length "1..1965";
                pattern "[^?' =,>|]+";
            }
            description "Use this attribute to set the request signal";
        } // END of request-signal definition.

        leaf active-path  {
            type  string {
                length "1..1965";
                pattern "[^?' =,>|]+";
            }
            description "Use this attribute to set the active path";
        } // END of active-path definition.

        leaf dfop-state  {
            type  string {
                length "1..1965";
            }
            description "Use this attribute to set the dfop state";
        } // END of dfop-state definition.

        leaf local-freeze  {
            type  string {
                length "1..1965";
                pattern "[^?' =,>|]+";
            }
            description "Use this attribute to set the local freeze";
        } // END of local-freeze definition.

        leaf local-lockout  {
            type  string {
                length "1..1965";
                pattern "[^?' =,>|]+";
            }
            description "Use this attribute to set the local lockout";
        } // END of local-lockout definition.

        leaf timer-status  {
            type  string {
                length "1..1965";
                pattern "[^?' =,>|]+";
            }
            description "Use this attribute to set the WTR";
        } // END of timer-status definition.

        leaf hold-off  {
            type  string {
                length "1..1965";
                pattern "[^?' =,>|]+";
            }
            description "Use this attribute to set the hold off state";
        } // END of hold-off definition.

        leaf working-cfm-mep-id  {
            type  uint16;
            description "Use this attribute to set the mep id for working cfm";
        } // END of working-cfm-mep-id definition.

        leaf working-cfm-cc-interval  {
            type  string {
                length "1..1965";
                pattern "[^?' =,>|]+";
            }
            description "Use this attribute to set the cc interval working cfm";
        } // END of working-cfm-cc-interval definition.

        leaf working-cfm-domain  {
            type  string {
                length "1..1965";
                pattern "[^?' =,>|]+";
            }
            description "Use this attribute to set the domain name for working cfm";
        } // END of working-cfm-domain definition.

        leaf working-cfm-ma  {
            type  string {
                length "1..1965";
                pattern "[^?' =,>|]+";
            }
            description "Use this attribute to set the ma name for working cfm";
        } // END of working-cfm-ma definition.

        leaf protection-cfm-mep-id  {
            type  uint16;
            description "Use this attribute to set the mep id for protection cfm";
        } // END of protection-cfm-mep-id definition.

        leaf protection-cfm-cc-interval  {
            type  string {
                length "1..1965";
                pattern "[^?' =,>|]+";
            }
            description "Use this attribute to set the cc interval protection cfm";
        } // END of protection-cfm-cc-interval definition.

        leaf protection-cfm-domain  {
            type  string {
                length "1..1965";
                pattern "[^?' =,>|]+";
            }
            description "Use this attribute to set the domain name for protection cfm";
        } // END of protection-cfm-domain definition.

        leaf protection-cfm-ma  {
            type  string {
                length "1..1965";
                pattern "[^?' =,>|]+";
            }
            description "Use this attribute to set the ma name for protection cfm";
        } // END of protection-cfm-ma definition.

        leaf vlan-id  {
            type  uint16;
            description "Use this attribute to set the vlanid";
        } // END of vlan-id definition.

        leaf inner-vid  {
            type  uint16;
            description "Use this attribute to set the inner vlanid";
        } // END of inner-vid definition.

        leaf data-vlan  {
            type  string {
                length "1..1965";
            }
            description "Use this attribute to set the data-vlan";
        } // END of data-vlan definition.

        leaf level  {
            type  uint8;
            description "Use this attribute to set the level";
        } // END of level definition.

        leaf aps-statistics-tx  {
            type  uint32;
            description "Use this attribute to set the tx";
        } // END of aps-statistics-tx definition.

        leaf aps-statistics-rx  {
            type  uint32;
            description "Use this attribute to set the tx";
        } // END of aps-statistics-rx definition.

    } // END of eps-instance-state definition.
    grouping eps-instance-config {
        description
            "Configuration for EPS instance configuration data";
        leaf name  {
            type  string {
                length "1..100";
                pattern "[^?' =,>|]+";
            }
            description "Instance name to identify the EPS protection group";
        } // END of name definition.

        leaf eps-protection-group  {
            type  leafref {
                path  "/ipi-g8031:g8031/g8031-elps/protections/protection/group-name";
            }
            description "Group name for protection EPS";
        } // END of eps-protection-group definition.

        leaf g8031-profile-name  {
            type  leafref {
                path  "/ipi-g8031:g8031/g8031-elps/profiles/profile/name";
            }
            description "G8031 profile name";
        } // END of g8031-profile-name definition.

    } // END of eps-instance-config definition.
    grouping g8031-eps-instance-top {
        description
            "Top level grouping for EPS instance configuration data";
        container eps-instances {
            description
                "Container for EPS instances configuration data";

            list eps-instance {
                key "name";
                unique "config/eps-protection-group";
                description
                    "List of EPS instance configuration data";
                leaf name  {
                    type  leafref {
                        path  "../config/name";
                    }
                    description "Instance name to identify the EPS protection group";
                } // END of name definition.

                container config {
                    description
                        "Configuration data for EPS instance";
                    uses eps-instance-config;
                } // END of config-container definition.
                container state {
                    config false;
                    description
                        "Operation data for Eps instance";
                    uses eps-instance-config;
                    uses eps-instance-state;
                } // END of state-container definition.
                uses g8031-aps-channel-top;
                uses g8031-control-vlan-top;
                uses g8031-data-vlan-top;
            } // End of eps-instance-list
        } // END of eps-instances-container definition.
    } // END of g8031-eps-instance-top definition.
    grouping eps-protection-config {
        description
            "Grouping for ELPS protection configuration data";
        leaf group-name  {
            type  string {
                length "1..100";
                pattern "[^?' =,>|]+";
            }
            description "G.8031 ELPS protection group name";
        } // END of group-name definition.

        leaf working-port  {
            type  leafref {
                path  "/ipi-interface:interfaces/ipi-interface:interface/ipi-interface:name";
            }
            description "Port for working ELPS path";
        } // END of working-port definition.

        leaf protection-port  {
            // when " ../working-port ";
            type  leafref {
                path  "/ipi-interface:interfaces/ipi-interface:interface/ipi-interface:name";
            }
            description "Port for the protection ELPS path";
        } // END of protection-port definition.

    } // END of eps-protection-config definition.
    grouping g8031-eps-protection-top {
        description
            "Grouping for ELPS protection top grouping";
        container protections {
            description
                "Container for ELPS protection";

            list protection {
                if-feature feature-list:HAVE_G8031;
                key "group-name";
                description
                    "Lis of ELPS protection";
                leaf group-name  {
                    type  leafref {
                        path  "../config/group-name";
                    }
                    description "G.8031 ELPS protection group name";
                } // END of group-name definition.

                container config {
                    description
                        "Configuration data for ELPS profile";
                    uses eps-protection-config;
                } // END of config-container definition.
                container state {
                    config false;
                    description
                        "Operational state data for ELPS profile";
                    uses eps-protection-config;
                } // END of state-container definition.
            } // End of protection-list
        } // END of protections-container definition.
    } // END of g8031-eps-protection-top definition.
    grouping g8031-profile-config {
        description
            "Grouping for ELPS profile configuration data";
        leaf name  {
            type  string {
                length "1..100";
                pattern "[^?' =,>|]+";
            }
            description "G.8031 profile name";
        } // END of name definition.

        leaf mode  {
            type  ipi-g8031-elps-types:g8031_mode_type_t;
            description "G.8031 mode";
        } // END of mode definition.

        leaf switching-mode  {
            type  ipi-g8031-elps-types:g8031_switching_mode_type_t;
            description "Use this attribute to set/unset switching mode";
        } // END of switching-mode definition.

        leaf timer-hold-off  {
            type  uint8 {
                 range "1..10"  {
                    description "1..10: Supported range 1 - 10";
                 }
            }
            description "The hold-off timer is used to coordinate the timing of protection
                        switches";
        } // END of timer-hold-off definition.

        leaf timer-wait-to-restore  {
            type  uint32 {
                 range "300..720"  {
                    description "300..720: Supported range 300 - 720";
                 }
            }
            description "Use this attribute to set/unset the timer wait to restore";
        } // END of timer-wait-to-restore definition.

    } // END of g8031-profile-config definition.
    grouping g8031-profile-top {
        description
            "Grouping for ELPS profile";
        container profiles {
            description
                "Container for ELPS profiles";

            list profile {
                if-feature feature-list:HAVE_G8031;
                key "name";
                description
                    "List of ELPS profile";
                leaf name  {
                    type  leafref {
                        path  "../config/name";
                    }
                    description "G.8031 profile name";
                } // END of name definition.

                container config {
                    description
                        "Configuration data for ELPS profile";
                    uses g8031-profile-config;
                } // END of config-container definition.
                container state {
                    config false;
                    description
                        "Operational state data for ELPS profile";
                    uses g8031-profile-config;
                } // END of state-container definition.
            } // End of profile-list
        } // END of profiles-container definition.
    } // END of g8031-profile-top definition.

    grouping  elps-grouping {
    description
        "Ethernet Linear Protection Switching main container";
    container elps {
        if-feature feature-list:HAVE_G8031;
        if-feature feature-list:HAVE_ONMD;
        description
            "Ethernet Linear Protection Switching main container";
        uses elps-top;
    } // END of elps-container definition.
    } // END of elps-grouping definition.

    grouping  g8031-elps-grouping {
    description
        "Top level container for g8031 elps";
    container g8031-elps {
        if-feature feature-list:HAVE_G8031;
        if-feature feature-list:HAVE_ONMD;
        description
            "Top level container for g8031 elps";
        uses g8031-profile-top;
        uses g8031-eps-protection-top;
        uses g8031-eps-instance-top;
    } // END of g8031-elps-container definition.
    } // END of g8031-elps-grouping definition.

    grouping  debug-grouping {
    description
        "Container for g8031 debugging functions";
    container debug {
        if-feature feature-list:HAVE_G8031;
        if-feature feature-list:HAVE_ONMD;
        description
            "Container for g8031 debugging functions";
        container config {
            description
                "Configuration data for g8031 debug";
            uses g8031-debug-config;
        } // END of config-container definition.
        container state {
            config false;
            description
                "Operational state data for g8031 debug";
            uses g8031-debug-config;
            uses g8031-debug-terminal-state;
        } // END of state-container definition.
    } // END of debug-container definition.
    } // END of debug-grouping definition.


}
