/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-g8031-elps-types.yang
*
*/

module ipi-g8031-elps-types {

    yang-version 1.1;

    namespace   "http://www.ipinfusion.com/yang/ocnos/ipi-g8031-elps-types";

    prefix "ipi-g8031-elps-types";

    organization
        "IP Infusion Inc.";

    contact
        "Address: 3965 Freedom Circle, Suite 200, Santa Clara, CA 95054
         Phone: +1 408-400-1900
         E-mail: support@ipinfusion.com
         Web: http://www.ip    infusion.com/";

    description
        "YANG version of the ipi-g8031-elps-types";


    revision "2023-12-20" {
        description "New ELPS Manual Switch CLI support";
        reference " 0.3.1.";
    }

    revision "2023-11-15" {
        description "New ELPS CLI Restructuring support.";
        reference " 0.3.0.";
    }

    revision "2022-06-28" {
        description "Fix description of rx and tx element on G8031_DEBUG_T";
        reference " 0.2.3.";
    }

    revision "2022-06-01" {
        description "Updated the yang file with feature";
        reference " 0.2.2.";
    }

    revision "2022-04-27" {
        description "Added debug support";
        reference " 0.2.1.";
    }

    revision "2022-03-17" {
        description "Restructured module as per open-config";
        reference " 0.2.0.";
    }

    revision "2021-05-14" {
        description "Initial Version";
        reference " 0.1.0.";
    }



    typedef  g8031_elps_protection_type_t {
        type enumeration {
            enum one-plus-one-bidirectional {
                value 1;
                description "1+1 bidirectional mode";
            }
            enum one-plus-one-unidirectional {
                value 2;
                description "1+1 unidirectional mode";
            }
            enum one-and-one-bidirectional {
                value 3;
                description "1:1 bidirectional mode";
            }
        }
        description "type definition for G8031_ELPS_PROTECTION_TYPE_T";
    }

    typedef  g8031_current_state_type_t {
        type enumeration {
            enum no-request {
                value 0;
                description "no request";
            }
            enum do-not-revert {
                value 1;
                description "do not revert";
            }
            enum reverse-request {
                value 2;
                description "reverse request";
            }
            enum exercise {
                value 4;
                description "normal";
            }
            enum wait-to-restore {
                value 5;
                description "wait to restore";
            }
            enum manual-switch-to-protection {
                value 8;
                description "manual switch to protection";
            }
            enum signal-degrade {
                value 9;
                description "signal degrade";
            }
            enum working-signal-fail {
                value 11;
                description "working signal fail";
            }
            enum forced-switch {
                value 13;
                description "forced-switch";
            }
            enum signal-fail-for-protection {
                value 14;
                description "signal fail for protection";
            }
            enum lockout-of-protection {
                value 15;
                description "lockout of protection";
            }
            enum invalid {
                value 16;
                description "invalid";
            }
        }
        description "type definition for G8031_CURRENT_STATE_TYPE_T";
    }

    typedef  g8031_request_signal_type_t {
        type enumeration {
            enum null {
                value 0;
                description "null";
            }
            enum normal {
                value 1;
                description "normal";
            }
        }
        description "type definition for G8031_REQUEST_SIGNAL_TYPE_T";
    }

    typedef  g8031_failure_of_protocol_state_type_t {
        type enumeration {
            enum no-failure {
                value 0;
                description "No failure";
            }
            enum aps-rcvd-on-working {
                value 2;
                description "APS PDU Received on Working";
            }
            enum b-bit-mismatch {
                value 5;
                description "B Bit Mismatch";
            }
            enum d-bit-mismatch {
                value 7;
                description "D Bit Mismatch";
            }
            enum r-bit-mismatch {
                value 8;
                description "R Bit Mismatch";
            }
            enum aps-not-rcvd-on-state-change {
                value 9;
                description "APS PDU not received after state change";
            }
        }
        description "type definition for G8031_FAILURE_OF_PROTOCOL_STATE_TYPE_T";
    }

    typedef  g8031_active_path_type_t {
        type enumeration {
            enum protection {
                value 0;
                description "protection path";
            }
            enum working {
                value 1;
                description "working path";
            }
        }
        description "type definition for G8031_ACTIVE_PATH_TYPE_T";
    }

    typedef  g8031_direction_type_t {
        type enumeration {
            enum uni {
                value 0;
                description "unidirectional mode";
            }
            enum bi {
                value 1;
                description "bidirectional mode";
            }
        }
        description "type definition for G8031_DIRECTION_TYPE_T";
    }

    typedef  g8031_mode_type_t {
        type enumeration {
            enum one-and-one-bidirectional {
                value 1;
                description "1:1 bidirectional mode";
            }
            enum one-plus-one-bidirectional {
                value 2;
                description "1+1 bidirectional mode";
            }
            enum one-plus-one-unidirectional {
                value 3;
                description "1+1 unidirectional mode";
            }
        }
        description "type definition for G8031_MODE_TYPE_T";
    }

    typedef  g8031_switching_mode_type_t {
        type enumeration {
            enum non-revertive {
                value 1;
                description "Non revertive mode";
            }
            enum revertive {
                value 2;
                description "revertive mode";
            }
        }
        description "type definition for G8031_SWITCHING_MODE_TYPE_T";
    }

    typedef  g8031_eps_instance_switch {
        type enumeration {
            enum local-freeze {
                value 1;
                description "Local freeze";
            }
            enum local-lockout {
                value 2;
                description "Local lockout";
            }
            enum force-switch {
                value 3;
                description "force-switch";
            }
            enum manual-switch-working {
                value 4;
                description "manual-switch-working";
            }
            enum manual-switch-protection {
                value 5;
                description "manual-switch-protection";
            }
            enum lockout {
                value 6;
                description "lockout";
            }
            enum exercise {
                value 7;
                description "exercise";
            }
        }
        description "type definition for G8031_EPS_INSTANCE_SWITCH";
    }

    typedef  g8031_eps_instance_type {
        type enumeration {
            enum local-freeze {
                value 1;
                description "Local freeze";
            }
            enum local-lockout {
                value 2;
                description "Local lockout";
            }
        }
        description "type definition for G8031_EPS_INSTANCE_TYPE";
    }

    typedef  g8031_debug_t {
        type bits {
            bit rx {
                position 0;
                description "Received PDUs";
            }
            bit tx {
                position 1;
                description "Transmitted PDUs";
            }
            bit fsm {
                position 2;
                description "Instance Finite State Machine updates";
            }
            bit events {
                position 3;
                description "Protocol related events";
            }
            bit hal {
                position 4;
                description "HAL events";
            }
        }
        description "type definition for G8031_DEBUG_T";
    }

}
