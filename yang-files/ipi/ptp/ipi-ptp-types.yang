/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-ptp-types.yang
*
*/

module ipi-ptp-types {

    yang-version 1.1;

    namespace   "http://www.ipinfusion.com/yang/ocnos/ipi-ptp-types";

    prefix "ipi-ptp-types";

    import cml-data-types {
        prefix cml-data-types;
        revision-date 2026-05-15;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "PTP data types";


    revision "2025-02-03" {
        description "Add PRC type in PTP_SERVO_APTS_MODE_T";
        reference " 0.14.0.";
    }

    revision "2024-11-19" {
        description "Removed the datatype PTP_CONFIG_STATE_T";
        reference " 0.13.0.";
    }

    revision "2024-05-31" {
        description "Blocked smpte profile for Marvel board";
        reference " 0.12.0.";
    }

    revision "2023-12-07" {
        description "updated no form command for transport type";
        reference " 0.11.0.";
    }

    revision "2023-09-06" {
        description "Added smpte profile ";
        reference " 0.10.0.";
    }

    revision "2023-08-07" {
        description "Added ptp l3 mulitcast support for broadptp";
        reference " 0.9.0.";
    }

    revision "2023-01-23" {
        description "Extended support for PTP profile";
        reference " 0.8.0.";
    }

    revision "2022-11-21" {
        description "added new configure option for servo";
        reference " 0.7.0.";
    }

    revision "2022-06-29" {
        description "added new cli for servo config";
        reference " 0.6.0.";
    }

    revision "2022-06-01" {
        description "Updated the yang file with feature";
        reference " 0.5.0.";
    }

    revision "2021-09-03" {
        description "Update descriptions of attribute";
        reference " 0.4.0.";
    }

    revision "2021-04-29" {
        description "Added support for G8265 network option";
        reference " 0.3.0.";
    }

    revision "2021-03-04" {
        description "PTP servo APTS mode type updated";
        reference " 0.2.0.";
    }

    revision "2020-12-17" {
        description "PTP restructuring according to OpenConfig style";
        reference " 0.1.0.";
    }



    typedef  ptp_encap_type_t {
        type enumeration {
            enum ipv4 {
                value 1;
                description "IPv4 Transport";
            }
            enum ipv6 {
                value 2;
                description "IPv6 Transport";
            }
            enum ipv4-multicast {
                value 3;
                description "Ipv4 Transport Multicast";
            }
            enum ipv6-multicast {
                value 4;
                description "Ipv6 Transport Multicast";
            }
        }
        description "type definition for PTP_ENCAP_TYPE_T";
    }

    typedef  ptp_v6_multicast_type_t {
        type enumeration {
            enum site-local {
                value 1;
                description "ff05::181";
            }
            enum interface-local {
                value 2;
                description "ff01::181";
            }
            enum link-local {
                value 3;
                description "ff02::181";
            }
            enum admin-local {
                value 4;
                description "ff04::181";
            }
            enum organization-local {
                value 5;
                description "ff08::181";
            }
            enum global-local {
                value 6;
                description "ff0e::181";
            }
        }
        description "type definition for PTP_V6_MULTICAST_TYPE_T";
    }

    typedef  ptp_servo_config_type_t {
        type enumeration {
            enum fts {
                value 1;
                description "full time support with synce";
            }
            enum fts-no-synce {
                value 2;
                description "full time support without synce";
            }
        }
        description "type definition for PTP_SERVO_CONFIG_TYPE_T";
    }

    typedef  ptp_1pss_in_smx_tod_type_t {
        type enumeration {
            enum smx {
                value 1;
                description "SMA Or SMB 1pps";
            }
            enum tod {
                value 2;
                description "TOD 1pps (default)";
            }
        }
        description "type definition for PTP_1PSS_IN_SMX_TOD_TYPE_T";
    }

    typedef  ptp_g8265p1_option_type_t {
        type enumeration {
            enum 1 {
                value 1;
                description "Set network option1";
            }
            enum 2 {
                value 2;
                description "Set network option2";
            }
        }
        description "type definition for PTP_G8265P1_OPTION_TYPE_T";
    }

    typedef  ptp_servo_state_t {
        type enumeration {
            enum Acquiring-lock {
                value 0;
                description "Servo state is Acquiring-lock";
            }
            enum Warmup {
                value 1;
                description "Servo state is Warmup";
            }
            enum Fast-loop {
                value 2;
                description "Servo state is Fast-loop";
            }
            enum Normal-loop {
                value 3;
                description "Servo state is Normal-loop";
            }
            enum Bridge {
                value 4;
                description "Servo state is Bridge";
            }
            enum Holdover {
                value 5;
                description "Servo state is Holdover";
            }
            enum Initial {
                value 6;
                description "Servo state is Initial";
            }
            enum Unqualified {
                value 7;
                description "Servo state is Unqualified";
            }
            enum Freq-Locked {
                value 8;
                description "Servo state is Freq-Locked";
            }
            enum Time-Locked {
                value 9;
                description "Servo state is Time-Locked";
            }
            enum Holdover-in-spec {
                value 10;
                description "Servo state is Holdover-in-spec";
            }
            enum Holdover-out-spec {
                value 11;
                description "Servo state is Holdover-out-spec";
            }
            enum Free-run {
                value 12;
                description "Servo state is Free-run";
            }
        }
        description "type definition for PTP_SERVO_STATE_T";
    }

    typedef  ptp_servo_state_custom_t {
        type enumeration {
            enum Acquiring-lock {
                value 0;
                description "Servo state is Acquiring-lock";
            }
            enum Freq-Locked {
                value 1;
                description "Servo state is Freq-Locked";
            }
            enum Time-Locked {
                value 2;
                description "Servo state is Time-Locked";
            }
            enum Holdover {
                value 3;
                description "Servo state is Holdover";
            }
            enum Input-Reference-Failed {
                value 4;
                description "Servo state is Input Reference Failed";
            }
            enum No-Input-Reference-Selected {
                value 5;
                description "Servo state is No Input Reference Selected";
            }
            enum Unknown {
                value 6;
                description "Servo state is Unknown";
            }
            enum Manual-Freerun-Mode {
                value 7;
                description "Servo state is Manual Freerun Mode";
            }
            enum Manual-Holdover {
                value 8;
                description "Servo state is Manual Holdover";
            }
            enum Manual-Holdover-set-on-active-APR-Server {
                value 9;
                description "Servo state is Manual Holdover set on active APR Server";
            }
            enum Holdover-in-spec {
                value 10;
                description "Servo state is Holdover-in-spec";
            }
            enum Holdover-out-spec {
                value 11;
                description "Servo state is Holdover-out-spec";
            }
        }
        description "type definition for PTP_SERVO_STATE_CUSTOM_T";
    }

    typedef  ptp_servo_apts_mode_t {
        type enumeration {
            enum GPS {
                value 2;
                description "APTS mode is GPS";
            }
            enum PTP {
                value 3;
                description "APTS mode is PTP";
            }
            enum Not-Applicable {
                value 4;
                description "APTS mode is NA";
            }
            enum PRC {
                value 5;
                description "APTS mode is PRC";
            }
        }
        description "type definition for PTP_SERVO_APTS_MODE_T";
    }

    typedef  ptp_port_state_t {
        type enumeration {
            enum initializing {
                value 1;
                description "The port is initializing its data sets - hardware and communication facilities";
            }
            enum faulty {
                value 2;
                description "The port is in the fault state";
            }
            enum disabled {
                value 3;
                description "The port is disabled and is not communicating PTP messages";
            }
            enum listening {
                value 4;
                description "The port is listening for an Announce message";
            }
            enum pre-master {
                value 5;
                description "The port is in the pre-master state";
            }
            enum master {
                value 6;
                description "The port is behaving as a master port";
            }
            enum passive {
                value 7;
                description "The port is in the passive state";
            }
            enum uncalibrated {
                value 8;
                description "A master port has been selected but the port is still in the uncalibrated state";
            }
            enum slave {
                value 9;
                description "The port is synchronizing to the selected master port";
            }
        }
        description "type definition for PTP_PORT_STATE_T";
    }

    typedef  ptp_delay_mechanism_t {
        type enumeration {
            enum E2E {
                value 1;
                description "The port is configured to use the delay request-response mechanism";
            }
            enum P2P {
                value 2;
                description "The port is configured to use the peer delay mechanism";
            }
            enum disabled {
                value 254;
                description "The port does not implement the delay mechanism";
            }
        }
        description "type definition for PTP_DELAY_MECHANISM_T";
    }

    typedef  ptp_time_interval_t {
        type int64;
        description "type definition for PTP_TIME_INTERVAL_T";
    }

    typedef  ptp_clock_identity_t {
        type string {
            length 18..26;
        }
        description "type definition for PTP_CLOCK_IDENTITY_T";
    }

    typedef  ptp_clock_type_tgm_t {
        type enumeration {
            enum tgm {
                value 1;
                description "Grand Master Clock";
            }
        }
        description "type definition for PTP_CLOCK_TYPE_TGM_T";
    }

    typedef  ptp_profile_t {
        type enumeration {
            enum g8265.1 {
                value 0;
                description "PTP frequency telecom profile";
            }
            enum g8275.1 {
                value 1;
                description "PTP time/phase telecom profile";
            }
            enum g8275.2 {
                value 2;
                description "PTP time/phase telecom g8275.2 profile";
            }
            enum e2e-transparent {
                value 3;
                description "PTP E2E transparent clock profile";
            }
            enum default {
                value 4;
                description "PTP time/phase default profile";
            }
            enum smpte {
                value 5;
                if-feature feature-list:HAVE_DUNE;
                description "PTP time/phase smpte profile";
            }
        }
        description "type definition for PTP_PROFILE_T";
    }

    typedef  ptp_clock_io_type_t {
        type enumeration {
            enum input {
                value 1;
                description "Clock input";
            }
            enum output {
                value 2;
                description "Clock output";
            }
        }
        description "type definition for PTP_CLOCK_IO_TYPE_T";
    }

    typedef  ptp_time_source_t {
        type enumeration {
            enum Atomic-clock {
                value 16;
                description "None";
            }
            enum Global-positioning-system {
                value 32;
                description "None";
            }
            enum Terrestrial-radio {
                value 48;
                description "None";
            }
            enum PTP-based-source {
                value 64;
                description "None";
            }
            enum Network-Time-Protocol-source {
                value 80;
                description "None";
            }
            enum Handset {
                value 96;
                description "None";
            }
            enum Other-timesource {
                value 144;
                description "None";
            }
            enum Internal-Oscillator {
                value 160;
                description "None";
            }
        }
        description "type definition for PTP_TIME_SOURCE_T";
    }

    typedef  ptp_gps_sma_smb_interface_t {
        type enumeration {
            enum gps {
                value 0;
                description "GPS interface";
            }
            enum prc {
                value 1;
                description "SMA/SMB or external interfaces";
            }
        }
        description "type definition for PTP_GPS_SMA_SMB_INTERFACE_T";
    }

    typedef  ptp_network_interface_t {
        type union {
            type cml-data-types:cml_ifname_t {

            }
            type ptp_gps_sma_smb_interface_t {

            }
        }
        description "type definition for PTP_NETWORK_INTERFACE_T";
    }

}
