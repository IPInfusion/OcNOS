/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-port-mirror-types.yang
*
*/

module ipi-port-mirror-types {

    yang-version 1.1;

    namespace   "http://www.ipinfusion.com/yang/ocnos/ipi-port-mirror-types";

    prefix "ipi-port-mirror-types";

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Datatypes related to Port Mirroring";


    revision "2025-09-04" {
        description "Additional types for sniff monitor session and filter";
        reference " 0.6.0.";
    }

    revision "2024-07-31" {
        description "Add types used for ERSPAN";
        reference " 0.5.0.";
    }

    revision "2023-09-12" {
        description "Changed PMIROR_DIR_T type from enum to bitmap";
        reference " 0.4.0.";
    }

    revision "2022-06-01" {
        description "Updated the yang file with feature";
        reference " 0.3.0.";
    }

    revision "2022-01-13" {
        description "Added if-feature for data types";
        reference " 0.2.0.";
    }

    revision "2021-11-16" {
        description "Initial Version";
        reference " 0.1.0.";
    }



    typedef  pmirror_mac_addr_t {
        type string {
            pattern "[0-9A-F]{4}\\.[0-9A-F]{4}\\.[0-9A-F]{4}";
        }
        description "type definition for PMIRROR_MAC_ADDR_T";
    }

    typedef  pmirror_sess_type_t {
        type enumeration {
            enum local {
                value 1;
                description "Create a local session";
            }
            enum remote {
                value 2;
                description "Create a remote source node session";
            }
            enum sniff {
                value 3;
                if-feature feature-list:HAVE_SNIFF_INTF;
                if-feature feature-list:HAVE_XGS5;
                if-feature feature-list:NOT_HAVE_DUNE;
                description "Create a sniff session";
            }
            enum erspan-sender {
                value 4;
                description "Create an ERSPAN sender session";
            }
        }
        description "type definition for PMIRROR_SESS_TYPE_T";
    }

    typedef  pmirror_erspan_type_t {
        type enumeration {
            enum 1 {
                value 1;
                description "ERSPAN type 1";
            }
            enum 3 {
                value 3;
                description "ERSPAN type 3";
            }
        }
        description "type definition for PMIRROR_ERSPAN_TYPE_T";
    }

    typedef  pmirror_dir_t {
        type bits {
            bit rx {
                position 0;
                description "Ingress";
            }
            bit tx {
                position 1;
                description "Egress";
            }
        }
        description "type definition for PMIRROR_DIR_T";
    }

    typedef  pmirror_ether_type_val_t {
        type enumeration {
            enum ipv4 {
                value 2048;
                description "Specify frame type as IPv4. Ethertype 0x0800";
            }
            enum arp {
                value 2054;
                description "Specify frame type as ARP. Ethertype 0x806";
            }
            enum ipv6 {
                value 34525;
                description "Specify frame type as IPv6. Ethertype 0x86dd";
            }
        }
        description "type definition for PMIRROR_ETHER_TYPE_VAL_T";
    }

    typedef  pmirror_ether_hex_val_string_t {
        type string;
        description "type definition for PMIRROR_ETHER_HEX_VAL_STRING_T";
    }

    typedef  pmirror_ethertype_t {
        type union {
            type pmirror_ether_type_val_t {

            }
            type pmirror_ether_hex_val_string_t {

            }
        }
        description "type definition for PMIRROR_ETHERTYPE_T";
    }

    typedef  pmirror_arp_type_t {
        type enumeration {
            enum req {
                value 1;
                description "Match ARP request packets";
            }
            enum resp {
                value 2;
                description "Match ARP response packets";
            }
        }
        description "type definition for PMIRROR_ARP_TYPE_T";
    }

    typedef  pmirror_alt_dir_t {
        type enumeration {
            enum receive {
                value 1;
                description "Mirror received traffic";
            }
            enum transmit {
                value 2;
                description "Mirror transmit traffic";
            }
            enum both {
                value 3;
                description "Mirror traffic in both directions";
            }
        }
        description "type definition for PMIRROR_ALT_DIR_T";
    }

    typedef  pmirror_ip_protocol_name_t {
        type enumeration {
            enum icmp {
                value 1;
                description "Internet Control Message Protocol";
            }
            enum tcp {
                value 6;
                description "Transmission Control Protocol";
            }
            enum udp {
                value 17;
                description "User Datagram Protocol";
            }
        }
        description "type definition for PMIRROR_IP_PROTOCOL_NAME_T";
    }

    typedef  pmirror_ip_protocol_t {
        type union {
            type pmirror_ip_protocol_name_t {

            }
            type uint8 {
                range "0..255";

            }
        }
        description "type definition for PMIRROR_IP_PROTOCOL_T";
    }

    typedef  pmirror_next_header_name_t {
        type enumeration {
            enum tcp {
                value 6;
                description "Transmission Control Protocol";
            }
            enum udp {
                value 17;
                description "User Datagram Protocol";
            }
            enum icmpv6 {
                value 58;
                description "Internet Control Message Protocol for IPv6";
            }
        }
        description "type definition for PMIRROR_NEXT_HEADER_NAME_T";
    }

    typedef  pmirror_next_header_t {
        type union {
            type pmirror_next_header_name_t {

            }
            type uint8 {
                range "0..255";

            }
        }
        description "type definition for PMIRROR_NEXT_HEADER_T";
    }

    typedef  pmirror_sniff_interface_t {
        type enumeration {
            enum sniff {
                value 0;
                description "sniff interfaces. Ingress mirrored to sniff0 and egress mirrored to sniff1";
            }
        }
        description "type definition for PMIRROR_SNIFF_INTERFACE_T";
    }

}
