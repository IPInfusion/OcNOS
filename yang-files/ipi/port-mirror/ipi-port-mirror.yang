/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-port-mirror.yang
*
*/

module ipi-port-mirror {

    yang-version 1.1;

    namespace   "http://www.ipinfusion.com/yang/ocnos/ipi-port-mirror";

    prefix "ipi-port-mirror";

    import ietf-inet-types {
        prefix inet;
        revision-date 2013-07-15;
    }

    import ietf-yang-types {
        prefix yang;
        revision-date 2013-07-15;
    }

    import cml-data-types {
        prefix cml-data-types;
        revision-date 2026-05-15;
    }

    import ipi-port-mirror-types {
        prefix ipi-port-mirror-types;
        revision-date 2025-09-04;
    }

    import ipi-interface {
        prefix ipi-interface;
        revision-date 2026-03-10;
    }

    import ipi-acl-types {
        prefix ipi-acl-types;
        revision-date 2025-04-10;
    }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "This module provides Port Mirroring configuration";


    revision "2026-12-21" {
        description "added implicit delete for source-vlans and session-enabled containers";
        reference " 0.13.5.";
    }

    revision "2026-12-01" {
        description "Changing configuration order to move no shut to come after filters";
        reference " 0.13.4.";
    }

    revision "2026-09-11" {
        description "Added dependentObject for monitor destination erspan";
        reference " 0.14.0.";
    }

    revision "2025-10-14" {
        description "Change sniff truncate attribute and limit the command to platforms that support it";
        reference " 0.13.3.";
    }

    revision "2025-10-13" {
        description "Change in session-filter RDN attribute name";
        reference " 0.13.2.";
    }

    revision "2025-09-17" {
        description "Change sniff truncate attribute and limit the command to platforms that support it";
        reference " 0.13.1.";
    }

    revision "2025-09-04" {
        description "Added sniff monitor session and additional attributes for monitor session filters";
        reference " 0.13.0.";
    }

    revision "2025-01-24" {
        description "Added dependentObject for port-mirror destination config";
        reference " 0.11.4.";
    }

    revision "2025-01-09" {
        description "Added ERSPAN support for Trident4, Tomahawk3, Tomahawk4 and Tomahawk5 boards";
        reference " 0.12.0.";
    }

    revision "2024-12-05" {
        description "Removed ERSPAN type 3 configurations on TH/TH2 boards";
        reference " 0.11.3.";
    }

    revision "2024-11-28" {
        description "CLI changes for monitor destination erspan";
        reference " 0.11.2.";
    }

    revision "2024-11-26" {
        description "Modified ERSPAN switch ID range from 0-1023 to 0-511";
        reference " 0.11.1.";
    }

    revision "2024-11-18" {
        description "Removed ERSPAN truncate option on TH/TH2 boards";
        reference " 0.11.0.";
    }

    revision "2024-07-31" {
        description "Added data for ERSPAN implementation";
        reference " 0.10.0.";
    }

    revision "2024-07-08" {
        description "Fixed port mirror / interface dependencies";
        reference " 0.9.3.";
    }

    revision "2024-01-27" {
        description "Added CML_SKIP_HITLESS_MERGE to port mirror filters";
        reference " 0.11.5.";
    }

    revision "2023-10-17" {
        description "Support filter by inner vlan";
        reference " 0.9.2.";
    }

    revision "2023-10-04" {
        description "pmirror-destination-local-config's destination interface is now a leafref to an interface";
        reference " 0.9.1.";
    }

    revision "2023-09-12" {
        description "Changed PMIROR_DIR_T type from enum to bitmap";
        reference " 0.9.0.";
    }

    revision "2023-08-02" {
        description "Support filter vlan ranges";
        reference " 0.8.0.";
    }

    revision "2022-07-28" {
        description "updated leaf-ref for interface name";
        reference " 0.7.0.";
    }

    revision "2022-07-20" {
        description "Added utils function port_monitor_filter_convert_known_frame_type";
        reference " 0.6.0.";
    }

    revision "2022-06-27" {
        description "Updated when expressions in yang file";
        reference " 0.5.0.";
    }

    revision "2022-06-01" {
        description "Updated the yang file with feature";
        reference " 0.4.0.";
    }

    revision "2022-01-13" {
        description "Modified sub module";
        reference " 0.3.0.";
    }

    revision "2021-11-16" {
        description "Module restructuring";
        reference " 0.2.0.";
    }

    revision "2018-06-21" {
        description "Initial Version";
        reference " 0.1.0.";
    }

    grouping pmirror-interface-config {
        description
            "Port mirror interface configuration";
        leaf name  {
            type  string {
                length "1..1965";
                pattern "[^?' =,>|]+";
            }
            description "Use this attribute to specify the interface name that will be used for
                        receive mirror packets.";
        } // END of name definition.

        leaf source-interface-name  {
            type  string {
                length "1..1965";
                pattern "[^?' =,>|]+";
            }
            description "Use this attribute to specify the source interface name in port
                        mirror.";
        } // END of source-interface-name definition.

        leaf direction  {
            type  ipi-port-mirror-types:pmirror_alt_dir_t;
            mandatory true;
            description "Use this attribute to specify the direction in interface port mirror.";
        } // END of direction definition.

    } // END of pmirror-interface-config definition.
    grouping pmirror-interface-top {
        description
            "Port mirror interface top level configuration";
        container interfaces {
            description
                "Port mirror interfaces configuration";

            list interface {
                if-feature feature-list:NOT_HAVE_ADVANCE_MIRROR;
                key "name source-interface-name";
                description
                    "Port mirror interface list";
                leaf name  {
                    type  leafref {
                        path  "../config/name";
                    }
                    description "Use this attribute  to specify the interface name that will be used
                                for receive mirror packets.";
                } // END of name definition.

                leaf source-interface-name  {
                    type  leafref {
                        path  "../config/source-interface-name";
                    }
                    description "Use this attribute to specify the source interface name in port
                                mirror.";
                } // END of source-interface-name definition.

                container config {
                    presence "yes";
                    description
                        "Configuration data for port mirror interface";
                    uses pmirror-interface-config;
                } // END of config-container definition.
                container state {
                    config false;
                    description
                        "Operational state data for port mirror interface";
                    uses pmirror-interface-config;
                } // END of state-container definition.
            } // End of interface-list
        } // END of interfaces-container definition.
    } // END of pmirror-interface-top definition.
    grouping pmirror-filters-dst-mac-config {
        description
            "Port mirror filter destination MAC configuration";
        choice destination-mac-options {
            description
                "destination-mac-options";
            case host-mac {

                description
                    "host-mac";

                leaf destination-mac-address-host  {
                    type  ipi-port-mirror-types:pmirror_mac_addr_t {
                        length "1..1965";
                    }
                    description "Use this attribute to set host destination MAC address.";
                } // END of destination-mac-address-host definition.

            }
            case mac-with-mask {

                description
                    "mac-with-mask";

                leaf destination-mac-address  {
                    // when " ../destination-mac-mask ";
                    type  ipi-port-mirror-types:pmirror_mac_addr_t {
                        length "1..1965";
                    }
                    description "Use this attribute to set destination MAC address.";
                } // END of destination-mac-address definition.

                leaf destination-mac-mask  {
                    // when " ../destination-mac-address ";
                    type  ipi-port-mirror-types:pmirror_mac_addr_t {
                        length "1..1965";
                    }
                    description "Use this attribute to set destination MAC mask address.";
                } // END of destination-mac-mask definition.

            }
        } // END of destination-mac-options-choice definition.
    } // END of pmirror-filters-dst-mac-config definition.
    grouping pmirror-filters-src-mac-config {
        description
            "Port mirror filter source MAC configuration";
        choice source-mac-options {
            description
                "source-mac-options";
            case host-mac {

                description
                    "host-mac";

                leaf source-mac-address-host  {
                    type  ipi-port-mirror-types:pmirror_mac_addr_t {
                        length "1..1965";
                    }
                    description "Use this attribute to set host source MAC address.";
                } // END of source-mac-address-host definition.

            }
            case mac-with-mask {

                description
                    "mac-with-mask";

                leaf source-mac-address  {
                    // when " ../source-mac-mask ";
                    type  ipi-port-mirror-types:pmirror_mac_addr_t {
                        length "1..1965";
                    }
                    description "Use this attribute to set source MAC address.";
                } // END of source-mac-address definition.

                leaf source-mac-mask  {
                    // when " ../source-mac-address ";
                    type  ipi-port-mirror-types:pmirror_mac_addr_t {
                        length "1..1965";
                    }
                    description "Use this attribute to set source MAC mask address.";
                } // END of source-mac-mask definition.

            }
        } // END of source-mac-options-choice definition.
    } // END of pmirror-filters-src-mac-config definition.
    grouping pmirror-filters-global-config {
        description
            "Port mirror filter global configuration";
        leaf frame-type  {
            type  ipi-port-mirror-types:pmirror_ethertype_t;
            description "Use this attribute to set ethertype.";
        } // END of frame-type definition.

        leaf arp-type  {
            // when " ../frame-type='arp' ";
            type  ipi-port-mirror-types:pmirror_arp_type_t;
            description "Use this attribute to set ARP packet type.";
        } // END of arp-type definition.

        leaf sender-ip-address  {
            // when " ../frame-type='arp' ";
            type  inet:ipv4-address;
            description "Use this attribute to set sender IP Address.";
        } // END of sender-ip-address definition.

        leaf target-ip-address  {
            // when " ../frame-type='arp' ";
            type  inet:ipv4-address;
            description "Use this attribute to set target IP Address.";
        } // END of target-ip-address definition.

        leaf cos  {
            type  uint8 {
                 range "0..7"  {
                    description "0..7: Supported range 0 - 7";
                 }
            }
            description "Use this attribute to set cos.";
        } // END of cos definition.

        leaf vlan  {
            type  cml-data-types:cml_range_t;
            description "Use this attribute to set VLAN.";
        } // END of vlan definition.

        leaf inner-vlan  {
            if-feature feature-list:NOT_HAVE_DUNE;
            type  cml-data-types:cml_range_t;
            description "Use this attribute to set inner VLAN.";
        } // END of inner-vlan definition.

        leaf source-ipv4-address  {
            // when " ../frame-type='ipv4' ";
            type  cml-data-types:cml_ipv4_addr_or_prefix_t;
            description "Use this attribute to set source IPv4 address.";
        } // END of source-ipv4-address definition.

        leaf destination-ipv4-address  {
            // when " ../frame-type='ipv4' ";
            type  cml-data-types:cml_ipv4_addr_or_prefix_t;
            description "Use this attribute to set destination IPv4 address.";
        } // END of destination-ipv4-address definition.

        leaf source-ipv6-address  {
            // when " ../frame-type='ipv6' ";
            type  cml-data-types:cml_ipv6_prefix_t;
            description "Use this attribute to set source IPv6 address.";
        } // END of source-ipv6-address definition.

        leaf destination-ipv6-address  {
            // when " ../frame-type='ipv6' ";
            type  cml-data-types:cml_ipv6_prefix_t;
            description "Use this attribute to set destination IPv6 address.";
        } // END of destination-ipv6-address definition.

        leaf filter-dscp  {
            // when " ../frame-type='ipv4' or ../frame-type='ipv6' ";
            if-feature feature-list:HAVE_SNIFF_INTF;
            if-feature feature-list:HAVE_XGS5;
            if-feature feature-list:NOT_HAVE_DUNE;
            type  uint8 {
                 range "0..63"  {
                    description "0..63: Supported range 0 - 63";
                 }
            }
            description "Use this attribute to set the DSCP value.";
        } // END of filter-dscp definition.

        leaf filter-hop-limit  {
            // when " ../frame-type='ipv6' ";
            if-feature feature-list:HAVE_SNIFF_INTF;
            if-feature feature-list:HAVE_XGS5;
            if-feature feature-list:NOT_HAVE_DUNE;
            type  uint8 {
                 range "1..255"  {
                    description "1..255: Supported range 1 - 255";
                 }
            }
            description "Use this attribute to set the IPv6 hop limit value.";
        } // END of filter-hop-limit definition.

        leaf filter-ttl  {
            // when " ../frame-type='ipv4' ";
            if-feature feature-list:HAVE_SNIFF_INTF;
            if-feature feature-list:HAVE_XGS5;
            if-feature feature-list:NOT_HAVE_DUNE;
            type  uint8 {
                 range "1..255"  {
                    description "1..255: Supported range 1 - 255";
                 }
            }
            description "Use this attribute to set the TTL value.";
        } // END of filter-ttl definition.

        leaf filter-ip-protocol  {
            // when " ../frame-type='ipv4' ";
            if-feature feature-list:HAVE_SNIFF_INTF;
            if-feature feature-list:HAVE_XGS5;
            if-feature feature-list:NOT_HAVE_DUNE;
            type  ipi-port-mirror-types:pmirror_ip_protocol_t;
            description "Use this attribute to set IP protocol.";
        } // END of filter-ip-protocol definition.

        leaf filter-next-header  {
            // when " ../frame-type='ipv6' ";
            if-feature feature-list:HAVE_SNIFF_INTF;
            if-feature feature-list:HAVE_XGS5;
            if-feature feature-list:NOT_HAVE_DUNE;
            type  ipi-port-mirror-types:pmirror_next_header_t;
            description "Use this attribute to set IPv6 next header.";
        } // END of filter-next-header definition.

        leaf filter-icmp-type  {
            // when " ../filter-ip-protocol='icmp' or ../filter-next-header='icmpv6' ";
            if-feature feature-list:HAVE_SNIFF_INTF;
            if-feature feature-list:HAVE_XGS5;
            if-feature feature-list:NOT_HAVE_DUNE;
            type  uint8;
            description "Use this attribute to set the ICMP type byte.";
        } // END of filter-icmp-type definition.

        leaf filter-icmp-code  {
            // when " ../filter-icmp-type ";
            if-feature feature-list:HAVE_SNIFF_INTF;
            if-feature feature-list:HAVE_XGS5;
            if-feature feature-list:NOT_HAVE_DUNE;
            type  uint8;
            description "Use this attribute to set the ICMP code byte.";
        } // END of filter-icmp-code definition.

        leaf filter-l4-src-port  {
            // when " filter-ip-protocol='tcp' or ../filter-ip-protocol='udp' or ../filter-next-header='tcp' or ../filter-next-header='udp' ";
            if-feature feature-list:HAVE_SNIFF_INTF;
            if-feature feature-list:HAVE_XGS5;
            if-feature feature-list:NOT_HAVE_DUNE;
            type  uint16;
            description "Use this attribute to set the L4 source port.";
        } // END of filter-l4-src-port definition.

        leaf filter-l4-dst-port  {
            // when " filter-ip-protocol='tcp' or ../filter-ip-protocol='udp' or ../filter-next-header='tcp' or ../filter-next-header='udp' ";
            if-feature feature-list:HAVE_SNIFF_INTF;
            if-feature feature-list:HAVE_XGS5;
            if-feature feature-list:NOT_HAVE_DUNE;
            type  uint16;
            description "Use this attribute to set the L4 destination port.";
        } // END of filter-l4-dst-port definition.

        leaf filter-tcp-flags  {
            // when " ../filter-ip-protocol='tcp' or ../filter-next-header='tcp' ";
            if-feature feature-list:HAVE_SNIFF_INTF;
            if-feature feature-list:HAVE_XGS5;
            if-feature feature-list:NOT_HAVE_DUNE;
            type  ipi-acl-types:acl_tcp_flags_t;
            description "Use this attribute to set the TCP flags.";
        } // END of filter-tcp-flags definition.

    } // END of pmirror-filters-global-config definition.
    grouping pmirror-filters-global-top {
        description
            "Port mirror filter global top level configuration";
        container filters {
            description
                "Port mirror filters configuration";
            container config {
                description
                    "Configuration data for";
                uses pmirror-filters-global-config;
                uses pmirror-filters-src-mac-config;
                uses pmirror-filters-dst-mac-config;
            } // END of config-container definition.
            container state {
                config false;
                description
                    "Operational state data for";
                uses pmirror-filters-global-config;
                uses pmirror-filters-src-mac-config;
                uses pmirror-filters-dst-mac-config;
            } // END of state-container definition.
        } // END of filters-container definition.
    } // END of pmirror-filters-global-top definition.
    grouping pmirror-filters-config {
        description
            "Port mirror filter configuration";
        leaf sequence-id  {
            type  uint32 {
                 range "1..4294967295"  {
                    description "1..4294967295:Feature : HAVE_CUSTOM1_ACL Supported range 1 -
                            268435453Feature : HAVE_CUSTOM2_ACL Supported range 1 - 268435453Not
                            Feature : HAVE_CUSTOM1_ACL,HAVE_CUSTOM2_ACL  Supported range 1 -
                            4294967295";
                 }
            }
            description "The sequence id determines the order in which ACL entries are applied.
                        The sequence id must be unique for each entry in an filter set.";
        } // END of sequence-id definition.

    } // END of pmirror-filters-config definition.
    grouping pmirror-filters-top {
        description
            "Port mirror filter top level configuration";
        container session-filters {
            description
                "Port mirror filters configuration";

            list session-filter {
                key "sequence-id";
                description
                    "Port mirror filter list";
                leaf sequence-id  {
                    type  leafref {
                        path  "../config/sequence-id";
                    }
                    description "The sequence id determines the order in which ACL entries are applied.
                                The sequence id must be unique for each entry in an filter set.";
                } // END of sequence-id definition.

                container config {
                    // when " ipi-port-mirror:port-mirror/sessions/session/session-filters/session-filter/filters/config  ";
                    description
                        "Configuration data for port mirror filter";
                    uses pmirror-filters-config;
                } // END of config-container definition.
                container state {
                    config false;
                    description
                        "Operational state data for port mirror filter";
                    uses pmirror-filters-config;
                } // END of state-container definition.
                uses pmirror-filters-global-top;
            } // End of session-filter-list
        } // END of session-filters-container definition.
    } // END of pmirror-filters-top definition.
    grouping pmirror-src-itf-config {
        description
            "Port mirror source interface configuration";
        leaf name  {
            type  leafref {
                path  "/ipi-interface:interfaces/ipi-interface:interface/ipi-interface:name";
            }
            description "Source interface name";
        } // END of name definition.

        leaf direction  {
            type  ipi-port-mirror-types:pmirror_dir_t;
            mandatory true;
            description "Source interface direction";
        } // END of direction definition.

    } // END of pmirror-src-itf-config definition.
    grouping pmirror-src-itf-top {
        description
            "Port mirror source interface top level configuration";
        container source-interfaces {
            description
                "Port mirror source interfaces";

            list source-interface {
                key "name";
                description
                    "Port mirror source interface";
                leaf name  {
                    type  leafref {
                        path  "../config/name";
                    }
                    description "Source interface name";
                } // END of name definition.

                container config {
                    presence "yes";
                    description
                        "Configuration data for port mirror source interface";
                    uses pmirror-src-itf-config;
                } // END of config-container definition.
                container state {
                    config false;
                    description
                        "Operational state data for port mirror source interface";
                    uses pmirror-src-itf-config;
                } // END of state-container definition.
            } // End of source-interface-list
        } // END of source-interfaces-container definition.
    } // END of pmirror-src-itf-top definition.
    grouping pmirror-destination-remote-config {
        description
            "Port mirror destination remote configuration";
        leaf vlan-id  {
            type  uint16 {
                 range "2..4094"  {
                    description "2..4094: Supported range 2 - 4094";
                 }
            }
            mandatory true;
            description "Use this attribute to configure port mirror remote vlan-id";
        } // END of vlan-id definition.

        leaf reflector-interface-name  {
            type  leafref {
                path  "/ipi-interface:interfaces/ipi-interface:interface/ipi-interface:name";
            }
            mandatory true;
            description "Use this attribute to configure port mirror remote reflector interface";
        } // END of reflector-interface-name definition.

    } // END of pmirror-destination-remote-config definition.
    grouping pmirror-destination-remote-top {
        description
            "Port mirror destination remote top level configuration";
        container remote {
            // when " ../../config/type='remote' ";
            description
                "Port mirror destination remote configuration";
            container config {
                presence "yes";
                description
                    "Configuration data for port-mirror remote";
                uses pmirror-destination-remote-config;
            } // END of config-container definition.
            container state {
                config false;
                description
                    "Operational state data for port-mirror remote";
                uses pmirror-destination-remote-config;
            } // END of state-container definition.
        } // END of remote-container definition.
    } // END of pmirror-destination-remote-top definition.
    grouping pmirror-destination-local-config {
        description
            "Port mirror destination local configuration";
        leaf interface-name  {
            type  leafref {
                path  "/ipi-interface:interfaces/ipi-interface:interface/ipi-interface:name";
            }
            description "Use this attribute to configure port mirror local interface";
        } // END of interface-name definition.

    } // END of pmirror-destination-local-config definition.
    grouping pmirror-destination-local-top {
        description
            "Port mirror destination local top level configuration";
        container local {
            // when " ../config/type='local' or ../../config/type='8' ";
            description
                "Port mirror destination local configuration";
            container config {
                description
                    "Configuration data for port mirror local";
                uses pmirror-destination-local-config;
            } // END of config-container definition.
            container state {
                config false;
                description
                    "Operational state data for port mirror local";
                uses pmirror-destination-local-config;
            } // END of state-container definition.
        } // END of local-container definition.
    } // END of pmirror-destination-local-top definition.
    grouping pmirror-destination-sniff-config {
        description
            "Port mirror destination sniff configuration";
        leaf sniff-interface  {
            type  ipi-port-mirror-types:pmirror_sniff_interface_t;
            description "Use this attribute to configure port mirror sniff interface";
        } // END of sniff-interface definition.

    } // END of pmirror-destination-sniff-config definition.
    grouping pmirror-destination-sniff-top {
        description
            "Port mirror destination sniff top level configuration";
        container sniff {
            when " /ipi-port-mirror:port-mirror/ipi-port-mirror:sessions/ipi-port-mirror:session/ipi-port-mirror:config/ipi-port-mirror:type = 'sniff' ";
            if-feature feature-list:HAVE_SNIFF_INTF;
            if-feature feature-list:HAVE_XGS5;
            if-feature feature-list:NOT_HAVE_DUNE;
            description
                "Port mirror destination sniff configuration";
            container config {
                description
                    "Configuration data for port mirror sniff";
                uses pmirror-destination-sniff-config;
            } // END of config-container definition.
            container state {
                config false;
                description
                    "Operational state data for port mirror sniff";
                uses pmirror-destination-sniff-config;
            } // END of state-container definition.
        } // END of sniff-container definition.
    } // END of pmirror-destination-sniff-top definition.
    grouping pmirror-destination-erspan-config {
        description
            "Port mirror destination erspan attributes configuration";
        leaf name  {
            type  string {
                length "1..1965";
                pattern "[^?' =,>|]+";
            }
            description "Configure ERSPAN destination";
        } // END of name definition.

        leaf dest-ip  {
            type  inet:ip-address;
            description "Set the destination IP of the GRE tunnel";
        } // END of dest-ip definition.

        leaf vrf-name  {
            type  string {
                length "1..1965";
                pattern "[^?' =,>|]+";
            }
            description "Use this attribute to set the connection VRF name";
        } // END of vrf-name definition.

        leaf erspan-id  {
            type  uint32 {
                 range "1..1023"  {
                    description "1..1023: Supported range 1 - 1023";
                 }
            }
            description "ERSPAN session id";
        } // END of erspan-id definition.

        leaf origin-ip  {
            type  inet:ip-address;
            description "Set the origin IP of the GRE tunnel";
        } // END of origin-ip definition.

        leaf ttl  {
            type  uint16 {
                 range "1..255"  {
                    description "1..255: Supported range 1 - 255";
                 }
            }
            description "This attribute is used to set time to live";
        } // END of ttl definition.

        leaf dscp  {
            type  uint8 {
                 range "0..63"  {
                    description "0..63: Supported range 0 - 63";
                 }
            }
            description "Use this attribute to set the DSCP value used for the GRE tunnel";
        } // END of dscp definition.

        leaf enable-truncate  {
            type  boolean;
            description "Enable/Disable packet truncate on the ERSPAN sender session";
        } // END of enable-truncate definition.

        leaf erspan-type  {
            type  ipi-port-mirror-types:pmirror_erspan_type_t;
            description "Use this attribute to set the ERSPAN type";
        } // END of erspan-type definition.

        leaf hardware-id  {
            type  uint8 {
                 range "0..63"  {
                    description "0..63: Supported range 0 - 63";
                 }
            }
            description "Unique identifier of an ERSPAN engine within a system.";
        } // END of hardware-id definition.

        leaf switch-id  {
            type  uint16 {
                 range "0..511"  {
                    description "0..511: Supported range 0 - 511";
                 }
            }
            description "Use this attribute to set the switch ID (platform specific info)";
        } // END of switch-id definition.

    } // END of pmirror-destination-erspan-config definition.
    grouping pmirror-erspan-destination-list-top {
        description
            "Port mirror erspan destination list top level configuration";
        container erspan-destinations {
            description
                "Port mirror erspan destinations";

            list erspan-destination {
                if-feature feature-list:HAVE_ADVANCE_MIRROR;
                key "name";
                description
                    "Port mirror erspan destination";
                leaf name  {
                    type  leafref {
                        path  "../config/name";
                    }
                    description "Sets the ERSPAN destination name";
                } // END of name definition.

                container config {
                    presence "yes";
                    description
                        "Configuration for erspan destination";
                    uses pmirror-destination-erspan-config;
                } // END of config-container definition.
                container state {
                    config false;
                    description
                        "Operational state data for port mirror erspan";
                    uses pmirror-destination-erspan-config;
                } // END of state-container definition.
            } // End of erspan-destination-list
        } // END of erspan-destinations-container definition.
    } // END of pmirror-erspan-destination-list-top definition.
    grouping pmirror-destination-erspan-session-config {
        description
            "Port mirror destination erspan configuration";
        leaf name  {
            type  string {
                length "1..1965";
                pattern "[^?' =,>|]+";
            }
            description "Configure ERSPAN destination name";
        } // END of name definition.

    } // END of pmirror-destination-erspan-session-config definition.
    grouping pmirror-destination-erspan-top {
        description
            "Port mirror destination erspan top level configuration";
        container erspan {
            // when " ../../config/type='erspan-sender' ";
            description
                "Port mirror destination erspan configuration";
            container config {
                description
                    "Configuration for port mirror erspan destination";
                uses pmirror-destination-erspan-session-config;
            } // END of config-container definition.
            container state {
                config false;
                description
                    "Operational state data for port mirror erspan";
                uses pmirror-destination-erspan-session-config;
            } // END of state-container definition.
        } // END of erspan-container definition.
    } // END of pmirror-destination-erspan-top definition.
    grouping pmirror-destination-top {
        description
            "Port mirror destination top configuration";
        container destination {
            description
                "Port mirror session destination configuration";
            uses pmirror-destination-local-top;
            uses pmirror-destination-remote-top;
            uses pmirror-destination-sniff-top;
            uses pmirror-destination-erspan-top;
        } // END of destination-container definition.
    } // END of pmirror-destination-top definition.
    grouping pmirror-counters {
        description
            "Port mirror counters";
        leaf filter-count  {
            type  yang:counter32;
            description "Port mirror session filter count";
        } // END of filter-count definition.

        leaf tx-source-count  {
            type  yang:counter32;
            description "Port mirror session tx source count";
        } // END of tx-source-count definition.

    } // END of pmirror-counters definition.
    grouping pmirror-config {
        description
            "Port mirror configuration";
        leaf id  {
            type  uint32 {
                 range "1..18"  {
                    description "1..18: Supported range 1 - 18";
                 }
            }
            description "Port mirror session index";
        } // END of id definition.

        leaf type  {
            type  ipi-port-mirror-types:pmirror_sess_type_t;
            mandatory true;
            description "Port mirror session type. The default is local";
        } // END of type definition.

        leaf description  {
            type  cml-data-types:cml_line_t {
                length "1..32";
            }
            description "Use this attribute to add a description to port-mirror session";
        } // END of description definition.

    } // END of pmirror-config definition.
    grouping pmirror-src-vlan {
        description
            "Port mirror configuration";
        leaf source-vlan  {
            type  cml-data-types:cml_range_t;
            description "Use this attribute to add VLAN monitor source";
        } // END of source-vlan definition.

    } // END of pmirror-src-vlan definition.
    grouping pmirror-source-vlan {
        description
            "Port mirror source-vlan top";
        container source-vlans {
            description
                "Port mirror source vlan configurations";
            container config {
                description
                    "Configuration data for port-mirror session";
                uses pmirror-src-vlan;
            } // END of config-container definition.
            container state {
                config false;
                description
                    "Operational state data for port-mirror session";
                uses pmirror-src-vlan;
            } // END of state-container definition.
        } // END of source-vlans-container definition.
    } // END of pmirror-source-vlan definition.
    grouping pmirror-enable {
        description
            "Port mirror configuration";
        leaf enabled  {
            type  empty;
            description "Use this attribute to shut/unshut a port-mirror session";
        } // END of enabled definition.

    } // END of pmirror-enable definition.
    grouping pmirror-enabled-top {
        description
            "Port mirror admin status";
        container session-enabled {
            description
                "Port mirror enable configurations";
            container config {
                description
                    "Configuration data for port-mirror session";
                uses pmirror-enable;
            } // END of config-container definition.
            container state {
                config false;
                description
                    "Operational state data for port-mirror session";
                uses pmirror-enable;
            } // END of state-container definition.
        } // END of session-enabled-container definition.
    } // END of pmirror-enabled-top definition.
    grouping pmirror-top {
        description
            "Port mirror top level configuration";
        container sessions {
            description
                "All port-mirror sessions configuration";

            list session {
                if-feature feature-list:HAVE_ADVANCE_MIRROR;
                key "id";
                description
                    "port-mirror session list";
                leaf id  {
                    type  leafref {
                        path  "../config/id";
                    }
                    description "Port mirror session index";
                } // END of id definition.

                container config {
                    description
                        "Configuration data for port-mirror session";
                    uses pmirror-config;
                } // END of config-container definition.
                container state {
                    config false;
                    description
                        "Operational state data for port-mirror session";
                    container counters {
                        config false;
                        description
                            "port-mirror session counters";
                        uses pmirror-counters;
                    } // END of counters-container definition.
                    uses pmirror-config;
                } // END of state-container definition.
                uses pmirror-destination-top;
                uses pmirror-src-itf-top;
                uses pmirror-filters-top;
                uses pmirror-source-vlan;
                uses pmirror-enabled-top;
            } // End of session-list
        } // END of sessions-container definition.
    } // END of pmirror-top definition.
    grouping pmirror-global-config {
        description
            "Port mirror global configuration";
        leaf sniff-packet-truncate-disable  {
            if-feature feature-list:HAVE_ADVANCE_MIRROR;
            if-feature feature-list:HAVE_SNIFF_INTF;
            if-feature feature-list:HAVE_XGS5;
            if-feature feature-list:NOT_HAVE_DUNE;
            type  empty;
            description "Use this attribute to globally enable or disable truncation of sniffed
                        packets";
        } // END of sniff-packet-truncate-disable definition.

    } // END of pmirror-global-config definition.
    grouping pmirror-global-top {
        description
            "Top-level grouping for port mirror global configuration";
        container global {
            description
                "All global configurations";
            container config {
                description
                    "Configuration data for port mirror global";
                uses pmirror-global-config;
            } // END of config-container definition.
            container state {
                config false;
                description
                    "Operational state data for port-mirror global";
                uses pmirror-global-config;
            } // END of state-container definition.
        } // END of global-container definition.
    } // END of pmirror-global-top definition.

    grouping  port-mirror-grouping {
    description
        "Container for all port-mirror configuration";
    container port-mirror {
        if-feature feature-list:HAVE_L2;
        description
            "Container for all port-mirror configuration";
        uses pmirror-top;
        uses pmirror-interface-top;
        uses pmirror-erspan-destination-list-top;
        uses pmirror-global-top;
    } // END of port-mirror-container definition.
    } // END of port-mirror-grouping definition.

    uses port-mirror-grouping;

}
