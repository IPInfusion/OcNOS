/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-platform-sff8024-types.yang
*
*/

module ipi-platform-sff8024-types {

    yang-version 1.1;

    namespace   "http://www.ipinfusion.com/yang/ocnos/ipi-platform-sff8024-types";

    prefix "ipi-platform-sff8024-types";

    organization
        "IP Infusion Inc.";

    contact
        "Address: 3965 Freedom Circle, Suite 200, Santa Clara, CA 95054
         Phone: +1 408-4001900
         E-mail: support@ipinfusion.com
         Web: http://www.ipinfusion.com/";

    description
        "YANG version of the ipi-platform-sff8024-types";


    revision "2026-01-06" {
        description "Add 'Invalid' connector type";
        reference " 0.4.1.";
    }

    revision "2025-12-30" {
        description "Update transceiver identifier list";
        reference " 0.4.0.";
    }

    revision "2025-09-23" {
        description "Adding the OSFP 8X identifier code";
        reference " 0.3.0.";
    }

    revision "2023-10-16" {
        description "TIBIT Build Issue Handling";
        reference " 0.2.0.";
    }

    revision "2022-07-07" {
        description "Initial Version";
        reference " 0.1.0.";
    }



    typedef  cmm_sff8024_identifier_t {
        type enumeration {
            enum unknown {
                value 0;
                description "trans identifier unknown";
            }
            enum gbic {
                value 1;
                description "trans identifier gbic";
            }
            enum soldered-to-motherboard {
                value 2;
                description "trans identifier soldered-to-motherboard";
            }
            enum sfp-or-sfpplus-or-sfp28 {
                value 3;
                description "trans identifier sfp-or-sfpplus-or-sfp28";
            }
            enum xbi-300pin {
                value 4;
                description "trans identifier xbi-300pin";
            }
            enum xenpak {
                value 5;
                description "trans identifier xenpak";
            }
            enum xfp {
                value 6;
                description "trans identifier xfp";
            }
            enum xff {
                value 7;
                description "trans identifier xff";
            }
            enum xfpe {
                value 8;
                description "trans identifier xfpe";
            }
            enum xpak {
                value 9;
                description "trans identifier xpak";
            }
            enum x2 {
                value 10;
                description "trans identifier x2";
            }
            enum dwdmsfp-or-dwdmsfpplus {
                value 11;
                description "trans identifier dwdmsfp-or-dwdmsfpplus";
            }
            enum qsfp {
                value 12;
                description "trans identifier qsfp";
            }
            enum qsfpplus-or-later {
                value 13;
                description "trans identifier qsfpplus-or-later";
            }
            enum cxp-or-later {
                value 14;
                description "trans identifier cxp-or-later";
            }
            enum shielded-mini-multilane-hd4x {
                value 15;
                description "trans identifier shielded-mini-multilane-hd4x";
            }
            enum shielded-mini-multilane-hd8x {
                value 16;
                description "trans identifier shielded-mini-multilane-hd8x";
            }
            enum qsfp28-or-later {
                value 17;
                description "trans identifier qsfp28-or-later";
            }
            enum cxp2-aka-cxp28-or-later {
                value 18;
                description "trans identifier cxp2-aka-cxp28-or-later";
            }
            enum cdfpstyle1-or-cdfpstyle2 {
                value 19;
                description "trans identifier cdfpstyle1-or-cdfpstyle2";
            }
            enum shielded-mini-multilane-hd4x-fanoutcable {
                value 20;
                description "trans identifier shielded-mini-multilane-hd4x-fanoutcable";
            }
            enum shielded-mini-multilane-hd8x-fanoutcable {
                value 21;
                description "trans identifier shielded-mini-multilane-hd8x-fanoutcable";
            }
            enum cdfpstyle3 {
                value 22;
                description "trans identifier cdfpstyle3";
            }
            enum microqsfp {
                value 23;
                description "trans identifier microqsfp";
            }
            enum qsfp-doubledensity-8x-pluggable-transceiver {
                value 24;
                description "trans identifier qsfp-doubledensity-8x-pluggable-transceiver";
            }
            enum osfp-8x-pluggable-transceiver {
                value 25;
                description "trans identifier osfp-8x-pluggable-transceiver";
            }
            enum sfp-dd-double-density-2x-pluggable-transceiver {
                value 26;
                description "trans identifier sfp-dd-double-density-2x-pluggable-transceiver";
            }
            enum dsfp-dual-small-form-factor-pluggable-transceiver {
                value 27;
                description "trans identifier dsfp-dual-small-form-factor-pluggable-transceiver";
            }
            enum x4-miniLink-ocuLink {
                value 28;
                description "trans identifier x4-miniLink-ocuLink";
            }
            enum x8-miniLink {
                value 29;
                description "trans identifier x8-miniLink";
            }
            enum qsfp+-or-later-with-cmis {
                value 30;
                description "trans identifier qsfp+-or-later-with-cmis";
            }
            enum reserved {
                value 254;
                description "trans identifier reserved";
            }
            enum vendor-specific {
                value 255;
                description "trans identifier vendor-specific";
            }
        }
        description "type definition for CMM_SFF8024_IDENTIFIER_T";
    }

    typedef  cmm_sff8024_connector_type_t {
        type enumeration {
            enum Invalid {
                value -1;
                description "None";
            }
            enum Unknown {
                value 0;
                description "None";
            }
            enum SC-Subscriber-Connector {
                value 1;
                description "None";
            }
            enum Fibre-Channel-Style-1-copper-connector {
                value 2;
                description "None";
            }
            enum Fibre-Channel-Style-2-copper-connector {
                value 3;
                description "None";
            }
            enum BNC-TNC-Bayonet-Threaded-Neill-Concelman {
                value 4;
                description "None";
            }
            enum Fibre-Channel-coax-headers {
                value 5;
                description "None";
            }
            enum Fiber-Jack {
                value 6;
                description "None";
            }
            enum LC-Lucent-Connector {
                value 7;
                description "None";
            }
            enum MT-RJ-Mechanical-Transfer---Registered-Jack {
                value 8;
                description "None";
            }
            enum MU---Multiple-Optical {
                value 9;
                description "None";
            }
            enum SG {
                value 10;
                description "None";
            }
            enum Optical-Pigtail {
                value 11;
                description "None";
            }
            enum MPO-1x12---Multifiber-Parallel-Optic {
                value 12;
                description "None";
            }
            enum MPO-2x16---Multifiber-Parallel-Optic {
                value 13;
                description "None";
            }
            enum HSSDC-II---High-Speed-Serial-Data-Connector {
                value 32;
                description "None";
            }
            enum Copper-Pigtail {
                value 33;
                description "None";
            }
            enum RJ45---Registered-Jack {
                value 34;
                description "None";
            }
            enum No-Separable-Connector {
                value 35;
                description "None";
            }
            enum MXC-2x16 {
                value 36;
                description "None";
            }
            enum CS-optical-connector {
                value 37;
                description "None";
            }
            enum SN---previously-Mini-CS---optical-connector {
                value 38;
                description "None";
            }
            enum MPO-2x12 {
                value 39;
                description "None";
            }
            enum MPO-1x16 {
                value 40;
                description "None";
            }
        }
        description "type definition for CMM_SFF8024_CONNECTOR_TYPE_T";
    }

}
