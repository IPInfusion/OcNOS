/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-platform-transceiver-tibit-types.yang
*
*/

module ipi-platform-transceiver-tibit-types {

    yang-version 1.1;

    namespace   "http://www.ipinfusion.com/yang/ocnos/ipi-platform-transceiver-tibit-types";

    prefix "ipi-platform-transceiver-tibit-types";

    organization
        "IP Infusion Inc.";

    contact
        "Address: 3965 Freedom Circle, Suite 200, Santa Clara, CA 95054
         Phone: +1 408-400-1900
         E-mail: support@ipinfusion.com
         Web: http://www.ipinfusion.com/";

    description
        "YANG version of the ipi-platform-transceiver-tibit-types";


    revision "2022-07-14" {
        description "Initial Version for adding Tibit specific data and control for Tibit OLT transceiver";
        reference " 0.1.0.";
    }



    typedef  trans_tibit_cmm_warranty_seal_t {
        type enumeration {
            enum unsupported {
                value 0;
                description "The warranty seal feature is not supported";
            }
            enum not-VOID {
                value 1;
                description "The module reports warranty is not VOID";
            }
            enum receiver-blinded-by-power {
                value 2;
                description "Optical Receiver had been blinded by received power";
            }
            enum temperature-check-disabled {
                value 3;
                description "The temperature check has been disabled";
            }
            enum alarm-threshold-relaxed {
                value 4;
                description "The alarm threshold has been relaxed";
            }
            enum unknown {
                value 5;
                description "The unknown warranty seal";
            }
        }
        description "type definition for TRANS_TIBIT_CMM_WARRANTY_SEAL_T";
    }

    typedef  trans_tibit_cmm_oper_mode_t {
        type enumeration {
            enum managed {
                value 0;
                description "The managed mode";
            }
            enum auto-boot {
                value 1;
                description "The auto-boot mode";
            }
        }
        description "type definition for TRANS_TIBIT_CMM_OPER_MODE_T";
    }

    typedef  trans_tibit_cmm_pon_mode_t {
        type enumeration {
            enum xgs-pon {
                value 0;
                description "The XGS-PON mode";
            }
            enum 10g-epon {
                value 1;
                description "The 10G-EPON mode";
            }
        }
        description "type definition for TRANS_TIBIT_CMM_PON_MODE_T";
    }

    typedef  trans_tibit_cmm_pon_status_t {
        type enumeration {
            enum down {
                value 0;
                description "The down status";
            }
            enum up {
                value 1;
                description "The up status";
            }
        }
        description "type definition for TRANS_TIBIT_CMM_PON_STATUS_T";
    }

    typedef  trans_tibit_cmm_application_type_t {
        type enumeration {
            enum not-set {
                value 0;
                description "The application type is not set";
            }
            enum pon {
                value 1;
                description "The PON application";
            }
            enum manufacturing {
                value 2;
                description "The manufacturing application";
            }
            enum bootloader {
                value 3;
                description "The bootloader application";
            }
            enum tool {
                value 4;
                description "The tool application";
            }
            enum special-test {
                value 5;
                description "The special test application";
            }
            enum unknown {
                value 6;
                description "The unknown application";
            }
        }
        description "type definition for TRANS_TIBIT_CMM_APPLICATION_TYPE_T";
    }

    typedef  trans_tibit_cmm_string_t {
        type string;
        description "The info string";
    }

    typedef  trans_tibit_cmm_tpid_t {
        type string {
            pattern "(0x8100)|(0x88[aA]8)";
        }
        description "The VLAN TPID in the hexadecimal string format of 0xXXXX. The
                    hexadecimal number is either 0x8100 or 0x88a8";
    }

}
