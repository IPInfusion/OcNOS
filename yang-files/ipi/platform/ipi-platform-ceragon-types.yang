/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-platform-ceragon-types.yang
*
*/

module ipi-platform-ceragon-types {

    yang-version 1.1;

    namespace   "http://www.ipinfusion.com/yang/ocnos/ipi-platform-ceragon-types";

    prefix "ipi-platform-ceragon-types";

    organization
        "IP Infusion Inc.";

    contact
        "Address: 3965 Freedom Circle, Suite 200, Santa Clara, CA 95054
         Phone: +1 408-4001900
         E-mail: support@ipinfusion.com
         Web: http://www.ipinfusion.com/";

    description
        "YANG version of the ipi-platform-ceragon-types";


    revision "2023-08-08" {
        description "Initial Version";
        reference " 0.1.0.";
    }



    typedef  cmm_poe_port_status_t {
        type enumeration {
            enum Disable {
                value 0;
                description "PoE state is disabled";
            }
            enum Enable {
                value 1;
                description "PoE state is enabled";
            }
        }
        description "type definition for CMM_POE_PORT_STATUS_T";
    }

}
