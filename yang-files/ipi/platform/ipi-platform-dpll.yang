/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-platform-dpll.yang
*
*/

submodule ipi-platform-dpll {

    yang-version 1.1;

    belongs-to  ipi-platform { prefix ipi-platform; }

    import feature-list {
        prefix feature-list;
        revision-date 2026-09-15;
    }

    import ipi-platform-types {
        prefix ipi-platform-types;
        revision-date 2026-04-16;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for DPLL information";


    revision "2024-07-01" {
        description "Add DPLL status";
        reference " 0.1.0.";
    }

    grouping dpll-status-state {
        description
            "Grouping for DPLL status state";
        leaf dpll-output-1pps-squelch  {
            type  ipi-platform-types:cml_dpll_output_t;
            description "DPLL output 1pps squelch";
        } // END of dpll-output-1pps-squelch definition.

        leaf dpll-output-10mhz-squelch  {
            type  ipi-platform-types:cml_dpll_output_t;
            description "DPLL output 10MHz squelch";
        } // END of dpll-output-10mhz-squelch definition.

        leaf dpll-input-frequency-alarm  {
            type  ipi-platform-types:cml_dpll_output_t;
            description "DPLL input frequency alarm";
        } // END of dpll-input-frequency-alarm definition.

    } // END of dpll-status-state definition.
    grouping dpll-status {
        description
            "Grouping for DPLL status";
        container dpll-status {
            config false;
            description
                "DPLL status";
            container state {
                config false;
                description
                    "Operational state data for DPLL status";
                uses dpll-status-state;
            } // END of state-container definition.
        } // END of dpll-status-container definition.
    } // END of dpll-status definition.
    grouping dpll-entry-status-state {
        description
            "Grouping for DPLL entry status state";
        leaf dpll-index  {
            type  uint8;
            description "Satellite index";
        } // END of dpll-index definition.

        leaf dpll-input  {
            type  string {
                length "1..1965";
            }
            description "DPLL input";
        } // END of dpll-input definition.

        leaf dpll-valid  {
            type  boolean;
            description "DPLL valid";
        } // END of dpll-valid definition.

        leaf dpll-conf-mode  {
            type  string {
                length "1..1965";
            }
            description "DPLL configured operation mode";
        } // END of dpll-conf-mode definition.

        leaf dpll-actual-mode  {
            type  string {
                length "1..1965";
            }
            description "DPLL actual operation mode";
        } // END of dpll-actual-mode definition.

    } // END of dpll-entry-status-state definition.
    grouping dpll-entry-status {
        description
            "Grouping for DPLL entries status";
        container dpll-entries-status {
            config false;
            description
                "DPLL entries status";

            list dpll-entry-status {
                key "dpll-index";
                config false;
                description
                    "List of DPLL entries";
                leaf dpll-index  {
                    type  leafref {
                        path  "../state/dpll-index";
                    }
                    description "DPLL entry status index.";
                } // END of dpll-index definition.

                container state {
                    config false;
                    description
                        "Operational state data for DPLL entry status";
                    uses dpll-entry-status-state;
                } // END of state-container definition.
            } // End of dpll-entry-status-list
        } // END of dpll-entries-status-container definition.
    } // END of dpll-entry-status definition.
    grouping dpll-state {
        description
            "Grouping for DPLL statistics";
        container dpll {
            if-feature feature-list:HAVE_PTP_HW_OFFLOAD;
            if-feature feature-list:HAVE_DUNE_OR_HAVE_MARVELL;
            config false;
            description
                "DPLL statistics parameters";
            uses dpll-status;
            uses dpll-entry-status;
        } // END of dpll-container definition.
    } // END of dpll-state definition.


}
