/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-platform-cmis.yang
*
*/

submodule ipi-platform-cmis {

    yang-version 1.1;

    belongs-to  ipi-platform { prefix ipi-platform; }

    import feature-list {
        prefix feature-list;
        revision-date 2026-09-15;
    }

    import ipi-platform-cmis-types {
        prefix ipi-platform-cmis-types;
        revision-date 2026-02-18;
    }

    import ipi-platform-sff8024-types {
        prefix ipi-platform-sff8024-types;
        revision-date 2026-01-06;
    }

    organization
        "IP Infusion Inc.";

    contact
        "Address: 3965 Freedom Circle, Suite 200, Santa Clara, CA 95054
         Phone: +1 408-4001900
         E-mail: support@ipinfusion.com
         Web: http://www.ipinfusion.com/";

    description
        "This module defines a schema for CMIS transceivers in platform
                datamodel";


    revision "2025-09-24" {
        description "Add 4 new attributes in advertisement/controls/state";
        reference " 0.10.2.";
    }

    revision "2025-07-22" {
        description "Added error codes in custom get and set RPCs";
        reference " 0.10.1.";
    }

    revision "2025-06-26" {
        description "Added extra interface types and baud rates";
        reference " 0.10.0.";
    }

    revision "2025-06-13" {
        description "Added error codes in custom get and set RPCs";
        reference " 0.9.8.";
    }

    revision "2025-04-28" {
        description "Revert transceiver CLI migration changes";
        reference " 0.9.7.";
    }

    revision "2025-04-14" {
        description "Added proper helpstring for Port Number";
        reference " 0.9.6.";
    }

    revision "2025-04-08" {
        description "Added internal notifications for sending the port to interface mapping to Netconf";
        reference " 0.9.5.";
    }

    revision "2025-04-02" {
        description "Changed names of custom get and set RPCs";
        reference " 0.9.4.";
    }

    revision "2025-04-01" {
        description "Fixing revision history";
        reference " 0.9.3.";
    }

    revision "2025-03-28" {
        description "Remove auto-restart attribute from config CLI";
        reference " 0.9.2.";
    }

    revision "2025-03-14" {
        description "CLI migration from qsfp-dd references to xcvr references";
        reference " 0.9.1.";
    }

    revision "2025-03-07" {
        description "Reverted cli-commands to CLIs using attributes itself for gating and tx-shaping features";
        reference " 0.9.0.";
    }

    revision "2025-01-17" {
        description "Added custom get and set RPCs";
        reference " 0.8.10.";
    }

    revision "2024-12-23" {
        description "Added media lane provision support";
        reference " 0.8.9.";
    }

    revision "2024-12-04" {
        description "Added CMIS module gating support";
        reference " 0.8.8.";
    }

    revision "2024-11-27" {
        description "Added C-CMIS revision 1.3 attributes";
        reference " 0.8.7.";
    }

    revision "2024-09-03" {
        description "Add alarm-type field for monitor recovery notifications";
        reference " 0.8.6.";
    }

    revision "2024-08-20" {
        description "Fixed releases in OcNOS 6.5.3 revisions";
        reference " 0.8.5.";
    }

    revision "2024-08-16" {
        description "Fixes for custom application after DM review";
        reference " 0.8.4.";
    }

    revision "2024-08-09" {
        description "Added CMIS module laser status";
        reference " 0.8.3.";
    }

    revision "2024-07-29" {
        description "Added flag skip-netconf-validation to qsfp-dd model to skip some checks in netconf";
        reference " 0.8.2.";
    }

    revision "2024-07-15" {
        description "Added custom application advertisement";
        reference " 0.8.1.";
    }

    revision "2024-06-11" {
        description "Added custom application config CLI";
        reference " 0.8.0.";
    }

    revision "2024-04-08" {
        description "Added host-config attribute to host side application advertisement";
        reference " 0.7.4.";
    }

    revision "2024-03-28" {
        description "Changed modsel-wait-time type to CML_UINT32_T";
        reference " 0.7.3.";
    }

    revision "2024-03-01" {
        description "Added CDR bypass HW status information and SI advertisement";
        reference " 0.7.2.";
    }

    revision "2024-02-26" {
        description "Added CDR control support";
        reference " 0.7.1.";
    }

    revision "2024-02-06" {
        description "Added transceiver-application-change-host and transceiver-application-change-media notification";
        reference " 0.7.0.";
    }

    revision "2024-01-31" {
        description "Added support for CMIS SI and user thresholds HW config status";
        reference " 0.6.10.";
    }

    revision "2024-01-08" {
        description "Added CMIS modules paths for Streaming Telemetry";
        reference " 0.6.9.";
    }

    revision "2023-12-27" {
        description "Add CLI to configure QSFP-DD SI parameters";
        reference " 0.6.8.";
    }

    revision "2023-12-12" {
        description "Removed mandatory high-alarm and low-alarm in user threshold configs";
        reference " 0.6.7.";
    }

    revision "2023-10-30" {
        description "Added CMIS module advertisements";
        reference " 0.6.6.";
    }

    revision "2023-10-27" {
        description "Added CMIS module datapath assigned interface name state info";
        reference " 0.6.5.";
    }

    revision "2023-10-19" {
        description "Added additional state attributes for datapaths in the cmis-modules model";
        reference " 0.6.4.";
    }

    revision "2023-10-18" {
        description "Handle QSFP-DD media and host lane emtpy config cases";
        reference " 0.6.3.";
    }

    revision "2023-10-16" {
        description "TIBIT Build Issue Handling";
        reference " 0.6.2.";
    }

    revision "2023-09-27" {
        description "Supressed cmis-module runtime container for TIBIT VM";
        reference " 0.6.1.";
    }

    revision "2023-09-06" {
        description "Moved container cmis-modules under /components/component/transceiver";
        reference " 0.6.0.";
    }

    revision "2023-08-29" {
        description "Add autoPopulate tag to QSFP-DD config media lane number key attribute";
        reference " 0.5.9.";
    }

    revision "2023-08-11" {
        description "Fixes made in order resolve QSFP-DD laser config DB sync issues";
        reference " 0.5.8.";
    }

    revision "2023-07-28" {
        description "Minor fixes introduced as result of review of CMIS Xpath v1.2";
        reference " 0.5.7.";
    }

    revision "2023-07-25" {
        description "Fixed QSFP-DD per media lane laser and user threshold config DB sync issues";
        reference " 0.5.6.";
    }

    revision "2023-07-21" {
        description "service-disable will be supported for all QSFP-DD modules";
        reference " 0.5.5.";
    }

    revision "2023-06-30" {
        description "Added CLI command for QSFP-DD configurable threshold support";
        reference " 0.5.4.";
    }

    revision "2023-06-29" {
        description "Fixed QSFP-DD media side flags datatype";
        reference " 0.5.3.";
    }

    revision "2023-06-20" {
        description "Added CCMIS media threshold alarms";
        reference " 0.5.2.";
    }

    revision "2023-06-12" {
        description "Added CCMIS host threshold alarms";
        reference " 0.5.1.";
    }

    revision "2023-06-02" {
        description "Added CCMIS host and media discrete alarms";
        reference " 0.5.0.";
    }

    revision "2023-04-11" {
        description "Remove alarm type field from non-descrete alarm recovery notifications";
        reference " 0.4.5.";
    }

    revision "2023-03-15" {
        description "Replaced QSFP-DD laser grid config related WHEN condition for media lane laser channel to a DB trigger";
        reference " 0.4.4.";
    }

    revision "2023-03-06" {
        description "Fixed cmis-module list child nodes that were not compliant with the current CMIS XPath sheet";
        reference " 0.4.3.";
    }

    revision "2023-02-15" {
        description "Added CLI command to disable coherent license per QSFP-DD port";
        reference " 0.4.2.";
    }

    revision "2023-02-13" {
        description "Per host lane QSFP-DD configuration mode";
        reference " 0.4.1.";
    }

    revision "2023-01-24" {
        description "Per media lane QSFP-DD laser configurations";
        reference " 0.4.0.";
    }

    revision "2023-01-11" {
        description "Added WHEN tag to prevent commit of empty QSFP-DD config (empty list)";
        reference " 0.3.5.";
    }

    revision "2023-01-03" {
        description "Added basic module, host side and media side monitors";
        reference " 0.3.4.";
    }

    revision "2022-12-16" {
        description "Help String updation for fine tune freq config and target output power config CLIs";
        reference " 0.3.3.";
    }

    revision "2022-11-04" {
        description "Added unset CLI for QSFP-DD config mode and implicit_delete/autoPopulate where is needed to avoid DB sync";
        reference " 0.3.2.";
    }

    revision "2022-11-03" {
        description "Fixed DB sync issues related to laser grid spacing config for QSFP-DD";
        reference " 0.3.1.";
    }

    revision "2022-10-27" {
        description "Fixed DB sync issues for QSFP-DD configs";
        reference " 0.3.0.";
    }

    revision "2022-10-24" {
        description "Added TX laser grid spacing, fine tune frequency and output power configs";
        reference " 0.2.3.";
    }

    revision "2022-09-27" {
        description "Addressing CMIS datamodel XPath review comments";
        reference " 0.2.2.";
    }

    revision "2022-09-22" {
        description "Added CLI to configure QSFP-DD TX laser channel";
        reference " 0.2.1.";
    }

    revision "2022-08-25" {
        description "Added QSFP-DD configuration attributes and respective CLI";
        reference " 0.2.0.";
    }

    revision "2022-07-07" {
        description "Added datamodel file for SFF-8024 type definitions";
        reference " 0.1.1.";
    }

    revision "2022-06-28" {
        description "Initial Version";
        reference " 0.1.0.";
    }

    grouping ipi-platform-cmis-module-eeprom-state {
        description
            "ipi-platform-cmis-module-eeprom-state";
        leaf identifier  {
            type  ipi-platform-sff8024-types:cmm_sff8024_identifier_t;
            description "Module identifier";
        } // END of identifier definition.

        leaf vendor-name  {
            type  string {
                length "0..32";
            }
            description "Module vendor name";
        } // END of vendor-name definition.

        leaf vendor-oui  {
            type  string {
                length "0..32";
            }
            description "Module vendor OUI";
        } // END of vendor-oui definition.

        leaf part-number  {
            type  string {
                length "0..32";
            }
            description "Module part number";
        } // END of part-number definition.

        leaf revision-level  {
            type  string {
                length "0..32";
            }
            description "Module revision level";
        } // END of revision-level definition.

        leaf serial-number  {
            type  string {
                length "0..32";
            }
            description "Module serial number";
        } // END of serial-number definition.

        leaf manufacturing-date  {
            type  string {
                length "0..32";
            }
            description "Module manufacturing date";
        } // END of manufacturing-date definition.

        leaf clei-code  {
            type  string {
                length "0..32";
            }
            description "Module CLEI code";
        } // END of clei-code definition.

        leaf module-power-class  {
            type  ipi-platform-cmis-types:cmm_cmis_module_power_class_t;
            description "Module power class";
        } // END of module-power-class definition.

        leaf module-max-power  {
            type  decimal64 {
                 fraction-digits 2;            }
            units "Watt";
            description "Module maximum power consumption";
        } // END of module-max-power definition.

        leaf cooling-implemented  {
            type  ipi-platform-cmis-types:cmm_cmis_yes_no_t;
            description "If trasmitter device has cooling implemented";
        } // END of cooling-implemented definition.

        leaf temperature-max  {
            type  int16;
            units "Celsius";
            description "Maximum allowed module case temperature";
        } // END of temperature-max definition.

        leaf temperature-min  {
            type  int16;
            units "Celsius";
            description "Minimum allowed module case temperature";
        } // END of temperature-min definition.

        leaf operatin-voltage-min  {
            type  decimal64 {
                 fraction-digits 2;            }
            units "Volt";
            description "Minimum supported module operating voltage";
        } // END of operatin-voltage-min definition.

        leaf optical-detector  {
            type  ipi-platform-cmis-types:cmm_cmis_optical_detector_t;
            description "Module optical detector type";
        } // END of optical-detector definition.

        leaf rx-power-measurement  {
            type  ipi-platform-cmis-types:cmm_cmis_rx_power_measur_t;
            description "Module Rx power measurement type";
        } // END of rx-power-measurement definition.

        leaf tx-disable-module-wide  {
            type  ipi-platform-cmis-types:cmm_cmis_yes_no_t;
            description "If Tx disable is module wide or per lane";
        } // END of tx-disable-module-wide definition.

        leaf cable-assembly-link-length  {
            type  int16;
            units "Meter";
            description "Cable assembly link length. -1 means separable media, -2 means length
                        > 6300m, -3 means undefined length.";
        } // END of cable-assembly-link-length definition.

        leaf connector-type  {
            type  ipi-platform-sff8024-types:cmm_sff8024_connector_type_t;
            description "Module connector type";
        } // END of connector-type definition.

        leaf cca-5ghz  {
            type  uint8;
            units "dB";
            description "Copper cable attenuation at 5Ghz";
        } // END of cca-5ghz definition.

        leaf cca-7ghz  {
            type  uint8;
            units "dB";
            description "Copper cable attenuation at 7Ghz";
        } // END of cca-7ghz definition.

        leaf cca-12p9ghz  {
            type  uint8;
            units "dB";
            description "Copper cable attenuation at 12.9Ghz";
        } // END of cca-12p9ghz definition.

        leaf cca-25p8ghz  {
            type  uint8;
            units "dB";
            description "Copper cable attenuation at 25.8Ghz";
        } // END of cca-25p8ghz definition.

        leaf media-interface-technology  {
            type  ipi-platform-cmis-types:cmm_cmis_media_intf_tech_t;
            description "Module media interface technology";
        } // END of media-interface-technology definition.

        leaf cmis-revision  {
            type  string {
                length "0..32";
            }
            description "Module CMIS revision";
        } // END of cmis-revision definition.

        leaf ccmis-revision  {
            type  string {
                length "0..32";
            }
            description "Module C-CMIS revision";
        } // END of ccmis-revision definition.

        leaf memory-model  {
            type  ipi-platform-cmis-types:cmm_cmis_memory_model_t;
            description "Module memory model";
        } // END of memory-model definition.

        leaf mci-max-speed  {
            type  ipi-platform-cmis-types:cmm_cmis_mci_max_speed_t;
            description "Module MCI maximum speed";
        } // END of mci-max-speed definition.

        leaf active-firmware-revision  {
            type  string {
                length "0..32";
            }
            description "Module active firmware revision";
        } // END of active-firmware-revision definition.

        leaf inactive-firmware-revision  {
            type  string {
                length "0..32";
            }
            description "Module inactive firmware revision";
        } // END of inactive-firmware-revision definition.

        leaf hardware-revision  {
            type  string {
                length "0..32";
            }
            description "Module hardware revision";
        } // END of hardware-revision definition.

        leaf media-type  {
            type  ipi-platform-cmis-types:cmm_cmis_media_type_t;
            description "Module media type";
        } // END of media-type definition.

        leaf max-smf-link-length  {
            type  decimal64 {
                 fraction-digits 2;            }
            units "Kilometer";
            description "Module maximum SMF link length";
        } // END of max-smf-link-length definition.

        leaf max-mmf-om2-link-length  {
            type  uint8;
            units "Meter";
            description "Module maximum MMF OM2 link length";
        } // END of max-mmf-om2-link-length definition.

        leaf max-mmf-om3-link-length  {
            type  uint16;
            units "Meter";
            description "Module maximum MMF OM3 link length";
        } // END of max-mmf-om3-link-length definition.

        leaf max-mmf-om4-link-length  {
            type  uint16;
            units "Meter";
            description "Module maximum MMF OM4 link length";
        } // END of max-mmf-om4-link-length definition.

        leaf max-mmf-om5-link-length  {
            type  uint16;
            units "Meter";
            description "Module maximum MMF OM5 link length";
        } // END of max-mmf-om5-link-length definition.

        leaf wavelength-nominal  {
            type  decimal64 {
                 fraction-digits 2;            }
            units "nm";
            description "Module nominal wavelength";
        } // END of wavelength-nominal definition.

        leaf wavelength-tolerance  {
            type  decimal64 {
                 fraction-digits 2;            }
            units "nm";
            description "Module wavelength tolerance";
        } // END of wavelength-tolerance definition.

        leaf rx-los-detection-type  {
            type  ipi-platform-cmis-types:cmm_ccmis_rx_los_type_t;
            description "Rx LoS detection type";
        } // END of rx-los-detection-type definition.

    } // END of ipi-platform-cmis-module-eeprom-state definition.
    grouping ipi-platform-cmis-module-eeprom-top {
        description
            "ipi-platform-cmis-module-eeprom-top";
        container state {
            config false;
            description
                "State data for CMIS eeprom";
            uses ipi-platform-cmis-module-eeprom-state;
        } // END of state-container definition.
    } // END of ipi-platform-cmis-module-eeprom-top definition.
    grouping ipi-platform-cmis-module-advertisement-application-side-state {
        description
            "ipi-platform-cmis-module-advertisement-application-side-state";
        leaf interface-type  {
            type  ipi-platform-cmis-types:cmm_cmis_interface_type_t;
            description "Interface type";
        } // END of interface-type definition.

        leaf application-bitrate  {
            type  ipi-platform-cmis-types:cmm_cmis_bit_rate_t;
            description "Application bit rate";
        } // END of application-bitrate definition.

        leaf lane-count  {
            type  uint8;
            description "Lane count";
        } // END of lane-count definition.

        leaf signal-bitrate  {
            type  ipi-platform-cmis-types:cmm_cmis_bit_rate_t;
            description "Signal bit rate";
        } // END of signal-bitrate definition.

        leaf modulation-format  {
            type  ipi-platform-cmis-types:cmm_cmis_modulation_format_t;
            description "Modulation format";
        } // END of modulation-format definition.

        leaf bits-per-unit-interval  {
            type  decimal64 {
                 fraction-digits 2;            }
            description "Number of bits per unit interval";
        } // END of bits-per-unit-interval definition.

        leaf lane-assignment  {
            type  ipi-platform-cmis-types:cmm_cmis_lane_assignment_t;
            description "Lane assignment bitmap";
        } // END of lane-assignment definition.

    } // END of ipi-platform-cmis-module-advertisement-application-side-state definition.
    grouping ipi-platform-cmis-module-advertisement-application-host-info {
        description
            "ipi-platform-cmis-module-advertisement-application-host-info";
        leaf host-config  {
            type  string {
                length "1..1965";
            }
            description "Application host interface configuration details";
        } // END of host-config definition.

    } // END of ipi-platform-cmis-module-advertisement-application-host-info definition.
    grouping ipi-platform-cmis-module-advertisement-application-state {
        description
            "ipi-platform-cmis-module-advertisement-application-state";
        leaf id  {
            type  uint8 {
                 range "1..15"  {
                    description "1..15: Supported range 1 - 15";
                 }
            }
            description "Application id number";
        } // END of id definition.

    } // END of ipi-platform-cmis-module-advertisement-application-state definition.
    grouping ipi-platform-cmis-module-advertisement-applications-top {
        description
            "ipi-platform-cmis-module-advertisement-applications-top";

        list application {
            key "id";
            config false;
            description
                "List of applications";
            leaf id  {
                type  leafref {
                    path  "../state/id";
                }
                description "Application id number";
            } // END of id definition.

            container state {
                config false;
                description
                    "State data for CMIS advertised application";
                uses ipi-platform-cmis-module-advertisement-application-state;
            } // END of state-container definition.
            container host {
                config false;
                description
                    "Container for application host side information";
                container state {
                    config false;
                    description
                        "Application state data for host side";
                    uses ipi-platform-cmis-module-advertisement-application-side-state;
                    uses ipi-platform-cmis-module-advertisement-application-host-info;
                } // END of state-container definition.
            } // END of host-container definition.
            container media {
                config false;
                description
                    "Container for application media side information";
                container state {
                    config false;
                    description
                        "Application state data for media side";
                    uses ipi-platform-cmis-module-advertisement-application-side-state;
                } // END of state-container definition.
            } // END of media-container definition.
        } // End of application-list
    } // END of ipi-platform-cmis-module-advertisement-applications-top definition.
    grouping ipi-platform-cmis-module-advertisement-custom-app-side-id-state {
        description
            "ipi-platform-cmis-module-advertisement-custom-app-side-id-state";
        leaf id  {
            type  uint8 {
                 range "1..32"  {
                    description "1..32: Supported range 1 - 32";
                 }
            }
            description "Custom application host/media ID number";
        } // END of id definition.

    } // END of ipi-platform-cmis-module-advertisement-custom-app-side-id-state definition.
    grouping ipi-platform-cmis-module-advertisement-custom-application-host {
        description
            "ipi-platform-cmis-module-advertisement-custom-application-host";
        leaf host-config  {
            type  string {
                length "1..1965";
            }
            description "Application host interface configuration details";
        } // END of host-config definition.

    } // END of ipi-platform-cmis-module-advertisement-custom-application-host definition.
    grouping ipi-platform-cmis-module-advertisement-custom-application-state {
        description
            "ipi-platform-cmis-module-advertisement-custom-application-state";
        leaf application-selector  {
            type  uint8;
            description "Custom application application selector to be used";
        } // END of application-selector definition.

    } // END of ipi-platform-cmis-module-advertisement-custom-application-state definition.
    grouping ipi-platform-cmis-module-advertisement-custom-application-top {
        description
            "ipi-platform-cmis-module-advertisement-custom-application-top";
        container state {
            config false;
            description
                "State data for CMIS advertised custom application";
            uses ipi-platform-cmis-module-advertisement-custom-application-state;
        } // END of state-container definition.
        container host-ids {
            config false;
            description
                "Enclosing container for custom application host IDs list";

            list host-id {
                key "id";
                config false;
                description
                    "List of advertised host IDs";
                leaf id  {
                    type  leafref {
                        path  "../state/id";
                    }
                    description "Custom application host ID number";
                } // END of id definition.

                container state {
                    config false;
                    description
                        "Custom application state data for a host ID";
                    uses ipi-platform-cmis-module-advertisement-custom-app-side-id-state;
                    uses ipi-platform-cmis-module-advertisement-application-side-state;
                    uses ipi-platform-cmis-module-advertisement-custom-application-host;
                } // END of state-container definition.
            } // End of host-id-list
        } // END of host-ids-container definition.
        container media-ids {
            config false;
            description
                "Enclosing container for custom application media IDs list";

            list media-id {
                key "id";
                config false;
                description
                    "List of advertised media IDs";
                leaf id  {
                    type  leafref {
                        path  "../state/id";
                    }
                    description "Custom application media ID number";
                } // END of id definition.

                container state {
                    config false;
                    description
                        "Custom application state data for a host ID";
                    uses ipi-platform-cmis-module-advertisement-custom-app-side-id-state;
                    uses ipi-platform-cmis-module-advertisement-application-side-state;
                } // END of state-container definition.
            } // End of media-id-list
        } // END of media-ids-container definition.
    } // END of ipi-platform-cmis-module-advertisement-custom-application-top definition.
    grouping ipi-platform-cmis-module-advertisement-controls-top {
        description
            "ipi-platform-cmis-module-advertisement-controls-top";
        container state {
            config false;
            description
                "State data for CMIS advertised controls";
            leaf wavelength-control  {
                type  ipi-platform-cmis-types:cmm_cmis_yes_no_t;
                description "Indicates whether wavelength control is supported or not";
            } // END of wavelength-control definition.

            leaf tunable-transmitter  {
                type  ipi-platform-cmis-types:cmm_cmis_yes_no_t;
                description "Indicates whether the transmitter is tunnable or not";
            } // END of tunable-transmitter definition.

            leaf tx-output-squelching-method  {
                type  ipi-platform-cmis-types:cmm_cmis_tx_squelch_method_t;
                description "Indicates the method of used for Tx output squelching";
            } // END of tx-output-squelching-method definition.

            leaf forced-tx-output-squelching  {
                type  ipi-platform-cmis-types:cmm_cmis_yes_no_t;
                description "Indicates whether the host can force squelching of the Tx outputs or
                            not";
            } // END of forced-tx-output-squelching definition.

            leaf tx-output-squelching-disable  {
                type  ipi-platform-cmis-types:cmm_cmis_yes_no_t;
                description "Indicates whether the host can disable automatic squelching of the Tx
                            outputs or not";
            } // END of tx-output-squelching-disable definition.

            leaf tx-output-disable  {
                type  ipi-platform-cmis-types:cmm_cmis_yes_no_t;
                description "Indicates whether the host can disable the Tx outputs or not";
            } // END of tx-output-disable definition.

            leaf input-polarity-flip-tx  {
                type  ipi-platform-cmis-types:cmm_cmis_yes_no_t;
                description "Indicates whether InputPolarityFlipTx is supported or not";
            } // END of input-polarity-flip-tx definition.

            leaf rx-output-squelching-disable  {
                type  ipi-platform-cmis-types:cmm_cmis_yes_no_t;
                description "Indicates whether the host can disable automatic squelching of the Rx
                            outputs or not";
            } // END of rx-output-squelching-disable definition.

            leaf rx-output-disable  {
                type  ipi-platform-cmis-types:cmm_cmis_yes_no_t;
                description "Indicates whether the host can disable the Rx outputs or not";
            } // END of rx-output-disable definition.

            leaf output-polarity-flip-rx  {
                type  ipi-platform-cmis-types:cmm_cmis_yes_no_t;
                description "Indicates whether OutputPolarityFlipRx is supported or not";
            } // END of output-polarity-flip-rx definition.

            leaf rx-media-fed-pm-implemented  {
                type  ipi-platform-cmis-types:cmm_cmis_yes_no_t;
                description "Indicates whether rxMediaFedPmImpl is implemented or not";
            } // END of rx-media-fed-pm-implemented definition.

            leaf rx-media-fdd-pm-implemented  {
                type  ipi-platform-cmis-types:cmm_cmis_yes_no_t;
                description "Indicates whether rxMediaFddPmImpl is implemented or not";
            } // END of rx-media-fdd-pm-implemented definition.

            leaf tx-host-fed-pm-implemented  {
                type  ipi-platform-cmis-types:cmm_cmis_yes_no_t;
                description "Indicates whether txHostFedPmImpl is implemented or not";
            } // END of tx-host-fed-pm-implemented definition.

            leaf tx-host-fdd-pm-implemented  {
                type  ipi-platform-cmis-types:cmm_cmis_yes_no_t;
                description "Indicates whether txHostFddPmImpl is implemented or not";
            } // END of tx-host-fdd-pm-implemented definition.

        } // END of state-container definition.
    } // END of ipi-platform-cmis-module-advertisement-controls-top definition.
    grouping ipi-platform-cmis-module-advertisement-diagnostics-module-state {
        description
            "ipi-platform-cmis-module-advertisement-diagnostics-module-state";
        leaf simultaneous-host-and-media-loobpack  {
            type  ipi-platform-cmis-types:cmm_cmis_yes_no_t;
            description "Indicates whether simultaneous host and media side loopback is
                        supported or not";
        } // END of simultaneous-host-and-media-loobpack definition.

        leaf report-bit-error-ratio  {
            type  ipi-platform-cmis-types:cmm_cmis_yes_no_t;
            description "Indicates whether reporting of bit error ratio is supported or not";
        } // END of report-bit-error-ratio definition.

        leaf count-bits-and-errors  {
            type  ipi-platform-cmis-types:cmm_cmis_yes_no_t;
            description "Indicates whether counting of bits and bit erros is supported or not";
        } // END of count-bits-and-errors definition.

        leaf media-side-fec-prbs-error  {
            type  ipi-platform-cmis-types:cmm_cmis_yes_no_t;
            description "Indicates whether media side PRBS error information is supported or
                        not";
        } // END of media-side-fec-prbs-error definition.

        leaf host-side-fec-prbs-error  {
            type  ipi-platform-cmis-types:cmm_cmis_yes_no_t;
            description "Indicates whether host side PRBS error information is supported or not";
        } // END of host-side-fec-prbs-error definition.

        leaf media-side-input-snr-measurement  {
            type  ipi-platform-cmis-types:cmm_cmis_yes_no_t;
            description "Indicates whether media side SNR measurement is supported or not";
        } // END of media-side-input-snr-measurement definition.

        leaf host-side-input-snr-measurement  {
            type  ipi-platform-cmis-types:cmm_cmis_yes_no_t;
            description "Indicates whether host side SNR measurement is supported or not";
        } // END of host-side-input-snr-measurement definition.

        leaf gating-support  {
            type  ipi-platform-cmis-types:cmm_cmis_yes_no_t;
            description "Indicates whether gated performance monitoring (PM) is supported or
                        not";
        } // END of gating-support definition.

        leaf gating-results  {
            type  ipi-platform-cmis-types:cmm_cmis_yes_no_t;
            description "Indicates whether reporting gated performance monitoring (PM) is
                        supported or not";
        } // END of gating-results definition.

        leaf periodic-updates  {
            type  ipi-platform-cmis-types:cmm_cmis_yes_no_t;
            description "Indicates whether real-time statistics are periodically updated during
                        measurement or not";
        } // END of periodic-updates definition.

        leaf per-lane-gating-timers  {
            type  ipi-platform-cmis-types:cmm_cmis_yes_no_t;
            description "Indicates whether per lane gating timers are supported in all banks or
                        not";
        } // END of per-lane-gating-timers definition.

        leaf gating-auto-restart  {
            type  ipi-platform-cmis-types:cmm_cmis_yes_no_t;
            description "Indicates whether auto-restart gating control is supported or not";
        } // END of gating-auto-restart definition.

    } // END of ipi-platform-cmis-module-advertisement-diagnostics-module-state definition.
    grouping ipi-platform-cmis-module-advertisement-diagnostics-state {
        description
            "ipi-platform-cmis-module-advertisement-diagnostics-state";
        leaf output-loopack  {
            type  ipi-platform-cmis-types:cmm_cmis_yes_no_t;
            description "Indicates whether output loopback is supported or not";
        } // END of output-loopack definition.

        leaf input-loopack  {
            type  ipi-platform-cmis-types:cmm_cmis_yes_no_t;
            description "Indicates whether input loopback is supported or not";
        } // END of input-loopack definition.

        leaf per-lane-loopack  {
            type  ipi-platform-cmis-types:cmm_cmis_yes_no_t;
            description "Indicates whether per lane loopback is supported or not";
        } // END of per-lane-loopack definition.

        leaf report-input-snr  {
            type  ipi-platform-cmis-types:cmm_cmis_yes_no_t;
            description "Indicates whether input SNR reporting is supported or not";
        } // END of report-input-snr definition.

        leaf report-fec  {
            type  ipi-platform-cmis-types:cmm_cmis_yes_no_t;
            description "Indicates whether PRBS error information is available or not";
        } // END of report-fec definition.

        leaf prbs-checker-post-fec  {
            type  ipi-platform-cmis-types:cmm_cmis_yes_no_t;
            description "Indicates whether post FEC PRBS checker is supported or not";
        } // END of prbs-checker-post-fec definition.

        leaf prbs-checker-pre-fec  {
            type  ipi-platform-cmis-types:cmm_cmis_yes_no_t;
            description "Indicates whether pre FEC PRBS checker is supported or not";
        } // END of prbs-checker-pre-fec definition.

        leaf prbs-checker-types  {
            type  ipi-platform-cmis-types:cmm_cmis_prbs_support_type_t;
            description "Show supported PRBS checker pattern types";
        } // END of prbs-checker-types definition.

        leaf prbs-generator-post-fec  {
            type  ipi-platform-cmis-types:cmm_cmis_yes_no_t;
            description "Indicates whether post FEC PRBS generator is supported or not";
        } // END of prbs-generator-post-fec definition.

        leaf prbs-generator-pre-fec  {
            type  ipi-platform-cmis-types:cmm_cmis_yes_no_t;
            description "Indicates whether pre FEC PRBS generator is supported or not";
        } // END of prbs-generator-pre-fec definition.

        leaf prbs-generator-types  {
            type  ipi-platform-cmis-types:cmm_cmis_prbs_support_type_t;
            description "Show supported PRBS generator pattern types";
        } // END of prbs-generator-types definition.

    } // END of ipi-platform-cmis-module-advertisement-diagnostics-state definition.
    grouping ipi-platform-cmis-module-advertisement-diagnostics-top {
        description
            "ipi-platform-cmis-module-advertisement-diagnostics-top";
        container module {
            config false;
            description
                "CMIS module wise advertised diagnostics";
            container state {
                config false;
                description
                    "State data for CMIS module wise advertised diagnostics";
                uses ipi-platform-cmis-module-advertisement-diagnostics-module-state;
            } // END of state-container definition.
        } // END of module-container definition.
        container host {
            config false;
            description
                "CMIS host side advertised diagnostics";
            container state {
                config false;
                description
                    "State data for CMIS host side advertised diagnostics";
                uses ipi-platform-cmis-module-advertisement-diagnostics-state;
            } // END of state-container definition.
        } // END of host-container definition.
        container media {
            config false;
            description
                "CMIS media side advertised diagnostics";
            container state {
                config false;
                description
                    "State data for CMIS media side advertised diagnostics";
                uses ipi-platform-cmis-module-advertisement-diagnostics-state;
            } // END of state-container definition.
        } // END of media-container definition.
    } // END of ipi-platform-cmis-module-advertisement-diagnostics-top definition.
    grouping ipi-platform-cmis-module-advertisement-durations-top {
        description
            "ipi-platform-cmis-module-advertisement-durations-top";
        container state {
            config false;
            description
                "State data for CMIS advertised durations";
            leaf modsel-wait-time  {
                type  uint32;
                units "us";
                description "ModSel wait time in micro seconds";
            } // END of modsel-wait-time definition.

            leaf dpinit-maximun-duration  {
                type  ipi-platform-cmis-types:cmm_cmis_durations_t;
                description "DPInit state maximum duration";
            } // END of dpinit-maximun-duration definition.

            leaf dpdeinit-maximun-duration  {
                type  ipi-platform-cmis-types:cmm_cmis_durations_t;
                description "DPDeinit state maximum duration";
            } // END of dpdeinit-maximun-duration definition.

            leaf dptxturnon-maximum-duration  {
                type  ipi-platform-cmis-types:cmm_cmis_durations_t;
                description "DPTxTurnOn state maximum duration";
            } // END of dptxturnon-maximum-duration definition.

            leaf dptxturnoff-maximum-duration  {
                type  ipi-platform-cmis-types:cmm_cmis_durations_t;
                description "DPTxTurnOff state maximum duration";
            } // END of dptxturnoff-maximum-duration definition.

            leaf modulepwrup-maximum-duration  {
                type  ipi-platform-cmis-types:cmm_cmis_durations_t;
                description "ModulePwrUp state maximum duration";
            } // END of modulepwrup-maximum-duration definition.

            leaf modulepwrdn-maximum-duration  {
                type  ipi-platform-cmis-types:cmm_cmis_durations_t;
                description "MoudulePwrDn state maximum duration";
            } // END of modulepwrdn-maximum-duration definition.

            leaf npinit-maximum-duration  {
                type  ipi-platform-cmis-types:cmm_cmis_durations_t;
                description "NPInit state maximum duration";
            } // END of npinit-maximum-duration definition.

            leaf npdeinit-maximum-duration  {
                type  ipi-platform-cmis-types:cmm_cmis_durations_t;
                description "NPDeinit state maximum duration";
            } // END of npdeinit-maximum-duration definition.

            leaf nptxturnon-maximum-duration  {
                type  ipi-platform-cmis-types:cmm_cmis_durations_t;
                description "NPTxTurnOn state maximum duration";
            } // END of nptxturnon-maximum-duration definition.

            leaf nptxturnoff-maximum-duration  {
                type  ipi-platform-cmis-types:cmm_cmis_durations_t;
                description "NPTxTurnOff state maximum duration";
            } // END of nptxturnoff-maximum-duration definition.

        } // END of state-container definition.
    } // END of ipi-platform-cmis-module-advertisement-durations-top definition.
    grouping ipi-platform-cmis-module-advertisement-laser-state {
        description
            "ipi-platform-cmis-module-advertisement-laser-state";
        leaf supported-grids  {
            type  ipi-platform-cmis-types:cmm_cmis_laser_grid_support_t;
            description "Shows supported laser grids";
        } // END of supported-grids definition.

        leaf fine-tune-supported  {
            type  ipi-platform-cmis-types:cmm_cmis_yes_no_t;
            description "Indicates whether laser fine tuning is supported or not";
        } // END of fine-tune-supported definition.

        leaf fine-tune-resolution  {
            type  decimal64 {
                 fraction-digits 3;            }
            units "GHz";
            description "Fine tune resolution in GHz";
        } // END of fine-tune-resolution definition.

        leaf fine-tune-low-offset  {
            type  decimal64 {
                 fraction-digits 3;            }
            units "GHz";
            description "Fine tune low offset in GHz";
        } // END of fine-tune-low-offset definition.

        leaf fine-tune-high-offset  {
            type  decimal64 {
                 fraction-digits 3;            }
            units "GHz";
            description "Fine tune high offset in GHz";
        } // END of fine-tune-high-offset definition.

        leaf per-lane-programmable-output-power  {
            type  ipi-platform-cmis-types:cmm_cmis_yes_no_t;
            description "Indicates whether programming of output power per lane is supported or
                        not";
        } // END of per-lane-programmable-output-power definition.

        leaf minimum-programmable-output-power  {
            type  decimal64 {
                 fraction-digits 3;            }
            units "dBm";
            description "Minimum value for programmable output power in dBm";
        } // END of minimum-programmable-output-power definition.

        leaf maximum-programmable-output-power  {
            type  decimal64 {
                 fraction-digits 3;            }
            units "dBm";
            description "Maximum value for programmable output power in dBm";
        } // END of maximum-programmable-output-power definition.

    } // END of ipi-platform-cmis-module-advertisement-laser-state definition.
    grouping ipi-platform-cmis-module-advertisement-laser-grid-state {
        description
            "ipi-platform-cmis-module-advertisement-laser-grid-state";
        leaf id  {
            type  ipi-platform-cmis-types:cmm_cmis_laser_grid_spacing_t;
            description "Grid spacing ID";
        } // END of id definition.

        leaf lowest-channel-frequency  {
            type  decimal64 {
                 fraction-digits 3;            }
            units "THz";
            description "Grid lowest channel frequency in THz";
        } // END of lowest-channel-frequency definition.

        leaf highest-channel-frequency  {
            type  decimal64 {
                 fraction-digits 3;            }
            units "THz";
            description "Grid highest channel frequency in THz";
        } // END of highest-channel-frequency definition.

        leaf channel-count  {
            type  uint16;
            description "Total number of grid channels";
        } // END of channel-count definition.

    } // END of ipi-platform-cmis-module-advertisement-laser-grid-state definition.
    grouping ipi-platform-cmis-module-advertisement-laser-top {
        description
            "ipi-platform-cmis-module-advertisement-laser-top";
        container state {
            config false;
            description
                "State data for CMIS advertised laser tuning support";
            uses ipi-platform-cmis-module-advertisement-laser-state;
        } // END of state-container definition.
        container grids {
            config false;
            description
                "High level container for list of supported grids";

            list grid {
                key "id";
                config false;
                description
                    "List of grid spacing details";
                leaf id  {
                    type  leafref {
                        path  "../state/id";
                    }
                    description "Grid spacing ID";
                } // END of id definition.

                container state {
                    config false;
                    description
                        "State data for laser grid spacing information";
                    uses ipi-platform-cmis-module-advertisement-laser-grid-state;
                } // END of state-container definition.
            } // End of grid-list
        } // END of grids-container definition.
    } // END of ipi-platform-cmis-module-advertisement-laser-top definition.
    grouping ipi-platform-cmis-module-advertisement-monitoring-module-state {
        description
            "ipi-platform-cmis-module-advertisement-monitoring-module-state";
        leaf id  {
            type  ipi-platform-cmis-types:cmm_cmis_module_monitor_id_t;
            description "Module monitor ID";
        } // END of id definition.

        leaf supported  {
            type  ipi-platform-cmis-types:cmm_cmis_yes_no_t;
            description "Indicates whether this monitor ID is supported or not";
        } // END of supported definition.

    } // END of ipi-platform-cmis-module-advertisement-monitoring-module-state definition.
    grouping ipi-platform-cmis-module-advertisement-host-monitor-state {
        description
            "ipi-platform-cmis-module-advertisement-host-monitor-state";
        leaf id  {
            type  ipi-platform-cmis-types:cmm_cmis_host_monitor_id_t;
            description "Host side monitor ID";
        } // END of id definition.

    } // END of ipi-platform-cmis-module-advertisement-host-monitor-state definition.
    grouping ipi-platform-cmis-module-advertisement-host-flag-state {
        description
            "ipi-platform-cmis-module-advertisement-host-flag-state";
        leaf id  {
            type  ipi-platform-cmis-types:cmm_cmis_host_flag_id_t;
            description "Host side flag ID";
        } // END of id definition.

    } // END of ipi-platform-cmis-module-advertisement-host-flag-state definition.
    grouping ipi-platform-cmis-module-advertisement-media-monitor-state {
        description
            "ipi-platform-cmis-module-advertisement-media-monitor-state";
        leaf id  {
            type  ipi-platform-cmis-types:cmm_cmis_media_monitor_id_t;
            description "Media side monitor ID";
        } // END of id definition.

    } // END of ipi-platform-cmis-module-advertisement-media-monitor-state definition.
    grouping ipi-platform-cmis-module-advertisement-media-flag-state {
        description
            "ipi-platform-cmis-module-advertisement-media-flag-state";
        leaf id  {
            type  ipi-platform-cmis-types:cmm_cmis_media_flag_id_t;
            description "Media side flag ID";
        } // END of id definition.

    } // END of ipi-platform-cmis-module-advertisement-media-flag-state definition.
    grouping ipi-platform-cmis-module-advertisement-monitor-state-details {
        description
            "ipi-platform-cmis-module-advertisement-monitor-state-details";
        leaf supported  {
            type  ipi-platform-cmis-types:cmm_cmis_yes_no_t;
            description "Indicates whether this monitor/flag ID is supported or not";
        } // END of supported definition.

        leaf lanes-assigned  {
            type  ipi-platform-cmis-types:cmm_cmis_lane_assignment_t;
            description "Bitmap of which lanes support this monitor/flag ID";
        } // END of lanes-assigned definition.

    } // END of ipi-platform-cmis-module-advertisement-monitor-state-details definition.
    grouping ipi-platform-cmis-module-advertisement-monitoring-top {
        description
            "ipi-platform-cmis-module-advertisement-monitoring-top";
        container module {
            config false;
            description
                "State data for advertised module monitors";
            container monitors {
                config false;
                description
                    "High level container for the list of advertised module monitors";

                list monitor {
                    key "id";
                    config false;
                    description
                        "List of advertised module monitors";
                    leaf id  {
                        type  leafref {
                            path  "../state/id";
                        }
                        description "Module monitor ID";
                    } // END of id definition.

                    container state {
                        config false;
                        description
                            "State data for advertised module monitors";
                        uses ipi-platform-cmis-module-advertisement-monitoring-module-state;
                    } // END of state-container definition.
                } // End of monitor-list
            } // END of monitors-container definition.
        } // END of module-container definition.
        container host {
            config false;
            description
                "State data for advertised host side monitors";
            container monitors {
                config false;
                description
                    "High level container for the list of advertised host side monitors";

                list monitor {
                    key "id";
                    config false;
                    description
                        "List of advertised host side monitors";
                    leaf id  {
                        type  leafref {
                            path  "../state/id";
                        }
                        description "Host side monitor ID";
                    } // END of id definition.

                    container state {
                        config false;
                        description
                            "State data for advertised host side monitors";
                        uses ipi-platform-cmis-module-advertisement-host-monitor-state;
                        uses ipi-platform-cmis-module-advertisement-monitor-state-details;
                    } // END of state-container definition.
                } // End of monitor-list
            } // END of monitors-container definition.
            container flags {
                config false;
                description
                    "High level container for the list of advertised host side flags";

                list flag {
                    key "id";
                    config false;
                    description
                        "List of advertised host side flags";
                    leaf id  {
                        type  leafref {
                            path  "../state/id";
                        }
                        description "Host side flag ID";
                    } // END of id definition.

                    container state {
                        config false;
                        description
                            "State data for advertised host side flags";
                        uses ipi-platform-cmis-module-advertisement-host-flag-state;
                        uses ipi-platform-cmis-module-advertisement-monitor-state-details;
                    } // END of state-container definition.
                } // End of flag-list
            } // END of flags-container definition.
        } // END of host-container definition.
        container media {
            config false;
            description
                "State data for advertised media side monitors";
            container monitors {
                config false;
                description
                    "High level container for the list of advertised media side monitors";

                list monitor {
                    key "id";
                    config false;
                    description
                        "List of advertised media side monitors";
                    leaf id  {
                        type  leafref {
                            path  "../state/id";
                        }
                        description "Media side monitor ID";
                    } // END of id definition.

                    container state {
                        config false;
                        description
                            "State data for advertised media side monitors";
                        uses ipi-platform-cmis-module-advertisement-media-monitor-state;
                        uses ipi-platform-cmis-module-advertisement-monitor-state-details;
                    } // END of state-container definition.
                } // End of monitor-list
            } // END of monitors-container definition.
            container flags {
                config false;
                description
                    "High level container for the list of advertised media side flags";

                list flag {
                    key "id";
                    config false;
                    description
                        "List of advertised media side flags";
                    leaf id  {
                        type  leafref {
                            path  "../state/id";
                        }
                        description "Media side flag ID";
                    } // END of id definition.

                    container state {
                        config false;
                        description
                            "State data for advertised media side monitors";
                        uses ipi-platform-cmis-module-advertisement-media-flag-state;
                        uses ipi-platform-cmis-module-advertisement-monitor-state-details;
                    } // END of state-container definition.
                } // End of flag-list
            } // END of flags-container definition.
        } // END of media-container definition.
    } // END of ipi-platform-cmis-module-advertisement-monitoring-top definition.
    grouping ipi-platform-cmis-module-advertisement-pages-state {
        description
            "ipi-platform-cmis-module-advertisement-pages-state";
        leaf network-path-pages-supported  {
            type  ipi-platform-cmis-types:cmm_cmis_yes_no_t;
            description "Indicates whether network path pages are supported or not";
        } // END of network-path-pages-supported definition.

        leaf vdm-pages-supported  {
            type  ipi-platform-cmis-types:cmm_cmis_yes_no_t;
            description "Indicates whether VDM pages are supported or not";
        } // END of vdm-pages-supported definition.

        leaf vdm-groups  {
            type  ipi-platform-cmis-types:cmm_cmis_vdm_pages_support_t;
            description "Shows which VDM groups are supported in case VDM pages are supported";
        } // END of vdm-groups definition.

        leaf diagnostics-pages-supported  {
            type  ipi-platform-cmis-types:cmm_cmis_yes_no_t;
            description "Indicates whether diagnostics pages are supported or not";
        } // END of diagnostics-pages-supported definition.

        leaf user-page-supported  {
            type  ipi-platform-cmis-types:cmm_cmis_yes_no_t;
            description "Indicates whether user eeprom page (page 03h) is supported or not";
        } // END of user-page-supported definition.

        leaf banks-per-page  {
            type  ipi-platform-cmis-types:cmm_cmis_bank_per_page_support_t;
            description "Shows which banks are supported for pages 10h to 2Fh";
        } // END of banks-per-page definition.

    } // END of ipi-platform-cmis-module-advertisement-pages-state definition.
    grouping ipi-platform-cmis-module-advertisement-pages-top {
        description
            "ipi-platform-cmis-module-advertisement-pages-top";
        container state {
            config false;
            description
                "State data for CMIS advertised pages";
            uses ipi-platform-cmis-module-advertisement-pages-state;
        } // END of state-container definition.
    } // END of ipi-platform-cmis-module-advertisement-pages-top definition.
    grouping ipi-platform-cmis-module-advertisement-si-state {
        description
            "ipi-platform-cmis-module-advertisement-si-state";
        leaf tx-input-manual-eq  {
            type  ipi-platform-cmis-types:cmm_cmis_yes_no_t;
            description "Indicates whether manual Tx input equalizer is supported or not";
        } // END of tx-input-manual-eq definition.

        leaf tx-input-eq-max  {
            type  uint8;
            description "Maximum supported value for Tx input equalizer";
        } // END of tx-input-eq-max definition.

        leaf rx-output-eq-pre-cursor  {
            type  ipi-platform-cmis-types:cmm_cmis_yes_no_t;
            description "Indicates whether manual Rx output equalizer pre cursor is supported
                        or not";
        } // END of rx-output-eq-pre-cursor definition.

        leaf rx-output-eq-pre-cursor-max  {
            type  uint8;
            description "Maximum supported value for Rx output equalizer pre cursor";
        } // END of rx-output-eq-pre-cursor-max definition.

        leaf rx-output-eq-post-cursor  {
            type  ipi-platform-cmis-types:cmm_cmis_yes_no_t;
            description "Indicates whether manual Rx output equalizer post cursor is supported
                        or not";
        } // END of rx-output-eq-post-cursor definition.

        leaf rx-output-eq-post-cursor-max  {
            type  uint8;
            description "Maximum supported value for Rx output equalizer post cursor";
        } // END of rx-output-eq-post-cursor-max definition.

        leaf rx-output-amp  {
            type  ipi-platform-cmis-types:cmm_cmis_yes_no_t;
            description "Indicates whether manual Rx output amplitude is supported or not";
        } // END of rx-output-amp definition.

        leaf rx-output-amp-codes  {
            type  ipi-platform-cmis-types:cmm_cmis_si_amp_codes_t;
            description "Supported manual Rx output amplitude codes";
        } // END of rx-output-amp-codes definition.

        leaf tx-cdr  {
            type  ipi-platform-cmis-types:cmm_cmis_yes_no_t;
            description "Indicates whether Tx CDR is supported or not";
        } // END of tx-cdr definition.

        leaf tx-cdr-bypass  {
            type  ipi-platform-cmis-types:cmm_cmis_yes_no_t;
            description "Indicates whether Tx CDR bypass is supported or not";
        } // END of tx-cdr-bypass definition.

        leaf rx-cdr  {
            type  ipi-platform-cmis-types:cmm_cmis_yes_no_t;
            description "Indicates whether Rx CDR is supported or not";
        } // END of rx-cdr definition.

        leaf rx-cdr-bypass  {
            type  ipi-platform-cmis-types:cmm_cmis_yes_no_t;
            description "Indicates whether Rx CDR bypass is supported or not";
        } // END of rx-cdr-bypass definition.

    } // END of ipi-platform-cmis-module-advertisement-si-state definition.
    grouping ipi-platform-cmis-module-advertisement-si-top {
        description
            "ipi-platform-cmis-module-advertisement-si-top";
        container state {
            config false;
            description
                "State data for CMIS advertised SI support";
            uses ipi-platform-cmis-module-advertisement-si-state;
        } // END of state-container definition.
    } // END of ipi-platform-cmis-module-advertisement-si-top definition.
    grouping ipi-platform-cmis-module-advertisement-top {
        description
            "ipi-platform-cmis-module-advertisement-top";
        container applications {
            config false;
            description
                "CMIS transceiver advertised applications";
            uses ipi-platform-cmis-module-advertisement-applications-top;
        } // END of applications-container definition.
        container custom-application {
            config false;
            description
                "CMIS transceiver advertised custom application";
            uses ipi-platform-cmis-module-advertisement-custom-application-top;
        } // END of custom-application-container definition.
        container controls {
            config false;
            description
                "CMIS transceiver advertised controls";
            uses ipi-platform-cmis-module-advertisement-controls-top;
        } // END of controls-container definition.
        container diagnostics {
            config false;
            description
                "CMIS transceiver advertised diagnostics";
            uses ipi-platform-cmis-module-advertisement-diagnostics-top;
        } // END of diagnostics-container definition.
        container durations {
            config false;
            description
                "CMIS transceiver advertised durations";
            uses ipi-platform-cmis-module-advertisement-durations-top;
        } // END of durations-container definition.
        container laser {
            config false;
            description
                "CMIS transceiver advertised laser tuning features";
            uses ipi-platform-cmis-module-advertisement-laser-top;
        } // END of laser-container definition.
        container monitoring {
            config false;
            description
                "CMIS transceiver advertised monitoring capabilities";
            uses ipi-platform-cmis-module-advertisement-monitoring-top;
        } // END of monitoring-container definition.
        container pages {
            config false;
            description
                "CMIS transceiver advertised supported pages";
            uses ipi-platform-cmis-module-advertisement-pages-top;
        } // END of pages-container definition.
        container signal-integrity {
            config false;
            description
                "CMIS transceiver advertised SI support";
            uses ipi-platform-cmis-module-advertisement-si-top;
        } // END of signal-integrity-container definition.
    } // END of ipi-platform-cmis-module-advertisement-top definition.
    grouping ipi-platform-cmis-module-datapath-state {
        description
            "ipi-platform-cmis-module-datapath-state";
        leaf lane  {
            type  uint8 {
                 range "1..32"  {
                    description "1..32: Supported range 1 - 32";
                 }
            }
            description "Lane where the datapath starts";
        } // END of lane definition.

        leaf current-state  {
            type  ipi-platform-cmis-types:cmm_cmis_datapath_states_t;
            description "Current datapath state";
        } // END of current-state definition.

        leaf host-rate  {
            type  decimal64 {
                 fraction-digits 2;            }
            description "Current datapath instance bit rate";
        } // END of host-rate definition.

        leaf media-rate  {
            type  decimal64 {
                 fraction-digits 2;            }
            description "Current media side bit rate";
        } // END of media-rate definition.

        leaf interface-name  {
            type  string {
                length "1..1965";
            }
            description "Name of the interface assigned to this datapath";
        } // END of interface-name definition.

    } // END of ipi-platform-cmis-module-datapath-state definition.
    grouping ipi-platform-cmis-module-datapath-top {
        description
            "ipi-platform-cmis-module-datapath-top";

        list datapath {
            key "lane";
            config false;
            description
                "List of datapaths";
            leaf lane  {
                type  leafref {
                    path  "../state/lane";
                }
                description "Lane where the datapath starts";
            } // END of lane definition.

            container state {
                config false;
                description
                    "State data for CMIS module datapath";
                uses ipi-platform-cmis-module-datapath-state;
            } // END of state-container definition.
        } // End of datapath-list
    } // END of ipi-platform-cmis-module-datapath-top definition.
    grouping ipi-platform-cmis-module-module-state-state {
        description
            "ipi-platform-cmis-module-module-state-state";
        leaf fault-state  {
            type  ipi-platform-cmis-types:cmm_cmis_module_fault_state_t;
            description "CMIS transceiver module fault state";
        } // END of fault-state definition.

        leaf current-state  {
            type  ipi-platform-cmis-types:cmm_cmis_module_state_t;
            description "CMIS transceiver module state";
        } // END of current-state definition.

    } // END of ipi-platform-cmis-module-module-state-state definition.
    grouping ipi-platform-cmis-module-module-state-top {
        description
            "ipi-platform-cmis-module-module-state-top";
        container state {
            config false;
            description
                "State data for CMIS module state info";
            uses ipi-platform-cmis-module-module-state-state;
        } // END of state-container definition.
        container datapaths {
            config false;
            description
                "Top level container of datapaths";
            uses ipi-platform-cmis-module-datapath-top;
        } // END of datapaths-container definition.
    } // END of ipi-platform-cmis-module-module-state-top definition.
    grouping ipi-platform-cmis-module-module-monitor-state {
        description
            "ipi-platform-cmis-module-module-monitor-state";
        leaf id  {
            type  ipi-platform-cmis-types:cmm_cmis_module_monitor_id_t;
            description "Module monitor ID";
        } // END of id definition.

        leaf description  {
            type  string {
                length "1..1965";
            }
            description "Module monitor description";
        } // END of description definition.

        leaf value  {
            type  decimal64 {
                 fraction-digits 2;            }
            description "Module monitor value";
        } // END of value definition.

        leaf high-alarm  {
            type  decimal64 {
                 fraction-digits 2;            }
            description "Module monitor high alarm value";
        } // END of high-alarm definition.

        leaf high-warning  {
            type  decimal64 {
                 fraction-digits 2;            }
            description "Module monitor high warning value";
        } // END of high-warning definition.

        leaf low-warning  {
            type  decimal64 {
                 fraction-digits 2;            }
            description "Module monitor low warning value";
        } // END of low-warning definition.

        leaf low-alarm  {
            type  decimal64 {
                 fraction-digits 2;            }
            description "Module monitor low alarm value";
        } // END of low-alarm definition.

    } // END of ipi-platform-cmis-module-module-monitor-state definition.
    grouping ipi-platform-cmis-module-module-monitor-alarm-state {
        description
            "ipi-platform-cmis-module-module-monitor-alarm-state";
        leaf alarm-id  {
            type  ipi-platform-cmis-types:cmm_cmis_module_monitor_id_t;
            description "Threshold alarm ID";
        } // END of alarm-id definition.

        leaf alarm-type  {
            type  ipi-platform-cmis-types:cmm_cmis_threshold_alarm_t;
            description "Threshold alarm type";
        } // END of alarm-type definition.

        leaf current-value  {
            type  decimal64 {
                 fraction-digits 2;            }
            description "Current monitor value";
        } // END of current-value definition.

        leaf threshold-minimum  {
            type  decimal64 {
                 fraction-digits 2;            }
            description "Threshold minimum value";
        } // END of threshold-minimum definition.

        leaf threshold-maximum  {
            type  decimal64 {
                 fraction-digits 2;            }
            description "Threshold maximum value";
        } // END of threshold-maximum definition.

    } // END of ipi-platform-cmis-module-module-monitor-alarm-state definition.
    grouping ipi-platform-cmis-module-module-monitors-top {
        description
            "ipi-platform-cmis-module-module-monitors-top";
        container monitors {
            config false;
            description
                "Top level container for module monitors";

            list monitor {
                key "id";
                config false;
                description
                    "List of module monitors";
                leaf id  {
                    type  leafref {
                        path  "../state/id";
                    }
                    description "Module monitor ID";
                } // END of id definition.

                container state {
                    config false;
                    description
                        "State data for CMIS module monitors";
                    uses ipi-platform-cmis-module-module-monitor-state;
                } // END of state-container definition.
            } // End of monitor-list
        } // END of monitors-container definition.
        container monitor-alarm {
            config false;
            description
                "Top level container for module monitor alarm";
            container state {
                config false;
                description
                    "State data for CMIS module monitor alarm";
                uses ipi-platform-cmis-module-module-monitor-alarm-state;
            } // END of state-container definition.
        } // END of monitor-alarm-container definition.
    } // END of ipi-platform-cmis-module-module-monitors-top definition.
    grouping ipi-platform-cmis-module-host-monitors-lane-monitor-state {
        description
            "ipi-platform-cmis-module-host-monitors-lane-monitor-state";
        leaf id  {
            type  ipi-platform-cmis-types:cmm_cmis_host_monitor_id_t;
            description "Host side monitor ID";
        } // END of id definition.

        leaf description  {
            type  string {
                length "1..1965";
            }
            description "Host side monitor description";
        } // END of description definition.

        leaf value  {
            type  decimal64 {
                 fraction-digits 2;            }
            description "Host side monitor value";
        } // END of value definition.

        leaf high-alarm  {
            type  decimal64 {
                 fraction-digits 2;            }
            description "Host side monitor high alarm value";
        } // END of high-alarm definition.

        leaf high-warning  {
            type  decimal64 {
                 fraction-digits 2;            }
            description "Host side monitor high warning value";
        } // END of high-warning definition.

        leaf low-warning  {
            type  decimal64 {
                 fraction-digits 2;            }
            description "Host side monitor low warning value";
        } // END of low-warning definition.

        leaf low-alarm  {
            type  decimal64 {
                 fraction-digits 2;            }
            description "Host side monitor low alarm value";
        } // END of low-alarm definition.

    } // END of ipi-platform-cmis-module-host-monitors-lane-monitor-state definition.
    grouping ipi-platform-cmis-module-host-monitor-alarm-state {
        description
            "ipi-platform-cmis-module-host-monitor-alarm-state";
        leaf alarm-id  {
            type  ipi-platform-cmis-types:cmm_cmis_host_monitor_id_t;
            description "Threshold alarm ID";
        } // END of alarm-id definition.

        leaf alarm-type  {
            type  ipi-platform-cmis-types:cmm_cmis_threshold_alarm_t;
            description "Threshold alarm type";
        } // END of alarm-type definition.

        leaf current-value  {
            type  decimal64 {
                 fraction-digits 2;            }
            description "Current monitor value";
        } // END of current-value definition.

        leaf threshold-minimum  {
            type  decimal64 {
                 fraction-digits 2;            }
            description "Threshold minimum value";
        } // END of threshold-minimum definition.

        leaf threshold-maximum  {
            type  decimal64 {
                 fraction-digits 2;            }
            description "Threshold maximum value";
        } // END of threshold-maximum definition.

    } // END of ipi-platform-cmis-module-host-monitor-alarm-state definition.
    grouping ipi-platform-cmis-module-host-monitors-lane-flag-state {
        description
            "ipi-platform-cmis-module-host-monitors-lane-flag-state";
        leaf id  {
            type  ipi-platform-cmis-types:cmm_cmis_host_flag_id_t;
            description "Host side flag ID";
        } // END of id definition.

        leaf description  {
            type  string {
                length "1..1965";
            }
            description "Host side flag description";
        } // END of description definition.

        leaf value  {
            type  boolean;
            description "Host side flag value";
        } // END of value definition.

    } // END of ipi-platform-cmis-module-host-monitors-lane-flag-state definition.
    grouping ipi-platform-cmis-module-host-flag-alarm-state {
        description
            "ipi-platform-cmis-module-host-flag-alarm-state";
        leaf alarm-id  {
            type  ipi-platform-cmis-types:cmm_cmis_host_flag_id_t;
            description "Flag alarm ID";
        } // END of alarm-id definition.

    } // END of ipi-platform-cmis-module-host-flag-alarm-state definition.
    grouping ipi-platform-cmis-module-host-monitors-lane-state {
        description
            "ipi-platform-cmis-module-host-monitors-lane-state";
        leaf number  {
            type  uint8 {
                 range "1..32"  {
                    description "1..32: Supported range 1 - 32";
                 }
            }
            description "Host side lane number";
        } // END of number definition.

        leaf dp-assigned  {
            type  boolean;
            description "Host side lane is datapath starting lane";
        } // END of dp-assigned definition.

    } // END of ipi-platform-cmis-module-host-monitors-lane-state definition.
    grouping ipi-platform-cmis-module-host-monitors-top {
        description
            "ipi-platform-cmis-module-host-monitors-top";
        container lanes {
            config false;
            description
                "Top level container for host side lanes";

            list lane {
                key "number";
                config false;
                description
                    "Host side list of lanes";
                leaf number  {
                    type  leafref {
                        path  "../state/number";
                    }
                    description "Host side lane number";
                } // END of number definition.

                container state {
                    config false;
                    description
                        "Per lane host side monitors state data";
                    uses ipi-platform-cmis-module-host-monitors-lane-state;
                } // END of state-container definition.
                container monitors {
                    config false;
                    description
                        "Top level container for host side per lane monitors";

                    list monitor {
                        key "id";
                        config false;
                        description
                            "Host side list of per lane monitors";
                        leaf id  {
                            type  leafref {
                                path  "../state/id";
                            }
                            description "Host side monitor ID";
                        } // END of id definition.

                        container state {
                            config false;
                            description
                                "Host side monitor state data";
                            uses ipi-platform-cmis-module-host-monitors-lane-monitor-state;
                        } // END of state-container definition.
                    } // End of monitor-list
                } // END of monitors-container definition.
                container flags {
                    config false;
                    description
                        "Top level container for host side per lane flags";

                    list flag {
                        key "id";
                        config false;
                        description
                            "Host side list of per lane flags";
                        leaf id  {
                            type  leafref {
                                path  "../state/id";
                            }
                            description "Host side flag ID";
                        } // END of id definition.

                        container state {
                            config false;
                            description
                                "Host side flag state data";
                            uses ipi-platform-cmis-module-host-monitors-lane-flag-state;
                        } // END of state-container definition.
                    } // End of flag-list
                } // END of flags-container definition.
                container monitor-alarm {
                    config false;
                    description
                        "Top level container for host side ler lane monitor alarm";
                    container state {
                        config false;
                        description
                            "State data for CMIS module host side per lane monitor alarm";
                        uses ipi-platform-cmis-module-host-monitor-alarm-state;
                    } // END of state-container definition.
                } // END of monitor-alarm-container definition.
                container flag-alarm {
                    config false;
                    description
                        "Top level container for host side per lane flag alarm";
                    container state {
                        config false;
                        description
                            "State data for CMIS module host side per lane flag alarm";
                        uses ipi-platform-cmis-module-host-flag-alarm-state;
                    } // END of state-container definition.
                } // END of flag-alarm-container definition.
            } // End of lane-list
        } // END of lanes-container definition.
    } // END of ipi-platform-cmis-module-host-monitors-top definition.
    grouping ipi-platform-cmis-module-media-monitors-lane-monitor-state {
        description
            "ipi-platform-cmis-module-media-monitors-lane-monitor-state";
        leaf id  {
            type  ipi-platform-cmis-types:cmm_cmis_media_monitor_id_t;
            description "Media side monitor ID";
        } // END of id definition.

        leaf description  {
            type  string {
                length "1..1965";
            }
            description "Media side monitor description";
        } // END of description definition.

        leaf value  {
            type  decimal64 {
                 fraction-digits 2;            }
            description "Media side monitor value";
        } // END of value definition.

        leaf high-alarm  {
            type  decimal64 {
                 fraction-digits 2;            }
            description "Media side monitor high alarm value";
        } // END of high-alarm definition.

        leaf high-warning  {
            type  decimal64 {
                 fraction-digits 2;            }
            description "Media side monitor high warning value";
        } // END of high-warning definition.

        leaf low-warning  {
            type  decimal64 {
                 fraction-digits 2;            }
            description "Media side monitor low warning value";
        } // END of low-warning definition.

        leaf low-alarm  {
            type  decimal64 {
                 fraction-digits 2;            }
            description "Media side monitor low alarm value";
        } // END of low-alarm definition.

    } // END of ipi-platform-cmis-module-media-monitors-lane-monitor-state definition.
    grouping ipi-platform-cmis-module-media-monitors-lane-flag-state {
        description
            "ipi-platform-cmis-module-media-monitors-lane-flag-state";
        leaf id  {
            type  ipi-platform-cmis-types:cmm_cmis_media_flag_id_t;
            description "Media side flag ID";
        } // END of id definition.

        leaf description  {
            type  string {
                length "1..1965";
            }
            description "Media side flag description";
        } // END of description definition.

        leaf value  {
            type  boolean;
            description "Media side flag value";
        } // END of value definition.

    } // END of ipi-platform-cmis-module-media-monitors-lane-flag-state definition.
    grouping ipi-platform-cmis-module-media-monitor-alarm-state {
        description
            "ipi-platform-cmis-module-media-monitor-alarm-state";
        leaf alarm-id  {
            type  ipi-platform-cmis-types:cmm_cmis_media_monitor_id_t;
            description "Threshold alarm ID";
        } // END of alarm-id definition.

        leaf alarm-type  {
            type  ipi-platform-cmis-types:cmm_cmis_threshold_alarm_t;
            description "Threshold alarm type";
        } // END of alarm-type definition.

        leaf current-value  {
            type  decimal64 {
                 fraction-digits 2;            }
            description "Current monitor value";
        } // END of current-value definition.

        leaf threshold-minimum  {
            type  decimal64 {
                 fraction-digits 2;            }
            description "Threshold minimum value";
        } // END of threshold-minimum definition.

        leaf threshold-maximum  {
            type  decimal64 {
                 fraction-digits 2;            }
            description "Threshold maximum value";
        } // END of threshold-maximum definition.

    } // END of ipi-platform-cmis-module-media-monitor-alarm-state definition.
    grouping ipi-platform-cmis-module-media-flag-alarm-state {
        description
            "ipi-platform-cmis-module-media-flag-alarm-state";
        leaf alarm-id  {
            type  ipi-platform-cmis-types:cmm_cmis_media_flag_id_t;
            description "Flag alarm ID";
        } // END of alarm-id definition.

    } // END of ipi-platform-cmis-module-media-flag-alarm-state definition.
    grouping ipi-platform-cmis-module-media-monitors-lane-state {
        description
            "ipi-platform-cmis-module-media-monitors-lane-state";
        leaf number  {
            type  uint8 {
                 range "1..32"  {
                    description "1..32: Supported range 1 - 32";
                 }
            }
            description "Media side lane number";
        } // END of number definition.

    } // END of ipi-platform-cmis-module-media-monitors-lane-state definition.
    grouping ipi-platform-cmis-module-media-monitors-top {
        description
            "ipi-platform-cmis-module-media-monitors-top";
        container lanes {
            config false;
            description
                "Top level container for media side lanes";

            list lane {
                key "number";
                config false;
                description
                    "Media side list of lanes";
                leaf number  {
                    type  leafref {
                        path  "../state/number";
                    }
                    description "media side lane number";
                } // END of number definition.

                container state {
                    config false;
                    description
                        "Per lane media side monitors state data";
                    uses ipi-platform-cmis-module-media-monitors-lane-state;
                } // END of state-container definition.
                container monitors {
                    config false;
                    description
                        "Top level container for media side per lane monitors";

                    list monitor {
                        key "id";
                        config false;
                        description
                            "Media side list of per lane monitors";
                        leaf id  {
                            type  leafref {
                                path  "../state/id";
                            }
                            description "Media side monitor ID";
                        } // END of id definition.

                        container state {
                            config false;
                            description
                                "Media side monitor state data";
                            uses ipi-platform-cmis-module-media-monitors-lane-monitor-state;
                        } // END of state-container definition.
                    } // End of monitor-list
                } // END of monitors-container definition.
                container flags {
                    config false;
                    description
                        "Top level container for media side per lane flags";

                    list flag {
                        key "id";
                        config false;
                        description
                            "Media side list of per lane flags";
                        leaf id  {
                            type  leafref {
                                path  "../state/id";
                            }
                            description "Media side flag ID";
                        } // END of id definition.

                        container state {
                            config false;
                            description
                                "Media side flag state data";
                            uses ipi-platform-cmis-module-media-monitors-lane-flag-state;
                        } // END of state-container definition.
                    } // End of flag-list
                } // END of flags-container definition.
                container monitor-alarm {
                    config false;
                    description
                        "Top level container for media side ler lane monitor alarm";
                    container state {
                        config false;
                        description
                            "State data for CMIS module media side per lane monitor alarm";
                        uses ipi-platform-cmis-module-media-monitor-alarm-state;
                    } // END of state-container definition.
                } // END of monitor-alarm-container definition.
                container flag-alarm {
                    config false;
                    description
                        "Top level container for media side per lane flag alarm";
                    container state {
                        config false;
                        description
                            "State data for CMIS module media side per lane flag alarm";
                        uses ipi-platform-cmis-module-media-flag-alarm-state;
                    } // END of state-container definition.
                } // END of flag-alarm-container definition.
            } // End of lane-list
        } // END of lanes-container definition.
    } // END of ipi-platform-cmis-module-media-monitors-top definition.
    grouping ipi-platform-cmis-module-user-thresholds-per-lane-state {
        description
            "ipi-platform-cmis-module-user-thresholds-per-lane-state";
        leaf value  {
            type  decimal64 {
                 fraction-digits 2;            }
            description "User threshold programmed value";
        } // END of value definition.

        leaf minimum  {
            type  decimal64 {
                 fraction-digits 2;            }
            description "User threshold minimum value";
        } // END of minimum definition.

        leaf maximum  {
            type  decimal64 {
                 fraction-digits 2;            }
            description "User threshold maximum value";
        } // END of maximum definition.

        leaf active  {
            type  boolean;
            description "User threshold activation state";
        } // END of active definition.

    } // END of ipi-platform-cmis-module-user-thresholds-per-lane-state definition.
    grouping ipi-platform-cmis-module-user-thresholds-host-per-lane-state {
        description
            "ipi-platform-cmis-module-user-thresholds-host-per-lane-state";
        leaf id  {
            type  ipi-platform-cmis-types:cmm_ccmis_thres_state_host_id_t;
            description "User threshold ID";
        } // END of id definition.

        uses ipi-platform-cmis-module-user-thresholds-per-lane-state;
    } // END of ipi-platform-cmis-module-user-thresholds-host-per-lane-state definition.
    grouping ipi-platform-cmis-module-user-thresholds-host-per-lane-top {
        description
            "ipi-platform-cmis-module-user-thresholds-host-per-lane-top";
        container thresholds {
            config false;
            description
                "Top level container for the list of user configurable thresholds";

            list threshold {
                key "id";
                config false;
                description
                    "List of user configurable thresholds";
                leaf id  {
                    type  leafref {
                        path  "../state/id";
                    }
                    description "User threshold ID";
                } // END of id definition.

                container state {
                    config false;
                    description
                        "Per user threshold state";
                    uses ipi-platform-cmis-module-user-thresholds-host-per-lane-state;
                } // END of state-container definition.
            } // End of threshold-list
        } // END of thresholds-container definition.
    } // END of ipi-platform-cmis-module-user-thresholds-host-per-lane-top definition.
    grouping ipi-platform-cmis-module-user-thresholds-media-per-lane-state {
        description
            "ipi-platform-cmis-module-user-thresholds-media-per-lane-state";
        leaf id  {
            type  ipi-platform-cmis-types:cmm_ccmis_thres_state_media_id_t;
            description "User threshold ID";
        } // END of id definition.

        uses ipi-platform-cmis-module-user-thresholds-per-lane-state;
    } // END of ipi-platform-cmis-module-user-thresholds-media-per-lane-state definition.
    grouping ipi-platform-cmis-module-user-thresholds-media-per-lane-top {
        description
            "ipi-platform-cmis-module-user-thresholds-media-per-lane-top";
        container thresholds {
            config false;
            description
                "Top level container for the list of user configurable thresholds";

            list threshold {
                key "id";
                config false;
                description
                    "List of user configurable thresholds";
                leaf id  {
                    type  leafref {
                        path  "../state/id";
                    }
                    description "User threshold ID";
                } // END of id definition.

                container state {
                    config false;
                    description
                        "Per user threshold state";
                    uses ipi-platform-cmis-module-user-thresholds-media-per-lane-state;
                } // END of state-container definition.
            } // End of threshold-list
        } // END of thresholds-container definition.
    } // END of ipi-platform-cmis-module-user-thresholds-media-per-lane-top definition.
    grouping ipi-platform-cmis-module-per-lane-state {
        description
            "ipi-platform-cmis-module-per-lane-state";
        leaf number  {
            type  uint8;
            description "Lane number";
        } // END of number definition.

    } // END of ipi-platform-cmis-module-per-lane-state definition.
    grouping ipi-platform-cmis-module-user-thresholds-host-top {
        description
            "ipi-platform-cmis-module-user-thresholds-host-top";
        container host {
            config false;
            description
                "Top level container for host side";
            container lanes {
                config false;
                description
                    "Top level container for host side lanes";

                list lane {
                    key "number";
                    config false;
                    description
                        "Host side list of lanes";
                    leaf number  {
                        type  leafref {
                            path  "../state/number";
                        }
                        description "Lane number";
                    } // END of number definition.

                    container state {
                        config false;
                        description
                            "Per lane host side user thresholds state data";
                        uses ipi-platform-cmis-module-per-lane-state;
                    } // END of state-container definition.
                    uses ipi-platform-cmis-module-user-thresholds-host-per-lane-top;
                } // End of lane-list
            } // END of lanes-container definition.
        } // END of host-container definition.
    } // END of ipi-platform-cmis-module-user-thresholds-host-top definition.
    grouping ipi-platform-cmis-module-user-thresholds-media-top {
        description
            "ipi-platform-cmis-module-user-thresholds-media-top";
        container media {
            config false;
            description
                "Top level container for media side";
            container lanes {
                config false;
                description
                    "Top level container for media side lanes";

                list lane {
                    key "number";
                    config false;
                    description
                        "Media side list of lanes";
                    leaf number  {
                        type  leafref {
                            path  "../state/number";
                        }
                        description "Lane number";
                    } // END of number definition.

                    container state {
                        config false;
                        description
                            "Per lane media side user thresholds state data";
                        uses ipi-platform-cmis-module-per-lane-state;
                    } // END of state-container definition.
                    uses ipi-platform-cmis-module-user-thresholds-media-per-lane-top;
                } // End of lane-list
            } // END of lanes-container definition.
        } // END of media-container definition.
    } // END of ipi-platform-cmis-module-user-thresholds-media-top definition.
    grouping ipi-platform-cmis-module-signal-integrity-per-lane-state {
        description
            "ipi-platform-cmis-module-signal-integrity-per-lane-state";
        leaf tx-input-equalizer-target  {
            type  uint8;
            description "Tx input equalizer target programmed value";
        } // END of tx-input-equalizer-target definition.

        leaf rx-output-equalizer-pre-cursor-target  {
            type  uint8;
            description "Rx output equalizer pre-cursor target programmed value";
        } // END of rx-output-equalizer-pre-cursor-target definition.

        leaf rx-output-equalizer-post-cursor-target  {
            type  uint8;
            description "Rx output equalizer post-cursor target programmed value";
        } // END of rx-output-equalizer-post-cursor-target definition.

        leaf rx-output-amplitude-target  {
            type  uint8;
            description "Rx output equalizer amplitude target programmed value";
        } // END of rx-output-amplitude-target definition.

        leaf tx-cdr-bypass  {
            type  boolean;
            description "Tx CDR bypassed or not";
        } // END of tx-cdr-bypass definition.

        leaf rx-cdr-bypass  {
            type  boolean;
            description "Rx CDR bypassed or not";
        } // END of rx-cdr-bypass definition.

    } // END of ipi-platform-cmis-module-signal-integrity-per-lane-state definition.
    grouping ipi-platform-cmis-module-signal-integrity-top {
        description
            "ipi-platform-cmis-module-signal-integrity-top";
        container host {
            config false;
            description
                "Top level container for host side";
            container lanes {
                config false;
                description
                    "Top level container for host side lanes";

                list lane {
                    key "number";
                    config false;
                    description
                        "Host side list of lanes";
                    leaf number  {
                        type  leafref {
                            path  "../state/number";
                        }
                        description "Lane number";
                    } // END of number definition.

                    container state {
                        config false;
                        description
                            "Per host lane signal integrity state";
                        uses ipi-platform-cmis-module-per-lane-state;
                        uses ipi-platform-cmis-module-signal-integrity-per-lane-state;
                    } // END of state-container definition.
                } // End of lane-list
            } // END of lanes-container definition.
        } // END of host-container definition.
    } // END of ipi-platform-cmis-module-signal-integrity-top definition.
    grouping ipi-platform-cmis-module-laser-status-per-lane-state {
        description
            "ipi-platform-cmis-module-laser-status-per-lane-state";
        leaf laser-frequency  {
            type  decimal64 {
                 fraction-digits 3;            }
            units "THz";
            description "Laser frequency in THz";
        } // END of laser-frequency definition.

        leaf wavelength  {
            type  decimal64 {
                 fraction-digits 2;            }
            units "nm";
            description "Laser wavelength in nm";
        } // END of wavelength definition.

    } // END of ipi-platform-cmis-module-laser-status-per-lane-state definition.
    grouping ipi-platform-cmis-module-laser-status-top {
        description
            "ipi-platform-cmis-module-laser-status-top";
        container media {
            config false;
            description
                "Top level container for media side";
            container lanes {
                config false;
                description
                    "Top level container for media side lanes";

                list lane {
                    key "number";
                    config false;
                    description
                        "Media side list of lanes";
                    leaf number  {
                        type  leafref {
                            path  "../state/number";
                        }
                        description "Lane number";
                    } // END of number definition.

                    container state {
                        config false;
                        description
                            "Per media lane laser status state";
                        uses ipi-platform-cmis-module-per-lane-state;
                        uses ipi-platform-cmis-module-laser-status-per-lane-state;
                    } // END of state-container definition.
                } // End of lane-list
            } // END of lanes-container definition.
        } // END of media-container definition.
    } // END of ipi-platform-cmis-module-laser-status-top definition.
    grouping ipi-platform-qsfp-dd-config {
        description
            "ipi-platform-qsfp-dd-config";
        leaf fp-port  {
            type  uint8;
            description "Front port panel number";
        } // END of fp-port definition.

        leaf application  {
            type  uint8 {
                 range "2..15"  {
                    description "2..15: Supported range 2 - 15";
                 }
            }
            description "Application configuration";
        } // END of application definition.

        leaf service-disable  {
            type  empty;
            description "To disable the service for a particular port";
        } // END of service-disable definition.

        leaf custom-app-host-id  {
            type  uint8 {
                 range "1..32"  {
                    description "1..32: Supported range 1 - 32";
                 }
            }
            description "Configuration of custom application host ID";
        } // END of custom-app-host-id definition.

        leaf custom-app-media-id  {
            type  uint8 {
                 range "1..32"  {
                    description "1..32: Supported range 1 - 32";
                 }
            }
            description "Configuration of custom application media ID";
        } // END of custom-app-media-id definition.

    } // END of ipi-platform-qsfp-dd-config definition.
    grouping ipi-platform-qsfp-dd-prbs-gen-check-host-config {
        description
            "ipi-platform-qsfp-dd-prbs-gen-check-host-config";
        leaf type  {
            type  ipi-platform-cmis-types:cmm_cmis_prbs_type_t;
            description "PRBS pattern type for generator/checker";
        } // END of type definition.

        leaf location  {
            type  ipi-platform-cmis-types:cmm_cmis_prbs_location_t;
            description "PRBS pattern generator/checker location";
        } // END of location definition.

    } // END of ipi-platform-qsfp-dd-prbs-gen-check-host-config definition.
    grouping ipi-platform-qsfp-dd-prbs-gen-check-media-config {
        description
            "ipi-platform-qsfp-dd-prbs-gen-check-media-config";
        leaf type  {
            type  ipi-platform-cmis-types:cmm_cmis_prbs_type_t;
            description "PRBS pattern type for generator/checker";
        } // END of type definition.

        leaf location  {
            type  ipi-platform-cmis-types:cmm_cmis_prbs_location_t;
            description "PRBS pattern generator/checker location";
        } // END of location definition.

    } // END of ipi-platform-qsfp-dd-prbs-gen-check-media-config definition.
    grouping ipi-platform-qsfp-dd-prbs-loopback-host-config {
        description
            "ipi-platform-qsfp-dd-prbs-loopback-host-config";
        leaf type  {
            type  ipi-platform-cmis-types:cmm_cmis_loopback_type_t;
            description "Loopback type";
        } // END of type definition.

    } // END of ipi-platform-qsfp-dd-prbs-loopback-host-config definition.
    grouping ipi-platform-qsfp-dd-prbs-loopback-media-config {
        description
            "ipi-platform-qsfp-dd-prbs-loopback-media-config";
        leaf type  {
            type  ipi-platform-cmis-types:cmm_cmis_loopback_type_t;
            description "Loopback type";
        } // END of type definition.

    } // END of ipi-platform-qsfp-dd-prbs-loopback-media-config definition.
    grouping ipi-platform-qsfp-dd-laser-config {
        description
            "Grouping for global laser configurable parameters";
        leaf channel  {
            type  int16;
            description "Channel number";
        } // END of channel definition.

        leaf grid  {
            type  ipi-platform-cmis-types:cmm_cmis_laser_grid_spacing_t;
            description "Grid spacing";
        } // END of grid definition.

        leaf fine-tune-freq  {
            type  decimal64 {
                 fraction-digits 3;            }
            units "GHz";
            description "Fine tune frequency offset";
        } // END of fine-tune-freq definition.

        leaf output-power  {
            type  decimal64 {
                 fraction-digits 2;            }
            units "dBm";
            description "Targeted output power";
        } // END of output-power definition.

    } // END of ipi-platform-qsfp-dd-laser-config definition.
    grouping ipi-platform-qsfp-dd-lane-laser-config {
        description
            "Grouping for per lane laser configurable parameters";
        leaf channel  {
            type  int16;
            description "Channel number";
        } // END of channel definition.

        leaf grid  {
            type  ipi-platform-cmis-types:cmm_cmis_laser_grid_spacing_t;
            description "Grid spacing";
        } // END of grid definition.

        leaf fine-tune-freq  {
            type  decimal64 {
                 fraction-digits 3;            }
            units "GHz";
            description "Fine tune frequency offset";
        } // END of fine-tune-freq definition.

        leaf output-power  {
            type  decimal64 {
                 fraction-digits 2;            }
            units "dBm";
            description "Targeted output power";
        } // END of output-power definition.

    } // END of ipi-platform-qsfp-dd-lane-laser-config definition.
    grouping ipi-platform-qsfp-dd-gating-config {
        description
            "Grouping for global gating configurable parameters";
        leaf interval  {
            type  ipi-platform-cmis-types:cmm_cmis_gating_interval_t;
            description "Configuration of gating interval";
        } // END of interval definition.

    } // END of ipi-platform-qsfp-dd-gating-config definition.
    grouping ipi-platform-qsfp-dd-provisions-config {
        description
            "Grouping for media lane provision configurable parameters";
        leaf tx-filter-type  {
            type  ipi-platform-cmis-types:cmm_cmis_tx_filter_type_t;
            description "Configuration of media lane tx filter type provisioning";
        } // END of tx-filter-type definition.

        leaf tx-filter-roll-off  {
            type  decimal64 {
                 fraction-digits 6;            }
            description "Configuration of media lane tx filter roll off factor provisioning";
        } // END of tx-filter-roll-off definition.

    } // END of ipi-platform-qsfp-dd-provisions-config definition.
    grouping ipi-platform-qsfp-dd-signal-integrity-config {
        description
            "Grouping for signal integrity configurable parameters";
        leaf tx-input-equalizer-target  {
            type  uint8 {
                 range "1..15"  {
                    description "1..15: Supported range 1 - 15";
                 }
            }
            description "Tx input equalizer target value code";
        } // END of tx-input-equalizer-target definition.

        leaf rx-output-equalizer-pre-cursor-target  {
            type  uint8 {
                 range "1..15"  {
                    description "1..15: Supported range 1 - 15";
                 }
            }
            description "Rx output equalizer pre-cursor target value code";
        } // END of rx-output-equalizer-pre-cursor-target definition.

        leaf rx-output-equalizer-post-cursor-target  {
            type  uint8 {
                 range "1..15"  {
                    description "1..15: Supported range 1 - 15";
                 }
            }
            description "Rx output equalizer post-cursor target value code";
        } // END of rx-output-equalizer-post-cursor-target definition.

        leaf rx-output-amplitude-target  {
            type  uint8 {
                 range "0..15"  {
                    description "0..15: Supported range 0 - 15";
                 }
            }
            description "Rx output equalizer amplitude target value code";
        } // END of rx-output-amplitude-target definition.

        leaf tx-cdr-bypass  {
            type  empty;
            description "Bypass the TX CDR control";
        } // END of tx-cdr-bypass definition.

        leaf rx-cdr-bypass  {
            type  empty;
            description "Bypass the CDR control";
        } // END of rx-cdr-bypass definition.

    } // END of ipi-platform-qsfp-dd-signal-integrity-config definition.
    grouping ipi-platform-qsfp-dd-media-laser-top {
        description
            "Grouping for per media lane laser configuration related data";
        container laser {
            description
                "Container enclosing laser related data";
            container config {
                description
                    "Laser parameters configutation data";
                uses ipi-platform-qsfp-dd-lane-laser-config;
            } // END of config-container definition.
            container state {
                config false;
                description
                    "Laser parameters operational data";
                uses ipi-platform-qsfp-dd-lane-laser-config;
            } // END of state-container definition.
        } // END of laser-container definition.
    } // END of ipi-platform-qsfp-dd-media-laser-top definition.
    grouping ipi-platform-qsfp-dd-laser-top {
        description
            "Grouping for laser configuration related data";
        container laser {
            description
                "Container enclosing laser related data";
            container config {
                description
                    "Laser parameters configutation data";
                uses ipi-platform-qsfp-dd-laser-config;
            } // END of config-container definition.
            container state {
                config false;
                description
                    "Laser parameters operational data";
                uses ipi-platform-qsfp-dd-laser-config;
            } // END of state-container definition.
        } // END of laser-container definition.
    } // END of ipi-platform-qsfp-dd-laser-top definition.
    grouping ipi-platform-qsfp-dd-threshold-parameters {
        description
            "Grouping of all configurable threshold parameters";
        leaf high-alarm  {
            type  decimal64 {
                 fraction-digits 6;            }
            description "High alarm threshold";
        } // END of high-alarm definition.

        leaf low-alarm  {
            type  decimal64 {
                 fraction-digits 6;            }
            description "Low alarm threshold";
        } // END of low-alarm definition.

        leaf high-warning  {
            type  decimal64 {
                 fraction-digits 6;            }
            description "High warn threshold";
        } // END of high-warning definition.

        leaf low-warning  {
            type  decimal64 {
                 fraction-digits 6;            }
            description "Low warn threshold";
        } // END of low-warning definition.

    } // END of ipi-platform-qsfp-dd-threshold-parameters definition.
    grouping ipi-platform-qsfp-dd-media-provisions-top {
        description
            "Grouping for per media lane provisions configuration related data";
        container provisions {
            description
                "Container enclosing media lane provisions related data";
            container config {
                description
                    "Media provisions parameters configutation data";
                uses ipi-platform-qsfp-dd-provisions-config;
            } // END of config-container definition.
            container state {
                config false;
                description
                    "Media provisions parameters operational data";
                uses ipi-platform-qsfp-dd-provisions-config;
            } // END of state-container definition.
        } // END of provisions-container definition.
    } // END of ipi-platform-qsfp-dd-media-provisions-top definition.
    grouping ipi-platform-qsfp-dd-provisions-top {
        description
            "Grouping for media provisions configuration related data";
        container provisions {
            description
                "Container enclosing media provisions related data";
            container config {
                description
                    "Media provisions parameters configutation data";
                uses ipi-platform-qsfp-dd-provisions-config;
            } // END of config-container definition.
            container state {
                config false;
                description
                    "Media provisions parameters operational data";
                uses ipi-platform-qsfp-dd-provisions-config;
            } // END of state-container definition.
        } // END of provisions-container definition.
    } // END of ipi-platform-qsfp-dd-provisions-top definition.
    grouping ipi-platform-qsfp-dd-gating-top {
        description
            "Grouping for gating configuration related data";
        container gating {
            description
                "Container enclosing measurement related data";
            container config {
                description
                    "Gating parameters configutation data";
                uses ipi-platform-qsfp-dd-gating-config;
            } // END of config-container definition.
            container state {
                config false;
                description
                    "Gating parameters operational data";
                uses ipi-platform-qsfp-dd-gating-config;
            } // END of state-container definition.
        } // END of gating-container definition.
    } // END of ipi-platform-qsfp-dd-gating-top definition.
    grouping ipi-platform-qsfp-dd-host-lane-threshold-config {
        description
            "Grouping for per host lane threshold configurable parameters";
        leaf id  {
            type  ipi-platform-cmis-types:cmm_ccmis_host_lane_thres_id_t;
            description "Threshold ID";
        } // END of id definition.

        uses ipi-platform-qsfp-dd-threshold-parameters;
    } // END of ipi-platform-qsfp-dd-host-lane-threshold-config definition.
    grouping ipi-platform-qsfp-dd-host-thresholds-top {
        description
            "Grouping for per host lane thresholds configuration related data";
        container thresholds {
            description
                "Top level container for per host lane thresholds";

            list threshold {
                key "id";
                description
                    "List of thresholds and their configuration";
                leaf id  {
                    type  leafref {
                        path  "../config/id";
                    }
                    description "Threshold ID";
                } // END of id definition.

                container config {
                    description
                        "Threshold configuration data";
                    uses ipi-platform-qsfp-dd-host-lane-threshold-config;
                } // END of config-container definition.
                container state {
                    config false;
                    description
                        "Threshold operational data";
                    uses ipi-platform-qsfp-dd-host-lane-threshold-config;
                } // END of state-container definition.
            } // End of threshold-list
        } // END of thresholds-container definition.
    } // END of ipi-platform-qsfp-dd-host-thresholds-top definition.
    grouping ipi-platform-qsfp-dd-media-lane-threshold-config {
        description
            "Grouping for per media lane threshold configurable parameters";
        leaf id  {
            type  ipi-platform-cmis-types:cmm_ccmis_media_lane_thres_id_t;
            description "Threshold ID";
        } // END of id definition.

        uses ipi-platform-qsfp-dd-threshold-parameters;
    } // END of ipi-platform-qsfp-dd-media-lane-threshold-config definition.
    grouping ipi-platform-qsfp-dd-media-thresholds-top {
        description
            "Grouping for per media lane thresholds configuration related data";
        container thresholds {
            description
                "Top level container for per media lane thresholds";

            list threshold {
                key "id";
                description
                    "List of thresholds and their configuration";
                leaf id  {
                    type  leafref {
                        path  "../config/id";
                    }
                    description "Threshold ID";
                } // END of id definition.

                container config {
                    description
                        "Threshold configuration data";
                    uses ipi-platform-qsfp-dd-media-lane-threshold-config;
                } // END of config-container definition.
                container state {
                    config false;
                    description
                        "Threshold operational data";
                    uses ipi-platform-qsfp-dd-media-lane-threshold-config;
                } // END of state-container definition.
            } // End of threshold-list
        } // END of thresholds-container definition.
    } // END of ipi-platform-qsfp-dd-media-thresholds-top definition.
    grouping ipi-platform-qsfp-dd-threshold-config {
        description
            "Grouping for global threshold configurable parameters";
        leaf id  {
            type  ipi-platform-cmis-types:cmm_ccmis_thres_id_t;
            description "Threshold ID";
        } // END of id definition.

        uses ipi-platform-qsfp-dd-threshold-parameters;
    } // END of ipi-platform-qsfp-dd-threshold-config definition.
    grouping ipi-platform-qsfp-dd-thresholds-top {
        description
            "Grouping for global thresholds configuration related data";
        container thresholds {
            description
                "Top level container for global thresholds";

            list threshold {
                key "id";
                description
                    "List of thresholds and their configuration";
                leaf id  {
                    type  leafref {
                        path  "../config/id";
                    }
                    description "Threshold ID";
                } // END of id definition.

                container config {
                    description
                        "Threshold configuration data";
                    uses ipi-platform-qsfp-dd-threshold-config;
                } // END of config-container definition.
                container state {
                    config false;
                    description
                        "Threshold operational data";
                    uses ipi-platform-qsfp-dd-threshold-config;
                } // END of state-container definition.
            } // End of threshold-list
        } // END of thresholds-container definition.
    } // END of ipi-platform-qsfp-dd-thresholds-top definition.
    grouping ipi-platform-qsfp-dd-host-lane-config {
        description
            "Host lane configuration data";
        leaf lane-number  {
            type  uint8 {
                 range "1..32"  {
                    description "1..32: Supported range 1 - 32";
                 }
            }
            description "Host lane number";
        } // END of lane-number definition.

    } // END of ipi-platform-qsfp-dd-host-lane-config definition.
    grouping ipi-platform-qsfp-dd-media-lane-config {
        description
            "Media lane configuration data";
        leaf lane-number  {
            type  uint8 {
                 range "1..32"  {
                    description "1..32: Supported range 1 - 32";
                 }
            }
            description "Media lane number";
        } // END of lane-number definition.

    } // END of ipi-platform-qsfp-dd-media-lane-config definition.
    grouping ipi-platform-qsfp-dd-host-signal-integrity-top {
        description
            "Grouping for signal integrity related data";
        container signal-integrity {
            description
                "Container enclosing laser related data";
            container config {
                description
                    "Signal integrity parameters configutation data";
                uses ipi-platform-qsfp-dd-signal-integrity-config;
            } // END of config-container definition.
            container state {
                config false;
                description
                    "Signal integrity parameters operational data";
                uses ipi-platform-qsfp-dd-signal-integrity-config;
            } // END of state-container definition.
        } // END of signal-integrity-container definition.
    } // END of ipi-platform-qsfp-dd-host-signal-integrity-top definition.
    grouping ipi-platform-qsfp-dd-host-top {
        description
            "Grouping for host side configuration related data";
        container host {
            description
                "Host side configuration parameters for QSFP-DD";
            container prbs {
                description
                    "PRBS configuration parameters for QSFP-DD";
                container generator {
                    description
                        "PRBS generator configuration parameters for QSFP-DD";
                    container config {
                        description
                            "Configuration data for PRBS host side generator";
                        uses ipi-platform-qsfp-dd-prbs-gen-check-host-config;
                    } // END of config-container definition.
                    container state {
                        config false;
                        description
                            "State data for PRBS host side generator";
                        uses ipi-platform-qsfp-dd-prbs-gen-check-host-config;
                    } // END of state-container definition.
                } // END of generator-container definition.
                container checker {
                    description
                        "PRBS checker configuration parameters for QSFP-DD";
                    container config {
                        description
                            "Configuration data for PRBS host side checker";
                        uses ipi-platform-qsfp-dd-prbs-gen-check-host-config;
                    } // END of config-container definition.
                    container state {
                        config false;
                        description
                            "State data for PRBS host side checker";
                        uses ipi-platform-qsfp-dd-prbs-gen-check-host-config;
                    } // END of state-container definition.
                } // END of checker-container definition.
            } // END of prbs-container definition.
            container loopback {
                description
                    "Loopback configuration parameters for QSFP-DD";
                container config {
                    description
                        "Configuration data for host side loopback";
                    uses ipi-platform-qsfp-dd-prbs-loopback-host-config;
                } // END of config-container definition.
                container state {
                    config false;
                    description
                        "State data for host side loopback";
                    uses ipi-platform-qsfp-dd-prbs-loopback-host-config;
                } // END of state-container definition.
            } // END of loopback-container definition.
            container lanes {
                description
                    "Top level container for per host lane configuration";

                list lane {
                // when " ipi-platform-cmis:qsfp-dds/qsfp-dd/host/lanes/lane/thresholds/threshold/config + ipi-platform-cmis:qsfp-dds/qsfp-dd/host/lanes/lane/signal-integrity/config ";
                    key "lane-number";
                    description
                        "List of host lanes and their configuration";
                    leaf lane-number  {
                        type  leafref {
                            path  "../config/lane-number";
                        }
                        description "Host lane number";
                    } // END of lane-number definition.

                    container config {
                        description
                            "Host lane configutation data";
                        uses ipi-platform-qsfp-dd-host-lane-config;
                    } // END of config-container definition.
                    container state {
                        config false;
                        description
                            "Host lane operational data";
                        uses ipi-platform-qsfp-dd-host-lane-config;
                    } // END of state-container definition.
                    uses ipi-platform-qsfp-dd-host-thresholds-top;
                    uses ipi-platform-qsfp-dd-host-signal-integrity-top;
                } // End of lane-list
            } // END of lanes-container definition.
        } // END of host-container definition.
    } // END of ipi-platform-qsfp-dd-host-top definition.
    grouping ipi-platform-qsfp-dd-media-top {
        description
            "Grouping for media side configuration related data";
        container media {
            description
                "Media side configuration parameters for QSFP-DD";
            container prbs {
                description
                    "PRBS configuration parameters for QSFP-DD";
                container generator {
                    description
                        "PRBS generator configuration parameters for QSFP-DD";
                    container config {
                        description
                            "Configuration data for PRBS media side generator";
                        uses ipi-platform-qsfp-dd-prbs-gen-check-media-config;
                    } // END of config-container definition.
                    container state {
                        config false;
                        description
                            "State data for PRBS media side generator";
                        uses ipi-platform-qsfp-dd-prbs-gen-check-media-config;
                    } // END of state-container definition.
                } // END of generator-container definition.
                container checker {
                    description
                        "PRBS checker configuration parameters for QSFP-DD";
                    container config {
                        description
                            "Configuration data for PRBS media side checker";
                        uses ipi-platform-qsfp-dd-prbs-gen-check-media-config;
                    } // END of config-container definition.
                    container state {
                        config false;
                        description
                            "State data for PRBS media side checker";
                        uses ipi-platform-qsfp-dd-prbs-gen-check-media-config;
                    } // END of state-container definition.
                } // END of checker-container definition.
            } // END of prbs-container definition.
            container loopback {
                description
                    "Loopback configuration parameters for QSFP-DD";
                container config {
                    description
                        "Configuration data for media side loopback";
                    uses ipi-platform-qsfp-dd-prbs-loopback-media-config;
                } // END of config-container definition.
                container state {
                    config false;
                    description
                        "State data for media side loopback";
                    uses ipi-platform-qsfp-dd-prbs-loopback-media-config;
                } // END of state-container definition.
            } // END of loopback-container definition.
            container lanes {
                description
                    "Top level container for per media lane configuration";

                list lane {
                // when " ipi-platform-cmis:qsfp-dds/qsfp-dd/media/lanes/lane/laser/config + ipi-platform-cmis:qsfp-dds/qsfp-dd/media/lanes/lane/thresholds/threshold/config + ipi-platform-cmis:qsfp-dds/qsfp-dd/media/lanes/lane/provisions/config ";
                    key "lane-number";
                    description
                        "List of media lanes and their configuration";
                    leaf lane-number  {
                        type  leafref {
                            path  "../config/lane-number";
                        }
                        description "Media lane number";
                    } // END of lane-number definition.

                    container config {
                        description
                            "Media lane configutation data";
                        uses ipi-platform-qsfp-dd-media-lane-config;
                    } // END of config-container definition.
                    container state {
                        config false;
                        description
                            "Media lane operational data";
                        uses ipi-platform-qsfp-dd-media-lane-config;
                    } // END of state-container definition.
                    uses ipi-platform-qsfp-dd-media-laser-top;
                    uses ipi-platform-qsfp-dd-media-thresholds-top;
                    uses ipi-platform-qsfp-dd-media-provisions-top;
                } // End of lane-list
            } // END of lanes-container definition.
        } // END of media-container definition.
    } // END of ipi-platform-qsfp-dd-media-top definition.
    grouping ipi-platform-qsfp-dd-signal-integrity-top {
        description
            "Grouping for signal integrity related data";
        container signal-integrity {
            description
                "Container enclosing laser related data";
            container config {
                description
                    "Signal integrity parameters configutation data";
                uses ipi-platform-qsfp-dd-signal-integrity-config;
            } // END of config-container definition.
            container state {
                config false;
                description
                    "Signal integrity parameters operational data";
                uses ipi-platform-qsfp-dd-signal-integrity-config;
            } // END of state-container definition.
        } // END of signal-integrity-container definition.
    } // END of ipi-platform-qsfp-dd-signal-integrity-top definition.
    grouping ipi-platform-qsfp-dd-top {
        description
            "ipi-platform-qsfp-dd-top";

        list qsfp-dd {
        // when " ipi-platform-cmis:qsfp-dds/qsfp-dd/config + ipi-platform-cmis:qsfp-dds/qsfp-dd/host/prbs/generator/config + ipi-platform-cmis:qsfp-dds/qsfp-dd/host/prbs/checker/config + ipi-platform-cmis:qsfp-dds/qsfp-dd/host/loopback/config + ipi-platform-cmis:qsfp-dds/qsfp-dd/media/prbs/generator/config + ipi-platform-cmis:qsfp-dds/qsfp-dd/media/prbs/checker/config + ipi-platform-cmis:qsfp-dds/qsfp-dd/media/loopback/config + ipi-platform-cmis:qsfp-dds/qsfp-dd/media/lanes/lane/laser/config + ipi-platform-cmis:qsfp-dds/qsfp-dd/laser/config + ipi-platform-cmis:qsfp-dds/qsfp-dd/thresholds/threshold/config + ipi-platform-cmis:qsfp-dds/qsfp-dd/host/lanes/lane/thresholds/threshold/config + ipi-platform-cmis:qsfp-dds/qsfp-dd/media/lanes/lane/thresholds/threshold/config + ipi-platform-cmis:qsfp-dds/qsfp-dd/signal-integrity/config + ipi-platform-cmis:qsfp-dds/qsfp-dd/host/lanes/lane/signal-integrity/config + ipi-platform-cmis:qsfp-dds/qsfp-dd/gating/config + ipi-platform-cmis:qsfp-dds/qsfp-dd/provisions/config + ipi-platform-cmis:qsfp-dds/qsfp-dd/media/lanes/lane/provisions/config ";
            key "fp-port";
            description
                "List of configured QSFP-DD transceivers";
            leaf fp-port  {
                type  leafref {
                    path  "../config/fp-port";
                }
                description "Front port panel number";
            } // END of fp-port definition.

            container config {
                description
                    "Configuration data for QSFP-DD";
                uses ipi-platform-qsfp-dd-config;
            } // END of config-container definition.
            container state {
                config false;
                description
                    "State data for QSFP-DD";
                uses ipi-platform-qsfp-dd-config;
            } // END of state-container definition.
            uses ipi-platform-qsfp-dd-host-top;
            uses ipi-platform-qsfp-dd-media-top;
            uses ipi-platform-qsfp-dd-laser-top;
            uses ipi-platform-qsfp-dd-thresholds-top;
            uses ipi-platform-qsfp-dd-signal-integrity-top;
            uses ipi-platform-qsfp-dd-gating-top;
            uses ipi-platform-qsfp-dd-provisions-top;
        } // End of qsfp-dd-list
    } // END of ipi-platform-qsfp-dd-top definition.
    grouping ipi-platform-xcvr-config {
        description
            "ipi-platform-xcvr-config";
        leaf fp-port-index  {
            type  uint8 {
                 range "1..128"  {
                    description "1..128: Supported range 1 - 128";
                 }
            }
            description "Internal port number for FP port";
        } // END of fp-port-index definition.

        leaf application  {
            type  uint8 {
                 range "2..15"  {
                    description "2..15: Supported range 2 - 15";
                 }
            }
            description "Application configuration";
        } // END of application definition.

        leaf service-disable  {
            type  empty;
            description "To disable the service for a particular port";
        } // END of service-disable definition.

        leaf custom-app-host-id  {
            type  uint8 {
                 range "1..32"  {
                    description "1..32: Supported range 1 - 32";
                 }
            }
            description "Configuration of custom application host ID";
        } // END of custom-app-host-id definition.

        leaf custom-app-media-id  {
            type  uint8 {
                 range "1..32"  {
                    description "1..32: Supported range 1 - 32";
                 }
            }
            description "Configuration of custom application media ID";
        } // END of custom-app-media-id definition.

        leaf monitoring-disable  {
            type  empty;
            description "To disable the DDM monitoring for a particular port";
        } // END of monitoring-disable definition.

        leaf amplifier-operating-mode  {
            type  ipi-platform-cmis-types:amplifier_operating_mode_t;
            description "To set the EDFA operating mode";
        } // END of amplifier-operating-mode definition.

        leaf amplifier-target-output-power  {
            type  decimal64 {
                 fraction-digits 3;            }
            units "dBm";
            description "To configure the target output power value in dBm";
        } // END of amplifier-target-output-power definition.

        leaf amplifier-target-gain  {
            type  decimal64 {
                 fraction-digits 3;            }
            units "dBm";
            description "To set the target-gain";
        } // END of amplifier-target-gain definition.

    } // END of ipi-platform-xcvr-config definition.
    grouping ipi-platform-xcvr-prbs-gen-check-host-config {
        description
            "ipi-platform-xcvr-prbs-gen-check-host-config";
        leaf type  {
            type  ipi-platform-cmis-types:cmm_cmis_prbs_type_t;
            description "PRBS pattern type for generator/checker";
        } // END of type definition.

        leaf location  {
            type  ipi-platform-cmis-types:cmm_cmis_prbs_location_t;
            description "PRBS pattern generator/checker location";
        } // END of location definition.

    } // END of ipi-platform-xcvr-prbs-gen-check-host-config definition.
    grouping ipi-platform-xcvr-prbs-gen-check-media-config {
        description
            "ipi-platform-xcvr-prbs-gen-check-media-config";
        leaf type  {
            type  ipi-platform-cmis-types:cmm_cmis_prbs_type_t;
            description "PRBS pattern type for generator/checker";
        } // END of type definition.

        leaf location  {
            type  ipi-platform-cmis-types:cmm_cmis_prbs_location_t;
            description "PRBS pattern generator/checker location";
        } // END of location definition.

    } // END of ipi-platform-xcvr-prbs-gen-check-media-config definition.
    grouping ipi-platform-xcvr-prbs-loopback-host-config {
        description
            "ipi-platform-xcvr-prbs-loopback-host-config";
        leaf type  {
            type  ipi-platform-cmis-types:cmm_cmis_loopback_type_t;
            description "Loopback type";
        } // END of type definition.

    } // END of ipi-platform-xcvr-prbs-loopback-host-config definition.
    grouping ipi-platform-xcvr-prbs-loopback-media-config {
        description
            "ipi-platform-xcvr-prbs-loopback-media-config";
        leaf type  {
            type  ipi-platform-cmis-types:cmm_cmis_loopback_type_t;
            description "Loopback type";
        } // END of type definition.

    } // END of ipi-platform-xcvr-prbs-loopback-media-config definition.
    grouping ipi-platform-xcvr-laser-config {
        description
            "Grouping for global laser configurable parameters";
        leaf channel  {
            type  int16;
            description "Channel number";
        } // END of channel definition.

        leaf grid  {
            type  ipi-platform-cmis-types:cmm_cmis_laser_grid_spacing_t;
            description "Grid spacing";
        } // END of grid definition.

        leaf fine-tune-freq  {
            type  decimal64 {
                 fraction-digits 3;            }
            units "GHz";
            description "Fine tune frequency offset";
        } // END of fine-tune-freq definition.

        leaf output-power  {
            type  decimal64 {
                 fraction-digits 2;            }
            units "dBm";
            description "Targeted output power";
        } // END of output-power definition.

    } // END of ipi-platform-xcvr-laser-config definition.
    grouping ipi-platform-xcvr-lane-laser-config {
        description
            "Grouping for per lane laser configurable parameters";
        leaf channel  {
            type  int16;
            description "Channel number";
        } // END of channel definition.

        leaf grid  {
            type  ipi-platform-cmis-types:cmm_cmis_laser_grid_spacing_t;
            description "Grid spacing";
        } // END of grid definition.

        leaf fine-tune-freq  {
            type  decimal64 {
                 fraction-digits 3;            }
            units "GHz";
            description "Fine tune frequency offset";
        } // END of fine-tune-freq definition.

        leaf output-power  {
            type  decimal64 {
                 fraction-digits 2;            }
            units "dBm";
            description "Targeted output power";
        } // END of output-power definition.

    } // END of ipi-platform-xcvr-lane-laser-config definition.
    grouping ipi-platform-xcvr-gating-config {
        description
            "Grouping for global gating configurable parameters";
        leaf interval  {
            type  ipi-platform-cmis-types:cmm_cmis_gating_interval_t;
            description "Configuration of gating interval";
        } // END of interval definition.

    } // END of ipi-platform-xcvr-gating-config definition.
    grouping ipi-platform-xcvr-provisions-config {
        description
            "Grouping for media lane provision configurable parameters";
        leaf tx-filter-type  {
            type  ipi-platform-cmis-types:cmm_cmis_tx_filter_type_t;
            description "Configuration of media lane tx filter type provisioning";
        } // END of tx-filter-type definition.

        leaf tx-filter-roll-off  {
            type  decimal64 {
                 fraction-digits 6;            }
            description "Configuration of media lane tx filter roll off factor provisioning";
        } // END of tx-filter-roll-off definition.

    } // END of ipi-platform-xcvr-provisions-config definition.
    grouping ipi-platform-xcvr-signal-integrity-config {
        description
            "Grouping for signal integrity configurable parameters";
        leaf tx-input-equalizer-target  {
            type  uint8 {
                 range "1..15"  {
                    description "1..15: Supported range 1 - 15";
                 }
            }
            description "Tx input equalizer target value code";
        } // END of tx-input-equalizer-target definition.

        leaf rx-output-equalizer-pre-cursor-target  {
            type  uint8 {
                 range "1..15"  {
                    description "1..15: Supported range 1 - 15";
                 }
            }
            description "Rx output equalizer pre-cursor target value code";
        } // END of rx-output-equalizer-pre-cursor-target definition.

        leaf rx-output-equalizer-post-cursor-target  {
            type  uint8 {
                 range "1..15"  {
                    description "1..15: Supported range 1 - 15";
                 }
            }
            description "Rx output equalizer post-cursor target value code";
        } // END of rx-output-equalizer-post-cursor-target definition.

        leaf rx-output-amplitude-target  {
            type  uint8 {
                 range "0..15"  {
                    description "0..15: Supported range 0 - 15";
                 }
            }
            description "Rx output equalizer amplitude target value code";
        } // END of rx-output-amplitude-target definition.

        leaf tx-cdr-bypass  {
            type  empty;
            description "Bypass the TX CDR control";
        } // END of tx-cdr-bypass definition.

        leaf rx-cdr-bypass  {
            type  empty;
            description "Bypass the CDR control";
        } // END of rx-cdr-bypass definition.

    } // END of ipi-platform-xcvr-signal-integrity-config definition.
    grouping ipi-platform-xcvr-media-control-config {
        description
            "Grouping for transceiver media control configurable parameters";
        leaf tx-disable  {
            type  empty;
            description "Attribute to disable the TX laser";
        } // END of tx-disable definition.

    } // END of ipi-platform-xcvr-media-control-config definition.
    grouping ipi-platform-xcvr-media-laser-top {
        description
            "Grouping for per media lane laser configuration related data";
        container laser {
            description
                "Container enclosing laser related data";
            container config {
                description
                    "Laser parameters configutation data";
                uses ipi-platform-xcvr-lane-laser-config;
            } // END of config-container definition.
            container state {
                config false;
                description
                    "Laser parameters operational data";
                uses ipi-platform-xcvr-lane-laser-config;
            } // END of state-container definition.
        } // END of laser-container definition.
    } // END of ipi-platform-xcvr-media-laser-top definition.
    grouping ipi-platform-xcvr-laser-top {
        description
            "Grouping for laser configuration related data";
        container laser {
            description
                "Container enclosing laser related data";
            container config {
                description
                    "Laser parameters configutation data";
                uses ipi-platform-xcvr-laser-config;
            } // END of config-container definition.
            container state {
                config false;
                description
                    "Laser parameters operational data";
                uses ipi-platform-xcvr-laser-config;
            } // END of state-container definition.
        } // END of laser-container definition.
    } // END of ipi-platform-xcvr-laser-top definition.
    grouping ipi-platform-xcvr-threshold-parameters {
        description
            "Grouping of all configurable threshold parameters";
        leaf high-alarm  {
            type  decimal64 {
                 fraction-digits 6;            }
            description "High alarm threshold";
        } // END of high-alarm definition.

        leaf low-alarm  {
            type  decimal64 {
                 fraction-digits 6;            }
            description "Low alarm threshold";
        } // END of low-alarm definition.

        leaf high-warning  {
            type  decimal64 {
                 fraction-digits 6;            }
            description "High warn threshold";
        } // END of high-warning definition.

        leaf low-warning  {
            type  decimal64 {
                 fraction-digits 6;            }
            description "Low warn threshold";
        } // END of low-warning definition.

    } // END of ipi-platform-xcvr-threshold-parameters definition.
    grouping ipi-platform-xcvr-media-provisions-top {
        description
            "Grouping for per media lane provisions configuration related data";
        container provisions {
            description
                "Container enclosing media lane provisions related data";
            container config {
                description
                    "Media provisions parameters configutation data";
                uses ipi-platform-xcvr-provisions-config;
            } // END of config-container definition.
            container state {
                config false;
                description
                    "Media provisions parameters operational data";
                uses ipi-platform-xcvr-provisions-config;
            } // END of state-container definition.
        } // END of provisions-container definition.
    } // END of ipi-platform-xcvr-media-provisions-top definition.
    grouping ipi-platform-xcvr-provisions-top {
        description
            "Grouping for media provisions configuration related data";
        container provisions {
            description
                "Container enclosing media provisions related data";
            container config {
                description
                    "Media provisions parameters configutation data";
                uses ipi-platform-xcvr-provisions-config;
            } // END of config-container definition.
            container state {
                config false;
                description
                    "Media provisions parameters operational data";
                uses ipi-platform-xcvr-provisions-config;
            } // END of state-container definition.
        } // END of provisions-container definition.
    } // END of ipi-platform-xcvr-provisions-top definition.
    grouping ipi-platform-xcvr-gating-top {
        description
            "Grouping for gating configuration related data";
        container gating {
            description
                "Container enclosing measurement related data";
            container config {
                description
                    "Gating parameters configutation data";
                uses ipi-platform-xcvr-gating-config;
            } // END of config-container definition.
            container state {
                config false;
                description
                    "Gating parameters operational data";
                uses ipi-platform-xcvr-gating-config;
            } // END of state-container definition.
        } // END of gating-container definition.
    } // END of ipi-platform-xcvr-gating-top definition.
    grouping ipi-platform-xcvr-host-lane-threshold-config {
        description
            "Grouping for per host lane threshold configurable parameters";
        leaf id  {
            type  ipi-platform-cmis-types:cmm_ccmis_host_lane_thres_id_t;
            description "Threshold ID";
        } // END of id definition.

        uses ipi-platform-xcvr-threshold-parameters;
    } // END of ipi-platform-xcvr-host-lane-threshold-config definition.
    grouping ipi-platform-xcvr-host-thresholds-top {
        description
            "Grouping for per host lane thresholds configuration related data";
        container thresholds {
            description
                "Top level container for per host lane thresholds";

            list threshold {
                key "id";
                description
                    "List of thresholds and their configuration";
                leaf id  {
                    type  leafref {
                        path  "../config/id";
                    }
                    description "Threshold ID";
                } // END of id definition.

                container config {
                    description
                        "Threshold configuration data";
                    uses ipi-platform-xcvr-host-lane-threshold-config;
                } // END of config-container definition.
                container state {
                    config false;
                    description
                        "Threshold operational data";
                    uses ipi-platform-xcvr-host-lane-threshold-config;
                } // END of state-container definition.
            } // End of threshold-list
        } // END of thresholds-container definition.
    } // END of ipi-platform-xcvr-host-thresholds-top definition.
    grouping ipi-platform-xcvr-media-lane-threshold-config {
        description
            "Grouping for per media lane threshold configurable parameters";
        leaf id  {
            type  ipi-platform-cmis-types:cmm_ccmis_media_lane_thres_id_t;
            description "Threshold ID";
        } // END of id definition.

        uses ipi-platform-xcvr-threshold-parameters;
    } // END of ipi-platform-xcvr-media-lane-threshold-config definition.
    grouping ipi-platform-xcvr-media-thresholds-top {
        description
            "Grouping for per media lane thresholds configuration related data";
        container thresholds {
            description
                "Top level container for per media lane thresholds";

            list threshold {
                key "id";
                description
                    "List of thresholds and their configuration";
                leaf id  {
                    type  leafref {
                        path  "../config/id";
                    }
                    description "Threshold ID";
                } // END of id definition.

                container config {
                    description
                        "Threshold configuration data";
                    uses ipi-platform-xcvr-media-lane-threshold-config;
                } // END of config-container definition.
                container state {
                    config false;
                    description
                        "Threshold operational data";
                    uses ipi-platform-xcvr-media-lane-threshold-config;
                } // END of state-container definition.
            } // End of threshold-list
        } // END of thresholds-container definition.
    } // END of ipi-platform-xcvr-media-thresholds-top definition.
    grouping ipi-platform-xcvr-threshold-config {
        description
            "Grouping for global threshold configurable parameters";
        leaf id  {
            type  ipi-platform-cmis-types:cmm_ccmis_thres_id_t;
            description "Threshold ID";
        } // END of id definition.

        uses ipi-platform-xcvr-threshold-parameters;
    } // END of ipi-platform-xcvr-threshold-config definition.
    grouping ipi-platform-xcvr-thresholds-top {
        description
            "Grouping for global thresholds configuration related data";
        container thresholds {
            description
                "Top level container for global thresholds";

            list threshold {
                key "id";
                description
                    "List of thresholds and their configuration";
                leaf id  {
                    type  leafref {
                        path  "../config/id";
                    }
                    description "Threshold ID";
                } // END of id definition.

                container config {
                    description
                        "Threshold configuration data";
                    uses ipi-platform-xcvr-threshold-config;
                } // END of config-container definition.
                container state {
                    config false;
                    description
                        "Threshold operational data";
                    uses ipi-platform-xcvr-threshold-config;
                } // END of state-container definition.
            } // End of threshold-list
        } // END of thresholds-container definition.
    } // END of ipi-platform-xcvr-thresholds-top definition.
    grouping ipi-platform-xcvr-host-lane-config {
        description
            "Host lane configuration data";
        leaf lane-number  {
            type  uint8 {
                 range "1..32"  {
                    description "1..32: Supported range 1 - 32";
                 }
            }
            description "Host lane number";
        } // END of lane-number definition.

    } // END of ipi-platform-xcvr-host-lane-config definition.
    grouping ipi-platform-xcvr-media-lane-config {
        description
            "Media lane configuration data";
        leaf lane-number  {
            type  uint8 {
                 range "1..32"  {
                    description "1..32: Supported range 1 - 32";
                 }
            }
            description "Media lane number";
        } // END of lane-number definition.

    } // END of ipi-platform-xcvr-media-lane-config definition.
    grouping ipi-platform-xcvr-host-signal-integrity-top {
        description
            "Grouping for signal integrity related data";
        container signal-integrity {
            description
                "Container enclosing laser related data";
            container config {
                description
                    "Signal integrity parameters configutation data";
                uses ipi-platform-xcvr-signal-integrity-config;
            } // END of config-container definition.
            container state {
                config false;
                description
                    "Signal integrity parameters operational data";
                uses ipi-platform-xcvr-signal-integrity-config;
            } // END of state-container definition.
        } // END of signal-integrity-container definition.
    } // END of ipi-platform-xcvr-host-signal-integrity-top definition.
    grouping ipi-platform-xcvr-host-top {
        description
            "Grouping for host side configuration related data";
        container host {
            description
                "Host side configuration parameters for the transceiver";
            container prbs {
                description
                    "PRBS configuration parameters for the transceiver";
                container generator {
                    description
                        "PRBS generator configuration parameters for the transceiver";
                    container config {
                        description
                            "Configuration data for PRBS host side generator";
                        uses ipi-platform-xcvr-prbs-gen-check-host-config;
                    } // END of config-container definition.
                    container state {
                        config false;
                        description
                            "State data for PRBS host side generator";
                        uses ipi-platform-xcvr-prbs-gen-check-host-config;
                    } // END of state-container definition.
                } // END of generator-container definition.
                container checker {
                    description
                        "PRBS checker configuration parameters for the transceiver";
                    container config {
                        description
                            "Configuration data for PRBS host side checker";
                        uses ipi-platform-xcvr-prbs-gen-check-host-config;
                    } // END of config-container definition.
                    container state {
                        config false;
                        description
                            "State data for PRBS host side checker";
                        uses ipi-platform-xcvr-prbs-gen-check-host-config;
                    } // END of state-container definition.
                } // END of checker-container definition.
            } // END of prbs-container definition.
            container loopback {
                description
                    "Loopback configuration parameters for the transceiver";
                container config {
                    description
                        "Configuration data for host side loopback";
                    uses ipi-platform-xcvr-prbs-loopback-host-config;
                } // END of config-container definition.
                container state {
                    config false;
                    description
                        "State data for host side loopback";
                    uses ipi-platform-xcvr-prbs-loopback-host-config;
                } // END of state-container definition.
            } // END of loopback-container definition.
            container lanes {
                description
                    "Top level container for per host lane configuration";

                list lane {
                // when " ipi-platform-cmis:xcvrs/xcvr/host/lanes/lane/thresholds/threshold/config + ipi-platform-cmis:xcvrs/xcvr/host/lanes/lane/signal-integrity/config ";
                    key "lane-number";
                    description
                        "List of host lanes and their configuration";
                    leaf lane-number  {
                        type  leafref {
                            path  "../config/lane-number";
                        }
                        description "Host lane number";
                    } // END of lane-number definition.

                    container config {
                        description
                            "Host lane configutation data";
                        uses ipi-platform-xcvr-host-lane-config;
                    } // END of config-container definition.
                    container state {
                        config false;
                        description
                            "Host lane operational data";
                        uses ipi-platform-xcvr-host-lane-config;
                    } // END of state-container definition.
                    uses ipi-platform-xcvr-host-thresholds-top;
                    uses ipi-platform-xcvr-host-signal-integrity-top;
                } // End of lane-list
            } // END of lanes-container definition.
        } // END of host-container definition.
    } // END of ipi-platform-xcvr-host-top definition.
    grouping ipi-platform-xcvr-media-top {
        description
            "Grouping for media side configuration related data";
        container media {
            description
                "Media side configuration parameters for the transceiver";
            container prbs {
                description
                    "PRBS configuration parameters for the transceiver";
                container generator {
                    description
                        "PRBS generator configuration parameters for the transceiver";
                    container config {
                        description
                            "Configuration data for PRBS media side generator";
                        uses ipi-platform-xcvr-prbs-gen-check-media-config;
                    } // END of config-container definition.
                    container state {
                        config false;
                        description
                            "State data for PRBS media side generator";
                        uses ipi-platform-xcvr-prbs-gen-check-media-config;
                    } // END of state-container definition.
                } // END of generator-container definition.
                container checker {
                    description
                        "PRBS checker configuration parameters for the transceiver";
                    container config {
                        description
                            "Configuration data for PRBS media side checker";
                        uses ipi-platform-xcvr-prbs-gen-check-media-config;
                    } // END of config-container definition.
                    container state {
                        config false;
                        description
                            "State data for PRBS media side checker";
                        uses ipi-platform-xcvr-prbs-gen-check-media-config;
                    } // END of state-container definition.
                } // END of checker-container definition.
            } // END of prbs-container definition.
            container loopback {
                description
                    "Loopback configuration parameters for the transceiver";
                container config {
                    description
                        "Configuration data for media side loopback";
                    uses ipi-platform-xcvr-prbs-loopback-media-config;
                } // END of config-container definition.
                container state {
                    config false;
                    description
                        "State data for media side loopback";
                    uses ipi-platform-xcvr-prbs-loopback-media-config;
                } // END of state-container definition.
            } // END of loopback-container definition.
            container lanes {
                description
                    "Top level container for per media lane configuration";

                list lane {
                // when " ipi-platform-cmis:xcvrs/xcvr/media/lanes/lane/config                   ipi-platform-cmis:xcvrs/xcvr/media/lanes/lane/laser/config + ipi-platform-cmis:xcvrs/xcvr/media/lanes/lane/thresholds/threshold/config + ipi-platform-cmis:xcvrs/xcvr/media/lanes/lane/provisions/config ";
                    key "lane-number";
                    description
                        "List of media lanes and their configuration";
                    leaf lane-number  {
                        type  leafref {
                            path  "../config/lane-number";
                        }
                        description "Media lane number";
                    } // END of lane-number definition.

                    container config {
                        description
                            "Media lane configutation data";
                        uses ipi-platform-xcvr-media-lane-config;
                        uses ipi-platform-xcvr-media-control-config;
                    } // END of config-container definition.
                    container state {
                        config false;
                        description
                            "Media lane operational data";
                        uses ipi-platform-xcvr-media-lane-config;
                        uses ipi-platform-xcvr-media-control-config;
                    } // END of state-container definition.
                    uses ipi-platform-xcvr-media-laser-top;
                    uses ipi-platform-xcvr-media-thresholds-top;
                    uses ipi-platform-xcvr-media-provisions-top;
                } // End of lane-list
            } // END of lanes-container definition.
        } // END of media-container definition.
    } // END of ipi-platform-xcvr-media-top definition.
    grouping ipi-platform-xcvr-signal-integrity-top {
        description
            "Grouping for signal integrity related data";
        container signal-integrity {
            description
                "Container enclosing signal integrity related data";
            container config {
                description
                    "Signal integrity parameters configutation data";
                uses ipi-platform-xcvr-signal-integrity-config;
            } // END of config-container definition.
            container state {
                config false;
                description
                    "Signal integrity parameters operational data";
                uses ipi-platform-xcvr-signal-integrity-config;
            } // END of state-container definition.
        } // END of signal-integrity-container definition.
    } // END of ipi-platform-xcvr-signal-integrity-top definition.
    grouping ipi-platform-xcvrs-top {
        description
            "ipi-platform-xcvrs-top";

        list xcvr {
        // when " ipi-platform-cmis:xcvrs/xcvr/config + ipi-platform-cmis:xcvrs/xcvr/host/prbs/generator/config + ipi-platform-cmis:xcvrs/xcvr/host/prbs/checker/config + ipi-platform-cmis:xcvrs/xcvr/host/loopback/config + ipi-platform-cmis:xcvrs/xcvr/media/prbs/generator/config + ipi-platform-cmis:xcvrs/xcvr/media/prbs/checker/config + ipi-platform-cmis:xcvrs/xcvr/media/loopback/config + ipi-platform-cmis:xcvrs/xcvr/media/lanes/lane/laser/config + ipi-platform-cmis:xcvrs/xcvr/laser/config + ipi-platform-cmis:xcvrs/xcvr/thresholds/threshold/config + ipi-platform-cmis:xcvrs/xcvr/host/lanes/lane/thresholds/threshold/config + ipi-platform-cmis:xcvrs/xcvr/media/lanes/lane/thresholds/threshold/config + ipi-platform-cmis:xcvrs/xcvr/signal-integrity/config + ipi-platform-cmis:xcvrs/xcvr/host/lanes/lane/signal-integrity/config + ipi-platform-cmis:xcvrs/xcvr/gating/config + ipi-platform-cmis:xcvrs/xcvr/provisions/config + ipi-platform-cmis:xcvrs/xcvr/media/lanes/lane/provisions/config ";
            key "fp-port-index";
            description
                "List of configured transceivers";
            leaf fp-port-index  {
                type  leafref {
                    path  "../config/fp-port-index";
                }
                description "Internal port number for FP port";
            } // END of fp-port-index definition.

            container config {
                description
                    "Configuration data for the transceiver";
                uses ipi-platform-xcvr-config;
                uses ipi-platform-xcvr-media-control-config;
            } // END of config-container definition.
            container state {
                config false;
                description
                    "State data for the transceiver";
                uses ipi-platform-xcvr-config;
                uses ipi-platform-xcvr-media-control-config;
            } // END of state-container definition.
            uses ipi-platform-xcvr-host-top;
            uses ipi-platform-xcvr-media-top;
            uses ipi-platform-xcvr-laser-top;
            uses ipi-platform-xcvr-thresholds-top;
            uses ipi-platform-xcvr-signal-integrity-top;
            uses ipi-platform-xcvr-gating-top;
            uses ipi-platform-xcvr-provisions-top;
        } // End of xcvr-list
    } // END of ipi-platform-xcvrs-top definition.
    grouping ipi-platform-remote-xcvr-media-top {
        description
            "Grouping for remote transceiver media side configuration related data";
        container media {
            description
                "Media side configuration parameters for the transceiver";
            container loopback {
                description
                    "Loopback configuration parameters for the transceiver";
                container config {
                    description
                        "Configuration data for media side loopback";
                    uses ipi-platform-xcvr-prbs-loopback-media-config;
                } // END of config-container definition.
                container state {
                    config false;
                    description
                        "State data for media side loopback";
                    uses ipi-platform-xcvr-prbs-loopback-media-config;
                } // END of state-container definition.
            } // END of loopback-container definition.
        } // END of media-container definition.
    } // END of ipi-platform-remote-xcvr-media-top definition.
    grouping ipi-platform-remote-xcvrs-top {
        description
            "ipi-platform-remote-xcvrs-top";

        list remote-xcvr {
        // when " ipi-platform-cmis:remote-xcvrs/remote-xcvr/config + ipi-platform-cmis:remote-xcvrs/remote-xcvr/media/loopback/config ";
            key "fp-port-index";
            description
                "List of configured remote transceivers";
            leaf fp-port-index  {
                type  leafref {
                    path  "../config/fp-port-index";
                }
                description "Internal port number for FP port";
            } // END of fp-port-index definition.

            container config {
                description
                    "Configuration data for the transceiver";
                uses ipi-platform-xcvr-config;
                uses ipi-platform-xcvr-media-control-config;
            } // END of config-container definition.
            container state {
                config false;
                description
                    "State data for the transceiver";
                uses ipi-platform-xcvr-config;
                uses ipi-platform-xcvr-media-control-config;
            } // END of state-container definition.
            uses ipi-platform-remote-xcvr-media-top;
        } // End of remote-xcvr-list
    } // END of ipi-platform-remote-xcvrs-top definition.
    grouping ipi-platform-xcvr-global-config-top {
        description
            "ipi-platform-xcvr-global-config-top";
        leaf monitor-time-interval  {
            type  uint16 {
                 range "60..3600"  {
                    description "60..3600: Supported range 60 - 3600";
                 }
            }
            description "To set DDM Monitor interval time.";
        } // END of monitor-time-interval definition.

    } // END of ipi-platform-xcvr-global-config-top definition.
    grouping ipi-platform-xcvr-global-top {
        description
            "ipi-platform-xcvr-global-top";
        container config {
            description
                "Global configuration data for transceivers";
            uses ipi-platform-xcvr-global-config-top;
        } // END of config-container definition.
        container state {
            config false;
            description
                "Global state data for transceivers";
            uses ipi-platform-xcvr-global-config-top;
        } // END of state-container definition.
    } // END of ipi-platform-xcvr-global-top definition.

    grouping  cmis-module-grouping {
    description
        "Top level container of CMIS modules, including configuration and state
                data";
    container cmis-module {
        if-feature feature-list:HAVE_CMMD;
        if-feature feature-list:NOT_HAVE_TIBIT;
        config false;
        description
            "Top level container of CMIS modules, including configuration and state
                    data";
        container eeprom {
            config false;
            description
                "CMIS transceiver EEPROM information";
            uses ipi-platform-cmis-module-eeprom-top;
        } // END of eeprom-container definition.
        container advertisement {
            config false;
            description
                "CMIS transceiver advertisement information";
            uses ipi-platform-cmis-module-advertisement-top;
        } // END of advertisement-container definition.
        container module-state {
            config false;
            description
                "CMIS transceiver module state info";
            uses ipi-platform-cmis-module-module-state-top;
        } // END of module-state-container definition.
        container module-monitors {
            config false;
            description
                "CMIS transceiver module monitors";
            uses ipi-platform-cmis-module-module-monitors-top;
        } // END of module-monitors-container definition.
        container host-monitors {
            config false;
            description
                "CMIS transceiver host monitors";
            uses ipi-platform-cmis-module-host-monitors-top;
        } // END of host-monitors-container definition.
        container media-monitors {
            config false;
            description
                "CMIS transceiver media monitors";
            uses ipi-platform-cmis-module-media-monitors-top;
        } // END of media-monitors-container definition.
        container user-thresholds {
            config false;
            description
                "Container for HW config state of CCMIS user configurable tresholds";
            uses ipi-platform-cmis-module-user-thresholds-host-top;
            uses ipi-platform-cmis-module-user-thresholds-media-top;
        } // END of user-thresholds-container definition.
        container signal-integrity {
            config false;
            description
                "Container for HW config state of signal integrity settings";
            uses ipi-platform-cmis-module-signal-integrity-top;
        } // END of signal-integrity-container definition.
        container laser-status {
            config false;
            description
                "Container for transceiver laser status";
            uses ipi-platform-cmis-module-laser-status-top;
        } // END of laser-status-container definition.
    } // END of cmis-module-container definition.
    } // END of cmis-module-grouping definition.

    grouping  qsfp-dds-grouping {
    description
        "Top level container of QSFP-DD, including configuration and state data";
    container qsfp-dds {
        if-feature feature-list:HAVE_CMMD;
        if-feature feature-list:NOT_HAVE_XCVR_MODEL;
        if-feature feature-list:NOT_HAVE_TIBIT;
        description
            "Top level container of QSFP-DD, including configuration and state data";
        uses ipi-platform-qsfp-dd-top;
    } // END of qsfp-dds-container definition.
    } // END of qsfp-dds-grouping definition.

    grouping  xcvrs-grouping {
    description
        "Top level container for transceivers, including configuration and
                state data";
    container xcvrs {
        if-feature feature-list:HAVE_XCVR_MODEL;
        if-feature feature-list:HAVE_CMMD;
        if-feature feature-list:NOT_HAVE_TIBIT;
        description
            "Top level container for transceivers, including configuration and
                    state data";
        uses ipi-platform-xcvrs-top;
    } // END of xcvrs-container definition.
    } // END of xcvrs-grouping definition.

    grouping  remote-xcvrs-grouping {
    description
        "Top level container for remote transceivers, including configuration
                and state data";
    container remote-xcvrs {
        if-feature feature-list:HAVE_XCVR_MODEL;
        if-feature feature-list:HAVE_CMMD;
        if-feature feature-list:NOT_HAVE_TIBIT;
        description
            "Top level container for remote transceivers, including configuration
                    and state data";
        uses ipi-platform-remote-xcvrs-top;
    } // END of remote-xcvrs-container definition.
    } // END of remote-xcvrs-grouping definition.

    grouping  xcvr-global-grouping {
    description
        "Top level container global transceiver configuration and state data";
    container xcvr-global {
        if-feature feature-list:HAVE_XCVR_MODEL;
        if-feature feature-list:HAVE_CMMD;
        if-feature feature-list:NOT_HAVE_TIBIT;
        description
            "Top level container global transceiver configuration and state data";
        uses ipi-platform-xcvr-global-top;
    } // END of xcvr-global-container definition.
    } // END of xcvr-global-grouping definition.


}
