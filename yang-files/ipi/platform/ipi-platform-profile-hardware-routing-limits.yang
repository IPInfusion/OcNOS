/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-platform-profile-hardware-routing-limits.yang
*
*/

submodule ipi-platform-profile-hardware-routing-limits {

    yang-version 1.1;

    belongs-to  ipi-platform { prefix ipi-platform; }

    import feature-list {
        prefix feature-list;
        revision-date 2026-09-15;
    }

    organization
        "IP Infusion Inc.";

    contact
        "Address: 3965 Freedom Circle, Suite 200, Santa Clara, CA 95054
         Phone: +1 408-400-1900
         E-mail: support@ipinfusion.com
         Web: http://www.ipinfusion.com/";

    description
        "Hardware routing limits and usage information";


    revision "2025-10-20" {
        description "Renamed ipi-platform-profile-hardware-capacity-limits module to ipi-platform-profile-hardware-routing-limits";
        reference " 0.1.2.";
    }

    revision "2025-09-13" {
        description "Add gnmi support to the hardware-capacity counters";
        reference " 0.1.1.";
    }

    revision "2025-09-11" {
        description "Initial Version";
        reference " 0.1.0.";
    }

    grouping hardware-routing-limits-state {
        description
            "Attributes used for database capacity and usage";
        leaf capacity  {
            type  uint32;
            description "Maximum number of entries in the database";
        } // END of capacity definition.

        leaf used  {
            type  uint32;
            description "Number of entries in use in the database";
        } // END of used definition.

        leaf free  {
            type  uint32;
            description "Number of entries available in the database";
        } // END of free definition.

        leaf percentage  {
            type  uint8;
            units "%";
            description "Proportion of entries in use, expressed as a percentage";
        } // END of percentage definition.

    } // END of hardware-routing-limits-state definition.
    grouping hardware-routing-limits-lpm-top {
        description
            "LPM database";
        container lpm {
            config false;
            description
                "LPM database";
            container state {
                config false;
                description
                    "Operational state data for the LPM hardware table capacity and usage";
                uses hardware-routing-limits-state;
            } // END of state-container definition.
        } // END of lpm-container definition.
    } // END of hardware-routing-limits-lpm-top definition.
    grouping hardware-routing-limits-lpm-ipv4-top {
        description
            "IPv4 LPM database";
        container ipv4-lpm {
            config false;
            description
                "IPv4 LPM database";
            container state {
                config false;
                description
                    "Operational state data for the IPv4 LPM hardware table capacity and
                            usage";
                uses hardware-routing-limits-state;
            } // END of state-container definition.
        } // END of ipv4-lpm-container definition.
    } // END of hardware-routing-limits-lpm-ipv4-top definition.
    grouping hardware-routing-limits-lpm-ipv6-top {
        description
            "IPv6 LPM database";
        container ipv6-lpm {
            config false;
            description
                "IPv6 LPM database";
            container state {
                config false;
                description
                    "Operational state data for the IPv6 LPM hardware table capacity and
                            usage";
                uses hardware-routing-limits-state;
            } // END of state-container definition.
        } // END of ipv6-lpm-container definition.
    } // END of hardware-routing-limits-lpm-ipv6-top definition.
    grouping hardware-routing-limits-mpls-label-pop-top {
        description
            "MPLS labels POP database";
        container mpls-labels-pop {
            config false;
            description
                "MPLS labels POP database";
            container state {
                config false;
                description
                    "Operational state data for the MPLS labels POP hardware table capacity
                            and usage";
                uses hardware-routing-limits-state;
            } // END of state-container definition.
        } // END of mpls-labels-pop-container definition.
    } // END of hardware-routing-limits-mpls-label-pop-top definition.
    grouping hardware-routing-limits-mpls-label-swap-top {
        description
            "MPLS labels SWAP database";
        container mpls-labels-swap {
            config false;
            description
                "MPLS labels SWAP database";
            container state {
                config false;
                description
                    "Operational state data for the MPLS labels SWAP hardware table
                            capacity and usage";
                uses hardware-routing-limits-state;
            } // END of state-container definition.
        } // END of mpls-labels-swap-container definition.
    } // END of hardware-routing-limits-mpls-label-swap-top definition.

    grouping  hardware-routing-limits-grouping {
    description
        "Container for hardware routing limits and usage attributes";
    container hardware-routing-limits {
        if-feature feature-list:HAVE_BROADCOM;
        if-feature feature-list:HAVE_DNX;
        if-feature feature-list:HAVE_CMMD;
        config false;
        description
            "Container for hardware routing limits and usage attributes";
        uses hardware-routing-limits-lpm-top;
        uses hardware-routing-limits-lpm-ipv4-top;
        uses hardware-routing-limits-lpm-ipv6-top;
        uses hardware-routing-limits-mpls-label-pop-top;
        uses hardware-routing-limits-mpls-label-swap-top;
    } // END of hardware-routing-limits-container definition.
    } // END of hardware-routing-limits-grouping definition.


}
