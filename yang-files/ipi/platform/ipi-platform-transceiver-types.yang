/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-platform-transceiver-types.yang
*
*/

module ipi-platform-transceiver-types {

    yang-version 1.1;

    namespace   "http://www.ipinfusion.com/yang/ocnos/ipi-platform-transceiver-types";

    prefix "ipi-platform-transceiver-types";

    organization
        "IP Infusion Inc.";

    contact
        "Address: 3965 Freedom Circle, Suite 200, Santa Clara, CA 95054
         Phone: +1 408-400-1900
         E-mail: support@ipinfusion.com
         Web: http://www.ipinfusion.com/";

    description
        "YANG version of the ipi-platform-transceiver-types";


    revision "2025-12-30" {
        description "Fix QSFP+ with CMIS transceiver identifier";
        reference " 0.10.1.";
    }

    revision "2025-12-12" {
        description "Add QSFP-DD and OSFP transceiver. Remove unknown type.";
        reference " 0.10.0.";
    }

    revision "2025-07-31" {
        description "Use CMM_SFF8024_CONNECTOR_TYPE_T instead of DDM_CMM_TRANS_CONNECTOR_TYPE_T";
        reference " 0.9.2.";
    }

    revision "2025-07-25" {
        description "Added OSFP port type in enum";
        reference " 0.9.1.";
    }

    revision "2025-06-10" {
        description "Added support for 800G OSFP transceiver";
        reference " 0.9.0.";
    }

    revision "2025-04-28" {
        description "Revert transceiver CLI migration changes";
        reference " 0.8.1.";
    }

    revision "2025-02-17" {
        description "CLI migration from qsfp-dd references to xcvr references";
        reference " 0.8.0.";
    }

    revision "2024-12-09" {
        description "Added DDM_CMM_TRANS_IDENTIFIER_T elements";
        reference " 0.7.2.";
    }

    revision "2024-08-22" {
        description "Fixed EDFA model datatype";
        reference " 0.7.1.";
    }

    revision "2023-12-13" {
        description "Added transceiver module-functional-type attribute";
        reference " 0.7.0.";
    }

    revision "2023-05-17" {
        description "Added multiple compliances";
        reference " 0.6.2.";
    }

    revision "2023-04-14" {
        description "Added EDFA model datatypes";
        reference " 0.6.1.";
    }

    revision "2023-03-31" {
        description "Added Smart SFP model datatypes";
        reference " 0.6.0.";
    }

    revision "2022-06-01" {
        description "Updated the yang file with feature";
        reference " 0.5.0.";
    }

    revision "2021-09-03" {
        description "Update descriptions of attribute";
        reference "Initial Version";
    }

    revision "2021-06-01" {
        description "New Types added";
        reference " 0.3.0.";
    }

    revision "2020-12-15" {
        description "Change to have data-types in lower case instead of camel case";
        reference " 0.2.0.";
    }

    revision "2018-06-21" {
        description "Initial Version";
        reference " 0.1.0.";
    }



    typedef  ddm_transceiver_t {
        type enumeration {
            enum 1000base-sx {
                value 1;
                description "sfp 1000base-sx";
            }
            enum 1000base-lx {
                value 2;
                description "sfp 1000base-lx";
            }
            enum 1000base-ex {
                value 3;
                description "sfp 1000base-ex";
            }
            enum 1000base-cx {
                value 4;
                description "sfp 1000base-cx";
            }
            enum 10gbase-sr {
                value 5;
                description "sfp+ 10gbase-sr";
            }
            enum 10gbase-lr {
                value 6;
                description "sfp+ 10gbase-lr";
            }
            enum 10gbase-er {
                value 7;
                description "sfp+ 10gbase-er";
            }
            enum 10gbase-cr {
                value 8;
                description "sfp+ 10gbase-cr";
            }
            enum 25gbase-sr {
                value 9;
                description "sfp+ 25gbase-sr";
            }
            enum 25gbase-lr {
                value 10;
                description "sfp+ 25gbase-lr";
            }
            enum 25gbase-er {
                value 11;
                description "sfp+ 25gbase-er";
            }
            enum 25gbase-cr {
                value 12;
                description "sfp+ 25gbase-cr";
            }
            enum 40gbase-sr4 {
                value 13;
                description "qsfp 40gbase-sr4";
            }
            enum 40gbase-lr4 {
                value 14;
                description "qsfp 40gbase-lr4";
            }
            enum 40gbase-er4 {
                value 15;
                description "qsfp 40gbase-er4";
            }
            enum 40gbase-cr4 {
                value 16;
                description "qsfp 40gbase-cr4";
            }
            enum 100gbase-sr4 {
                value 17;
                description "qsfp28 100gbase-sr4";
            }
            enum 100gbase-lr4 {
                value 18;
                description "qsfp28 100gbase-lr4";
            }
            enum 100gbase-er4 {
                value 19;
                description "qsfp28 100gbase-er4";
            }
            enum 100gbase-cr4 {
                value 20;
                description "qsfp28 100gbase-cr4";
            }
        }
        description "type definition for DDM_TRANSCEIVER_T";
    }

    typedef  ddm_cmm_trans_type_t {
        type enumeration {
            enum sfp {
                value 1;
                description "trans type sfp";
            }
            enum qsfp {
                value 2;
                description "trans type qsfp";
            }
            enum xfp {
                value 3;
                description "trans type xfp";
            }
            enum pon-xfp {
                value 4;
                description "trans type pon xfp";
            }
            enum qsfp-dd {
                value 5;
                description "trans type qsfp-dd";
            }
            enum osfp {
                value 6;
                description "trans type osfp";
            }
        }
        description "type definition for DDM_CMM_TRANS_TYPE_T";
    }

    typedef  ddm_cmm_trans_port_type_t {
        type enumeration {
            enum unknown {
                value -1;
                description "trans port type unknown";
            }
            enum sfp {
                value 1;
                description "trans port type sfp";
            }
            enum sfp-plus {
                value 2;
                description "trans port type sfp-plus";
            }
            enum sfp-28 {
                value 3;
                description "trans port type sfp-28";
            }
            enum sfp-56 {
                value 4;
                description "trans port type sfp-56";
            }
            enum sfp-56-dd {
                value 5;
                description "trans port type sfp-56-dd";
            }
            enum sfp-112 {
                value 6;
                description "trans port type sfp-112";
            }
            enum sfp-112-dd {
                value 7;
                description "trans port type sfp-112-dd";
            }
            enum qsfp {
                value 8;
                description "trans port type qsfp";
            }
            enum qsfp-plus {
                value 9;
                description "trans port type qsfp-plus";
            }
            enum qsfp-28 {
                value 10;
                description "trans port type qsfp-28";
            }
            enum qsfp-28-dd {
                value 11;
                description "trans port type qsfp-28-dd";
            }
            enum qsfp-56 {
                value 12;
                description "trans port type qsfp-56";
            }
            enum qsfp-56-dd {
                value 13;
                description "trans port type qsfp-56-dd";
            }
            enum qsfp-112 {
                value 14;
                description "trans port type qsfp-112";
            }
            enum qsfp-112-dd {
                value 15;
                description "trans port type qsfp-112-dd";
            }
            enum xfp {
                value 16;
                description "trans port type xfp";
            }
            enum osfp {
                value 17;
                description "trans port type osfp";
            }
        }
        description "type definition for DDM_CMM_TRANS_PORT_TYPE_T";
    }

    typedef  ddm_cmm_trans_module_type_t {
        type enumeration {
            enum unknown {
                value -1;
                description "trans type unknown";
            }
            enum sfp {
                value 1;
                description "trans type sfp";
            }
            enum sfp-plus {
                value 2;
                description "trans type sfp-plus";
            }
            enum sfp-plus-edfa {
                value 3;
                description "trans type sfp-plus-edfa";
            }
            enum sfp-28 {
                value 4;
                description "trans type sfp-28";
            }
            enum sfp-56 {
                value 5;
                description "trans type sfp-56";
            }
            enum sfp-56-dd {
                value 6;
                description "trans type sfp-28-dd";
            }
            enum sfp-112 {
                value 7;
                description "trans type sfp-112";
            }
            enum sfp-112-dd {
                value 8;
                description "trans type sfp-112-dd";
            }
            enum qsfp {
                value 9;
                description "trans type qsfp";
            }
            enum qsfp-plus {
                value 10;
                description "trans type qsfp-plus";
            }
            enum qsfp-28 {
                value 11;
                description "trans type qsfp-28";
            }
            enum qsfp-28-dd {
                value 12;
                description "trans type qsfp-28-dd";
            }
            enum qsfp-28-edfa {
                value 13;
                description "trans type qsfp-28-edfa";
            }
            enum qsfp-56 {
                value 14;
                description "trans type qsfp-56";
            }
            enum qsfp-56-dd {
                value 15;
                description "trans type qsfp-56-dd";
            }
            enum qsfp-112 {
                value 16;
                description "trans type qsfp-112";
            }
            enum qsfp-112-dd {
                value 17;
                description "trans type qsfp-112-dd";
            }
            enum qsa {
                value 18;
                description "trans type qsa";
            }
            enum xfp {
                value 19;
                description "trans type xfp";
            }
            enum pon-xfp {
                value 20;
                description "trans type xfp";
            }
            enum osfp-8x {
                value 21;
                description "trans type osfp-8x";
            }
        }
        description "type definition for DDM_CMM_TRANS_MODULE_TYPE_T";
    }

    typedef  ddm_cmm_trans_presence_t {
        type enumeration {
            enum Not-Present {
                value 0;
                description "Not,Transceiver Not present";
            }
            enum Present {
                value 1;
                description "Transceiver Present";
            }
        }
        description "type definition for DDM_CMM_TRANS_PRESENCE_T";
    }

    typedef  ddm_cmm_trans_reset_t {
        type enumeration {
            enum NA {
                value 0;
                description "Not Applicable";
            }
            enum Reset {
                value 1;
                description "In Reset";
            }
            enum Normal {
                value 2;
                description "Out of Reset";
            }
        }
        description "type definition for DDM_CMM_TRANS_RESET_T";
    }

    typedef  ddm_tx_rx_state_t {
        type enumeration {
            enum NA {
                value 0;
                description "Not Applicable";
            }
            enum off {
                value 1;
                description "off";
            }
            enum on {
                value 2;
                description "on";
            }
        }
        description "type definition for DDM_TX_RX_STATE_T";
    }

    typedef  ddm_cmm_trans_power_t {
        type enumeration {
            enum NA {
                value 0;
                description "Not Applicable";
            }
            enum Low {
                value 1;
                description "Power low";
            }
            enum High {
                value 2;
                description "Power high";
            }
        }
        description "type definition for DDM_CMM_TRANS_POWER_T";
    }

    typedef  ddm_cmm_trans_identifier_t {
        type enumeration {
            enum unknown {
                value 1;
                description "trans identifier unknown";
            }
            enum gbic {
                value 2;
                description "trans identifier gbic";
            }
            enum soldered-to-motherboard {
                value 3;
                description "trans identifier soldered-to-motherboard";
            }
            enum sfp-or-sfpplus-or-sfp28 {
                value 4;
                description "trans identifier sfp-or-sfpplus-or-sfp28";
            }
            enum xbi-300pin {
                value 5;
                description "trans identifier xbi-300pin";
            }
            enum xenpak {
                value 6;
                description "trans identifier xenpak";
            }
            enum xfp {
                value 7;
                description "trans identifier xfp";
            }
            enum xff {
                value 8;
                description "trans identifier xff";
            }
            enum xfpe {
                value 9;
                description "trans identifier xfpe";
            }
            enum xpak {
                value 10;
                description "trans identifier xpak";
            }
            enum x2 {
                value 11;
                description "trans identifier x2";
            }
            enum dwdmsfp-or-dwdmsfpplus {
                value 12;
                description "trans identifier dwdmsfp-or-dwdmsfpplus";
            }
            enum qsfp {
                value 13;
                description "trans identifier qsfp";
            }
            enum qsfpplus-or-later {
                value 14;
                description "trans identifier qsfpplus-or-later";
            }
            enum cxp-or-later {
                value 15;
                description "trans identifier cxp-or-later";
            }
            enum shielded-mini-multilane-hd4x {
                value 16;
                description "trans identifier shielded-mini-multilane-hd4x";
            }
            enum shielded-mini-multilane-hd8x {
                value 17;
                description "trans identifier shielded-mini-multilane-hd8x";
            }
            enum qsfp28-or-later {
                value 18;
                description "trans identifier qsfp28-or-later";
            }
            enum cxp2-aka-cxp28-or-later {
                value 19;
                description "trans identifier cxp2-aka-cxp28-or-later";
            }
            enum cdfpstyle1-or-cdfpstyle2 {
                value 20;
                description "trans identifier cdfpstyle1-or-cdfpstyle2";
            }
            enum shielded-mini-multilane-hd4x-fanoutcable {
                value 21;
                description "trans identifier shielded-mini-multilane-hd4x-fanoutcable";
            }
            enum shielded-mini-multilane-hd8x-fanoutcable {
                value 22;
                description "trans identifier shielded-mini-multilane-hd8x-fanoutcable";
            }
            enum cdfpstyle3 {
                value 23;
                description "trans identifier cdfpstyle3";
            }
            enum microqsfp {
                value 24;
                description "trans identifier microqsfp";
            }
            enum qsfp-doubledensity-8x-pluggable-transceiver {
                value 25;
                description "trans identifier qsfp-doubledensity-8x-pluggable-transceiver";
            }
            enum osfp-8x-pluggable-transceiver {
                value 26;
                description "trans identifier osfp-8x-pluggable-transceiver";
            }
            enum sfp-dd-double-density-2x-pluggable-transceiver {
                value 27;
                description "trans identifier sfp-dd-double-density-2x-pluggable-transceiver";
            }
            enum dsfp-dual-small-form-factor-pluggable-transceiver {
                value 28;
                description "trans identifier dsfp-dual-small-form-factor-pluggable-transceiver";
            }
            enum x4-miniLink-ocuLink {
                value 29;
                description "trans identifier x4-miniLink-ocuLink";
            }
            enum x8-miniLink {
                value 30;
                description "trans identifier x8-miniLink";
            }
            enum qsfp+-or-later-with-cmis {
                value 31;
                description "trans identifier qsfp+-or-later-with-cmis";
            }
            enum sfp-dd-double-density-2x-pluggable-transceiver-cmis {
                value 32;
                description "trans identifier sfp-dd-double-density-2x-pluggable-transceiver-cmis";
            }
            enum SFP+-and-later {
                value 33;
                description "trans identifier SFP+-and-later";
            }
            enum osfp-xd {
                value 34;
                description "trans identifier osfp-xd";
            }
            enum oif-elsfp {
                value 35;
                description "trans identifier oif-elsfp";
            }
            enum cdfp-x4-pci-sff-ta-1032 {
                value 36;
                description "trans identifier cdfp-x4-pci-sff-ta-1032";
            }
            enum cdfp-x8-pci-sff-ta-1032 {
                value 37;
                description "trans identifier cdfp-x8-pci-sff-ta-1032";
            }
            enum cdfp-x16-pci-sff-ta-1032 {
                value 38;
                description "trans identifier cdfp-x16-pci-sff-ta-1032";
            }
            enum reserved {
                value 255;
                description "trans identifier reserved";
            }
            enum vendor-specific {
                value 256;
                description "trans identifier vendor-specific";
            }
        }
        description "type definition for DDM_CMM_TRANS_IDENTIFIER_T";
    }

    typedef  ddm_cmm_trans_sfp_extended_identifier_t {
        type enumeration {
            enum gbic-notspecified-or-compliant-with-moddef {
                value 1;
                description "sfp ext-identifier gbic-notspecified-or-compliant-with-moddef ";
            }
            enum gbic-compliant-with-moddef1 {
                value 2;
                description "sfp ext-identifier gbic-compliant-with-moddef1";
            }
            enum gbic-compliant-with-moddef2 {
                value 3;
                description "sfp ext-identifier gbic-compliant-with-moddef2";
            }
            enum gbic-compliant-with-moddef3 {
                value 4;
                description "sfp ext-identifier gbic-compliant-with-moddef3";
            }
            enum gbic-or-sfp-definedby-twowire-interfaceid-only {
                value 5;
                description "sfp ext-identifier gbic-or-sfp-definedby-twowire-interfaceid-only";
            }
            enum gbic-compliant-with-moddef5 {
                value 6;
                description "sfp ext-identifier gbic-compliant-with-moddef5";
            }
            enum gbic-compliant-with-moddef6 {
                value 7;
                description "sfp ext-identifier gbic-compliant-with-moddef6";
            }
            enum gbic-compliant-with-moddef7 {
                value 8;
                description "sfp ext-identifier gbic-compliant-with-moddef7";
            }
            enum unallocated {
                value 9;
                description "sfp ext-identifier unallocated";
            }
            enum unknown {
                value 10;
                description "sfp ext-identifier unknown";
            }
        }
        description "type definition for DDM_CMM_TRANS_SFP_EXTENDED_IDENTIFIER_T";
    }

    typedef  ddm_cmm_qsfp_extended_identifier_t {
        type bits {
            bit powerclass1-1dot5wmax {
                position 0;
                description "qsfp ext-identifier powerclass1-1dot5wmax";
            }
            bit powerclass2-2wmax {
                position 1;
                description "qsfp ext-identifier powerclass2-2wmax";
            }
            bit powerclass3-2dot5wmax {
                position 2;
                description "qsfp ext-identifier powerclass3-2dot5wmax";
            }
            bit powerclass4-3dot5wmax {
                position 3;
                description "qsfp ext-identifier powerclass4-3dot5wmax";
            }
            bit cleicode-present {
                position 4;
                description "qsfp ext-identifier cleicode-present";
            }
            bit cdrpresent-in-tx {
                position 5;
                description "qsfp ext-identifier cdrpresent-in-tx";
            }
            bit cdrpresent-in-rx {
                position 6;
                description "qsfp ext-identifier cdrpresent-in-rx";
            }
            bit powerclass5-4wmax {
                position 7;
                description "qsfp ext-identifier powerclass5-4wmax";
            }
            bit powerclass6-4dot5wmax {
                position 8;
                description "qsfp ext-identifier powerclass6-4dot5wmax";
            }
            bit powerclass7-5wmax {
                position 9;
                description "qsfp ext-identifier powerclass7-5wmax";
            }
        }
        description "type definition for DDM_CMM_QSFP_EXTENDED_IDENTIFIER_T";
    }

    typedef  ddm_cmm_trans_xfp_extended_identifier_t {
        type bits {
            bit powerlevel1-1dot5wmax {
                position 0;
                description "XFP power level 1 with maximum 1.5w";
            }
            bit powerlevel2-2dot5wmax {
                position 1;
                description "XFP power level 2 with maximum 2.5w";
            }
            bit powerlevel3-3dot5wmax {
                position 2;
                description "XFP power level 3 with maximum 3.5w";
            }
            bit powerlevel4-over3dot5w {
                position 3;
                description "XFP power level 4 with over3.5w";
            }
            bit cdr-none {
                position 4;
                description "XFP CDR unsupported";
            }
            bit txrefclk-input-notrequired {
                position 5;
                description "XFP Tx RefClock input unrequired";
            }
            bit cleicode-present {
                position 6;
                description "XFP CLEI code present in table 2";
            }
        }
        description "type definition for DDM_CMM_TRANS_XFP_EXTENDED_IDENTIFIER_T";
    }

    typedef  ddm_cmm_trans_eth_compliance_t {
        type enumeration {
            enum ec-unknown {
                value 1;
                description "trans compliance ec-unknown";
            }
            enum ec-10gbase-sr {
                value 2;
                description "trans compliance ec-10gbase-sr";
            }
            enum ec-10gbase-lr {
                value 3;
                description "trans compliance ec-10gbase-lr";
            }
            enum ec-10gbase-lrm {
                value 4;
                description "trans compliance ec-10gbase-lrm";
            }
            enum ec-10gbase-er {
                value 5;
                description "trans compliance ec-10gbase-er";
            }
            enum ec-1000base-sx {
                value 6;
                description "trans compliance ec-1000base-sx";
            }
            enum ec-1000base-lx {
                value 7;
                description "trans compliance ec-1000base-lx";
            }
            enum ec-1000base-cx {
                value 8;
                description "trans compliance ec-1000base-cx";
            }
            enum ec-1000base-t {
                value 9;
                description "trans compliance ec-1000base-t";
            }
            enum ec-100base-lx-or-lx10 {
                value 10;
                description "trans compliance ec-100base-lx-or-lx10";
            }
            enum ec-100base-fx {
                value 11;
                description "trans compliance ec-100base-fx";
            }
            enum ec-base-bx10 {
                value 12;
                description "trans compliance ec-base-bx10";
            }
            enum ec-base-px {
                value 13;
                description "trans compliance ec-base-px";
            }
            enum ec-40gbase-cr4 {
                value 14;
                description "trans compliance ec-40gbase-cr4";
            }
            enum ec-40gbase-sr4 {
                value 15;
                description "trans compliance ec-40gbase-sr4";
            }
            enum ec-40gbase-lr4 {
                value 16;
                description "trans compliance ec-40gbase-lr4";
            }
            enum ec-40g-activecable {
                value 17;
                description "trans compliance ec-40g-activecable";
            }
        }
        description "type definition for DDM_CMM_TRANS_ETH_COMPLIANCE_T";
    }

    typedef  ddm_cmm_trans_ext_eth_compliance_t {
        type enumeration {
            enum eec-unspecified {
                value 0;
                description "trans ext compliance eec-unspecified";
            }
            enum eec-100g-activeopticalcable-or-25g-auic2maoc {
                value 1;
                description "transext compliance eec-100g-activeopticalcable-or-25g-auic2maoc";
            }
            enum eec-100gbase-sr4-or-25gbase-sr {
                value 2;
                description "trans ext compliance eec-100gbase-sr4-or-25gbase-sr";
            }
            enum eec-100gbase-lr4-or-25gbase-lr {
                value 3;
                description "trans ext compliance eec-100gbase-lr4-or-25gbase-lr";
            }
            enum eec-100gbase-er4-or-25gbase-er {
                value 4;
                description "trans ext compliance eec-100gbase-er4-or-25gbase-er";
            }
            enum eec-100gbase-sr10 {
                value 5;
                description "trans ext compliance eec-100gbase-sr10";
            }
            enum eec-100g-cwdm4 {
                value 6;
                description "trans ext compliance eec-100g-cwdm4";
            }
            enum eec-100g-psm4-parallelsmf {
                value 7;
                description "trans ext compliance eec-100g-psm4-parallelsmf";
            }
            enum eec-100g-activecoppercable-or-25g-auic2macc {
                value 8;
                description "trans ext compliance eec-100g-activecoppercable-or-25g-auic2macc";
            }
            enum eec-obsolete {
                value 9;
                description "trans ext compliance eec-obsolete";
            }
            enum eec-reserved {
                value 10;
                description "trans ext compliance eec-reserved";
            }
            enum eec-100gbase-cr4-or-25gbase-crca-l {
                value 11;
                description "trans ext compliance eec-100gbase-cr4-or-25gbase-crca-l";
            }
            enum eec-25gbase-crca-s {
                value 12;
                description "trans ext compliance eec-25gbase-crca-s";
            }
            enum eec-25gbase-crca-n {
                value 13;
                description "trans ext compliance eec-25gbase-crca-n";
            }
            enum eec-10mb-single-pair-eth {
                value 14;
                description "trans ext compliance eec-10mb-single-pair-eth";
            }
            enum eec-40gbase-er4 {
                value 16;
                description "trans ext compliance eec-40gbase-er4";
            }
            enum eec-4x10gbase-sr {
                value 17;
                description "trans ext compliance eec-4x10gbase-sr";
            }
            enum eec-40g-psm4-parallelsmf {
                value 18;
                description "trans ext compliance eec-40g-psm4-parallelsmf";
            }
            enum eec-g959-dot1-profilep1-i1-2d1 {
                value 19;
                description "trans ext compliance eec-g959-dot1-profilep1-i1-2d1";
            }
            enum eec-g959-dot1-profilep1-s1-2d2 {
                value 20;
                description "trans ext compliance eec-g959-dot1-profilep1-s1-2d2";
            }
            enum eec-g959-dot1-profilep1-l1-2d2 {
                value 21;
                description "trans ext compliance eec-g959-dot1-profilep1-l1-2d2";
            }
            enum eec-100gbase-t-with-sfi-electricalinterface {
                value 22;
                description "trans ext compliance eec-100gbase-t-with-sfi-electricalinterface";
            }
            enum eec-100g-clr4 {
                value 23;
                description "trans ext compliance eec-100g-clr4";
            }
            enum eec-100g-aoc-or-25g-auic2maoc {
                value 24;
                description "trans ext compliance eec-100g-aoc-or-25g-auic2maoc";
            }
            enum eec-100g-acc-or-25g-auic2macc {
                value 25;
                description "trans ext compliance eec-100g-acc-or-25g-auic2macc";
            }
            enum eec-100ge-dwdm2 {
                value 26;
                description "trans ext compliance eec-100ge-dwdm2";
            }
            enum eec-100g-1550nm-wdm {
                value 27;
                description "trans ext compliance eec-100g-1550nm-wdm";
            }
            enum eec-10gbaset-short-reach {
                value 28;
                description "trans ext compliance eec-10gbaset-short-reach";
            }
            enum eec-5gbaset {
                value 29;
                description "trans ext compliance eec-5gbaset";
            }
            enum eec-2point5gbaset {
                value 30;
                description "trans ext compliance eec-2point5gbaset";
            }
            enum eec-40g-swdm4 {
                value 31;
                description "trans ext compliance eec-40g-swdm4";
            }
            enum eec-100g-swdm4 {
                value 32;
                description "trans ext compliance eec-100g-swdm4";
            }
            enum eec-100g-pam4-bidi {
                value 33;
                description "trans ext compliance eec-100g-pam4-bidi";
            }
            enum eec-100g-4wdm-10msa {
                value 34;
                description "trans ext compliance eec-100g-4wdm-10msa";
            }
            enum eec-100g-4wdm-20msa {
                value 35;
                description "trans ext compliance eec-100g-4wdm-20msa";
            }
            enum eec-100g-4wdm-40msa {
                value 36;
                description "trans ext compliance eec-100g-4wdm-40msa";
            }
            enum eec-100gbase-dr-clause140 {
                value 37;
                description "trans ext compliance eec-100gbase-dr-clause140";
            }
            enum eec-100g-fr-or-fr1-clause140 {
                value 38;
                description "trans ext compliance eec-100g-fr-or-fr1-clause140";
            }
            enum eec-100g-lr-or-lr1-clause140 {
                value 39;
                description "trans ext compliance eec-100g-lr-or-lr1-clause140";
            }
            enum eec-100gbase-sr1-p802-clause167 {
                value 40;
                description "trans ext compliance eec-100gbase-sr1-p802-clause167";
            }
            enum eec-100gbase-sr1-200gbase-sr2-400gbase-sr4-clause167 {
                value 41;
                description "trans ext compliance eec-100gbase-sr1-200gbase-sr2-400gbase-sr4-clause167";
            }
            enum eec-100gbase-fr1-clause140 {
                value 42;
                description "trans ext compliance eec-100gbase-fr1-clause140";
            }
            enum eec-100gbase-lr1-clause140 {
                value 43;
                description "trans ext compliance eec-100gbase-lr1-clause140";
            }
            enum eec-100g-lr1-20msa-and-caui4 {
                value 44;
                description "trans ext compliance eec-100g-lr1-20msa-and-caui4";
            }
            enum eec-100g-er1-30msa-and-caui4 {
                value 45;
                description "trans ext compliance eec-100g-er1-30msa-and-caui4";
            }
            enum eec-100g-er1-40msa-and-caui4 {
                value 46;
                description "trans ext compliance eec-100g-er1-40msa-and-caui4";
            }
            enum eec-100g-lr1-20msa {
                value 47;
                description "trans ext compliance eec-100g-lr1-20msa";
            }
            enum eec-acc-with-50gaui-100gaui2-200gaui4-c2m-worst-ber-10minus6 {
                value 48;
                description "trans ext compliance eec-acc-with-50gaui-100gaui2-200gaui4-c2m-worst-ber-10minus6";
            }
            enum eec-aoc-with-50gaui-100gaui2-200gaui4-c2m-worst-ber-10minus6 {
                value 49;
                description "trans ext compliance eec-aoc-with-50gaui-100gaui2-200gaui4-c2m-worst-ber-10minus6";
            }
            enum eec-acc-with-50gaui-100gaui2-200gaui4-c2m-worst-ber-10minus5 {
                value 50;
                description "trans ext compliance eec-acc-with-50gaui-100gaui2-200gaui4-c2m-worst-ber-10minus5";
            }
            enum eec-aoc-with-50gaui-100gaui2-200gaui4-c2m-worst-ber-10minus5 {
                value 51;
                description "trans ext compliance eec-aoc-with-50gaui-100gaui2-200gaui4-c2m-worst-ber-10minus5";
            }
            enum eec-100g-er1-30msa {
                value 52;
                description "trans ext compliance eec-100g-er1-30msa";
            }
            enum eec-100g-er1-40msa {
                value 53;
                description "trans ext compliance eec-100g-er1-40msa";
            }
            enum eec-100gbase-vr1-200gbase-vr2-400gbase-sr4-clause167 {
                value 54;
                description "trans ext compliance eec-100gbase-vr1-200gbase-vr2-400gbase-sr4-clause167";
            }
            enum eec-10gbase-br {
                value 55;
                description "trans ext compliance eec-10gbase-br";
            }
            enum eec-25gbase-br {
                value 56;
                description "trans ext compliance eec-25gbase-br";
            }
            enum eec-50gbase-br {
                value 57;
                description "trans ext compliance eec-50gbase-br";
            }
            enum eec-100gbase-vr1-p802-clause167 {
                value 58;
                description "trans ext compliance eec-100gbase-vr1-p802-clause167";
            }
            enum eec-100gbase-cr1-200gbase-cr2-400gbase-cr4-clause162 {
                value 63;
                description "trans ext compliance eec-100gbase-cr1-200gbase-cr2-400gbase-cr4-clause162";
            }
            enum eec-50gbase-cr-100gbase-cr2-200gbase-cr4 {
                value 64;
                description "trans ext compliance eec-50gbase-cr-100gbase-cr2-200gbase-cr4";
            }
            enum eec-50gbase-sr-100gbase-sr2-200gbase-sr4 {
                value 65;
                description "trans ext compliance eec-50gbase-sr-100gbase-sr2-200gbase-sr4";
            }
            enum eec-50gbase-fr-200gbase-dr4 {
                value 66;
                description "trans ext compliance eec-50gbase-fr-200gbase-dr4";
            }
            enum eec-200gbase-fr4 {
                value 67;
                description "trans ext compliance eec-200gbase-fr4";
            }
            enum eec-200g-1550nm-psm4 {
                value 68;
                description "trans ext compliance eec-200g-1550nm-psm4";
            }
            enum eec-50gbase-lr {
                value 69;
                description "trans ext compliance eec-50gbase-lr";
            }
            enum eec-200gbase-lr4 {
                value 70;
                description "trans ext compliance eec-200gbase-lr4";
            }
            enum eec-400gbase-dr4-clause124 {
                value 71;
                description "trans ext compliance eec-400gbase-dr4-clause124";
            }
            enum eec-400gbase-fr4-clause151 {
                value 72;
                description "trans ext compliance eec-400gbase-fr4-clause151";
            }
            enum eec-400gbase-fr46-clause151 {
                value 73;
                description "trans ext compliance eec-400gbase-fr46-clause151";
            }
            enum eec-50gbase-er-clause139 {
                value 74;
                description "trans ext compliance eec-50gbase-er-clause139";
            }
            enum eec-400g-lr410 {
                value 75;
                description "trans ext compliance eec-400g-lr410";
            }
            enum eec-400gbase-zr-clause156 {
                value 76;
                description "trans ext compliance eec-400gbase-zr-clause156";
            }
            enum eec-256gfc-sw4 {
                value 127;
                description "trans ext compliance eec-256gfc-sw4";
            }
            enum eec-64gfc {
                value 128;
                description "trans ext compliance eec-64gfc";
            }
            enum eec-128gfc {
                value 129;
                description "trans ext compliance eec-128gfc";
            }
        }
        description "type definition for DDM_CMM_TRANS_EXT_ETH_COMPLIANCE_T";
    }

    typedef  ddm_cmm_trans_sonet_compliance_t {
        type bits {
            bit oc192-shortreach {
                position 0;
                description "oc192-shortreach";
            }
            bit sonet-reachspecifier-bit1 {
                position 1;
                description "sonet-reachspecifier-bit1";
            }
            bit sonet-reachspecifier-bit2 {
                position 2;
                description "sonet-reachspecifier-bit2";
            }
            bit oc48-longreach {
                position 3;
                description "oc48-longreach";
            }
            bit oc48-intermediatereach {
                position 4;
                description "oc48-intermediatereach";
            }
            bit oc48-shortreach {
                position 5;
                description "oc48-shortreach";
            }
            bit oc12-singlemode-longreach {
                position 6;
                description "oc12-singlemode-longreach";
            }
            bit oc12-singlemode-intermediatereach {
                position 7;
                description "oc12-singlemode-intermediatereach";
            }
            bit oc12-singlemode-shortreach {
                position 8;
                description "oc12-singlemode-shortreach";
            }
            bit oc3-singlemode-longreach {
                position 9;
                description "oc3-singlemode-longreach";
            }
            bit oc3-singlemode-intermediatereach {
                position 10;
                description "oc3-singlemode-intermediatereach";
            }
            bit oc3-singlemode-shortreach {
                position 11;
                description "oc3-singlemode-shortreach";
            }
            bit null {
                position 31;
                description "NULL";
            }
        }
        description "type definition for DDM_CMM_TRANS_SONET_COMPLIANCE_T";
    }

    typedef  ddm_cmm_trans_fiber_channel_linklen_t {
        type bits {
            bit short {
                position 0;
                description "short";
            }
            bit medium {
                position 1;
                description "medium";
            }
            bit intermediate {
                position 2;
                description "intermediate";
            }
            bit long {
                position 3;
                description "long";
            }
            bit verylong {
                position 4;
                description "very long";
            }
            bit null {
                position 31;
                description "NULL";
            }
        }
        description "type definition for DDM_CMM_TRANS_FIBER_CHANNEL_LINKLEN_T";
    }

    typedef  ddm_cmm_trans_fiber_channel_transmittech_t {
        type bits {
            bit shortwaveLaserLinearRx {
                position 0;
                description "shortwaveLaserLinearRx";
            }
            bit longwaveLaserLC {
                position 1;
                description "longwaveLaser LC";
            }
            bit electricalInter-Enclosure {
                position 2;
                description "electricalInter-Enclosure";
            }
            bit electricalIntra-Enclosure {
                position 3;
                description "electricalIntra-Enclosure";
            }
            bit shortwaveLaserWithOutOFC {
                position 4;
                description "shortwaveLaserWithOutOFC";
            }
            bit shortwaveLaserwithOFC {
                position 5;
                description "shortwaveLaserwithOFC";
            }
            bit longwaveLaserLL {
                position 6;
                description "longwaveLaser LL";
            }
            bit null {
                position 31;
                description "NULL";
            }
        }
        description "type definition for DDM_CMM_TRANS_FIBER_CHANNEL_TRANSMITTECH_T";
    }

    typedef  ddm_cmm_trans_fiber_channel_transmitmedia_t {
        type bits {
            bit twinaxial-pair {
                position 0;
                description "twinaxial-pair";
            }
            bit twisted-pair {
                position 1;
                description "twisted-pair";
            }
            bit miniature-coax {
                position 2;
                description "miniature-coax";
            }
            bit video-coax {
                position 3;
                description "video-coax";
            }
            bit multi-mode62dot5m {
                position 4;
                description "multi-mode62dot5m";
            }
            bit multi-mode50m {
                position 5;
                description "multi-mode50m";
            }
            bit multi-mode50um {
                position 6;
                description "multi-mode50um";
            }
            bit single-mode {
                position 7;
                description "single-mode";
            }
            bit null {
                position 31;
                description "NULL";
            }
        }
        description "type definition for DDM_CMM_TRANS_FIBER_CHANNEL_TRANSMITMEDIA_T";
    }

    typedef  ddm_cmm_trans_fiber_channel_speed_t {
        type bits {
            bit fcs-3200mbps {
                position 0;
                description "fcs-3200mbps";
            }
            bit fcs-1600mbps {
                position 1;
                description "fcs-1600mbps";
            }
            bit fcs-1200mbps {
                position 2;
                description "fcs-1200mbps";
            }
            bit fcs-800mbps {
                position 3;
                description "fcs-800mbps";
            }
            bit fcs-400mbps {
                position 4;
                description "fcs-400mbps";
            }
            bit fcs-200mbps {
                position 5;
                description "fcs-200mbps";
            }
            bit fcs-100mbps {
                position 6;
                description "fcs-100mbps";
            }
            bit null {
                position 31;
                description "NULL";
            }
        }
        description "type definition for DDM_CMM_TRANS_FIBER_CHANNEL_SPEED_T";
    }

    typedef  ddm_cmm_trans_sfp_infiniband_compliance_t {
        type enumeration {
            enum ibc-1xsx {
                value 1;
                description "ibc-1xsx";
            }
            enum ibc-1xlx {
                value 2;
                description "ibc-1xlx";
            }
            enum ibc-1xcopperactive {
                value 3;
                description "ibc-1xcopperactive";
            }
            enum ibc-1xcopperpassive {
                value 4;
                description "ibc-1xcopperpassive";
            }
            enum ibc-unknown {
                value 5;
                description "ibc-unknown";
            }
            enum ibc-notapplicable {
                value 6;
                description "ibc-notapplicable";
            }
        }
        description "type definition for DDM_CMM_TRANS_SFP_INFINIBAND_COMPLIANCE_T";
    }

    typedef  ddm_cmm_trans_sfp_escon_compliance_t {
        type enumeration {
            enum escon-mmf-1310nm-led {
                value 1;
                description "escon-mmf-1310nm-led";
            }
            enum escon-smf-1310nm-laser {
                value 2;
                description "escon-smf-1310nm-laser";
            }
            enum unknown {
                value 3;
                description "unknown";
            }
            enum notapplicable {
                value 4;
                description "notapplicable";
            }
        }
        description "type definition for DDM_CMM_TRANS_SFP_ESCON_COMPLIANCE_T";
    }

    typedef  ddm_cmm_trans_sfp_plus_cable_tech_t {
        type enumeration {
            enum active {
                value 1;
                description "active";
            }
            enum passive {
                value 2;
                description "passive";
            }
            enum unknown {
                value 3;
                description "unknown";
            }
            enum notapplicable {
                value 4;
                description "notapplicable";
            }
        }
        description "type definition for DDM_CMM_TRANS_SFP_PLUS_CABLE_TECH_T";
    }

    typedef  ddm_cmm_trans_xfp_10g_eth_compliance_t {
        type bits {
            bit xec-10gbase-sr {
                position 0;
                description "Transceiver ethernet compliance 10GBASE-SR";
            }
            bit xec-10gbase-lr {
                position 1;
                description "Transceiver ethernet compliance 10GBASE-LR";
            }
            bit xec-10gbase-er {
                position 2;
                description "Transceiver ethernet compliance 10GBASE-ER";
            }
            bit xec-10gbase-lrm {
                position 3;
                description "Transceiver ethernet compliance 10GBASE-LRM";
            }
            bit xec-10gbase-sw {
                position 4;
                description "Transceiver ethernet compliance 10GBASE-SW";
            }
            bit xec-10gbase-lw {
                position 5;
                description "Transceiver ethernet compliance 10GBASE-LW";
            }
            bit xec-10gbase-ew {
                position 6;
                description "Transceiver ethernet compliance 10GBASE-EW";
            }
        }
        description "type definition for DDM_CMM_TRANS_XFP_10G_ETH_COMPLIANCE_T";
    }

    typedef  ddm_cmm_trans_xfp_10g_fiber_chn_compliance_t {
        type bits {
            bit xfcc-1200-mx-sn-i {
                position 0;
                description "Transceiver fiber channel compliance 1200-MX-SN-I";
            }
            bit xfcc-1200-sm-ll-l {
                position 1;
                description "Transceiver fiber channel compliance 1200-SM-LL-L";
            }
            bit xfcc-exended-reach-1550nm {
                position 2;
                description "Transceiver fiber channel compliance Extended Reach 1550 nm";
            }
            bit xfcc-intermediate-reach-1300nm-fp {
                position 3;
                description "Transceiver fiber channel compliance Intermediate Reach 1300 nm FP";
            }
        }
        description "type definition for DDM_CMM_TRANS_XFP_10G_FIBER_CHN_COMPLIANCE_T";
    }

    typedef  ddm_cmm_trans_xfp_10g_copper_links_rsvd_t {
        type bits {
            bit xcl-rsvd {
                position 0;
                description "Transceiver 10G Copper links reserved";
            }
        }
        description "type definition for DDM_CMM_TRANS_XFP_10G_COPPER_LINKS_RSVD_T";
    }

    typedef  ddm_cmm_trans_xfp_lower_speed_links_t {
        type bits {
            bit xlsl-1000base-sx {
                position 0;
                description "Transceiver 1000BASE-SX/1xFC MMF";
            }
            bit xlsl-1000base-lx {
                position 1;
                description "Transceiver 1000BASE-LX/1xFC SMF";
            }
            bit xlsl-2xfc-mmf {
                position 2;
                description "Transceiver 2xFC MMF";
            }
            bit xlsl-2xfc-smf {
                position 3;
                description "Transceiver 2xFC SMF";
            }
            bit xlsl-oc48-sr {
                position 4;
                description "Transceiver OC 48-SR";
            }
            bit xlsl-oc48-ir {
                position 5;
                description "Transceiver OC 48-IR";
            }
            bit xlsl-oc48-lr {
                position 6;
                description "Transceiver OC 48-LR";
            }
        }
        description "type definition for DDM_CMM_TRANS_XFP_LOWER_SPEED_LINKS_T";
    }

    typedef  ddm_cmm_trans_xfp_sonet_interconnect_t {
        type bits {
            bit xsi-i-64-lr {
                position 0;
                description "SONET/SDH compliant code I-64.1r";
            }
            bit xsi-i-64-l {
                position 1;
                description "SONET/SDH compliant code I-64.1";
            }
            bit xsi-i-64-2r {
                position 2;
                description "SONET/SDH compliant code I-64.2r";
            }
            bit xsi-i-64-2 {
                position 3;
                description "SONET/SDH compliant code I-64.2";
            }
            bit xsi-i-64-3 {
                position 4;
                description "SONET/SDH compliant code I-64.3";
            }
            bit xsi-i-64-5 {
                position 5;
                description "SONET/SDH compliant code I-64.5";
            }
        }
        description "type definition for DDM_CMM_TRANS_XFP_SONET_INTERCONNECT_T";
    }

    typedef  ddm_cmm_trans_xfp_sonet_short_haul_t {
        type bits {
            bit xssh-s-64-l {
                position 0;
                description "SONET/SDH compliant code S-64.1r";
            }
            bit xssh-s-64-2a {
                position 1;
                description "SONET/SDH compliant code S-64.2a";
            }
            bit xssh-s-64-2b {
                position 2;
                description "SONET/SDH compliant code s-64.2b";
            }
            bit xssh-s-64-3a {
                position 3;
                description "SONET/SDH compliant code S-64.3a";
            }
            bit xssh-s-64-3b {
                position 4;
                description "SONET/SDH compliant code S-64.3b";
            }
            bit xssh-s-64-5a {
                position 5;
                description "SONET/SDH compliant code S-64.5a";
            }
            bit xssh-s-64-56 {
                position 6;
                description "SONET/SDH compliant code S-64.5b";
            }
        }
        description "type definition for DDM_CMM_TRANS_XFP_SONET_SHORT_HAUL_T";
    }

    typedef  ddm_cmm_trans_xfp_sonet_long_haul_t {
        type bits {
            bit xslh-l-64-l {
                position 0;
                description "SONET/SDH compliant code L-64.1";
            }
            bit xslh-l-64-2a {
                position 1;
                description "SONET/SDH compliant code L-64.2a";
            }
            bit xslh-l-64-2b {
                position 2;
                description "SONET/SDH compliant code L-64.2b";
            }
            bit xslh-l-64-2c {
                position 3;
                description "SONET/SDH compliant code L-64.2c";
            }
            bit xslh-l-64-3 {
                position 4;
                description "SONET/SDH compliant code L-64.3";
            }
            bit xlsh-l-g959-1-p1l1-2d2 {
                position 5;
                description "SONET/SDH compliant code G.959.1 P1L1-2D2";
            }
        }
        description "type definition for DDM_CMM_TRANS_XFP_SONET_LONG_HAUL_T";
    }

    typedef  ddm_cmm_trans_xfp_sonet_very_long_haul_t {
        type bits {
            bit xsvh-v-64-2a {
                position 0;
                description "SONET/SDH compliant code V-64.2a";
            }
            bit xsvh-v-64-2b {
                position 1;
                description "SONET/SDH compliant code V-64.2b";
            }
            bit xsvh-v-64-3 {
                position 2;
                description "SONET/SDH compliant code V-64.3";
            }
        }
        description "type definition for DDM_CMM_TRANS_XFP_SONET_VERY_LONG_HAUL_T";
    }

    typedef  ddm_cmm_trans_encoding_t {
        type enumeration {
            enum enc-unspecified {
                value 1;
                description "enc-unspecified";
            }
            enum enc-8b-or-10b {
                value 2;
                description "enc-8b-or-10b";
            }
            enum enc-4b-or-5b {
                value 3;
                description "enc-4b-or-5b";
            }
            enum enc-nrz {
                value 4;
                description "enc-nrz";
            }
            enum enc-manchester {
                value 5;
                description "enc-manchester";
            }
            enum enc-sonet-scrambled {
                value 6;
                description "enc-sonet-scrambled";
            }
            enum enc-64b-or-66b {
                value 7;
                description "enc-64b-or-66b";
            }
            enum enc-256b-or-257b {
                value 8;
                description "enc-256b-or-257b";
            }
            enum enc-pam4 {
                value 9;
                description "enc-pam4";
            }
            enum enc-reserved {
                value 10;
                description "enc-reserved";
            }
        }
        description "type definition for DDM_CMM_TRANS_ENCODING_T";
    }

    typedef  ddm_cmm_trans_xfp_encoding_t {
        type bits {
            bit enc-reserved0 {
                position 0;
                description "XFP encoding reserved 0";
            }
            bit enc-reserved1 {
                position 1;
                description "XFP encoding reserved 1";
            }
            bit enc-reserved2 {
                position 2;
                description "XFP encoding reserved 2";
            }
            bit enc-rz {
                position 3;
                description "XFP encoding RZ";
            }
            bit enc-nrz {
                position 4;
                description "XFP encoding NRZ";
            }
            bit enc-sonet-scrambled {
                position 5;
                description "XFP encoding SONET Scrambled";
            }
            bit enc-8b-10b {
                position 6;
                description "XFP encoding 8b/10b";
            }
            bit enc-64b-66b {
                position 7;
                description "XFP encoding 64b/66b";
            }
        }
        description "type definition for DDM_CMM_TRANS_XFP_ENCODING_T";
    }

    typedef  ddm_cmm_trans_ddm_support_t {
        type enumeration {
            enum yes {
                value 1;
                description "DDM is supported";
            }
            enum no {
                value 2;
                description "DDM is not supported";
            }
            enum unknown {
                value 3;
                description "DDM support unknown";
            }
        }
        description "type definition for DDM_CMM_TRANS_DDM_SUPPORT_T";
    }

    typedef  ddm_cmm_trans_sfp_options_implemented_t {
        type bits {
            bit reserved {
                position 0;
                description "reserved";
            }
            bit power-level3 {
                position 1;
                description "power-level3";
            }
            bit paging {
                position 2;
                description "paging";
            }
            bit internal-retimer-or-cdr {
                position 3;
                description "internal-retimer-or-cdr";
            }
            bit cooled-laser-transmitter {
                position 4;
                description "cooled-laser-transmitter";
            }
            bit power-level2 {
                position 5;
                description "power-level2";
            }
            bit power-level1 {
                position 6;
                description "power-level1";
            }
            bit linear-receiver-output {
                position 7;
                description "linear-receiver-output";
            }
            bit receiver-decision-threshold {
                position 8;
                description "receiver-decision-threshold";
            }
            bit transmitter-wavelength-or-tunable-frequency {
                position 9;
                description "transmitter-wavelength-or-tunable-frequency";
            }
            bit rate-select {
                position 10;
                description "rate-select";
            }
            bit tx-disable {
                position 11;
                description "tx-disable";
            }
            bit tx-fault {
                position 12;
                description "tx-fault";
            }
            bit rx-loss-of-signal {
                position 13;
                description "rx-loss-of-signal";
            }
            bit null {
                position 31;
                description "NULL";
            }
        }
        description "type definition for DDM_CMM_TRANS_SFP_OPTIONS_IMPLEMENTED_T";
    }

    typedef  ddm_cmm_trans_qsfp_options_implemented_t {
        type bits {
            bit reserved {
                position 0;
                description "reserved";
            }
            bit tx-inputequalization-auto-adaptive {
                position 1;
                description "tx-inputequalization-auto-adaptive";
            }
            bit tx-inputequalization-fixed-programmable {
                position 2;
                description "tx-inputequalization-fixed-programmable";
            }
            bit tx-outputemphasis-fixed-programmable {
                position 3;
                description "tx-outputemphasis-fixed-programmable";
            }
            bit tx-outputamplitude-fixed-programmable {
                position 4;
                description "tx-outputamplitude-fixed-programmable";
            }
            bit tx-cdr-on-or-off-controllable {
                position 5;
                description "tx-cdr-on-or-off-controllable";
            }
            bit tx-cdr-on-or-off-fixed {
                position 6;
                description "tx-cdr-on-or-off-fixed";
            }
            bit rx-cdr-on-or-off-controllable {
                position 7;
                description "rx-cdr-on-or-off-controllable";
            }
            bit rx-cdr-on-or-off-fixed {
                position 8;
                description "rx-cdr-on-or-off-fixed";
            }
            bit tx-cdr-lossoflock {
                position 9;
                description "tx-cdr-lossoflock";
            }
            bit rx-cdr-lossoflock {
                position 10;
                description "rx-cdr-lossoflock";
            }
            bit rx-squelch-disable {
                position 11;
                description "rx-squelch-disable";
            }
            bit rx-output-disable {
                position 12;
                description "rx-output-disable";
            }
            bit tx-squelch-disable {
                position 13;
                description "tx-squelch-disable";
            }
            bit tx-squelch {
                position 14;
                description "tx-squelch";
            }
            bit page2-provided {
                position 15;
                description "page2-provided";
            }
            bit page1-provided {
                position 16;
                description "page1-provided";
            }
            bit rateselect-controllable {
                position 17;
                description "rateselect-controllable";
            }
            bit rateselect-fixed {
                position 18;
                description "rateselect-fixed";
            }
            bit tx-disable {
                position 19;
                description "tx-disable";
            }
            bit tx-fault {
                position 20;
                description "tx-fault";
            }
            bit tx-squelch-to-reduce-pave {
                position 21;
                description "tx-squelch-to-reduce-pave";
            }
            bit tx-squelch-to-reduce-oma {
                position 22;
                description "tx-squelch-to-reduce-oma";
            }
            bit tx-loss-of-signal {
                position 23;
                description "tx-loss-of-signal";
            }
            bit null {
                position 31;
                description "NULL";
            }
        }
        description "type definition for DDM_CMM_TRANS_QSFP_OPTIONS_IMPLEMENTED_T";
    }

    typedef  ddm_cmm_trans_xfp_options_implemented_t {
        type bits {
            bit xfp-vps {
                position 0;
                description "XFP optional variable power supply";
            }
            bit xfp_tx-disable {
                position 1;
                description "XFP soft TX disable support";
            }
            bit xfp-p-down {
                position 2;
                description "XFP soft power down support";
            }
            bit xfp-vps-lv {
                position 3;
                description "XFP VPS low voltage regulator mode";
            }
            bit xfp-vps-bypass {
                position 4;
                description "XFP VPS bypass mode";
            }
            bit xfp-active-fec {
                position 5;
                description "XFP active FEC control";
            }
            bit xfp-wavelength-tunability {
                position 6;
                description "XFP wavelength tunability";
            }
            bit xfp-cmu {
                position 7;
                description "XFP Clock Multiplier Unit mode";
            }
        }
        description "type definition for DDM_CMM_TRANS_XFP_OPTIONS_IMPLEMENTED_T";
    }

    typedef  ddm_cmm_trans_xfp_voltage_aux_monitor_t {
        type bits {
            bit xfp-vcc-5 {
                position 0;
                description "XFP auxiliary monitor for VCC5";
            }
            bit xfp-vcc-3 {
                position 1;
                description "XFP auxiliary monitor for VCC3";
            }
            bit xfp-vcc-2 {
                position 2;
                description "XFP auxiliary monitor for VCC2";
            }
        }
        description "type definition for DDM_CMM_TRANS_XFP_VOLTAGE_AUX_MONITOR_T";
    }

    typedef  cmm_smart_sfp_protocol_running_state_t {
        type enumeration {
            enum NA {
                value 0;
                description "Not Applicable";
            }
            enum on {
                value 1;
                description "On";
            }
            enum off {
                value 2;
                description "Off";
            }
        }
        description "type definition for CMM_SMART_SFP_PROTOCOL_RUNNING_STATE_T";
    }

    typedef  cmm_smart_sfp_protocol_status_t {
        type enumeration {
            enum NA {
                value 0;
                description "Not Applicable";
            }
            enum local-tcvr-ready {
                value 1;
                description "Local transceiver ready";
            }
            enum remote-tcvr-ready {
                value 2;
                description "Remote transceiver ready";
            }
            enum normal {
                value 3;
                description "Normal";
            }
            enum receiving-failure {
                value 4;
                description "Receiving failure";
            }
            enum link-failure {
                value 5;
                description "Link failure";
            }
        }
        description "type definition for CMM_SMART_SFP_PROTOCOL_STATUS_T";
    }

    typedef  cmm_ddm_threshold_alarm_t {
        type enumeration {
            enum high-alarm {
                value 0;
                description "None";
            }
            enum low-alarm {
                value 1;
                description "None";
            }
            enum high-warning {
                value 2;
                description "None";
            }
            enum low-warning {
                value 3;
                description "None";
            }
        }
        description "type definition for CMM_DDM_THRESHOLD_ALARM_T";
    }

    typedef  cmm_smart_sfp_ddm_monitor_id_t {
        type enumeration {
            enum temperature {
                value 0;
                description "None";
            }
            enum voltage {
                value 1;
                description "None";
            }
            enum bias-current {
                value 2;
                description "None";
            }
            enum tx-power {
                value 3;
                description "None";
            }
            enum rx-power {
                value 4;
                description "None";
            }
        }
        description "type definition for CMM_SMART_SFP_DDM_MONITOR_ID_T";
    }

    typedef  cmm_smart_sfp_protocol_alarm_id_t {
        type enumeration {
            enum local-status {
                value 0;
                description "None";
            }
            enum remote-status {
                value 1;
                description "None";
            }
        }
        description "type definition for CMM_SMART_SFP_PROTOCOL_ALARM_ID_T";
    }

    typedef  cmm_edfa_ddm_monitor_id_t {
        type enumeration {
            enum temperature {
                value 0;
                description "None";
            }
            enum voltage {
                value 1;
                description "None";
            }
            enum gain {
                value 2;
                description "None";
            }
            enum output-power {
                value 3;
                description "None";
            }
            enum input-power {
                value 4;
                description "None";
            }
            enum pump-bias {
                value 5;
                description "None";
            }
        }
        description "type definition for CMM_EDFA_DDM_MONITOR_ID_T";
    }

    typedef  cmm_transceiver_functional_type_t {
        type enumeration {
            enum standard-optic {
                value 0;
                description "Transceiver non-coherent";
            }
            enum digital-coherent-optic {
                value 1;
                description "Coherent Transceiver";
            }
            enum unknown {
                value 2;
                description "Unknown";
            }
        }
        description "type definition for CMM_TRANSCEIVER_FUNCTIONAL_TYPE_T";
    }

}
