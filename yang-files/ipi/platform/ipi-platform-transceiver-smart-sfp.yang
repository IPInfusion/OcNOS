/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-platform-transceiver-smart-sfp.yang
*
*/

module ipi-platform-transceiver-smart-sfp {

    yang-version 1.1;

    namespace   "http://www.ipinfusion.com/yang/ocnos/ipi-platform-transceiver-smart-sfp";

    prefix "ipi-platform-transceiver-smart-sfp";

    import ipi-interface {
        prefix ipi-interface;
        revision-date 2026-03-10;
    }

    import feature-list {
        prefix feature-list;
        revision-date 2026-09-15;
    }

    organization
        "IP Infusion Inc.";

    contact
        "Address: 3965 Freedom Circle, Suite 200, Santa Clara, CA 95054
         Phone: +1 408-4001900
         E-mail: support@ipinfusio.com
         Web: http://www.ipinfusion.com/";

    description
        "Datamodel for smart sfp module";


    revision "2022-11-15" {
        description "Adding the ifname support to xcvr reset remote CLI and xcvr tx-disable 1 to 256 remote CLI";
        reference " 0.1.1.";
    }

    revision "2022-11-08" {
        description "Initial version";
        reference " 0.1.0.";
    }



    typedef  cmm_xcvr_direction_t {
        type enumeration {
            enum in {
                value 1;
                description "inner";
            }
            enum out {
                value 2;
                description "outer";
            }
        }
        description "type definition for CMM_XCVR_DIRECTION_T";
    }    grouping smart-sfp-interface-config {
        description
            "Grouping for smart SFP module config objects";
        leaf interface-name  {
            type  leafref {
                path  "/ipi-interface:interfaces/ipi-interface:interface/ipi-interface:name";
            }
            description "This attribute describes the textual name of the interface";
        } // END of interface-name definition.

        leaf xcvr-loopback-remote  {
            type  cmm_xcvr_direction_t;
            description "Use this attribute to set TX/RX loopback for remote";
        } // END of xcvr-loopback-remote definition.

    } // END of smart-sfp-interface-config definition.
    grouping smart-sfp-components-top {
        description
            "Top level grouping for smart SFP componets in the sysytem";
        container components {
            description
                "container for the components in the system.";

            list component {
                key "name";
                config false;
                description
                    "List of components, keyed by smart SFP component name.";
                leaf name  {
                    type  leafref {
                        path  "../state/name";
                    }
                    description "References the smart SFP component name";
                } // END of name definition.

                container state {
                    config false;
                    description
                        "Operational state data for each smart SFP component";
                    leaf name  {
                        type  string {
                            length "1..1965";
                        }
                        description "References the smart SFP component name";
                    } // END of name definition.

                } // END of state-container definition.
            } // End of component-list
        } // END of components-container definition.
    } // END of smart-sfp-components-top definition.
    grouping platform-smart-sfp-interface-top {
        description
            "Top level grouping for interface configuration group";
        container interfaces {
            description
                "container for interface level configuration for platform smart SFP";

            list interface {
                key "interface-name";
                description
                    "Platform smart SFP interface related operations";
                leaf interface-name  {
                    type  leafref {
                        path  "../config/interface-name";
                    }
                    description "Use this attribute to perform platform's interface smart SFP related
                                configurations";
                } // END of interface-name definition.

                container config {
                    description
                        "configuration container for interface list";
                    uses smart-sfp-interface-config;
                } // END of config-container definition.
                container state {
                    config false;
                    description
                        "Operational data for interface";
                    uses smart-sfp-interface-config;
                } // END of state-container definition.
            } // End of interface-list
        } // END of interfaces-container definition.
    } // END of platform-smart-sfp-interface-top definition.

    grouping  smart-sfp-grouping {
    description
        "Main Global container for smart SFP";
    container smart-sfp {
        if-feature feature-list:HAVE_CMMD;
        description
            "Main Global container for smart SFP";
        uses platform-smart-sfp-interface-top;
        uses smart-sfp-components-top;
    } // END of smart-sfp-container definition.
    } // END of smart-sfp-grouping definition.

    uses smart-sfp-grouping;

    rpc smart-sfp-xcvr-txdisable-duration {
        if-feature feature-list:HAVE_CMMD;
        description "use this command to set xcvr tx-disable";
        input  {
            leaf if-name  {
                type string;
                mandatory true;
                description "Name of the interface";
            }
            leaf xcvr-tx-disable-duration  {
                type uint16 {
                    range "1..256";
                }
                mandatory true;
                description "Use this attribute to Laser off the remote transceiver for 1 to 256
                            seconds and then on the laser";
            }
        }
    }

    rpc smart-sfp-xcvr-reset-remote {
        if-feature feature-list:HAVE_CMMD;
        description "Use this command to reset the remote transceiver";
        input  {
            leaf if-name  {
                type string;
                mandatory true;
                description "Name of the interface";
            }
        }
    }

}
