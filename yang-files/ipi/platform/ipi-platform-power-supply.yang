/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-platform-power-supply.yang
*
*/

submodule ipi-platform-power-supply {

    yang-version 1.1;

    belongs-to  ipi-platform { prefix ipi-platform; }

    import feature-list {
        prefix feature-list;
        revision-date 2026-09-15;
    }

    import ipi-platform-types {
        prefix ipi-platform-types;
        revision-date 2026-04-16;
    }

    organization
        "IP Infusion Inc.";

    contact
        "Address: 3965 Freedom Circle, Suite 200, Santa Clara, CA 95054
         Phone: +1 408-400-1900
         E-mail: support@ipinfusio.com
         Web: http://www.ipinfusion.com/";

    description
        "This module defines a schema for power supply components in platform
                datamodel";


    revision "2026-01-02" {
        description "Changed to power-supply-absent from power-supply-removed";
        reference " 0.6.0.";
    }

    revision "2025-02-04" {
        description "Inclusion of 4th BMC PSU temperature sensor attribute";
        reference " 0.5.0.";
    }

    revision "2023-06-12" {
        description "Inclusion of streaming telemetry yaml file";
        reference " 0.4.1.";
    }

    revision "2022-06-01" {
        description "Updated the yang file with feature";
        reference " 0.4.0.";
    }

    revision "2021-09-03" {
        description "Update descriptions of attribute";
        reference " 0.3.0.";
    }

    revision "2021-03-18" {
        description "Added capacity attribute and notifications for power supply alarms";
        reference " 0.2.0.";
    }

    revision "2021-01-25" {
        description "Initial version adding support to power supply components in ipi-platform module";
        reference " 0.1.0.";
    }



    typedef  cml_cmm_power_supply_operstatus_t {
        type enumeration {
            enum unknown {
                value 0;
                description "Operational status unavailable";
            }
            enum not-present {
                value 1;
                description "Power supply is not present";
            }
            enum running {
                value 2;
                description "Power supply is operating in normal conditions";
            }
            enum faulty {
                value 3;
                description "Power supply has failed";
            }
        }
        description "type definition for CML_CMM_POWER_SUPPLY_OPERSTATUS_T";
    }

    typedef  cml_cmm_psu_pmbus_param_support_t {
        type bits {
            bit volt-in {
                position 0;
                description "input voltage supported";
            }
            bit volt-out {
                position 1;
                description "output voltage supported";
            }
            bit curr-in {
                position 2;
                description "input current supported";
            }
            bit curr-out {
                position 3;
                description "output current supported";
            }
            bit power-in {
                position 4;
                description "input power supported";
            }
            bit power-out {
                position 5;
                description "output power supported";
            }
            bit temp-1 {
                position 6;
                description "PSU Temp senor 1 supported";
            }
            bit temp-2 {
                position 7;
                description "PSU Temp sensor 2 supported";
            }
            bit temp-3 {
                position 8;
                description "PSU Temp sensor 3 supported";
            }
            bit fan-1 {
                position 9;
                description "PSU Fan 1 supported";
            }
            bit fan-2 {
                position 10;
                description "PSU Fan 2 supported";
            }
            bit fan-3 {
                position 11;
                description "PSU Fan 3 supported";
            }
            bit fan-4 {
                position 12;
                description "PSU Fan 4 supported";
            }
        }
        description "type definition for CML_CMM_PSU_PMBUS_PARAM_SUPPORT_T";
    }    grouping psu-state {
        description
            "Power supply data for platform components";
        leaf operational-status  {
            type  cml_cmm_power_supply_operstatus_t;
            description "The status of the power supply";
        } // END of operational-status definition.

        leaf hot-swap-state  {
            type  ipi-platform-types:cml_cmm_power_rail_t;
            description "Power status for HOT SWAP";
        } // END of hot-swap-state definition.

        leaf capacity  {
            type  decimal64 {
                 fraction-digits 2;            }
            units "watts";
            description "Maximum power capacity of the power supply";
        } // END of capacity definition.

        leaf power-consumption  {
            type  decimal64 {
                 fraction-digits 2;            }
            units "watts";
            description "Output power of power supply";
        } // END of power-consumption definition.

        leaf input-power  {
            type  decimal64 {
                 fraction-digits 2;            }
            units "watts";
            description "Input power of power supply";
        } // END of input-power definition.

        leaf input-voltage  {
            type  decimal64 {
                 fraction-digits 2;            }
            units "volts";
            description "Input voltage of power supply";
        } // END of input-voltage definition.

        leaf output-voltage  {
            type  decimal64 {
                 fraction-digits 2;            }
            units "volts";
            description "Output voltage of power supply";
        } // END of output-voltage definition.

        leaf input-current  {
            type  decimal64 {
                 fraction-digits 2;            }
            units "amperes";
            description "Input current of power supply";
        } // END of input-current definition.

        leaf output-current  {
            type  decimal64 {
                 fraction-digits 2;            }
            units "amperes";
            description "Output current of power supply";
        } // END of output-current definition.

        leaf temperature-sensor1  {
            type  decimal64 {
                 fraction-digits 2;            }
            units "celsius";
            description "Temperature of power supply sensor 1";
        } // END of temperature-sensor1 definition.

        leaf temperature-sensor2  {
            type  decimal64 {
                 fraction-digits 2;            }
            units "celsius";
            description "Temperature of power supply sensor 2";
        } // END of temperature-sensor2 definition.

        leaf temperature-sensor3  {
            type  decimal64 {
                 fraction-digits 2;            }
            units "celsius";
            description "Temperature of power supply sensor 3";
        } // END of temperature-sensor3 definition.

        leaf temperature-sensor4  {
            type  decimal64 {
                 fraction-digits 2;            }
            units "celsius";
            description "Temperature of power supply sensor 4";
        } // END of temperature-sensor4 definition.

        leaf fan1-rpm  {
            type  uint32;
            description "Fan1 RPM of power supply";
        } // END of fan1-rpm definition.

        leaf fan2-rpm  {
            type  uint32;
            description "Fan2 RPM of power supply";
        } // END of fan2-rpm definition.

        leaf fan3-rpm  {
            type  uint32;
            description "Fan3 RPM of power supply";
        } // END of fan3-rpm definition.

        leaf fan4-rpm  {
            type  uint32;
            description "Fan4 RPM of power supply";
        } // END of fan4-rpm definition.

        leaf input-power-status  {
            type  ipi-platform-types:cml_cmm_power_rail_t;
            description "Status of input power";
        } // END of input-power-status definition.

        leaf output-power-status  {
            type  ipi-platform-types:cml_cmm_power_rail_t;
            description "Status of output power";
        } // END of output-power-status definition.

        leaf supported-parameters  {
            type  cml_cmm_psu_pmbus_param_support_t;
            description "Bitmap of supported parameters of power supply unit";
        } // END of supported-parameters definition.

        leaf vin-alert-threshold-min  {
            type  decimal64 {
                 fraction-digits 2;            }
            units "volts";
            description "Psu input volatge alert threshold minimum value";
        } // END of vin-alert-threshold-min definition.

        leaf vin-alert-threshold-max  {
            type  decimal64 {
                 fraction-digits 2;            }
            units "volts";
            description "Psu input volatge alert threshold maximum value";
        } // END of vin-alert-threshold-max definition.

        leaf vin-critical-threshold-min  {
            type  decimal64 {
                 fraction-digits 2;            }
            units "volts";
            description "Psu input volatge critical threshold minimun value";
        } // END of vin-critical-threshold-min definition.

        leaf vin-critical-threshold-max  {
            type  decimal64 {
                 fraction-digits 2;            }
            units "volts";
            description "Psu input volatge critical threshold maximum value";
        } // END of vin-critical-threshold-max definition.

        leaf vout-alert-threshold-min  {
            type  decimal64 {
                 fraction-digits 2;            }
            units "volts";
            description "Psu output volatge alert threshold minimum value";
        } // END of vout-alert-threshold-min definition.

        leaf vout-alert-threshold-max  {
            type  decimal64 {
                 fraction-digits 2;            }
            units "volts";
            description "Psu output volatge alert threshold maximum value";
        } // END of vout-alert-threshold-max definition.

        leaf vout-critical-threshold-min  {
            type  decimal64 {
                 fraction-digits 2;            }
            units "volts";
            description "Psu output volatge critical threshold minimum value";
        } // END of vout-critical-threshold-min definition.

        leaf vout-critical-threshold-max  {
            type  decimal64 {
                 fraction-digits 2;            }
            units "volts";
            description "Psu output volatge critical threshold maximum value";
        } // END of vout-critical-threshold-max definition.

        leaf pout-alert-threshold-min  {
            type  decimal64 {
                 fraction-digits 2;            }
            units "watts";
            description "Psu output power alert threshold minimum value";
        } // END of pout-alert-threshold-min definition.

        leaf pout-alert-threshold-max  {
            type  decimal64 {
                 fraction-digits 2;            }
            units "watts";
            description "Psu output power alert threshold maximum value";
        } // END of pout-alert-threshold-max definition.

        leaf pout-critical-threshold-min  {
            type  decimal64 {
                 fraction-digits 2;            }
            units "watts";
            description "Psu output power critical threshold minimum value";
        } // END of pout-critical-threshold-min definition.

        leaf pout-critical-threshold-max  {
            type  decimal64 {
                 fraction-digits 2;            }
            units "watts";
            description "Psu output power critical threshold maximum value";
        } // END of pout-critical-threshold-max definition.

        leaf pin-alert-threshold-min  {
            type  decimal64 {
                 fraction-digits 2;            }
            units "watts";
            description "Psu input power alert threshold minimum value";
        } // END of pin-alert-threshold-min definition.

        leaf pin-alert-threshold-max  {
            type  decimal64 {
                 fraction-digits 2;            }
            units "watts";
            description "Psu input power alert threshold maximum value";
        } // END of pin-alert-threshold-max definition.

        leaf pin-critical-threshold-min  {
            type  decimal64 {
                 fraction-digits 2;            }
            units "watts";
            description "Psu input power critical threshold minimum value";
        } // END of pin-critical-threshold-min definition.

        leaf pin-critical-threshold-max  {
            type  decimal64 {
                 fraction-digits 2;            }
            units "watts";
            description "Psu input power critical threshold maximum value";
        } // END of pin-critical-threshold-max definition.

        leaf iin-alert-threshold-min  {
            type  decimal64 {
                 fraction-digits 2;            }
            units "ampere";
            description "Psu input current alert threshold minimum value";
        } // END of iin-alert-threshold-min definition.

        leaf iin-alert-threshold-max  {
            type  decimal64 {
                 fraction-digits 2;            }
            units "ampere";
            description "Psu input current alert threshold maximum value";
        } // END of iin-alert-threshold-max definition.

        leaf iin-critical-threshold-min  {
            type  decimal64 {
                 fraction-digits 2;            }
            units "ampere";
            description "Psu input current critical threshold minimum value";
        } // END of iin-critical-threshold-min definition.

        leaf iin-critical-threshold-max  {
            type  decimal64 {
                 fraction-digits 2;            }
            units "ampere";
            description "Psu input current critical threshold maximum value";
        } // END of iin-critical-threshold-max definition.

        leaf iout-alert-threshold-min  {
            type  decimal64 {
                 fraction-digits 2;            }
            units "ampere";
            description "Psu output current alert threshold minimum value";
        } // END of iout-alert-threshold-min definition.

        leaf iout-alert-threshold-max  {
            type  decimal64 {
                 fraction-digits 2;            }
            units "ampere";
            description "Psu output current alert threshold maximum value";
        } // END of iout-alert-threshold-max definition.

        leaf iout-critical-threshold-min  {
            type  decimal64 {
                 fraction-digits 2;            }
            units "ampere";
            description "Psu output current critical threshold minimum value";
        } // END of iout-critical-threshold-min definition.

        leaf iout-critical-threshold-max  {
            type  decimal64 {
                 fraction-digits 2;            }
            units "ampere";
            description "Psu output current critical threshold maximum value";
        } // END of iout-critical-threshold-max definition.

        leaf temp1-alert-threshold-min  {
            type  decimal64 {
                 fraction-digits 2;            }
            units "celsius";
            description "Psu temperature 1 alert threshold minimum value";
        } // END of temp1-alert-threshold-min definition.

        leaf temp1-alert-threshold-max  {
            type  decimal64 {
                 fraction-digits 2;            }
            units "celsius";
            description "Psu temperature 1 alert threshold maximum value";
        } // END of temp1-alert-threshold-max definition.

        leaf temp1-critical-threshold-min  {
            type  decimal64 {
                 fraction-digits 2;            }
            units "celsius";
            description "Psu temperature 1 critical threshold minimum value";
        } // END of temp1-critical-threshold-min definition.

        leaf temp1-critical-threshold-max  {
            type  decimal64 {
                 fraction-digits 2;            }
            units "celsius";
            description "Psu temperature 1 critical threshold maximum value";
        } // END of temp1-critical-threshold-max definition.

        leaf temp2-alert-threshold-min  {
            type  decimal64 {
                 fraction-digits 2;            }
            units "celsius";
            description "Psu temperature 2 alert threshold minimum value";
        } // END of temp2-alert-threshold-min definition.

        leaf temp2-alert-threshold-max  {
            type  decimal64 {
                 fraction-digits 2;            }
            units "celsius";
            description "Psu temperature 2 alert threshold maximum value";
        } // END of temp2-alert-threshold-max definition.

        leaf temp2-critical-threshold-min  {
            type  decimal64 {
                 fraction-digits 2;            }
            description "Psu temperature 2 critical threshold minimum value";
        } // END of temp2-critical-threshold-min definition.

        leaf temp2-critical-threshold-max  {
            type  decimal64 {
                 fraction-digits 2;            }
            units "celsius";
            description "Psu temperature 2 critical threshold maximum value";
        } // END of temp2-critical-threshold-max definition.

        leaf temp3-alert-threshold-min  {
            type  decimal64 {
                 fraction-digits 2;            }
            units "celsius";
            description "Psu temperature 3 alert threshold minimum value";
        } // END of temp3-alert-threshold-min definition.

        leaf temp3-alert-threshold-max  {
            type  decimal64 {
                 fraction-digits 2;            }
            units "celsius";
            description "Psu temperature 3 alert threshold maximum value";
        } // END of temp3-alert-threshold-max definition.

        leaf temp3-critical-threshold-min  {
            type  decimal64 {
                 fraction-digits 2;            }
            description "Psu temperature 3 critical threshold minimum value";
        } // END of temp3-critical-threshold-min definition.

        leaf temp3-critical-threshold-max  {
            type  decimal64 {
                 fraction-digits 2;            }
            units "celsius";
            description "Psu temperature 3 critical threshold maximum value";
        } // END of temp3-critical-threshold-max definition.

        leaf temp4-alert-threshold-min  {
            type  decimal64 {
                 fraction-digits 2;            }
            units "celsius";
            description "Psu temperature 4 alert threshold minimum value";
        } // END of temp4-alert-threshold-min definition.

        leaf temp4-alert-threshold-max  {
            type  decimal64 {
                 fraction-digits 2;            }
            units "celsius";
            description "Psu temperature 4 alert threshold maximum value";
        } // END of temp4-alert-threshold-max definition.

        leaf temp4-critical-threshold-min  {
            type  decimal64 {
                 fraction-digits 2;            }
            description "Psu temperature 4 critical threshold minimum value";
        } // END of temp4-critical-threshold-min definition.

        leaf temp4-critical-threshold-max  {
            type  decimal64 {
                 fraction-digits 2;            }
            units "celsius";
            description "Psu temperature 4 critical threshold maximum value";
        } // END of temp4-critical-threshold-max definition.

        leaf vin-hw-shut-max-threshold  {
            type  decimal64 {
                 fraction-digits 2;            }
            units "volts";
            description "Psh hardware input voltage shutdown over threshold";
        } // END of vin-hw-shut-max-threshold definition.

        leaf vin-hw-shut-min-threshold  {
            type  decimal64 {
                 fraction-digits 2;            }
            units "volts";
            description "Psh hardware input voltage shutdown under threshold";
        } // END of vin-hw-shut-min-threshold definition.

        leaf vin-hw-resume_max_threshold  {
            type  decimal64 {
                 fraction-digits 2;            }
            units "volts";
            description "Psh hardware input voltage resume under threshold";
        } // END of vin-hw-resume_max_threshold definition.

        leaf vin-hw-resume_min_threshold  {
            type  decimal64 {
                 fraction-digits 2;            }
            units "volts";
            description "Psh hardware input voltage resume under threshold";
        } // END of vin-hw-resume_min_threshold definition.

        leaf vout-hw-shut-max-threshold  {
            type  decimal64 {
                 fraction-digits 2;            }
            units "volts";
            description "Psh hardware output voltage shutdown over threshold";
        } // END of vout-hw-shut-max-threshold definition.

        leaf vout-hw-shut-min-threshold  {
            type  decimal64 {
                 fraction-digits 2;            }
            units "volts";
            description "Psh hardware output voltage shutdown under threshold";
        } // END of vout-hw-shut-min-threshold definition.

        leaf vout-hw-resume_max_threshold  {
            type  decimal64 {
                 fraction-digits 2;            }
            units "volts";
            description "Psh hardware output voltage resume under threshold";
        } // END of vout-hw-resume_max_threshold definition.

        leaf vout-hw-resume_min_threshold  {
            type  decimal64 {
                 fraction-digits 2;            }
            units "volts";
            description "Psh hardware output voltage resume under threshold";
        } // END of vout-hw-resume_min_threshold definition.

        leaf pin-hw-shut-max-threshold  {
            type  decimal64 {
                 fraction-digits 2;            }
            units "watts";
            description "Psh hardware input power shutdown over threshold";
        } // END of pin-hw-shut-max-threshold definition.

        leaf pin-hw-shut-min-threshold  {
            type  decimal64 {
                 fraction-digits 2;            }
            units "watts";
            description "Psh hardware input power shutdown under threshold";
        } // END of pin-hw-shut-min-threshold definition.

        leaf pin-hw-resume_max_threshold  {
            type  decimal64 {
                 fraction-digits 2;            }
            units "watts";
            description "Psh hardware output voltage resume under threshold";
        } // END of pin-hw-resume_max_threshold definition.

        leaf pin-hw-resume_min_threshold  {
            type  decimal64 {
                 fraction-digits 2;            }
            units "watts";
            description "Psh hardware output voltage resume under threshold";
        } // END of pin-hw-resume_min_threshold definition.

        leaf pout-hw-shut-max-threshold  {
            type  decimal64 {
                 fraction-digits 2;            }
            units "watts";
            description "Psh hardware output power shutdown over threshold";
        } // END of pout-hw-shut-max-threshold definition.

        leaf pout-hw-shut-min-threshold  {
            type  decimal64 {
                 fraction-digits 2;            }
            units "watts";
            description "Psh hardware output power shutdown under threshold";
        } // END of pout-hw-shut-min-threshold definition.

        leaf pout-hw-resume_max_threshold  {
            type  decimal64 {
                 fraction-digits 2;            }
            units "watts";
            description "Psh hardware output power  resume under threshold";
        } // END of pout-hw-resume_max_threshold definition.

        leaf pout-hw-resume_min_threshold  {
            type  decimal64 {
                 fraction-digits 2;            }
            units "watts";
            description "Psh hardware output power  resume under threshold";
        } // END of pout-hw-resume_min_threshold definition.

        leaf iin-hw-shut-max-threshold  {
            type  decimal64 {
                 fraction-digits 2;            }
            units "ampere";
            description "Psh hardware input current shutdown over threshold";
        } // END of iin-hw-shut-max-threshold definition.

        leaf iin-hw-shut-min-threshold  {
            type  decimal64 {
                 fraction-digits 2;            }
            units "ampere";
            description "Psh hardware input current shutdown under threshold";
        } // END of iin-hw-shut-min-threshold definition.

        leaf iin-hw-resume_max_threshold  {
            type  decimal64 {
                 fraction-digits 2;            }
            units "ampere";
            description "Psh hardware input current  resume under threshold";
        } // END of iin-hw-resume_max_threshold definition.

        leaf iin-hw-resume_min_threshold  {
            type  decimal64 {
                 fraction-digits 2;            }
            units "ampere";
            description "Psh hardware input current  resume under threshold";
        } // END of iin-hw-resume_min_threshold definition.

        leaf iout-hw-shut-max-threshold  {
            type  decimal64 {
                 fraction-digits 2;            }
            units "ampere";
            description "Psh hardware output current shutdown over threshold";
        } // END of iout-hw-shut-max-threshold definition.

        leaf iout-hw-shut-min-threshold  {
            type  decimal64 {
                 fraction-digits 2;            }
            units "ampere";
            description "Psh hardware output current shutdown under threshold";
        } // END of iout-hw-shut-min-threshold definition.

        leaf iout-hw-resume_max_threshold  {
            type  decimal64 {
                 fraction-digits 2;            }
            units "ampere";
            description "Psh hardware output current  resume under threshold";
        } // END of iout-hw-resume_max_threshold definition.

        leaf iout-hw-resume_min_threshold  {
            type  decimal64 {
                 fraction-digits 2;            }
            units "ampere";
            description "Psh hardware output current  resume under threshold";
        } // END of iout-hw-resume_min_threshold definition.

        leaf temp1-hw-shut-max-threshold  {
            type  decimal64 {
                 fraction-digits 2;            }
            units "celsius";
            description "Psh hardware temperature 1 shutdown over threshold";
        } // END of temp1-hw-shut-max-threshold definition.

        leaf temp1-hw-shut-min-threshold  {
            type  decimal64 {
                 fraction-digits 2;            }
            units "celsius";
            description "Psh hardware temperature 1 shutdown under threshold";
        } // END of temp1-hw-shut-min-threshold definition.

        leaf temp1-hw-resume_max_threshold  {
            type  decimal64 {
                 fraction-digits 2;            }
            units "celsius";
            description "Psh hardware temperature 1  resume under threshold";
        } // END of temp1-hw-resume_max_threshold definition.

        leaf temp1-hw-resume_min_threshold  {
            type  decimal64 {
                 fraction-digits 2;            }
            units "celsius";
            description "Psh hardware temperature 1  resume under threshold";
        } // END of temp1-hw-resume_min_threshold definition.

        leaf temp2-hw-shut-max-threshold  {
            type  decimal64 {
                 fraction-digits 2;            }
            units "celsius";
            description "Psh hardware temperature 2 shutdown over threshold";
        } // END of temp2-hw-shut-max-threshold definition.

        leaf temp2-hw-shut-min-threshold  {
            type  decimal64 {
                 fraction-digits 2;            }
            units "celsius";
            description "Psh hardware temperature 2 shutdown under threshold";
        } // END of temp2-hw-shut-min-threshold definition.

        leaf temp2-hw-resume_max_threshold  {
            type  decimal64 {
                 fraction-digits 2;            }
            units "celsius";
            description "Psh hardware temperature 2  resume under threshold";
        } // END of temp2-hw-resume_max_threshold definition.

        leaf temp2-hw-resume_min_threshold  {
            type  decimal64 {
                 fraction-digits 2;            }
            units "celsius";
            description "Psh hardware temperature 2  resume under threshold";
        } // END of temp2-hw-resume_min_threshold definition.

        leaf temp3-hw-shut-max-threshold  {
            type  decimal64 {
                 fraction-digits 2;            }
            units "celsius";
            description "Psh hardware temperature 3 shutdown over threshold";
        } // END of temp3-hw-shut-max-threshold definition.

        leaf temp3-hw-shut-min-threshold  {
            type  decimal64 {
                 fraction-digits 2;            }
            units "celsius";
            description "Psh hardware temperature 3 shutdown under threshold";
        } // END of temp3-hw-shut-min-threshold definition.

        leaf temp3-hw-resume_max_threshold  {
            type  decimal64 {
                 fraction-digits 2;            }
            units "celsius";
            description "Psh hardware temperature 3 resume under threshold";
        } // END of temp3-hw-resume_max_threshold definition.

        leaf temp3-hw-resume_min_threshold  {
            type  decimal64 {
                 fraction-digits 2;            }
            units "celsius";
            description "Psh hardware temperature 3 resume under threshold";
        } // END of temp3-hw-resume_min_threshold definition.

        leaf temp4-hw-shut-max-threshold  {
            type  decimal64 {
                 fraction-digits 2;            }
            units "celsius";
            description "Psh hardware temperature 4 shutdown over threshold";
        } // END of temp4-hw-shut-max-threshold definition.

        leaf temp4-hw-shut-min-threshold  {
            type  decimal64 {
                 fraction-digits 2;            }
            units "celsius";
            description "Psh hardware temperature 4 shutdown under threshold";
        } // END of temp4-hw-shut-min-threshold definition.

        leaf temp4-hw-resume_max_threshold  {
            type  decimal64 {
                 fraction-digits 2;            }
            units "celsius";
            description "Psh hardware temperature 4 resume under threshold";
        } // END of temp4-hw-resume_max_threshold definition.

        leaf temp4-hw-resume_min_threshold  {
            type  decimal64 {
                 fraction-digits 2;            }
            units "celsius";
            description "Psh hardware temperature 4 resume under threshold";
        } // END of temp4-hw-resume_min_threshold definition.

    } // END of psu-state definition.

    grouping  power-supply-grouping {
    description
        "Container for power supply component";
    container power-supply {
        if-feature feature-list:HAVE_CMMD;
        config false;
        description
            "Container for power supply component";
        container state {
            config false;
            description
                "Operational state data for power supply components";
            uses psu-state;
        } // END of state-container definition.
    } // END of power-supply-container definition.
    } // END of power-supply-grouping definition.


}
