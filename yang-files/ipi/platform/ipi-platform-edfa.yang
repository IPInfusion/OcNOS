/* Copyright (C) 2001-2025 IP Infusion, Inc. All Rights Reserved. */
/*
*** Auto generated by zebmdc

* Unless required by applicable law or agreed to in writing,
* software distributed under the License is distributed on an
* "AS IS" BASIS, WITHOUT WARRANTIES OR CONDITIONS OF ANY
* KIND, either express or implied.

* File name : ipi-platform-edfa.yang
*
*/

submodule ipi-platform-edfa {

    yang-version 1.1;

    belongs-to  ipi-platform { prefix ipi-platform; }

    import feature-list {
        prefix feature-list;
        revision-date 2026-09-15;
    }

    import ipi-platform-transceiver-types {
        prefix ipi-platform-transceiver-types;
        revision-date 2025-12-30;
    }

    organization
        "IP Infusion Inc.";

    contact
        "Address: 3965 Freedom Circle, Suite 200, Santa Clara, CA 95054
         Phone: +1 408-4001900
         E-mail: support@ipinfusion.com
         Web: http://www.ipinfusion.com/";

    description
        "This module defines a schema for EDFA transceivers in platform
                datamodel";


    revision "2023-04-11" {
        description "Initial version";
        reference " 0.1.0.";
    }

    grouping ipi-platform-edfa-monitor-state {
        description
            "ipi-platform-edfa-monitor-state";
        leaf id  {
            type  ipi-platform-transceiver-types:cmm_edfa_ddm_monitor_id_t;
            description "Module monitor ID";
        } // END of id definition.

        leaf description  {
            type  string {
                length "1..1965";
            }
            description "Module monitor description";
        } // END of description definition.

        leaf value  {
            type  decimal64 {
                 fraction-digits 3;            }
            description "Module monitor value";
        } // END of value definition.

        leaf high-alarm  {
            type  decimal64 {
                 fraction-digits 3;            }
            description "Module monitor high alarm value";
        } // END of high-alarm definition.

        leaf high-warning  {
            type  decimal64 {
                 fraction-digits 3;            }
            description "Module monitor high warning value";
        } // END of high-warning definition.

        leaf low-warning  {
            type  decimal64 {
                 fraction-digits 3;            }
            description "Module monitor low warning value";
        } // END of low-warning definition.

        leaf low-alarm  {
            type  decimal64 {
                 fraction-digits 3;            }
            description "Module monitor low alarm value";
        } // END of low-alarm definition.

    } // END of ipi-platform-edfa-monitor-state definition.
    grouping ipi-platform-edfa-monitors-top {
        description
            "ipi-platform-edfa-monitors-top";

        list monitor {
            key "id";
            config false;
            description
                "List of EDFA monitors";
            leaf id  {
                type  leafref {
                    path  "../state/id";
                }
                description "DDM monitor ID";
            } // END of id definition.

            container state {
                config false;
                description
                    "EDFA monitor state";
                uses ipi-platform-edfa-monitor-state;
            } // END of state-container definition.
        } // End of monitor-list
    } // END of ipi-platform-edfa-monitors-top definition.
    grouping ipi-platform-edfa-monitor-alarm-state {
        description
            "ipi-platform-edfa-monitor-alarm-state";
        leaf alarm-id  {
            type  ipi-platform-transceiver-types:cmm_edfa_ddm_monitor_id_t;
            description "Threshold alarm ID";
        } // END of alarm-id definition.

        leaf alarm-type  {
            type  ipi-platform-transceiver-types:cmm_ddm_threshold_alarm_t;
            description "Threshold alarm type";
        } // END of alarm-type definition.

        leaf current-value  {
            type  decimal64 {
                 fraction-digits 3;            }
            description "Current monitor value";
        } // END of current-value definition.

        leaf threshold-minimum  {
            type  decimal64 {
                 fraction-digits 3;            }
            description "Threshold minimum value";
        } // END of threshold-minimum definition.

        leaf threshold-maximum  {
            type  decimal64 {
                 fraction-digits 3;            }
            description "Threshold maximum value";
        } // END of threshold-maximum definition.

    } // END of ipi-platform-edfa-monitor-alarm-state definition.
    grouping ipi-platform-edfa-monitor-alarm-top {
        description
            "ipi-platform-edfa-monitor-alarm-top";
        container state {
            config false;
            description
                "State data for EDFA alarms";
            uses ipi-platform-edfa-monitor-alarm-state;
        } // END of state-container definition.
    } // END of ipi-platform-edfa-monitor-alarm-top definition.
    grouping ipi-platform-edfa-state {
        description
            "ipi-platform-edfa-state";
        leaf port  {
            type  uint8 {
                 range "1..128"  {
                    description "1..128: Supported range 1 - 128";
                 }
            }
            description "A unique value for each panel port within the unit";
        } // END of port definition.

    } // END of ipi-platform-edfa-state definition.
    grouping ipi-platform-edfa-top {
        description
            "ipi-platform-edfa-top";

        list edfa {
            key "port";
            config false;
            description
                "List of EDFA available";
            leaf port  {
                type  leafref {
                    path  "../state/port";
                }
                description "A value for each panel port within the unit";
            } // END of port definition.

            container state {
                config false;
                description
                    "Operational state data for EDFA";
                uses ipi-platform-edfa-state;
            } // END of state-container definition.
            container monitors {
                config false;
                description
                    "EDFA monitors information";
                uses ipi-platform-edfa-monitors-top;
            } // END of monitors-container definition.
            container monitor-alarm {
                config false;
                description
                    "EDFA alarm information";
                uses ipi-platform-edfa-monitor-alarm-top;
            } // END of monitor-alarm-container definition.
        } // End of edfa-list
    } // END of ipi-platform-edfa-top definition.

    grouping  edfas-grouping {
    description
        "Top level container of EDFA modules with their state data";
    container edfas {
        if-feature feature-list:HAVE_CMMD;
        config false;
        description
            "Top level container of EDFA modules with their state data";
        uses ipi-platform-edfa-top;
    } // END of edfas-container definition.
    } // END of edfas-grouping definition.


}
